--
-- V1600D_20230413.my
-- MIB generated by MG-SOFT Visual MIB Builder Version 6.0  Build 88
-- Thursday, April 13, 2023 at 09:23:11
--

--  V1600D_230328.my
-- MIB generated by MG-SOFT Visual MIB Builder Version 6.0  Build 88
-- Tuesday, March 28, 2023 at 11:02:44
-- 
--  V1600D.my
-- MIB generated by MG-SOFT Visual MIB Builder Version 6.0  Build 88
-- Monday, February 27, 2023 at 15:26:50
-- 
--  V1600D_20221017.my
-- MIB generated by MG-SOFT Visual MIB Builder Version 6.0  Build 88
-- Monday, October 17, 2022 at 13:39:41
-- 
--  V1600D_20220908.my
-- MIB generated by MG-SOFT Visual MIB Builder Version 6.0  Build 88
-- Thursday, September 08, 2022 at 15:51:16
-- 
--  V1600D_20220818.my
-- MIB generated by MG-SOFT Visual MIB Builder Version 6.0  Build 88
-- Thursday, August 18, 2022 at 16:58:35
-- 
--  V1600D_220818.my
-- MIB generated by MG-SOFT Visual MIB Builder Version 6.0  Build 88
-- Thursday, August 18, 2022 at 16:33:30
-- 
--  V1600D.my
-- MIB generated by MG-SOFT Visual MIB Builder Version 6.0  Build 88
-- Tuesday, March 22, 2022 at 08:51:58
-- 
--  V1600D.my
-- MIB generated by MG-SOFT Visual MIB Builder Version 6.0  Build 88
-- Friday, May 21, 2021 at 20:34:23
-- 

	V1600D DEFINITIONS ::= BEGIN
 
		IMPORTS
			enterprises, TimeTicks, IpAddress, Integer32, Unsigned32, 
			Gauge32, Counter32, Counter64, OBJECT-TYPE, NOTIFICATION-TYPE			
				FROM SNMPv2-SMI			
			RowStatus			
				FROM SNMPv2-TC;
	
	
	
--
-- Node definitions
--
	
--  Node definitions
-- 
-- Node definitions
-- 
-- Node definitions
-- 
-- Node definitions
-- 
-- Node definitions
-- 
-- Node definitions
-- 
-- Node definitions
-- 
-- Node definitions
-- 
-- Node definitions
-- 
-- 1.3.6.1.4.1.37950
-- 1.3.6.1.4.1.37950
-- 1.3.6.1.4.1.37950
-- 1.3.6.1.4.1.37950
-- 1.3.6.1.4.1.37950
-- 1.3.6.1.4.1.37950
-- 1.3.6.1.4.1.37950
-- 1.3.6.1.4.1.37950
-- 1.3.6.1.4.1.37950
		-- 1.3.6.1.4.1.37950
		vsolution OBJECT IDENTIFIER ::= { enterprises 37950 }

		
--          1.3.6.1.4.1.37950.1
-- 1.3.6.1.4.1.37950.1
-- 1.3.6.1.4.1.37950.1
-- 1.3.6.1.4.1.37950.1
-- 1.3.6.1.4.1.37950.1
-- 1.3.6.1.4.1.37950.1
-- 1.3.6.1.4.1.37950.1
-- 1.3.6.1.4.1.37950.1
-- 1.3.6.1.4.1.37950.1
		-- 1.3.6.1.4.1.37950.1
		business OBJECT IDENTIFIER ::= { vsolution 1 }

		
--          1.3.6.1.4.1.37950.1.1
-- 1.3.6.1.4.1.37950.1.1
-- 1.3.6.1.4.1.37950.1.1
-- 1.3.6.1.4.1.37950.1.1
-- 1.3.6.1.4.1.37950.1.1
-- 1.3.6.1.4.1.37950.1.1
-- 1.3.6.1.4.1.37950.1.1
-- 1.3.6.1.4.1.37950.1.1
-- 1.3.6.1.4.1.37950.1.1
		-- 1.3.6.1.4.1.37950.1.1
		devices OBJECT IDENTIFIER ::= { business 1 }

		
--          1.3.6.1.4.1.37950.1.1.5
-- 1.3.6.1.4.1.37950.1.1.5
-- 1.3.6.1.4.1.37950.1.1.5
-- 1.3.6.1.4.1.37950.1.1.5
-- 1.3.6.1.4.1.37950.1.1.5
-- 1.3.6.1.4.1.37950.1.1.5
-- 1.3.6.1.4.1.37950.1.1.5
-- 1.3.6.1.4.1.37950.1.1.5
-- 1.3.6.1.4.1.37950.1.1.5
		-- 1.3.6.1.4.1.37950.1.1.5
		v1600d OBJECT IDENTIFIER ::= { devices 5 }

		
--          1.3.6.1.4.1.37950.1.1.5.10
-- 1.3.6.1.4.1.37950.1.1.5.10
-- 1.3.6.1.4.1.37950.1.1.5.10
-- 1.3.6.1.4.1.37950.1.1.5.10
-- 1.3.6.1.4.1.37950.1.1.5.10
-- 1.3.6.1.4.1.37950.1.1.5.10
-- 1.3.6.1.4.1.37950.1.1.5.10
-- 1.3.6.1.4.1.37950.1.1.5.10
-- 1.3.6.1.4.1.37950.1.1.5.10
		-- 1.3.6.1.4.1.37950.1.1.5.10
		v1600dSwitch OBJECT IDENTIFIER ::= { v1600d 10 }

		
--          1.3.6.1.4.1.37950.1.1.5.10.1
-- 1.3.6.1.4.1.37950.1.1.5.10.1
-- 1.3.6.1.4.1.37950.1.1.5.10.1
-- 1.3.6.1.4.1.37950.1.1.5.10.1
-- 1.3.6.1.4.1.37950.1.1.5.10.1
-- 1.3.6.1.4.1.37950.1.1.5.10.1
-- 1.3.6.1.4.1.37950.1.1.5.10.1
-- 1.3.6.1.4.1.37950.1.1.5.10.1
-- 1.3.6.1.4.1.37950.1.1.5.10.1
		-- 1.3.6.1.4.1.37950.1.1.5.10.1
		v1600dPort OBJECT IDENTIFIER ::= { v1600dSwitch 1 }

		
--          1.3.6.1.4.1.37950.1.1.5.10.1.1
-- 1.3.6.1.4.1.37950.1.1.5.10.1.1
-- 1.3.6.1.4.1.37950.1.1.5.10.1.1
-- 1.3.6.1.4.1.37950.1.1.5.10.1.1
-- 1.3.6.1.4.1.37950.1.1.5.10.1.1
-- 1.3.6.1.4.1.37950.1.1.5.10.1.1
-- 1.3.6.1.4.1.37950.1.1.5.10.1.1
-- 1.3.6.1.4.1.37950.1.1.5.10.1.1
-- 1.3.6.1.4.1.37950.1.1.5.10.1.1
		-- 1.3.6.1.4.1.37950.1.1.5.10.1.1
		upLinkPort OBJECT IDENTIFIER ::= { v1600dPort 1 }

		
--          1.3.6.1.4.1.37950.1.1.5.10.1.1.1
-- 1.3.6.1.4.1.37950.1.1.5.10.1.1.1
-- 1.3.6.1.4.1.37950.1.1.5.10.1.1.1
-- 1.3.6.1.4.1.37950.1.1.5.10.1.1.1
-- 1.3.6.1.4.1.37950.1.1.5.10.1.1.1
-- 1.3.6.1.4.1.37950.1.1.5.10.1.1.1
-- 1.3.6.1.4.1.37950.1.1.5.10.1.1.1
-- 1.3.6.1.4.1.37950.1.1.5.10.1.1.1
-- 1.3.6.1.4.1.37950.1.1.5.10.1.1.1
		-- 1.3.6.1.4.1.37950.1.1.5.10.1.1.1
		uplinkPortConfigTable OBJECT-TYPE
			SYNTAX SEQUENCE OF UplinkPortConfigEntry
			MAX-ACCESS not-accessible
			STATUS current
			DESCRIPTION
				"Description."
			::= { upLinkPort 1 }

		
--          1.3.6.1.4.1.37950.1.1.5.10.1.1.1.1
-- 1.3.6.1.4.1.37950.1.1.5.10.1.1.1.1
-- 1.3.6.1.4.1.37950.1.1.5.10.1.1.1.1
-- 1.3.6.1.4.1.37950.1.1.5.10.1.1.1.1
-- 1.3.6.1.4.1.37950.1.1.5.10.1.1.1.1
-- 1.3.6.1.4.1.37950.1.1.5.10.1.1.1.1
-- 1.3.6.1.4.1.37950.1.1.5.10.1.1.1.1
-- 1.3.6.1.4.1.37950.1.1.5.10.1.1.1.1
-- 1.3.6.1.4.1.37950.1.1.5.10.1.1.1.1
		-- 1.3.6.1.4.1.37950.1.1.5.10.1.1.1.1
		uplinkPortConfigEntry OBJECT-TYPE
			SYNTAX UplinkPortConfigEntry
			MAX-ACCESS not-accessible
			STATUS current
			DESCRIPTION
				"Description."
			INDEX { upLinkPortIndex }
			::= { uplinkPortConfigTable 1 }

		
		UplinkPortConfigEntry ::=
			SEQUENCE { 
				upLinkPortIndex
					INTEGER,
				upLinkPortDescr
					OCTET STRING,
				upLinkPortType
					INTEGER,
				upLinkPortAdminStatus
					INTEGER,
				upLinkPortAutoNegotiation
					INTEGER,
				upLinkPortSpeed
					INTEGER,
				upLinkPortDuplex
					INTEGER,
				upLinkPortFlowControl
					INTEGER,
				upLinkPortMacLearnEn
					INTEGER,
				upLinkPortPriEn
					INTEGER,
				upLinkPortPriValue
					Integer32,
				upLinkPortIngressRate
					INTEGER,
				upLinkPortEgressRate
					INTEGER,
				upLinkPortBCStromCtrl
					INTEGER,
				upLinkPortMCStromCtrl
					INTEGER,
				upLinkPortUCStromCtrl
					INTEGER,
				upLinkPortIsolate
					INTEGER,
				upLinkPortPvid
					INTEGER,
				uplinkPortJumboFrameEn
					INTEGER,
				upLinkPortDescr2
					OCTET STRING,
				uplinkPortHardwareSpeed
					INTEGER,
				uplinkPortMode
					INTEGER,
				uplinkPortMacAddrLearnState
					INTEGER
			 }

--          1.3.6.1.4.1.37950.1.1.5.10.1.1.1.1.1
-- 1.3.6.1.4.1.37950.1.1.5.10.1.1.1.1.1
-- 1.3.6.1.4.1.37950.1.1.5.10.1.1.1.1.1
-- 1.3.6.1.4.1.37950.1.1.5.10.1.1.1.1.1
-- 1.3.6.1.4.1.37950.1.1.5.10.1.1.1.1.1
-- 1.3.6.1.4.1.37950.1.1.5.10.1.1.1.1.1
-- 1.3.6.1.4.1.37950.1.1.5.10.1.1.1.1.1
-- 1.3.6.1.4.1.37950.1.1.5.10.1.1.1.1.1
-- 1.3.6.1.4.1.37950.1.1.5.10.1.1.1.1.1
		-- 1.3.6.1.4.1.37950.1.1.5.10.1.1.1.1.1
		upLinkPortIndex OBJECT-TYPE
			SYNTAX INTEGER (1..16)
			MAX-ACCESS read-only
			STATUS current
			DESCRIPTION
				"Description."
			::= { uplinkPortConfigEntry 1 }

		
--          1.3.6.1.4.1.37950.1.1.5.10.1.1.1.1.2
-- 1.3.6.1.4.1.37950.1.1.5.10.1.1.1.1.2
-- 1.3.6.1.4.1.37950.1.1.5.10.1.1.1.1.2
-- 1.3.6.1.4.1.37950.1.1.5.10.1.1.1.1.2
-- 1.3.6.1.4.1.37950.1.1.5.10.1.1.1.1.2
-- 1.3.6.1.4.1.37950.1.1.5.10.1.1.1.1.2
-- 1.3.6.1.4.1.37950.1.1.5.10.1.1.1.1.2
-- 1.3.6.1.4.1.37950.1.1.5.10.1.1.1.1.2
-- 1.3.6.1.4.1.37950.1.1.5.10.1.1.1.1.2
		-- 1.3.6.1.4.1.37950.1.1.5.10.1.1.1.1.2
		upLinkPortDescr OBJECT-TYPE
			SYNTAX OCTET STRING
			MAX-ACCESS read-write
			STATUS current
			DESCRIPTION
				"Description."
			::= { uplinkPortConfigEntry 2 }

		
--          1.3.6.1.4.1.37950.1.1.5.10.1.1.1.1.3
-- 1.3.6.1.4.1.37950.1.1.5.10.1.1.1.1.3
-- 1.3.6.1.4.1.37950.1.1.5.10.1.1.1.1.3
-- 1.3.6.1.4.1.37950.1.1.5.10.1.1.1.1.3
-- 1.3.6.1.4.1.37950.1.1.5.10.1.1.1.1.3
-- 1.3.6.1.4.1.37950.1.1.5.10.1.1.1.1.3
-- 1.3.6.1.4.1.37950.1.1.5.10.1.1.1.1.3
-- 1.3.6.1.4.1.37950.1.1.5.10.1.1.1.1.3
-- 1.3.6.1.4.1.37950.1.1.5.10.1.1.1.1.3
		-- 1.3.6.1.4.1.37950.1.1.5.10.1.1.1.1.3
		upLinkPortType OBJECT-TYPE
			SYNTAX INTEGER
				{
				fiber(0),
				copper(1)
				}
			MAX-ACCESS read-only
			STATUS current
			DESCRIPTION
				"Description."
			::= { uplinkPortConfigEntry 3 }

		
--          1.3.6.1.4.1.37950.1.1.5.10.1.1.1.1.4
-- 1.3.6.1.4.1.37950.1.1.5.10.1.1.1.1.4
-- 1.3.6.1.4.1.37950.1.1.5.10.1.1.1.1.4
-- 1.3.6.1.4.1.37950.1.1.5.10.1.1.1.1.4
-- 1.3.6.1.4.1.37950.1.1.5.10.1.1.1.1.4
-- 1.3.6.1.4.1.37950.1.1.5.10.1.1.1.1.4
-- 1.3.6.1.4.1.37950.1.1.5.10.1.1.1.1.4
-- 1.3.6.1.4.1.37950.1.1.5.10.1.1.1.1.4
-- 1.3.6.1.4.1.37950.1.1.5.10.1.1.1.1.4
		-- 1.3.6.1.4.1.37950.1.1.5.10.1.1.1.1.4
		upLinkPortAdminStatus OBJECT-TYPE
			SYNTAX INTEGER
				{
				disable(0),
				enable(1)
				}
			MAX-ACCESS read-write
			STATUS current
			DESCRIPTION
				"Description."
			::= { uplinkPortConfigEntry 4 }

		
--          1.3.6.1.4.1.37950.1.1.5.10.1.1.1.1.5
-- 1.3.6.1.4.1.37950.1.1.5.10.1.1.1.1.5
-- 1.3.6.1.4.1.37950.1.1.5.10.1.1.1.1.5
-- 1.3.6.1.4.1.37950.1.1.5.10.1.1.1.1.5
-- 1.3.6.1.4.1.37950.1.1.5.10.1.1.1.1.5
-- 1.3.6.1.4.1.37950.1.1.5.10.1.1.1.1.5
-- 1.3.6.1.4.1.37950.1.1.5.10.1.1.1.1.5
-- 1.3.6.1.4.1.37950.1.1.5.10.1.1.1.1.5
-- 1.3.6.1.4.1.37950.1.1.5.10.1.1.1.1.5
		-- 1.3.6.1.4.1.37950.1.1.5.10.1.1.1.1.5
		upLinkPortAutoNegotiation OBJECT-TYPE
			SYNTAX INTEGER
				{
				disable(0),
				enable(1)
				}
			MAX-ACCESS read-write
			STATUS current
			DESCRIPTION
				"Description."
			::= { uplinkPortConfigEntry 5 }

		
--          1.3.6.1.4.1.37950.1.1.5.10.1.1.1.1.6
-- 1.3.6.1.4.1.37950.1.1.5.10.1.1.1.1.6
-- 1.3.6.1.4.1.37950.1.1.5.10.1.1.1.1.6
-- 1.3.6.1.4.1.37950.1.1.5.10.1.1.1.1.6
-- 1.3.6.1.4.1.37950.1.1.5.10.1.1.1.1.6
-- 1.3.6.1.4.1.37950.1.1.5.10.1.1.1.1.6
-- 1.3.6.1.4.1.37950.1.1.5.10.1.1.1.1.6
-- 1.3.6.1.4.1.37950.1.1.5.10.1.1.1.1.6
-- 1.3.6.1.4.1.37950.1.1.5.10.1.1.1.1.6
		-- 1.3.6.1.4.1.37950.1.1.5.10.1.1.1.1.6
		upLinkPortSpeed OBJECT-TYPE
			SYNTAX INTEGER
				{
				auto(1),
				s10M(2),
				s100M(3),
				s1000M(4)
				}
			MAX-ACCESS read-write
			STATUS current
			DESCRIPTION
				"Description."
			DEFVAL { 1 }
			::= { uplinkPortConfigEntry 6 }

		
--          1.3.6.1.4.1.37950.1.1.5.10.1.1.1.1.7
-- 1.3.6.1.4.1.37950.1.1.5.10.1.1.1.1.7
-- 1.3.6.1.4.1.37950.1.1.5.10.1.1.1.1.7
-- 1.3.6.1.4.1.37950.1.1.5.10.1.1.1.1.7
-- 1.3.6.1.4.1.37950.1.1.5.10.1.1.1.1.7
-- 1.3.6.1.4.1.37950.1.1.5.10.1.1.1.1.7
-- 1.3.6.1.4.1.37950.1.1.5.10.1.1.1.1.7
-- 1.3.6.1.4.1.37950.1.1.5.10.1.1.1.1.7
-- 1.3.6.1.4.1.37950.1.1.5.10.1.1.1.1.7
		-- 1.3.6.1.4.1.37950.1.1.5.10.1.1.1.1.7
		upLinkPortDuplex OBJECT-TYPE
			SYNTAX INTEGER
				{
				auto(1),
				full(2),
				half(3)
				}
			MAX-ACCESS read-write
			STATUS current
			DESCRIPTION
				"Description."
			DEFVAL { 1 }
			::= { uplinkPortConfigEntry 7 }

		
--          1.3.6.1.4.1.37950.1.1.5.10.1.1.1.1.8
-- 1.3.6.1.4.1.37950.1.1.5.10.1.1.1.1.8
-- 1.3.6.1.4.1.37950.1.1.5.10.1.1.1.1.8
-- 1.3.6.1.4.1.37950.1.1.5.10.1.1.1.1.8
-- 1.3.6.1.4.1.37950.1.1.5.10.1.1.1.1.8
-- 1.3.6.1.4.1.37950.1.1.5.10.1.1.1.1.8
-- 1.3.6.1.4.1.37950.1.1.5.10.1.1.1.1.8
-- 1.3.6.1.4.1.37950.1.1.5.10.1.1.1.1.8
-- 1.3.6.1.4.1.37950.1.1.5.10.1.1.1.1.8
		-- 1.3.6.1.4.1.37950.1.1.5.10.1.1.1.1.8
		upLinkPortFlowControl OBJECT-TYPE
			SYNTAX INTEGER
				{
				disable(0),
				enable(1)
				}
			MAX-ACCESS read-write
			STATUS current
			DESCRIPTION
				"Description."
			::= { uplinkPortConfigEntry 8 }

		
--          1.3.6.1.4.1.37950.1.1.5.10.1.1.1.1.9
-- 1.3.6.1.4.1.37950.1.1.5.10.1.1.1.1.9
-- 1.3.6.1.4.1.37950.1.1.5.10.1.1.1.1.9
-- 1.3.6.1.4.1.37950.1.1.5.10.1.1.1.1.9
-- 1.3.6.1.4.1.37950.1.1.5.10.1.1.1.1.9
-- 1.3.6.1.4.1.37950.1.1.5.10.1.1.1.1.9
-- 1.3.6.1.4.1.37950.1.1.5.10.1.1.1.1.9
-- 1.3.6.1.4.1.37950.1.1.5.10.1.1.1.1.9
-- 1.3.6.1.4.1.37950.1.1.5.10.1.1.1.1.9
		-- 1.3.6.1.4.1.37950.1.1.5.10.1.1.1.1.9
		upLinkPortMacLearnEn OBJECT-TYPE
			SYNTAX INTEGER
				{
				disable(0),
				enable(1)
				}
			MAX-ACCESS read-write
			STATUS current
			DESCRIPTION
				"Description."
			::= { uplinkPortConfigEntry 9 }

		
--          1.3.6.1.4.1.37950.1.1.5.10.1.1.1.1.10
-- 1.3.6.1.4.1.37950.1.1.5.10.1.1.1.1.10
-- 1.3.6.1.4.1.37950.1.1.5.10.1.1.1.1.10
-- 1.3.6.1.4.1.37950.1.1.5.10.1.1.1.1.10
-- 1.3.6.1.4.1.37950.1.1.5.10.1.1.1.1.10
-- 1.3.6.1.4.1.37950.1.1.5.10.1.1.1.1.10
-- 1.3.6.1.4.1.37950.1.1.5.10.1.1.1.1.10
-- 1.3.6.1.4.1.37950.1.1.5.10.1.1.1.1.10
-- 1.3.6.1.4.1.37950.1.1.5.10.1.1.1.1.10
		-- 1.3.6.1.4.1.37950.1.1.5.10.1.1.1.1.10
		upLinkPortPriEn OBJECT-TYPE
			SYNTAX INTEGER
				{
				disable(0),
				enable(1)
				}
			MAX-ACCESS read-write
			STATUS current
			DESCRIPTION
				"Description."
			::= { uplinkPortConfigEntry 10 }

		
--          1.3.6.1.4.1.37950.1.1.5.10.1.1.1.1.11
-- 1.3.6.1.4.1.37950.1.1.5.10.1.1.1.1.11
-- 1.3.6.1.4.1.37950.1.1.5.10.1.1.1.1.11
-- 1.3.6.1.4.1.37950.1.1.5.10.1.1.1.1.11
-- 1.3.6.1.4.1.37950.1.1.5.10.1.1.1.1.11
-- 1.3.6.1.4.1.37950.1.1.5.10.1.1.1.1.11
-- 1.3.6.1.4.1.37950.1.1.5.10.1.1.1.1.11
-- 1.3.6.1.4.1.37950.1.1.5.10.1.1.1.1.11
-- 1.3.6.1.4.1.37950.1.1.5.10.1.1.1.1.11
		-- 1.3.6.1.4.1.37950.1.1.5.10.1.1.1.1.11
		upLinkPortPriValue OBJECT-TYPE
			SYNTAX Integer32 (0..7)
			MAX-ACCESS read-write
			STATUS current
			DESCRIPTION
				"Description."
			::= { uplinkPortConfigEntry 11 }

		
--          1.3.6.1.4.1.37950.1.1.5.10.1.1.1.1.12
-- 1.3.6.1.4.1.37950.1.1.5.10.1.1.1.1.12
-- 1.3.6.1.4.1.37950.1.1.5.10.1.1.1.1.12
-- 1.3.6.1.4.1.37950.1.1.5.10.1.1.1.1.12
-- 1.3.6.1.4.1.37950.1.1.5.10.1.1.1.1.12
-- 1.3.6.1.4.1.37950.1.1.5.10.1.1.1.1.12
-- 1.3.6.1.4.1.37950.1.1.5.10.1.1.1.1.12
-- 1.3.6.1.4.1.37950.1.1.5.10.1.1.1.1.12
-- 1.3.6.1.4.1.37950.1.1.5.10.1.1.1.1.12
		-- 1.3.6.1.4.1.37950.1.1.5.10.1.1.1.1.12
		upLinkPortIngressRate OBJECT-TYPE
			SYNTAX INTEGER (0 | 64..1000000)
			MAX-ACCESS read-write
			STATUS current
			DESCRIPTION
				"Description."
			DEFVAL { 0 }
			::= { uplinkPortConfigEntry 12 }

		
--          1.3.6.1.4.1.37950.1.1.5.10.1.1.1.1.13
-- 1.3.6.1.4.1.37950.1.1.5.10.1.1.1.1.13
-- 1.3.6.1.4.1.37950.1.1.5.10.1.1.1.1.13
-- 1.3.6.1.4.1.37950.1.1.5.10.1.1.1.1.13
-- 1.3.6.1.4.1.37950.1.1.5.10.1.1.1.1.13
-- 1.3.6.1.4.1.37950.1.1.5.10.1.1.1.1.13
-- 1.3.6.1.4.1.37950.1.1.5.10.1.1.1.1.13
-- 1.3.6.1.4.1.37950.1.1.5.10.1.1.1.1.13
-- 1.3.6.1.4.1.37950.1.1.5.10.1.1.1.1.13
		-- 1.3.6.1.4.1.37950.1.1.5.10.1.1.1.1.13
		upLinkPortEgressRate OBJECT-TYPE
			SYNTAX INTEGER (0 | 64..1000000)
			MAX-ACCESS read-write
			STATUS current
			DESCRIPTION
				"Description."
			DEFVAL { 0 }
			::= { uplinkPortConfigEntry 13 }

		
--          1.3.6.1.4.1.37950.1.1.5.10.1.1.1.1.14
-- 1.3.6.1.4.1.37950.1.1.5.10.1.1.1.1.14
-- 1.3.6.1.4.1.37950.1.1.5.10.1.1.1.1.14
-- 1.3.6.1.4.1.37950.1.1.5.10.1.1.1.1.14
-- 1.3.6.1.4.1.37950.1.1.5.10.1.1.1.1.14
-- 1.3.6.1.4.1.37950.1.1.5.10.1.1.1.1.14
-- 1.3.6.1.4.1.37950.1.1.5.10.1.1.1.1.14
-- 1.3.6.1.4.1.37950.1.1.5.10.1.1.1.1.14
-- 1.3.6.1.4.1.37950.1.1.5.10.1.1.1.1.14
		-- 1.3.6.1.4.1.37950.1.1.5.10.1.1.1.1.14
		upLinkPortBCStromCtrl OBJECT-TYPE
			SYNTAX INTEGER (0 | 64..1000000)
			MAX-ACCESS read-write
			STATUS current
			DESCRIPTION
				"Description."
			::= { uplinkPortConfigEntry 14 }

		
--          1.3.6.1.4.1.37950.1.1.5.10.1.1.1.1.15
-- 1.3.6.1.4.1.37950.1.1.5.10.1.1.1.1.15
-- 1.3.6.1.4.1.37950.1.1.5.10.1.1.1.1.15
-- 1.3.6.1.4.1.37950.1.1.5.10.1.1.1.1.15
-- 1.3.6.1.4.1.37950.1.1.5.10.1.1.1.1.15
-- 1.3.6.1.4.1.37950.1.1.5.10.1.1.1.1.15
-- 1.3.6.1.4.1.37950.1.1.5.10.1.1.1.1.15
-- 1.3.6.1.4.1.37950.1.1.5.10.1.1.1.1.15
-- 1.3.6.1.4.1.37950.1.1.5.10.1.1.1.1.15
		-- 1.3.6.1.4.1.37950.1.1.5.10.1.1.1.1.15
		upLinkPortMCStromCtrl OBJECT-TYPE
			SYNTAX INTEGER (0 | 64..1000000)
			MAX-ACCESS read-write
			STATUS current
			DESCRIPTION
				"Description."
			::= { uplinkPortConfigEntry 15 }

		
--          1.3.6.1.4.1.37950.1.1.5.10.1.1.1.1.16
-- 1.3.6.1.4.1.37950.1.1.5.10.1.1.1.1.16
-- 1.3.6.1.4.1.37950.1.1.5.10.1.1.1.1.16
-- 1.3.6.1.4.1.37950.1.1.5.10.1.1.1.1.16
-- 1.3.6.1.4.1.37950.1.1.5.10.1.1.1.1.16
-- 1.3.6.1.4.1.37950.1.1.5.10.1.1.1.1.16
-- 1.3.6.1.4.1.37950.1.1.5.10.1.1.1.1.16
-- 1.3.6.1.4.1.37950.1.1.5.10.1.1.1.1.16
-- 1.3.6.1.4.1.37950.1.1.5.10.1.1.1.1.16
		-- 1.3.6.1.4.1.37950.1.1.5.10.1.1.1.1.16
		upLinkPortUCStromCtrl OBJECT-TYPE
			SYNTAX INTEGER (0 | 64..1000000)
			MAX-ACCESS read-write
			STATUS current
			DESCRIPTION
				"Description."
			::= { uplinkPortConfigEntry 16 }

		
--          1.3.6.1.4.1.37950.1.1.5.10.1.1.1.1.17
-- 1.3.6.1.4.1.37950.1.1.5.10.1.1.1.1.17
-- 1.3.6.1.4.1.37950.1.1.5.10.1.1.1.1.17
-- 1.3.6.1.4.1.37950.1.1.5.10.1.1.1.1.17
-- 1.3.6.1.4.1.37950.1.1.5.10.1.1.1.1.17
-- 1.3.6.1.4.1.37950.1.1.5.10.1.1.1.1.17
-- 1.3.6.1.4.1.37950.1.1.5.10.1.1.1.1.17
-- 1.3.6.1.4.1.37950.1.1.5.10.1.1.1.1.17
-- 1.3.6.1.4.1.37950.1.1.5.10.1.1.1.1.17
		-- 1.3.6.1.4.1.37950.1.1.5.10.1.1.1.1.17
		upLinkPortIsolate OBJECT-TYPE
			SYNTAX INTEGER
				{
				no-isolate(0),
				isolate(1)
				}
			MAX-ACCESS read-write
			STATUS current
			DESCRIPTION
				"Description."
			::= { uplinkPortConfigEntry 17 }

		
--          1.3.6.1.4.1.37950.1.1.5.10.1.1.1.1.18
-- 1.3.6.1.4.1.37950.1.1.5.10.1.1.1.1.18
-- 1.3.6.1.4.1.37950.1.1.5.10.1.1.1.1.18
-- 1.3.6.1.4.1.37950.1.1.5.10.1.1.1.1.18
-- 1.3.6.1.4.1.37950.1.1.5.10.1.1.1.1.18
-- 1.3.6.1.4.1.37950.1.1.5.10.1.1.1.1.18
-- 1.3.6.1.4.1.37950.1.1.5.10.1.1.1.1.18
-- 1.3.6.1.4.1.37950.1.1.5.10.1.1.1.1.18
-- 1.3.6.1.4.1.37950.1.1.5.10.1.1.1.1.18
		-- 1.3.6.1.4.1.37950.1.1.5.10.1.1.1.1.18
		upLinkPortPvid OBJECT-TYPE
			SYNTAX INTEGER (1..4096)
			MAX-ACCESS read-write
			STATUS current
			DESCRIPTION
				"Description."
			::= { uplinkPortConfigEntry 18 }

		
--          1.3.6.1.4.1.37950.1.1.5.10.1.1.1.1.19
-- 1.3.6.1.4.1.37950.1.1.5.10.1.1.1.1.19
-- 1.3.6.1.4.1.37950.1.1.5.10.1.1.1.1.19
-- 1.3.6.1.4.1.37950.1.1.5.10.1.1.1.1.19
-- 1.3.6.1.4.1.37950.1.1.5.10.1.1.1.1.19
-- 1.3.6.1.4.1.37950.1.1.5.10.1.1.1.1.19
-- 1.3.6.1.4.1.37950.1.1.5.10.1.1.1.1.19
-- 1.3.6.1.4.1.37950.1.1.5.10.1.1.1.1.19
-- 1.3.6.1.4.1.37950.1.1.5.10.1.1.1.1.19
		-- 1.3.6.1.4.1.37950.1.1.5.10.1.1.1.1.19
		uplinkPortJumboFrameEn OBJECT-TYPE
			SYNTAX INTEGER
				{
				disable(0),
				enable(1)
				}
			MAX-ACCESS read-write
			STATUS current
			DESCRIPTION
				"Description."
			::= { uplinkPortConfigEntry 19 }

		
--          1.3.6.1.4.1.37950.1.1.5.10.1.1.1.1.20
-- 1.3.6.1.4.1.37950.1.1.5.10.1.1.1.1.20
-- 1.3.6.1.4.1.37950.1.1.5.10.1.1.1.1.20
-- 1.3.6.1.4.1.37950.1.1.5.10.1.1.1.1.20
-- 1.3.6.1.4.1.37950.1.1.5.10.1.1.1.1.20
-- 1.3.6.1.4.1.37950.1.1.5.10.1.1.1.1.20
-- 1.3.6.1.4.1.37950.1.1.5.10.1.1.1.1.20
-- 1.3.6.1.4.1.37950.1.1.5.10.1.1.1.1.20
-- 1.3.6.1.4.1.37950.1.1.5.10.1.1.1.1.20
		-- 1.3.6.1.4.1.37950.1.1.5.10.1.1.1.1.20
		upLinkPortDescr2 OBJECT-TYPE
			SYNTAX OCTET STRING
			MAX-ACCESS read-write
			STATUS current
			DESCRIPTION
				"Description."
			::= { uplinkPortConfigEntry 20 }

		
--         1.3.6.1.4.1.37950.1.1.5.10.1.1.1.1.21
-- 1.3.6.1.4.1.37950.1.1.5.10.1.1.1.1.21
-- 1.3.6.1.4.1.37950.1.1.5.10.1.1.1.1.21
-- 1.3.6.1.4.1.37950.1.1.5.10.1.1.1.1.21
-- 1.3.6.1.4.1.37950.1.1.5.10.1.1.1.1.21
-- 1.3.6.1.4.1.37950.1.1.5.10.1.1.1.1.21
-- 1.3.6.1.4.1.37950.1.1.5.10.1.1.1.1.21
-- 1.3.6.1.4.1.37950.1.1.5.10.1.1.1.1.21
		-- 1.3.6.1.4.1.37950.1.1.5.10.1.1.1.1.21
		uplinkPortHardwareSpeed OBJECT-TYPE
			SYNTAX INTEGER
				{
				ge(0),
				ge10(1)
				}
			MAX-ACCESS read-write
			STATUS current
			DESCRIPTION
				"Description."
			::= { uplinkPortConfigEntry 21 }

		
--         1.3.6.1.4.1.37950.1.1.5.10.1.1.1.1.22
-- 1.3.6.1.4.1.37950.1.1.5.10.1.1.1.1.22
-- 1.3.6.1.4.1.37950.1.1.5.10.1.1.1.1.22
-- 1.3.6.1.4.1.37950.1.1.5.10.1.1.1.1.22
-- 1.3.6.1.4.1.37950.1.1.5.10.1.1.1.1.22
-- 1.3.6.1.4.1.37950.1.1.5.10.1.1.1.1.22
-- 1.3.6.1.4.1.37950.1.1.5.10.1.1.1.1.22
-- 1.3.6.1.4.1.37950.1.1.5.10.1.1.1.1.22
		-- 1.3.6.1.4.1.37950.1.1.5.10.1.1.1.1.22
		uplinkPortMode OBJECT-TYPE
			SYNTAX INTEGER
				{
				access(1),
				trunk(2),
				hybrid(3)
				}
			MAX-ACCESS read-write
			STATUS current
			DESCRIPTION
				"Description."
			::= { uplinkPortConfigEntry 22 }

		
--         1.3.6.1.4.1.37950.1.1.5.10.1.1.1.1.23
-- 1.3.6.1.4.1.37950.1.1.5.10.1.1.1.1.23
-- 1.3.6.1.4.1.37950.1.1.5.10.1.1.1.1.23
-- 1.3.6.1.4.1.37950.1.1.5.10.1.1.1.1.23
-- 1.3.6.1.4.1.37950.1.1.5.10.1.1.1.1.23
-- 1.3.6.1.4.1.37950.1.1.5.10.1.1.1.1.23
-- 1.3.6.1.4.1.37950.1.1.5.10.1.1.1.1.23
-- 1.3.6.1.4.1.37950.1.1.5.10.1.1.1.1.23
		-- 1.3.6.1.4.1.37950.1.1.5.10.1.1.1.1.23
		uplinkPortMacAddrLearnState OBJECT-TYPE
			SYNTAX INTEGER
				{
				disable(0),
				enable(1)
				}
			MAX-ACCESS read-write
			STATUS current
			DESCRIPTION
				"Description."
			::= { uplinkPortConfigEntry 23 }

		
--          1.3.6.1.4.1.37950.1.1.5.10.1.1.2
-- 1.3.6.1.4.1.37950.1.1.5.10.1.1.2
-- 1.3.6.1.4.1.37950.1.1.5.10.1.1.2
-- 1.3.6.1.4.1.37950.1.1.5.10.1.1.2
-- 1.3.6.1.4.1.37950.1.1.5.10.1.1.2
-- 1.3.6.1.4.1.37950.1.1.5.10.1.1.2
-- 1.3.6.1.4.1.37950.1.1.5.10.1.1.2
-- 1.3.6.1.4.1.37950.1.1.5.10.1.1.2
-- 1.3.6.1.4.1.37950.1.1.5.10.1.1.2
		-- 1.3.6.1.4.1.37950.1.1.5.10.1.1.2
		uplinkPortPerformanceDataTable OBJECT-TYPE
			SYNTAX SEQUENCE OF UplinkPortPerformanceDataEntry
			MAX-ACCESS not-accessible
			STATUS current
			DESCRIPTION
				"Description."
			::= { upLinkPort 2 }

		
--          1.3.6.1.4.1.37950.1.1.5.10.1.1.2.1
-- 1.3.6.1.4.1.37950.1.1.5.10.1.1.2.1
-- 1.3.6.1.4.1.37950.1.1.5.10.1.1.2.1
-- 1.3.6.1.4.1.37950.1.1.5.10.1.1.2.1
-- 1.3.6.1.4.1.37950.1.1.5.10.1.1.2.1
-- 1.3.6.1.4.1.37950.1.1.5.10.1.1.2.1
-- 1.3.6.1.4.1.37950.1.1.5.10.1.1.2.1
-- 1.3.6.1.4.1.37950.1.1.5.10.1.1.2.1
-- 1.3.6.1.4.1.37950.1.1.5.10.1.1.2.1
		-- 1.3.6.1.4.1.37950.1.1.5.10.1.1.2.1
		uplinkPortPerformanceDataEntry OBJECT-TYPE
			SYNTAX UplinkPortPerformanceDataEntry
			MAX-ACCESS not-accessible
			STATUS current
			DESCRIPTION
				"Description."
			INDEX { upLinkPIndex }
			::= { uplinkPortPerformanceDataTable 1 }

		
		UplinkPortPerformanceDataEntry ::=
			SEQUENCE { 
				upLinkPIndex
					INTEGER,
				upLinkPortDownOctets
					Counter32,
				upLinkDownSpeed
					Counter32,
				upLinkPortDownMaxBand
					Counter32,
				upLinkPortDownProportion
					Counter32,
				upLinkPortDownUcastPkts
					Counter32,
				upLinkPortDownMulicastPkts
					Counter32,
				upLinkPortDownBrocastPkts
					Counter32,
				upLinkPortDownPackets
					Counter32,
				upLinkPortDownNormalOctets
					Counter32,
				upLinkPortDownErrOctets
					Counter32,
				upLinkPortDownPausePkts
					Counter32,
				upLinkPortUpOctets
					Counter32,
				upLinkPortUpSpeed
					Counter32,
				upLinkPortUpMaxBand
					Counter32,
				upLinkPortUpProportion
					Counter32,
				upLinkPortUpUcastPkts
					Counter32,
				upLinkPortUpMulicastPkts
					Counter32,
				upLinkPortUpBrocastPkts
					Counter32,
				upLinkPortUpPackets
					Counter32,
				upLinkPortUpNormalOctets
					Counter32,
				upLinkPortUpErrOctets
					Counter32,
				upLinkPortUpPausePkts
					Counter32,
				upLinkPortDroppedPkts
					Counter32,
				upLinkPortCrcError
					Counter32,
				upLinkPortJabber
					Counter32,
				upLinkPortOverSize
					Counter32,
				upLinkPortUnderSize
					Counter32,
				upLinkPortCollision
					Counter32,
				upLinkPort64OctetFrames
					Counter32,
				upLinkPort65To127OctetFrames
					Counter32,
				upLinkPort128To255OctetFrames
					Counter32,
				upLinkPort256To511OctetFrames
					Counter32,
				upLinkPort512To1023OctetFrames
					Counter32,
				upLinkPortOver1024OctetFrames
					Counter32,
				uplinkPortDownBytes
					Counter64,
				uplinkPortUpBytes
					Counter64
			 }

--          1.3.6.1.4.1.37950.1.1.5.10.1.1.2.1.1
-- 1.3.6.1.4.1.37950.1.1.5.10.1.1.2.1.1
-- 1.3.6.1.4.1.37950.1.1.5.10.1.1.2.1.1
-- 1.3.6.1.4.1.37950.1.1.5.10.1.1.2.1.1
-- 1.3.6.1.4.1.37950.1.1.5.10.1.1.2.1.1
-- 1.3.6.1.4.1.37950.1.1.5.10.1.1.2.1.1
-- 1.3.6.1.4.1.37950.1.1.5.10.1.1.2.1.1
-- 1.3.6.1.4.1.37950.1.1.5.10.1.1.2.1.1
-- 1.3.6.1.4.1.37950.1.1.5.10.1.1.2.1.1
		-- 1.3.6.1.4.1.37950.1.1.5.10.1.1.2.1.1
		upLinkPIndex OBJECT-TYPE
			SYNTAX INTEGER (1..16)
			MAX-ACCESS read-only
			STATUS current
			DESCRIPTION
				"Description."
			::= { uplinkPortPerformanceDataEntry 1 }

		
--          1.3.6.1.4.1.37950.1.1.5.10.1.1.2.1.2
-- 1.3.6.1.4.1.37950.1.1.5.10.1.1.2.1.2
-- 1.3.6.1.4.1.37950.1.1.5.10.1.1.2.1.2
-- 1.3.6.1.4.1.37950.1.1.5.10.1.1.2.1.2
-- 1.3.6.1.4.1.37950.1.1.5.10.1.1.2.1.2
-- 1.3.6.1.4.1.37950.1.1.5.10.1.1.2.1.2
-- 1.3.6.1.4.1.37950.1.1.5.10.1.1.2.1.2
-- 1.3.6.1.4.1.37950.1.1.5.10.1.1.2.1.2
-- 1.3.6.1.4.1.37950.1.1.5.10.1.1.2.1.2
		-- 1.3.6.1.4.1.37950.1.1.5.10.1.1.2.1.2
		upLinkPortDownOctets OBJECT-TYPE
			SYNTAX Counter32
			MAX-ACCESS read-only
			STATUS current
			DESCRIPTION
				"Description."
			::= { uplinkPortPerformanceDataEntry 2 }

		
--          1.3.6.1.4.1.37950.1.1.5.10.1.1.2.1.3
-- 1.3.6.1.4.1.37950.1.1.5.10.1.1.2.1.3
-- 1.3.6.1.4.1.37950.1.1.5.10.1.1.2.1.3
-- 1.3.6.1.4.1.37950.1.1.5.10.1.1.2.1.3
-- 1.3.6.1.4.1.37950.1.1.5.10.1.1.2.1.3
-- 1.3.6.1.4.1.37950.1.1.5.10.1.1.2.1.3
-- 1.3.6.1.4.1.37950.1.1.5.10.1.1.2.1.3
-- 1.3.6.1.4.1.37950.1.1.5.10.1.1.2.1.3
-- 1.3.6.1.4.1.37950.1.1.5.10.1.1.2.1.3
		-- 1.3.6.1.4.1.37950.1.1.5.10.1.1.2.1.3
		upLinkDownSpeed OBJECT-TYPE
			SYNTAX Counter32
			MAX-ACCESS read-only
			STATUS current
			DESCRIPTION
				"Description."
			::= { uplinkPortPerformanceDataEntry 3 }

		
--          1.3.6.1.4.1.37950.1.1.5.10.1.1.2.1.4
-- 1.3.6.1.4.1.37950.1.1.5.10.1.1.2.1.4
-- 1.3.6.1.4.1.37950.1.1.5.10.1.1.2.1.4
-- 1.3.6.1.4.1.37950.1.1.5.10.1.1.2.1.4
-- 1.3.6.1.4.1.37950.1.1.5.10.1.1.2.1.4
-- 1.3.6.1.4.1.37950.1.1.5.10.1.1.2.1.4
-- 1.3.6.1.4.1.37950.1.1.5.10.1.1.2.1.4
-- 1.3.6.1.4.1.37950.1.1.5.10.1.1.2.1.4
-- 1.3.6.1.4.1.37950.1.1.5.10.1.1.2.1.4
		-- 1.3.6.1.4.1.37950.1.1.5.10.1.1.2.1.4
		upLinkPortDownMaxBand OBJECT-TYPE
			SYNTAX Counter32
			MAX-ACCESS read-only
			STATUS current
			DESCRIPTION
				"Description."
			::= { uplinkPortPerformanceDataEntry 4 }

		
--          1.3.6.1.4.1.37950.1.1.5.10.1.1.2.1.5
-- 1.3.6.1.4.1.37950.1.1.5.10.1.1.2.1.5
-- 1.3.6.1.4.1.37950.1.1.5.10.1.1.2.1.5
-- 1.3.6.1.4.1.37950.1.1.5.10.1.1.2.1.5
-- 1.3.6.1.4.1.37950.1.1.5.10.1.1.2.1.5
-- 1.3.6.1.4.1.37950.1.1.5.10.1.1.2.1.5
-- 1.3.6.1.4.1.37950.1.1.5.10.1.1.2.1.5
-- 1.3.6.1.4.1.37950.1.1.5.10.1.1.2.1.5
-- 1.3.6.1.4.1.37950.1.1.5.10.1.1.2.1.5
		-- 1.3.6.1.4.1.37950.1.1.5.10.1.1.2.1.5
		upLinkPortDownProportion OBJECT-TYPE
			SYNTAX Counter32
			MAX-ACCESS read-only
			STATUS current
			DESCRIPTION
				"Description."
			::= { uplinkPortPerformanceDataEntry 5 }

		
--          1.3.6.1.4.1.37950.1.1.5.10.1.1.2.1.6
-- 1.3.6.1.4.1.37950.1.1.5.10.1.1.2.1.6
-- 1.3.6.1.4.1.37950.1.1.5.10.1.1.2.1.6
-- 1.3.6.1.4.1.37950.1.1.5.10.1.1.2.1.6
-- 1.3.6.1.4.1.37950.1.1.5.10.1.1.2.1.6
-- 1.3.6.1.4.1.37950.1.1.5.10.1.1.2.1.6
-- 1.3.6.1.4.1.37950.1.1.5.10.1.1.2.1.6
-- 1.3.6.1.4.1.37950.1.1.5.10.1.1.2.1.6
-- 1.3.6.1.4.1.37950.1.1.5.10.1.1.2.1.6
		-- 1.3.6.1.4.1.37950.1.1.5.10.1.1.2.1.6
		upLinkPortDownUcastPkts OBJECT-TYPE
			SYNTAX Counter32
			MAX-ACCESS read-only
			STATUS current
			DESCRIPTION
				"Description."
			::= { uplinkPortPerformanceDataEntry 6 }

		
--          1.3.6.1.4.1.37950.1.1.5.10.1.1.2.1.7
-- 1.3.6.1.4.1.37950.1.1.5.10.1.1.2.1.7
-- 1.3.6.1.4.1.37950.1.1.5.10.1.1.2.1.7
-- 1.3.6.1.4.1.37950.1.1.5.10.1.1.2.1.7
-- 1.3.6.1.4.1.37950.1.1.5.10.1.1.2.1.7
-- 1.3.6.1.4.1.37950.1.1.5.10.1.1.2.1.7
-- 1.3.6.1.4.1.37950.1.1.5.10.1.1.2.1.7
-- 1.3.6.1.4.1.37950.1.1.5.10.1.1.2.1.7
-- 1.3.6.1.4.1.37950.1.1.5.10.1.1.2.1.7
		-- 1.3.6.1.4.1.37950.1.1.5.10.1.1.2.1.7
		upLinkPortDownMulicastPkts OBJECT-TYPE
			SYNTAX Counter32
			MAX-ACCESS read-only
			STATUS current
			DESCRIPTION
				"Description."
			::= { uplinkPortPerformanceDataEntry 7 }

		
--          1.3.6.1.4.1.37950.1.1.5.10.1.1.2.1.8
-- 1.3.6.1.4.1.37950.1.1.5.10.1.1.2.1.8
-- 1.3.6.1.4.1.37950.1.1.5.10.1.1.2.1.8
-- 1.3.6.1.4.1.37950.1.1.5.10.1.1.2.1.8
-- 1.3.6.1.4.1.37950.1.1.5.10.1.1.2.1.8
-- 1.3.6.1.4.1.37950.1.1.5.10.1.1.2.1.8
-- 1.3.6.1.4.1.37950.1.1.5.10.1.1.2.1.8
-- 1.3.6.1.4.1.37950.1.1.5.10.1.1.2.1.8
-- 1.3.6.1.4.1.37950.1.1.5.10.1.1.2.1.8
		-- 1.3.6.1.4.1.37950.1.1.5.10.1.1.2.1.8
		upLinkPortDownBrocastPkts OBJECT-TYPE
			SYNTAX Counter32
			MAX-ACCESS read-only
			STATUS current
			DESCRIPTION
				"Description."
			::= { uplinkPortPerformanceDataEntry 8 }

		
--          1.3.6.1.4.1.37950.1.1.5.10.1.1.2.1.9
-- 1.3.6.1.4.1.37950.1.1.5.10.1.1.2.1.9
-- 1.3.6.1.4.1.37950.1.1.5.10.1.1.2.1.9
-- 1.3.6.1.4.1.37950.1.1.5.10.1.1.2.1.9
-- 1.3.6.1.4.1.37950.1.1.5.10.1.1.2.1.9
-- 1.3.6.1.4.1.37950.1.1.5.10.1.1.2.1.9
-- 1.3.6.1.4.1.37950.1.1.5.10.1.1.2.1.9
-- 1.3.6.1.4.1.37950.1.1.5.10.1.1.2.1.9
-- 1.3.6.1.4.1.37950.1.1.5.10.1.1.2.1.9
		-- 1.3.6.1.4.1.37950.1.1.5.10.1.1.2.1.9
		upLinkPortDownPackets OBJECT-TYPE
			SYNTAX Counter32
			MAX-ACCESS read-only
			STATUS current
			DESCRIPTION
				"Description."
			::= { uplinkPortPerformanceDataEntry 9 }

		
--          1.3.6.1.4.1.37950.1.1.5.10.1.1.2.1.10
-- 1.3.6.1.4.1.37950.1.1.5.10.1.1.2.1.10
-- 1.3.6.1.4.1.37950.1.1.5.10.1.1.2.1.10
-- 1.3.6.1.4.1.37950.1.1.5.10.1.1.2.1.10
-- 1.3.6.1.4.1.37950.1.1.5.10.1.1.2.1.10
-- 1.3.6.1.4.1.37950.1.1.5.10.1.1.2.1.10
-- 1.3.6.1.4.1.37950.1.1.5.10.1.1.2.1.10
-- 1.3.6.1.4.1.37950.1.1.5.10.1.1.2.1.10
-- 1.3.6.1.4.1.37950.1.1.5.10.1.1.2.1.10
		-- 1.3.6.1.4.1.37950.1.1.5.10.1.1.2.1.10
		upLinkPortDownNormalOctets OBJECT-TYPE
			SYNTAX Counter32
			MAX-ACCESS read-only
			STATUS current
			DESCRIPTION
				"Description."
			::= { uplinkPortPerformanceDataEntry 10 }

		
--          1.3.6.1.4.1.37950.1.1.5.10.1.1.2.1.11
-- 1.3.6.1.4.1.37950.1.1.5.10.1.1.2.1.11
-- 1.3.6.1.4.1.37950.1.1.5.10.1.1.2.1.11
-- 1.3.6.1.4.1.37950.1.1.5.10.1.1.2.1.11
-- 1.3.6.1.4.1.37950.1.1.5.10.1.1.2.1.11
-- 1.3.6.1.4.1.37950.1.1.5.10.1.1.2.1.11
-- 1.3.6.1.4.1.37950.1.1.5.10.1.1.2.1.11
-- 1.3.6.1.4.1.37950.1.1.5.10.1.1.2.1.11
-- 1.3.6.1.4.1.37950.1.1.5.10.1.1.2.1.11
		-- 1.3.6.1.4.1.37950.1.1.5.10.1.1.2.1.11
		upLinkPortDownErrOctets OBJECT-TYPE
			SYNTAX Counter32
			MAX-ACCESS read-only
			STATUS current
			DESCRIPTION
				"Description."
			::= { uplinkPortPerformanceDataEntry 11 }

		
--          1.3.6.1.4.1.37950.1.1.5.10.1.1.2.1.12
-- 1.3.6.1.4.1.37950.1.1.5.10.1.1.2.1.12
-- 1.3.6.1.4.1.37950.1.1.5.10.1.1.2.1.12
-- 1.3.6.1.4.1.37950.1.1.5.10.1.1.2.1.12
-- 1.3.6.1.4.1.37950.1.1.5.10.1.1.2.1.12
-- 1.3.6.1.4.1.37950.1.1.5.10.1.1.2.1.12
-- 1.3.6.1.4.1.37950.1.1.5.10.1.1.2.1.12
-- 1.3.6.1.4.1.37950.1.1.5.10.1.1.2.1.12
-- 1.3.6.1.4.1.37950.1.1.5.10.1.1.2.1.12
		-- 1.3.6.1.4.1.37950.1.1.5.10.1.1.2.1.12
		upLinkPortDownPausePkts OBJECT-TYPE
			SYNTAX Counter32
			MAX-ACCESS read-only
			STATUS current
			DESCRIPTION
				"Description."
			::= { uplinkPortPerformanceDataEntry 12 }

		
--          1.3.6.1.4.1.37950.1.1.5.10.1.1.2.1.13
-- 1.3.6.1.4.1.37950.1.1.5.10.1.1.2.1.13
-- 1.3.6.1.4.1.37950.1.1.5.10.1.1.2.1.13
-- 1.3.6.1.4.1.37950.1.1.5.10.1.1.2.1.13
-- 1.3.6.1.4.1.37950.1.1.5.10.1.1.2.1.13
-- 1.3.6.1.4.1.37950.1.1.5.10.1.1.2.1.13
-- 1.3.6.1.4.1.37950.1.1.5.10.1.1.2.1.13
-- 1.3.6.1.4.1.37950.1.1.5.10.1.1.2.1.13
-- 1.3.6.1.4.1.37950.1.1.5.10.1.1.2.1.13
		-- 1.3.6.1.4.1.37950.1.1.5.10.1.1.2.1.13
		upLinkPortUpOctets OBJECT-TYPE
			SYNTAX Counter32
			MAX-ACCESS read-only
			STATUS current
			DESCRIPTION
				"Description."
			::= { uplinkPortPerformanceDataEntry 13 }

		
--          1.3.6.1.4.1.37950.1.1.5.10.1.1.2.1.14
-- 1.3.6.1.4.1.37950.1.1.5.10.1.1.2.1.14
-- 1.3.6.1.4.1.37950.1.1.5.10.1.1.2.1.14
-- 1.3.6.1.4.1.37950.1.1.5.10.1.1.2.1.14
-- 1.3.6.1.4.1.37950.1.1.5.10.1.1.2.1.14
-- 1.3.6.1.4.1.37950.1.1.5.10.1.1.2.1.14
-- 1.3.6.1.4.1.37950.1.1.5.10.1.1.2.1.14
-- 1.3.6.1.4.1.37950.1.1.5.10.1.1.2.1.14
-- 1.3.6.1.4.1.37950.1.1.5.10.1.1.2.1.14
		-- 1.3.6.1.4.1.37950.1.1.5.10.1.1.2.1.14
		upLinkPortUpSpeed OBJECT-TYPE
			SYNTAX Counter32
			MAX-ACCESS read-only
			STATUS current
			DESCRIPTION
				"Description."
			::= { uplinkPortPerformanceDataEntry 14 }

		
--          1.3.6.1.4.1.37950.1.1.5.10.1.1.2.1.15
-- 1.3.6.1.4.1.37950.1.1.5.10.1.1.2.1.15
-- 1.3.6.1.4.1.37950.1.1.5.10.1.1.2.1.15
-- 1.3.6.1.4.1.37950.1.1.5.10.1.1.2.1.15
-- 1.3.6.1.4.1.37950.1.1.5.10.1.1.2.1.15
-- 1.3.6.1.4.1.37950.1.1.5.10.1.1.2.1.15
-- 1.3.6.1.4.1.37950.1.1.5.10.1.1.2.1.15
-- 1.3.6.1.4.1.37950.1.1.5.10.1.1.2.1.15
-- 1.3.6.1.4.1.37950.1.1.5.10.1.1.2.1.15
		-- 1.3.6.1.4.1.37950.1.1.5.10.1.1.2.1.15
		upLinkPortUpMaxBand OBJECT-TYPE
			SYNTAX Counter32
			MAX-ACCESS read-write
			STATUS current
			DESCRIPTION
				"Description."
			::= { uplinkPortPerformanceDataEntry 15 }

		
--          1.3.6.1.4.1.37950.1.1.5.10.1.1.2.1.16
-- 1.3.6.1.4.1.37950.1.1.5.10.1.1.2.1.16
-- 1.3.6.1.4.1.37950.1.1.5.10.1.1.2.1.16
-- 1.3.6.1.4.1.37950.1.1.5.10.1.1.2.1.16
-- 1.3.6.1.4.1.37950.1.1.5.10.1.1.2.1.16
-- 1.3.6.1.4.1.37950.1.1.5.10.1.1.2.1.16
-- 1.3.6.1.4.1.37950.1.1.5.10.1.1.2.1.16
-- 1.3.6.1.4.1.37950.1.1.5.10.1.1.2.1.16
-- 1.3.6.1.4.1.37950.1.1.5.10.1.1.2.1.16
		-- 1.3.6.1.4.1.37950.1.1.5.10.1.1.2.1.16
		upLinkPortUpProportion OBJECT-TYPE
			SYNTAX Counter32
			MAX-ACCESS read-only
			STATUS current
			DESCRIPTION
				"Description."
			::= { uplinkPortPerformanceDataEntry 16 }

		
--          1.3.6.1.4.1.37950.1.1.5.10.1.1.2.1.17
-- 1.3.6.1.4.1.37950.1.1.5.10.1.1.2.1.17
-- 1.3.6.1.4.1.37950.1.1.5.10.1.1.2.1.17
-- 1.3.6.1.4.1.37950.1.1.5.10.1.1.2.1.17
-- 1.3.6.1.4.1.37950.1.1.5.10.1.1.2.1.17
-- 1.3.6.1.4.1.37950.1.1.5.10.1.1.2.1.17
-- 1.3.6.1.4.1.37950.1.1.5.10.1.1.2.1.17
-- 1.3.6.1.4.1.37950.1.1.5.10.1.1.2.1.17
-- 1.3.6.1.4.1.37950.1.1.5.10.1.1.2.1.17
		-- 1.3.6.1.4.1.37950.1.1.5.10.1.1.2.1.17
		upLinkPortUpUcastPkts OBJECT-TYPE
			SYNTAX Counter32
			MAX-ACCESS read-only
			STATUS current
			DESCRIPTION
				"Description."
			::= { uplinkPortPerformanceDataEntry 17 }

		
--          1.3.6.1.4.1.37950.1.1.5.10.1.1.2.1.18
-- 1.3.6.1.4.1.37950.1.1.5.10.1.1.2.1.18
-- 1.3.6.1.4.1.37950.1.1.5.10.1.1.2.1.18
-- 1.3.6.1.4.1.37950.1.1.5.10.1.1.2.1.18
-- 1.3.6.1.4.1.37950.1.1.5.10.1.1.2.1.18
-- 1.3.6.1.4.1.37950.1.1.5.10.1.1.2.1.18
-- 1.3.6.1.4.1.37950.1.1.5.10.1.1.2.1.18
-- 1.3.6.1.4.1.37950.1.1.5.10.1.1.2.1.18
-- 1.3.6.1.4.1.37950.1.1.5.10.1.1.2.1.18
		-- 1.3.6.1.4.1.37950.1.1.5.10.1.1.2.1.18
		upLinkPortUpMulicastPkts OBJECT-TYPE
			SYNTAX Counter32
			MAX-ACCESS read-only
			STATUS current
			DESCRIPTION
				"Description."
			::= { uplinkPortPerformanceDataEntry 18 }

		
--          1.3.6.1.4.1.37950.1.1.5.10.1.1.2.1.19
-- 1.3.6.1.4.1.37950.1.1.5.10.1.1.2.1.19
-- 1.3.6.1.4.1.37950.1.1.5.10.1.1.2.1.19
-- 1.3.6.1.4.1.37950.1.1.5.10.1.1.2.1.19
-- 1.3.6.1.4.1.37950.1.1.5.10.1.1.2.1.19
-- 1.3.6.1.4.1.37950.1.1.5.10.1.1.2.1.19
-- 1.3.6.1.4.1.37950.1.1.5.10.1.1.2.1.19
-- 1.3.6.1.4.1.37950.1.1.5.10.1.1.2.1.19
-- 1.3.6.1.4.1.37950.1.1.5.10.1.1.2.1.19
		-- 1.3.6.1.4.1.37950.1.1.5.10.1.1.2.1.19
		upLinkPortUpBrocastPkts OBJECT-TYPE
			SYNTAX Counter32
			MAX-ACCESS read-only
			STATUS current
			DESCRIPTION
				"Description."
			::= { uplinkPortPerformanceDataEntry 19 }

		
--          1.3.6.1.4.1.37950.1.1.5.10.1.1.2.1.20
-- 1.3.6.1.4.1.37950.1.1.5.10.1.1.2.1.20
-- 1.3.6.1.4.1.37950.1.1.5.10.1.1.2.1.20
-- 1.3.6.1.4.1.37950.1.1.5.10.1.1.2.1.20
-- 1.3.6.1.4.1.37950.1.1.5.10.1.1.2.1.20
-- 1.3.6.1.4.1.37950.1.1.5.10.1.1.2.1.20
-- 1.3.6.1.4.1.37950.1.1.5.10.1.1.2.1.20
-- 1.3.6.1.4.1.37950.1.1.5.10.1.1.2.1.20
-- 1.3.6.1.4.1.37950.1.1.5.10.1.1.2.1.20
		-- 1.3.6.1.4.1.37950.1.1.5.10.1.1.2.1.20
		upLinkPortUpPackets OBJECT-TYPE
			SYNTAX Counter32
			MAX-ACCESS read-only
			STATUS current
			DESCRIPTION
				"Description."
			::= { uplinkPortPerformanceDataEntry 20 }

		
--          1.3.6.1.4.1.37950.1.1.5.10.1.1.2.1.21
-- 1.3.6.1.4.1.37950.1.1.5.10.1.1.2.1.21
-- 1.3.6.1.4.1.37950.1.1.5.10.1.1.2.1.21
-- 1.3.6.1.4.1.37950.1.1.5.10.1.1.2.1.21
-- 1.3.6.1.4.1.37950.1.1.5.10.1.1.2.1.21
-- 1.3.6.1.4.1.37950.1.1.5.10.1.1.2.1.21
-- 1.3.6.1.4.1.37950.1.1.5.10.1.1.2.1.21
-- 1.3.6.1.4.1.37950.1.1.5.10.1.1.2.1.21
-- 1.3.6.1.4.1.37950.1.1.5.10.1.1.2.1.21
		-- 1.3.6.1.4.1.37950.1.1.5.10.1.1.2.1.21
		upLinkPortUpNormalOctets OBJECT-TYPE
			SYNTAX Counter32
			MAX-ACCESS read-only
			STATUS current
			DESCRIPTION
				"Description."
			::= { uplinkPortPerformanceDataEntry 21 }

		
--          1.3.6.1.4.1.37950.1.1.5.10.1.1.2.1.22
-- 1.3.6.1.4.1.37950.1.1.5.10.1.1.2.1.22
-- 1.3.6.1.4.1.37950.1.1.5.10.1.1.2.1.22
-- 1.3.6.1.4.1.37950.1.1.5.10.1.1.2.1.22
-- 1.3.6.1.4.1.37950.1.1.5.10.1.1.2.1.22
-- 1.3.6.1.4.1.37950.1.1.5.10.1.1.2.1.22
-- 1.3.6.1.4.1.37950.1.1.5.10.1.1.2.1.22
-- 1.3.6.1.4.1.37950.1.1.5.10.1.1.2.1.22
-- 1.3.6.1.4.1.37950.1.1.5.10.1.1.2.1.22
		-- 1.3.6.1.4.1.37950.1.1.5.10.1.1.2.1.22
		upLinkPortUpErrOctets OBJECT-TYPE
			SYNTAX Counter32
			MAX-ACCESS read-only
			STATUS current
			DESCRIPTION
				"Description."
			::= { uplinkPortPerformanceDataEntry 22 }

		
--          1.3.6.1.4.1.37950.1.1.5.10.1.1.2.1.23
-- 1.3.6.1.4.1.37950.1.1.5.10.1.1.2.1.23
-- 1.3.6.1.4.1.37950.1.1.5.10.1.1.2.1.23
-- 1.3.6.1.4.1.37950.1.1.5.10.1.1.2.1.23
-- 1.3.6.1.4.1.37950.1.1.5.10.1.1.2.1.23
-- 1.3.6.1.4.1.37950.1.1.5.10.1.1.2.1.23
-- 1.3.6.1.4.1.37950.1.1.5.10.1.1.2.1.23
-- 1.3.6.1.4.1.37950.1.1.5.10.1.1.2.1.23
-- 1.3.6.1.4.1.37950.1.1.5.10.1.1.2.1.23
		-- 1.3.6.1.4.1.37950.1.1.5.10.1.1.2.1.23
		upLinkPortUpPausePkts OBJECT-TYPE
			SYNTAX Counter32
			MAX-ACCESS read-only
			STATUS current
			DESCRIPTION
				"Description."
			::= { uplinkPortPerformanceDataEntry 23 }

		
--          1.3.6.1.4.1.37950.1.1.5.10.1.1.2.1.24
-- 1.3.6.1.4.1.37950.1.1.5.10.1.1.2.1.24
-- 1.3.6.1.4.1.37950.1.1.5.10.1.1.2.1.24
-- 1.3.6.1.4.1.37950.1.1.5.10.1.1.2.1.24
-- 1.3.6.1.4.1.37950.1.1.5.10.1.1.2.1.24
-- 1.3.6.1.4.1.37950.1.1.5.10.1.1.2.1.24
-- 1.3.6.1.4.1.37950.1.1.5.10.1.1.2.1.24
-- 1.3.6.1.4.1.37950.1.1.5.10.1.1.2.1.24
-- 1.3.6.1.4.1.37950.1.1.5.10.1.1.2.1.24
		-- 1.3.6.1.4.1.37950.1.1.5.10.1.1.2.1.24
		upLinkPortDroppedPkts OBJECT-TYPE
			SYNTAX Counter32
			MAX-ACCESS read-only
			STATUS current
			DESCRIPTION
				"Description."
			::= { uplinkPortPerformanceDataEntry 24 }

		
--          1.3.6.1.4.1.37950.1.1.5.10.1.1.2.1.25
-- 1.3.6.1.4.1.37950.1.1.5.10.1.1.2.1.25
-- 1.3.6.1.4.1.37950.1.1.5.10.1.1.2.1.25
-- 1.3.6.1.4.1.37950.1.1.5.10.1.1.2.1.25
-- 1.3.6.1.4.1.37950.1.1.5.10.1.1.2.1.25
-- 1.3.6.1.4.1.37950.1.1.5.10.1.1.2.1.25
-- 1.3.6.1.4.1.37950.1.1.5.10.1.1.2.1.25
-- 1.3.6.1.4.1.37950.1.1.5.10.1.1.2.1.25
-- 1.3.6.1.4.1.37950.1.1.5.10.1.1.2.1.25
		-- 1.3.6.1.4.1.37950.1.1.5.10.1.1.2.1.25
		upLinkPortCrcError OBJECT-TYPE
			SYNTAX Counter32
			MAX-ACCESS read-only
			STATUS current
			DESCRIPTION
				"Description."
			::= { uplinkPortPerformanceDataEntry 25 }

		
--          1.3.6.1.4.1.37950.1.1.5.10.1.1.2.1.26
-- 1.3.6.1.4.1.37950.1.1.5.10.1.1.2.1.26
-- 1.3.6.1.4.1.37950.1.1.5.10.1.1.2.1.26
-- 1.3.6.1.4.1.37950.1.1.5.10.1.1.2.1.26
-- 1.3.6.1.4.1.37950.1.1.5.10.1.1.2.1.26
-- 1.3.6.1.4.1.37950.1.1.5.10.1.1.2.1.26
-- 1.3.6.1.4.1.37950.1.1.5.10.1.1.2.1.26
-- 1.3.6.1.4.1.37950.1.1.5.10.1.1.2.1.26
-- 1.3.6.1.4.1.37950.1.1.5.10.1.1.2.1.26
		-- 1.3.6.1.4.1.37950.1.1.5.10.1.1.2.1.26
		upLinkPortJabber OBJECT-TYPE
			SYNTAX Counter32
			MAX-ACCESS read-only
			STATUS current
			DESCRIPTION
				"Description."
			::= { uplinkPortPerformanceDataEntry 26 }

		
--          1.3.6.1.4.1.37950.1.1.5.10.1.1.2.1.27
-- 1.3.6.1.4.1.37950.1.1.5.10.1.1.2.1.27
-- 1.3.6.1.4.1.37950.1.1.5.10.1.1.2.1.27
-- 1.3.6.1.4.1.37950.1.1.5.10.1.1.2.1.27
-- 1.3.6.1.4.1.37950.1.1.5.10.1.1.2.1.27
-- 1.3.6.1.4.1.37950.1.1.5.10.1.1.2.1.27
-- 1.3.6.1.4.1.37950.1.1.5.10.1.1.2.1.27
-- 1.3.6.1.4.1.37950.1.1.5.10.1.1.2.1.27
-- 1.3.6.1.4.1.37950.1.1.5.10.1.1.2.1.27
		-- 1.3.6.1.4.1.37950.1.1.5.10.1.1.2.1.27
		upLinkPortOverSize OBJECT-TYPE
			SYNTAX Counter32
			MAX-ACCESS read-only
			STATUS current
			DESCRIPTION
				"Description."
			::= { uplinkPortPerformanceDataEntry 27 }

		
--          1.3.6.1.4.1.37950.1.1.5.10.1.1.2.1.28
-- 1.3.6.1.4.1.37950.1.1.5.10.1.1.2.1.28
-- 1.3.6.1.4.1.37950.1.1.5.10.1.1.2.1.28
-- 1.3.6.1.4.1.37950.1.1.5.10.1.1.2.1.28
-- 1.3.6.1.4.1.37950.1.1.5.10.1.1.2.1.28
-- 1.3.6.1.4.1.37950.1.1.5.10.1.1.2.1.28
-- 1.3.6.1.4.1.37950.1.1.5.10.1.1.2.1.28
-- 1.3.6.1.4.1.37950.1.1.5.10.1.1.2.1.28
-- 1.3.6.1.4.1.37950.1.1.5.10.1.1.2.1.28
		-- 1.3.6.1.4.1.37950.1.1.5.10.1.1.2.1.28
		upLinkPortUnderSize OBJECT-TYPE
			SYNTAX Counter32
			MAX-ACCESS read-only
			STATUS current
			DESCRIPTION
				"Description."
			::= { uplinkPortPerformanceDataEntry 28 }

		
--          1.3.6.1.4.1.37950.1.1.5.10.1.1.2.1.29
-- 1.3.6.1.4.1.37950.1.1.5.10.1.1.2.1.29
-- 1.3.6.1.4.1.37950.1.1.5.10.1.1.2.1.29
-- 1.3.6.1.4.1.37950.1.1.5.10.1.1.2.1.29
-- 1.3.6.1.4.1.37950.1.1.5.10.1.1.2.1.29
-- 1.3.6.1.4.1.37950.1.1.5.10.1.1.2.1.29
-- 1.3.6.1.4.1.37950.1.1.5.10.1.1.2.1.29
-- 1.3.6.1.4.1.37950.1.1.5.10.1.1.2.1.29
-- 1.3.6.1.4.1.37950.1.1.5.10.1.1.2.1.29
		-- 1.3.6.1.4.1.37950.1.1.5.10.1.1.2.1.29
		upLinkPortCollision OBJECT-TYPE
			SYNTAX Counter32
			MAX-ACCESS read-only
			STATUS current
			DESCRIPTION
				"Description."
			::= { uplinkPortPerformanceDataEntry 29 }

		
--          1.3.6.1.4.1.37950.1.1.5.10.1.1.2.1.30
-- 1.3.6.1.4.1.37950.1.1.5.10.1.1.2.1.30
-- 1.3.6.1.4.1.37950.1.1.5.10.1.1.2.1.30
-- 1.3.6.1.4.1.37950.1.1.5.10.1.1.2.1.30
-- 1.3.6.1.4.1.37950.1.1.5.10.1.1.2.1.30
-- 1.3.6.1.4.1.37950.1.1.5.10.1.1.2.1.30
-- 1.3.6.1.4.1.37950.1.1.5.10.1.1.2.1.30
-- 1.3.6.1.4.1.37950.1.1.5.10.1.1.2.1.30
-- 1.3.6.1.4.1.37950.1.1.5.10.1.1.2.1.30
		-- 1.3.6.1.4.1.37950.1.1.5.10.1.1.2.1.30
		upLinkPort64OctetFrames OBJECT-TYPE
			SYNTAX Counter32
			MAX-ACCESS read-only
			STATUS current
			DESCRIPTION
				"Description."
			::= { uplinkPortPerformanceDataEntry 30 }

		
--          1.3.6.1.4.1.37950.1.1.5.10.1.1.2.1.31
-- 1.3.6.1.4.1.37950.1.1.5.10.1.1.2.1.31
-- 1.3.6.1.4.1.37950.1.1.5.10.1.1.2.1.31
-- 1.3.6.1.4.1.37950.1.1.5.10.1.1.2.1.31
-- 1.3.6.1.4.1.37950.1.1.5.10.1.1.2.1.31
-- 1.3.6.1.4.1.37950.1.1.5.10.1.1.2.1.31
-- 1.3.6.1.4.1.37950.1.1.5.10.1.1.2.1.31
-- 1.3.6.1.4.1.37950.1.1.5.10.1.1.2.1.31
-- 1.3.6.1.4.1.37950.1.1.5.10.1.1.2.1.31
		-- 1.3.6.1.4.1.37950.1.1.5.10.1.1.2.1.31
		upLinkPort65To127OctetFrames OBJECT-TYPE
			SYNTAX Counter32
			MAX-ACCESS read-only
			STATUS current
			DESCRIPTION
				"Description."
			::= { uplinkPortPerformanceDataEntry 31 }

		
--          1.3.6.1.4.1.37950.1.1.5.10.1.1.2.1.32
-- 1.3.6.1.4.1.37950.1.1.5.10.1.1.2.1.32
-- 1.3.6.1.4.1.37950.1.1.5.10.1.1.2.1.32
-- 1.3.6.1.4.1.37950.1.1.5.10.1.1.2.1.32
-- 1.3.6.1.4.1.37950.1.1.5.10.1.1.2.1.32
-- 1.3.6.1.4.1.37950.1.1.5.10.1.1.2.1.32
-- 1.3.6.1.4.1.37950.1.1.5.10.1.1.2.1.32
-- 1.3.6.1.4.1.37950.1.1.5.10.1.1.2.1.32
-- 1.3.6.1.4.1.37950.1.1.5.10.1.1.2.1.32
		-- 1.3.6.1.4.1.37950.1.1.5.10.1.1.2.1.32
		upLinkPort128To255OctetFrames OBJECT-TYPE
			SYNTAX Counter32
			MAX-ACCESS read-only
			STATUS current
			DESCRIPTION
				"Description."
			::= { uplinkPortPerformanceDataEntry 32 }

		
--          1.3.6.1.4.1.37950.1.1.5.10.1.1.2.1.33
-- 1.3.6.1.4.1.37950.1.1.5.10.1.1.2.1.33
-- 1.3.6.1.4.1.37950.1.1.5.10.1.1.2.1.33
-- 1.3.6.1.4.1.37950.1.1.5.10.1.1.2.1.33
-- 1.3.6.1.4.1.37950.1.1.5.10.1.1.2.1.33
-- 1.3.6.1.4.1.37950.1.1.5.10.1.1.2.1.33
-- 1.3.6.1.4.1.37950.1.1.5.10.1.1.2.1.33
-- 1.3.6.1.4.1.37950.1.1.5.10.1.1.2.1.33
-- 1.3.6.1.4.1.37950.1.1.5.10.1.1.2.1.33
		-- 1.3.6.1.4.1.37950.1.1.5.10.1.1.2.1.33
		upLinkPort256To511OctetFrames OBJECT-TYPE
			SYNTAX Counter32
			MAX-ACCESS read-only
			STATUS current
			DESCRIPTION
				"Description."
			::= { uplinkPortPerformanceDataEntry 33 }

		
--          1.3.6.1.4.1.37950.1.1.5.10.1.1.2.1.34
-- 1.3.6.1.4.1.37950.1.1.5.10.1.1.2.1.34
-- 1.3.6.1.4.1.37950.1.1.5.10.1.1.2.1.34
-- 1.3.6.1.4.1.37950.1.1.5.10.1.1.2.1.34
-- 1.3.6.1.4.1.37950.1.1.5.10.1.1.2.1.34
-- 1.3.6.1.4.1.37950.1.1.5.10.1.1.2.1.34
-- 1.3.6.1.4.1.37950.1.1.5.10.1.1.2.1.34
-- 1.3.6.1.4.1.37950.1.1.5.10.1.1.2.1.34
-- 1.3.6.1.4.1.37950.1.1.5.10.1.1.2.1.34
		-- 1.3.6.1.4.1.37950.1.1.5.10.1.1.2.1.34
		upLinkPort512To1023OctetFrames OBJECT-TYPE
			SYNTAX Counter32
			MAX-ACCESS read-only
			STATUS current
			DESCRIPTION
				"Description."
			::= { uplinkPortPerformanceDataEntry 34 }

		
--          1.3.6.1.4.1.37950.1.1.5.10.1.1.2.1.35
-- 1.3.6.1.4.1.37950.1.1.5.10.1.1.2.1.35
-- 1.3.6.1.4.1.37950.1.1.5.10.1.1.2.1.35
-- 1.3.6.1.4.1.37950.1.1.5.10.1.1.2.1.35
-- 1.3.6.1.4.1.37950.1.1.5.10.1.1.2.1.35
-- 1.3.6.1.4.1.37950.1.1.5.10.1.1.2.1.35
-- 1.3.6.1.4.1.37950.1.1.5.10.1.1.2.1.35
-- 1.3.6.1.4.1.37950.1.1.5.10.1.1.2.1.35
-- 1.3.6.1.4.1.37950.1.1.5.10.1.1.2.1.35
		-- 1.3.6.1.4.1.37950.1.1.5.10.1.1.2.1.35
		upLinkPortOver1024OctetFrames OBJECT-TYPE
			SYNTAX Counter32
			MAX-ACCESS read-only
			STATUS current
			DESCRIPTION
				"Description."
			::= { uplinkPortPerformanceDataEntry 35 }

		
--          1.3.6.1.4.1.37950.1.1.5.10.1.1.2.1.36
-- 1.3.6.1.4.1.37950.1.1.5.10.1.1.2.1.36
-- 1.3.6.1.4.1.37950.1.1.5.10.1.1.2.1.36
-- 1.3.6.1.4.1.37950.1.1.5.10.1.1.2.1.36
-- 1.3.6.1.4.1.37950.1.1.5.10.1.1.2.1.36
-- 1.3.6.1.4.1.37950.1.1.5.10.1.1.2.1.36
-- 1.3.6.1.4.1.37950.1.1.5.10.1.1.2.1.36
-- 1.3.6.1.4.1.37950.1.1.5.10.1.1.2.1.36
-- 1.3.6.1.4.1.37950.1.1.5.10.1.1.2.1.36
		-- 1.3.6.1.4.1.37950.1.1.5.10.1.1.2.1.36
		uplinkPortDownBytes OBJECT-TYPE
			SYNTAX Counter64
			MAX-ACCESS read-only
			STATUS current
			DESCRIPTION
				"Description."
			::= { uplinkPortPerformanceDataEntry 36 }

		
--          1.3.6.1.4.1.37950.1.1.5.10.1.1.2.1.37
-- 1.3.6.1.4.1.37950.1.1.5.10.1.1.2.1.37
-- 1.3.6.1.4.1.37950.1.1.5.10.1.1.2.1.37
-- 1.3.6.1.4.1.37950.1.1.5.10.1.1.2.1.37
-- 1.3.6.1.4.1.37950.1.1.5.10.1.1.2.1.37
-- 1.3.6.1.4.1.37950.1.1.5.10.1.1.2.1.37
-- 1.3.6.1.4.1.37950.1.1.5.10.1.1.2.1.37
-- 1.3.6.1.4.1.37950.1.1.5.10.1.1.2.1.37
-- 1.3.6.1.4.1.37950.1.1.5.10.1.1.2.1.37
		-- 1.3.6.1.4.1.37950.1.1.5.10.1.1.2.1.37
		uplinkPortUpBytes OBJECT-TYPE
			SYNTAX Counter64
			MAX-ACCESS read-only
			STATUS current
			DESCRIPTION
				"Description."
			::= { uplinkPortPerformanceDataEntry 37 }

		
--          1.3.6.1.4.1.37950.1.1.5.10.1.1.3
-- 1.3.6.1.4.1.37950.1.1.5.10.1.1.3
-- 1.3.6.1.4.1.37950.1.1.5.10.1.1.3
-- 1.3.6.1.4.1.37950.1.1.5.10.1.1.3
-- 1.3.6.1.4.1.37950.1.1.5.10.1.1.3
-- 1.3.6.1.4.1.37950.1.1.5.10.1.1.3
-- 1.3.6.1.4.1.37950.1.1.5.10.1.1.3
-- 1.3.6.1.4.1.37950.1.1.5.10.1.1.3
-- 1.3.6.1.4.1.37950.1.1.5.10.1.1.3
		-- 1.3.6.1.4.1.37950.1.1.5.10.1.1.3
		uplinkPortLinkTable OBJECT-TYPE
			SYNTAX SEQUENCE OF UplinkPortLinkEntry
			MAX-ACCESS not-accessible
			STATUS current
			DESCRIPTION
				"Description."
			::= { upLinkPort 3 }

		
--          1.3.6.1.4.1.37950.1.1.5.10.1.1.3.1
-- 1.3.6.1.4.1.37950.1.1.5.10.1.1.3.1
-- 1.3.6.1.4.1.37950.1.1.5.10.1.1.3.1
-- 1.3.6.1.4.1.37950.1.1.5.10.1.1.3.1
-- 1.3.6.1.4.1.37950.1.1.5.10.1.1.3.1
-- 1.3.6.1.4.1.37950.1.1.5.10.1.1.3.1
-- 1.3.6.1.4.1.37950.1.1.5.10.1.1.3.1
-- 1.3.6.1.4.1.37950.1.1.5.10.1.1.3.1
-- 1.3.6.1.4.1.37950.1.1.5.10.1.1.3.1
		-- 1.3.6.1.4.1.37950.1.1.5.10.1.1.3.1
		uplinkPortLinkEntry OBJECT-TYPE
			SYNTAX UplinkPortLinkEntry
			MAX-ACCESS not-accessible
			STATUS current
			DESCRIPTION
				"Description."
			INDEX { portNumIndex }
			::= { uplinkPortLinkTable 1 }

		
		UplinkPortLinkEntry ::=
			SEQUENCE { 
				portNumIndex
					INTEGER,
				portLinkStatus
					INTEGER,
				uplinkPortLinkSpeed
					OCTET STRING
			 }

--          1.3.6.1.4.1.37950.1.1.5.10.1.1.3.1.1
-- 1.3.6.1.4.1.37950.1.1.5.10.1.1.3.1.1
-- 1.3.6.1.4.1.37950.1.1.5.10.1.1.3.1.1
-- 1.3.6.1.4.1.37950.1.1.5.10.1.1.3.1.1
-- 1.3.6.1.4.1.37950.1.1.5.10.1.1.3.1.1
-- 1.3.6.1.4.1.37950.1.1.5.10.1.1.3.1.1
-- 1.3.6.1.4.1.37950.1.1.5.10.1.1.3.1.1
-- 1.3.6.1.4.1.37950.1.1.5.10.1.1.3.1.1
-- 1.3.6.1.4.1.37950.1.1.5.10.1.1.3.1.1
		-- 1.3.6.1.4.1.37950.1.1.5.10.1.1.3.1.1
		portNumIndex OBJECT-TYPE
			SYNTAX INTEGER (1..16)
			MAX-ACCESS read-only
			STATUS current
			DESCRIPTION
				"Description."
			::= { uplinkPortLinkEntry 1 }

		
--          1.3.6.1.4.1.37950.1.1.5.10.1.1.3.1.2
-- 1.3.6.1.4.1.37950.1.1.5.10.1.1.3.1.2
-- 1.3.6.1.4.1.37950.1.1.5.10.1.1.3.1.2
-- 1.3.6.1.4.1.37950.1.1.5.10.1.1.3.1.2
-- 1.3.6.1.4.1.37950.1.1.5.10.1.1.3.1.2
-- 1.3.6.1.4.1.37950.1.1.5.10.1.1.3.1.2
-- 1.3.6.1.4.1.37950.1.1.5.10.1.1.3.1.2
-- 1.3.6.1.4.1.37950.1.1.5.10.1.1.3.1.2
-- 1.3.6.1.4.1.37950.1.1.5.10.1.1.3.1.2
		-- 1.3.6.1.4.1.37950.1.1.5.10.1.1.3.1.2
		portLinkStatus OBJECT-TYPE
			SYNTAX INTEGER
				{
				down(0),
				up(1)
				}
			MAX-ACCESS read-only
			STATUS current
			DESCRIPTION
				"Description."
			::= { uplinkPortLinkEntry 2 }

		
--          1.3.6.1.4.1.37950.1.1.5.10.1.1.3.1.3
-- 1.3.6.1.4.1.37950.1.1.5.10.1.1.3.1.3
-- 1.3.6.1.4.1.37950.1.1.5.10.1.1.3.1.3
-- 1.3.6.1.4.1.37950.1.1.5.10.1.1.3.1.3
-- 1.3.6.1.4.1.37950.1.1.5.10.1.1.3.1.3
-- 1.3.6.1.4.1.37950.1.1.5.10.1.1.3.1.3
-- 1.3.6.1.4.1.37950.1.1.5.10.1.1.3.1.3
-- 1.3.6.1.4.1.37950.1.1.5.10.1.1.3.1.3
-- 1.3.6.1.4.1.37950.1.1.5.10.1.1.3.1.3
		-- 1.3.6.1.4.1.37950.1.1.5.10.1.1.3.1.3
		uplinkPortLinkSpeed OBJECT-TYPE
			SYNTAX OCTET STRING
			MAX-ACCESS read-only
			STATUS current
			DESCRIPTION
				"Description."
			::= { uplinkPortLinkEntry 3 }

		
--          1.3.6.1.4.1.37950.1.1.5.10.1.1.4
-- 1.3.6.1.4.1.37950.1.1.5.10.1.1.4
-- 1.3.6.1.4.1.37950.1.1.5.10.1.1.4
-- 1.3.6.1.4.1.37950.1.1.5.10.1.1.4
-- 1.3.6.1.4.1.37950.1.1.5.10.1.1.4
-- 1.3.6.1.4.1.37950.1.1.5.10.1.1.4
-- 1.3.6.1.4.1.37950.1.1.5.10.1.1.4
-- 1.3.6.1.4.1.37950.1.1.5.10.1.1.4
-- 1.3.6.1.4.1.37950.1.1.5.10.1.1.4
		-- 1.3.6.1.4.1.37950.1.1.5.10.1.1.4
		uplinkPortPerfThresholdTable OBJECT-TYPE
			SYNTAX SEQUENCE OF UplinkPortPerfThresholdEntry
			MAX-ACCESS not-accessible
			STATUS current
			DESCRIPTION
				"Description."
			::= { upLinkPort 4 }

		
--          1.3.6.1.4.1.37950.1.1.5.10.1.1.4.1
-- 1.3.6.1.4.1.37950.1.1.5.10.1.1.4.1
-- 1.3.6.1.4.1.37950.1.1.5.10.1.1.4.1
-- 1.3.6.1.4.1.37950.1.1.5.10.1.1.4.1
-- 1.3.6.1.4.1.37950.1.1.5.10.1.1.4.1
-- 1.3.6.1.4.1.37950.1.1.5.10.1.1.4.1
-- 1.3.6.1.4.1.37950.1.1.5.10.1.1.4.1
-- 1.3.6.1.4.1.37950.1.1.5.10.1.1.4.1
-- 1.3.6.1.4.1.37950.1.1.5.10.1.1.4.1
		-- 1.3.6.1.4.1.37950.1.1.5.10.1.1.4.1
		uplinkPortPerfThresholdEntry OBJECT-TYPE
			SYNTAX UplinkPortPerfThresholdEntry
			MAX-ACCESS not-accessible
			STATUS current
			DESCRIPTION
				"Description."
			INDEX { porIndex }
			::= { uplinkPortPerfThresholdTable 1 }

		
		UplinkPortPerfThresholdEntry ::=
			SEQUENCE { 
				porIndex
					INTEGER,
				uplinkPortCRCThreshold
					INTEGER
			 }

--          1.3.6.1.4.1.37950.1.1.5.10.1.1.4.1.1
-- 1.3.6.1.4.1.37950.1.1.5.10.1.1.4.1.1
-- 1.3.6.1.4.1.37950.1.1.5.10.1.1.4.1.1
-- 1.3.6.1.4.1.37950.1.1.5.10.1.1.4.1.1
-- 1.3.6.1.4.1.37950.1.1.5.10.1.1.4.1.1
-- 1.3.6.1.4.1.37950.1.1.5.10.1.1.4.1.1
-- 1.3.6.1.4.1.37950.1.1.5.10.1.1.4.1.1
-- 1.3.6.1.4.1.37950.1.1.5.10.1.1.4.1.1
-- 1.3.6.1.4.1.37950.1.1.5.10.1.1.4.1.1
		-- 1.3.6.1.4.1.37950.1.1.5.10.1.1.4.1.1
		porIndex OBJECT-TYPE
			SYNTAX INTEGER (1..16)
			MAX-ACCESS read-only
			STATUS current
			DESCRIPTION
				"Description."
			::= { uplinkPortPerfThresholdEntry 1 }

		
--          1.3.6.1.4.1.37950.1.1.5.10.1.1.4.1.2
-- 1.3.6.1.4.1.37950.1.1.5.10.1.1.4.1.2
-- 1.3.6.1.4.1.37950.1.1.5.10.1.1.4.1.2
-- 1.3.6.1.4.1.37950.1.1.5.10.1.1.4.1.2
-- 1.3.6.1.4.1.37950.1.1.5.10.1.1.4.1.2
-- 1.3.6.1.4.1.37950.1.1.5.10.1.1.4.1.2
-- 1.3.6.1.4.1.37950.1.1.5.10.1.1.4.1.2
-- 1.3.6.1.4.1.37950.1.1.5.10.1.1.4.1.2
-- 1.3.6.1.4.1.37950.1.1.5.10.1.1.4.1.2
		-- 1.3.6.1.4.1.37950.1.1.5.10.1.1.4.1.2
		uplinkPortCRCThreshold OBJECT-TYPE
			SYNTAX INTEGER
			MAX-ACCESS read-write
			STATUS current
			DESCRIPTION
				"Description."
			::= { uplinkPortPerfThresholdEntry 2 }

		
--         1.3.6.1.4.1.37950.1.1.5.10.1.1.5
-- 1.3.6.1.4.1.37950.1.1.5.10.1.1.5
-- 1.3.6.1.4.1.37950.1.1.5.10.1.1.5
-- 1.3.6.1.4.1.37950.1.1.5.10.1.1.5
-- 1.3.6.1.4.1.37950.1.1.5.10.1.1.5
-- 1.3.6.1.4.1.37950.1.1.5.10.1.1.5
-- 1.3.6.1.4.1.37950.1.1.5.10.1.1.5
-- 1.3.6.1.4.1.37950.1.1.5.10.1.1.5
		-- 1.3.6.1.4.1.37950.1.1.5.10.1.1.5
		uplinkPortOpticalTransTable OBJECT-TYPE
			SYNTAX SEQUENCE OF UplinkPortOpticalTransEntry
			MAX-ACCESS not-accessible
			STATUS current
			DESCRIPTION
				"Description."
			::= { upLinkPort 5 }

		
--         1.3.6.1.4.1.37950.1.1.5.10.1.1.5.1
-- 1.3.6.1.4.1.37950.1.1.5.10.1.1.5.1
-- 1.3.6.1.4.1.37950.1.1.5.10.1.1.5.1
-- 1.3.6.1.4.1.37950.1.1.5.10.1.1.5.1
-- 1.3.6.1.4.1.37950.1.1.5.10.1.1.5.1
-- 1.3.6.1.4.1.37950.1.1.5.10.1.1.5.1
-- 1.3.6.1.4.1.37950.1.1.5.10.1.1.5.1
-- 1.3.6.1.4.1.37950.1.1.5.10.1.1.5.1
		-- 1.3.6.1.4.1.37950.1.1.5.10.1.1.5.1
		uplinkPortOpticalTransEntry OBJECT-TYPE
			SYNTAX UplinkPortOpticalTransEntry
			MAX-ACCESS not-accessible
			STATUS current
			DESCRIPTION
				"Description."
			INDEX { transceiverPortIndex }
			::= { uplinkPortOpticalTransTable 1 }

		
		UplinkPortOpticalTransEntry ::=
			SEQUENCE { 
				transceiverPortIndex
					Integer32,
				transceiverTempperature
					OCTET STRING,
				transceiverVoltage
					OCTET STRING,
				transceiverBiasCurrent
					OCTET STRING,
				transceiverTransmitPower
					OCTET STRING,
				transceiverReceivedPower
					OCTET STRING
			 }

--         1.3.6.1.4.1.37950.1.1.5.10.1.1.5.1.1
-- 1.3.6.1.4.1.37950.1.1.5.10.1.1.5.1.1
-- 1.3.6.1.4.1.37950.1.1.5.10.1.1.5.1.1
-- 1.3.6.1.4.1.37950.1.1.5.10.1.1.5.1.1
-- 1.3.6.1.4.1.37950.1.1.5.10.1.1.5.1.1
-- 1.3.6.1.4.1.37950.1.1.5.10.1.1.5.1.1
-- 1.3.6.1.4.1.37950.1.1.5.10.1.1.5.1.1
-- 1.3.6.1.4.1.37950.1.1.5.10.1.1.5.1.1
		-- 1.3.6.1.4.1.37950.1.1.5.10.1.1.5.1.1
		transceiverPortIndex OBJECT-TYPE
			SYNTAX Integer32
			MAX-ACCESS read-only
			STATUS current
			DESCRIPTION
				"Description."
			::= { uplinkPortOpticalTransEntry 1 }

		
--         1.3.6.1.4.1.37950.1.1.5.10.1.1.5.1.2
-- 1.3.6.1.4.1.37950.1.1.5.10.1.1.5.1.2
-- 1.3.6.1.4.1.37950.1.1.5.10.1.1.5.1.2
-- 1.3.6.1.4.1.37950.1.1.5.10.1.1.5.1.2
-- 1.3.6.1.4.1.37950.1.1.5.10.1.1.5.1.2
-- 1.3.6.1.4.1.37950.1.1.5.10.1.1.5.1.2
-- 1.3.6.1.4.1.37950.1.1.5.10.1.1.5.1.2
-- 1.3.6.1.4.1.37950.1.1.5.10.1.1.5.1.2
		-- 1.3.6.1.4.1.37950.1.1.5.10.1.1.5.1.2
		transceiverTempperature OBJECT-TYPE
			SYNTAX OCTET STRING
			MAX-ACCESS read-only
			STATUS current
			DESCRIPTION
				"Description."
			::= { uplinkPortOpticalTransEntry 2 }

		
--         1.3.6.1.4.1.37950.1.1.5.10.1.1.5.1.3
-- 1.3.6.1.4.1.37950.1.1.5.10.1.1.5.1.3
-- 1.3.6.1.4.1.37950.1.1.5.10.1.1.5.1.3
-- 1.3.6.1.4.1.37950.1.1.5.10.1.1.5.1.3
-- 1.3.6.1.4.1.37950.1.1.5.10.1.1.5.1.3
-- 1.3.6.1.4.1.37950.1.1.5.10.1.1.5.1.3
-- 1.3.6.1.4.1.37950.1.1.5.10.1.1.5.1.3
-- 1.3.6.1.4.1.37950.1.1.5.10.1.1.5.1.3
		-- 1.3.6.1.4.1.37950.1.1.5.10.1.1.5.1.3
		transceiverVoltage OBJECT-TYPE
			SYNTAX OCTET STRING
			MAX-ACCESS read-only
			STATUS current
			DESCRIPTION
				"Description."
			::= { uplinkPortOpticalTransEntry 3 }

		
--         1.3.6.1.4.1.37950.1.1.5.10.1.1.5.1.4
-- 1.3.6.1.4.1.37950.1.1.5.10.1.1.5.1.4
-- 1.3.6.1.4.1.37950.1.1.5.10.1.1.5.1.4
-- 1.3.6.1.4.1.37950.1.1.5.10.1.1.5.1.4
-- 1.3.6.1.4.1.37950.1.1.5.10.1.1.5.1.4
-- 1.3.6.1.4.1.37950.1.1.5.10.1.1.5.1.4
-- 1.3.6.1.4.1.37950.1.1.5.10.1.1.5.1.4
-- 1.3.6.1.4.1.37950.1.1.5.10.1.1.5.1.4
		-- 1.3.6.1.4.1.37950.1.1.5.10.1.1.5.1.4
		transceiverBiasCurrent OBJECT-TYPE
			SYNTAX OCTET STRING
			MAX-ACCESS read-only
			STATUS current
			DESCRIPTION
				"Description."
			::= { uplinkPortOpticalTransEntry 4 }

		
--         1.3.6.1.4.1.37950.1.1.5.10.1.1.5.1.5
-- 1.3.6.1.4.1.37950.1.1.5.10.1.1.5.1.5
-- 1.3.6.1.4.1.37950.1.1.5.10.1.1.5.1.5
-- 1.3.6.1.4.1.37950.1.1.5.10.1.1.5.1.5
-- 1.3.6.1.4.1.37950.1.1.5.10.1.1.5.1.5
-- 1.3.6.1.4.1.37950.1.1.5.10.1.1.5.1.5
-- 1.3.6.1.4.1.37950.1.1.5.10.1.1.5.1.5
-- 1.3.6.1.4.1.37950.1.1.5.10.1.1.5.1.5
		-- 1.3.6.1.4.1.37950.1.1.5.10.1.1.5.1.5
		transceiverTransmitPower OBJECT-TYPE
			SYNTAX OCTET STRING
			MAX-ACCESS read-only
			STATUS current
			DESCRIPTION
				"Description."
			::= { uplinkPortOpticalTransEntry 5 }

		
--         1.3.6.1.4.1.37950.1.1.5.10.1.1.5.1.6
-- 1.3.6.1.4.1.37950.1.1.5.10.1.1.5.1.6
-- 1.3.6.1.4.1.37950.1.1.5.10.1.1.5.1.6
-- 1.3.6.1.4.1.37950.1.1.5.10.1.1.5.1.6
-- 1.3.6.1.4.1.37950.1.1.5.10.1.1.5.1.6
-- 1.3.6.1.4.1.37950.1.1.5.10.1.1.5.1.6
-- 1.3.6.1.4.1.37950.1.1.5.10.1.1.5.1.6
-- 1.3.6.1.4.1.37950.1.1.5.10.1.1.5.1.6
		-- 1.3.6.1.4.1.37950.1.1.5.10.1.1.5.1.6
		transceiverReceivedPower OBJECT-TYPE
			SYNTAX OCTET STRING
			MAX-ACCESS read-only
			STATUS current
			DESCRIPTION
				"Description."
			::= { uplinkPortOpticalTransEntry 6 }

		
--         1.3.6.1.4.1.37950.1.1.5.10.1.1.6
-- 1.3.6.1.4.1.37950.1.1.5.10.1.1.6
-- 1.3.6.1.4.1.37950.1.1.5.10.1.1.6
-- 1.3.6.1.4.1.37950.1.1.5.10.1.1.6
-- 1.3.6.1.4.1.37950.1.1.5.10.1.1.6
-- 1.3.6.1.4.1.37950.1.1.5.10.1.1.6
-- 1.3.6.1.4.1.37950.1.1.5.10.1.1.6
-- 1.3.6.1.4.1.37950.1.1.5.10.1.1.6
		-- 1.3.6.1.4.1.37950.1.1.5.10.1.1.6
		uplinkPortAggregationTable OBJECT-TYPE
			SYNTAX SEQUENCE OF UplinkPortAggregationEntry
			MAX-ACCESS not-accessible
			STATUS current
			DESCRIPTION
				"Description."
			::= { upLinkPort 6 }

		
--         1.3.6.1.4.1.37950.1.1.5.10.1.1.6.1
-- 1.3.6.1.4.1.37950.1.1.5.10.1.1.6.1
-- 1.3.6.1.4.1.37950.1.1.5.10.1.1.6.1
-- 1.3.6.1.4.1.37950.1.1.5.10.1.1.6.1
-- 1.3.6.1.4.1.37950.1.1.5.10.1.1.6.1
-- 1.3.6.1.4.1.37950.1.1.5.10.1.1.6.1
-- 1.3.6.1.4.1.37950.1.1.5.10.1.1.6.1
-- 1.3.6.1.4.1.37950.1.1.5.10.1.1.6.1
		-- 1.3.6.1.4.1.37950.1.1.5.10.1.1.6.1
		uplinkPortAggregationEntry OBJECT-TYPE
			SYNTAX UplinkPortAggregationEntry
			MAX-ACCESS not-accessible
			STATUS current
			DESCRIPTION
				"Description."
			INDEX { upLinkAIndex }
			::= { uplinkPortAggregationTable 1 }

		
		UplinkPortAggregationEntry ::=
			SEQUENCE { 
				upLinkAIndex
					Integer32,
				uplinkPortAggregation
					INTEGER,
				uplinkPortTimeout
					INTEGER,
				uplinkPortChannelGroupID
					Integer32,
				uplinkPortLacpMode
					INTEGER,
				uplinkPortPriority
					Integer32
			 }

--         1.3.6.1.4.1.37950.1.1.5.10.1.1.6.1.1
-- 1.3.6.1.4.1.37950.1.1.5.10.1.1.6.1.1
-- 1.3.6.1.4.1.37950.1.1.5.10.1.1.6.1.1
-- 1.3.6.1.4.1.37950.1.1.5.10.1.1.6.1.1
-- 1.3.6.1.4.1.37950.1.1.5.10.1.1.6.1.1
-- 1.3.6.1.4.1.37950.1.1.5.10.1.1.6.1.1
-- 1.3.6.1.4.1.37950.1.1.5.10.1.1.6.1.1
-- 1.3.6.1.4.1.37950.1.1.5.10.1.1.6.1.1
		-- 1.3.6.1.4.1.37950.1.1.5.10.1.1.6.1.1
		upLinkAIndex OBJECT-TYPE
			SYNTAX Integer32
			MAX-ACCESS read-write
			STATUS current
			DESCRIPTION
				"Description."
			::= { uplinkPortAggregationEntry 1 }

		
--         1.3.6.1.4.1.37950.1.1.5.10.1.1.6.1.2
-- 1.3.6.1.4.1.37950.1.1.5.10.1.1.6.1.2
-- 1.3.6.1.4.1.37950.1.1.5.10.1.1.6.1.2
-- 1.3.6.1.4.1.37950.1.1.5.10.1.1.6.1.2
-- 1.3.6.1.4.1.37950.1.1.5.10.1.1.6.1.2
-- 1.3.6.1.4.1.37950.1.1.5.10.1.1.6.1.2
-- 1.3.6.1.4.1.37950.1.1.5.10.1.1.6.1.2
-- 1.3.6.1.4.1.37950.1.1.5.10.1.1.6.1.2
		-- 1.3.6.1.4.1.37950.1.1.5.10.1.1.6.1.2
		uplinkPortAggregation OBJECT-TYPE
			SYNTAX INTEGER
				{
				disable(0),
				enable(1)
				}
			MAX-ACCESS read-write
			STATUS current
			DESCRIPTION
				"Description."
			::= { uplinkPortAggregationEntry 2 }

		
--         1.3.6.1.4.1.37950.1.1.5.10.1.1.6.1.3
-- 1.3.6.1.4.1.37950.1.1.5.10.1.1.6.1.3
-- 1.3.6.1.4.1.37950.1.1.5.10.1.1.6.1.3
-- 1.3.6.1.4.1.37950.1.1.5.10.1.1.6.1.3
-- 1.3.6.1.4.1.37950.1.1.5.10.1.1.6.1.3
-- 1.3.6.1.4.1.37950.1.1.5.10.1.1.6.1.3
-- 1.3.6.1.4.1.37950.1.1.5.10.1.1.6.1.3
-- 1.3.6.1.4.1.37950.1.1.5.10.1.1.6.1.3
		-- 1.3.6.1.4.1.37950.1.1.5.10.1.1.6.1.3
		uplinkPortTimeout OBJECT-TYPE
			SYNTAX INTEGER
				{
				long(0),
				short(1)
				}
			MAX-ACCESS read-write
			STATUS current
			DESCRIPTION
				"Description."
			::= { uplinkPortAggregationEntry 3 }

		
--         1.3.6.1.4.1.37950.1.1.5.10.1.1.6.1.4
-- 1.3.6.1.4.1.37950.1.1.5.10.1.1.6.1.4
-- 1.3.6.1.4.1.37950.1.1.5.10.1.1.6.1.4
-- 1.3.6.1.4.1.37950.1.1.5.10.1.1.6.1.4
-- 1.3.6.1.4.1.37950.1.1.5.10.1.1.6.1.4
-- 1.3.6.1.4.1.37950.1.1.5.10.1.1.6.1.4
-- 1.3.6.1.4.1.37950.1.1.5.10.1.1.6.1.4
-- 1.3.6.1.4.1.37950.1.1.5.10.1.1.6.1.4
		-- 1.3.6.1.4.1.37950.1.1.5.10.1.1.6.1.4
		uplinkPortChannelGroupID OBJECT-TYPE
			SYNTAX Integer32
			MAX-ACCESS read-write
			STATUS current
			DESCRIPTION
				"Description."
			::= { uplinkPortAggregationEntry 4 }

		
--         1.3.6.1.4.1.37950.1.1.5.10.1.1.6.1.5
-- 1.3.6.1.4.1.37950.1.1.5.10.1.1.6.1.5
-- 1.3.6.1.4.1.37950.1.1.5.10.1.1.6.1.5
-- 1.3.6.1.4.1.37950.1.1.5.10.1.1.6.1.5
-- 1.3.6.1.4.1.37950.1.1.5.10.1.1.6.1.5
-- 1.3.6.1.4.1.37950.1.1.5.10.1.1.6.1.5
-- 1.3.6.1.4.1.37950.1.1.5.10.1.1.6.1.5
-- 1.3.6.1.4.1.37950.1.1.5.10.1.1.6.1.5
		-- 1.3.6.1.4.1.37950.1.1.5.10.1.1.6.1.5
		uplinkPortLacpMode OBJECT-TYPE
			SYNTAX INTEGER
				{
				passive(0),
				active(1)
				}
			MAX-ACCESS read-write
			STATUS current
			DESCRIPTION
				"Description."
			::= { uplinkPortAggregationEntry 5 }

		
--         1.3.6.1.4.1.37950.1.1.5.10.1.1.6.1.6
-- 1.3.6.1.4.1.37950.1.1.5.10.1.1.6.1.6
-- 1.3.6.1.4.1.37950.1.1.5.10.1.1.6.1.6
-- 1.3.6.1.4.1.37950.1.1.5.10.1.1.6.1.6
-- 1.3.6.1.4.1.37950.1.1.5.10.1.1.6.1.6
-- 1.3.6.1.4.1.37950.1.1.5.10.1.1.6.1.6
-- 1.3.6.1.4.1.37950.1.1.5.10.1.1.6.1.6
-- 1.3.6.1.4.1.37950.1.1.5.10.1.1.6.1.6
		-- 1.3.6.1.4.1.37950.1.1.5.10.1.1.6.1.6
		uplinkPortPriority OBJECT-TYPE
			SYNTAX Integer32 (0..65535)
			MAX-ACCESS read-write
			STATUS current
			DESCRIPTION
				"Description."
			::= { uplinkPortAggregationEntry 6 }

		
--         1.3.6.1.4.1.37950.1.1.5.10.1.1.7
-- 1.3.6.1.4.1.37950.1.1.5.10.1.1.7
-- 1.3.6.1.4.1.37950.1.1.5.10.1.1.7
-- 1.3.6.1.4.1.37950.1.1.5.10.1.1.7
-- 1.3.6.1.4.1.37950.1.1.5.10.1.1.7
-- 1.3.6.1.4.1.37950.1.1.5.10.1.1.7
-- 1.3.6.1.4.1.37950.1.1.5.10.1.1.7
-- 1.3.6.1.4.1.37950.1.1.5.10.1.1.7
		-- 1.3.6.1.4.1.37950.1.1.5.10.1.1.7
		uplinkPortAggregationCfg OBJECT IDENTIFIER ::= { upLinkPort 7 }

		
--         1.3.6.1.4.1.37950.1.1.5.10.1.1.7.1
-- 1.3.6.1.4.1.37950.1.1.5.10.1.1.7.1
-- 1.3.6.1.4.1.37950.1.1.5.10.1.1.7.1
-- 1.3.6.1.4.1.37950.1.1.5.10.1.1.7.1
-- 1.3.6.1.4.1.37950.1.1.5.10.1.1.7.1
-- 1.3.6.1.4.1.37950.1.1.5.10.1.1.7.1
-- 1.3.6.1.4.1.37950.1.1.5.10.1.1.7.1
-- 1.3.6.1.4.1.37950.1.1.5.10.1.1.7.1
		-- 1.3.6.1.4.1.37950.1.1.5.10.1.1.7.1
		upLinkAIndexS OBJECT-TYPE
			SYNTAX Integer32 (0..16)
			MAX-ACCESS read-write
			STATUS current
			DESCRIPTION
				"Description."
			::= { uplinkPortAggregationCfg 1 }

		
--         1.3.6.1.4.1.37950.1.1.5.10.1.1.7.2
-- 1.3.6.1.4.1.37950.1.1.5.10.1.1.7.2
-- 1.3.6.1.4.1.37950.1.1.5.10.1.1.7.2
-- 1.3.6.1.4.1.37950.1.1.5.10.1.1.7.2
-- 1.3.6.1.4.1.37950.1.1.5.10.1.1.7.2
-- 1.3.6.1.4.1.37950.1.1.5.10.1.1.7.2
-- 1.3.6.1.4.1.37950.1.1.5.10.1.1.7.2
-- 1.3.6.1.4.1.37950.1.1.5.10.1.1.7.2
		-- 1.3.6.1.4.1.37950.1.1.5.10.1.1.7.2
		uplinkPortAggregationS OBJECT-TYPE
			SYNTAX INTEGER
				{
				disable(0),
				enable(1)
				}
			MAX-ACCESS read-write
			STATUS current
			DESCRIPTION
				"Description."
			::= { uplinkPortAggregationCfg 2 }

		
--         1.3.6.1.4.1.37950.1.1.5.10.1.1.7.3
-- 1.3.6.1.4.1.37950.1.1.5.10.1.1.7.3
-- 1.3.6.1.4.1.37950.1.1.5.10.1.1.7.3
-- 1.3.6.1.4.1.37950.1.1.5.10.1.1.7.3
-- 1.3.6.1.4.1.37950.1.1.5.10.1.1.7.3
-- 1.3.6.1.4.1.37950.1.1.5.10.1.1.7.3
-- 1.3.6.1.4.1.37950.1.1.5.10.1.1.7.3
-- 1.3.6.1.4.1.37950.1.1.5.10.1.1.7.3
		-- 1.3.6.1.4.1.37950.1.1.5.10.1.1.7.3
		uplinkPortTimeoutS OBJECT-TYPE
			SYNTAX INTEGER
				{
				long(0),
				short(1)
				}
			MAX-ACCESS read-write
			STATUS current
			DESCRIPTION
				"Description."
			::= { uplinkPortAggregationCfg 3 }

		
--         1.3.6.1.4.1.37950.1.1.5.10.1.1.7.4
-- 1.3.6.1.4.1.37950.1.1.5.10.1.1.7.4
-- 1.3.6.1.4.1.37950.1.1.5.10.1.1.7.4
-- 1.3.6.1.4.1.37950.1.1.5.10.1.1.7.4
-- 1.3.6.1.4.1.37950.1.1.5.10.1.1.7.4
-- 1.3.6.1.4.1.37950.1.1.5.10.1.1.7.4
-- 1.3.6.1.4.1.37950.1.1.5.10.1.1.7.4
-- 1.3.6.1.4.1.37950.1.1.5.10.1.1.7.4
		-- 1.3.6.1.4.1.37950.1.1.5.10.1.1.7.4
		uplinkPortChannelGroupIDS OBJECT-TYPE
			SYNTAX Integer32
			MAX-ACCESS read-write
			STATUS current
			DESCRIPTION
				"Description."
			::= { uplinkPortAggregationCfg 4 }

		
--         1.3.6.1.4.1.37950.1.1.5.10.1.1.7.5
-- 1.3.6.1.4.1.37950.1.1.5.10.1.1.7.5
-- 1.3.6.1.4.1.37950.1.1.5.10.1.1.7.5
-- 1.3.6.1.4.1.37950.1.1.5.10.1.1.7.5
-- 1.3.6.1.4.1.37950.1.1.5.10.1.1.7.5
-- 1.3.6.1.4.1.37950.1.1.5.10.1.1.7.5
-- 1.3.6.1.4.1.37950.1.1.5.10.1.1.7.5
-- 1.3.6.1.4.1.37950.1.1.5.10.1.1.7.5
		-- 1.3.6.1.4.1.37950.1.1.5.10.1.1.7.5
		uplinkPortLacpModeS OBJECT-TYPE
			SYNTAX INTEGER
				{
				passive(0),
				active(1)
				}
			MAX-ACCESS read-write
			STATUS current
			DESCRIPTION
				"Description."
			::= { uplinkPortAggregationCfg 5 }

		
--         1.3.6.1.4.1.37950.1.1.5.10.1.1.7.6
-- 1.3.6.1.4.1.37950.1.1.5.10.1.1.7.6
-- 1.3.6.1.4.1.37950.1.1.5.10.1.1.7.6
-- 1.3.6.1.4.1.37950.1.1.5.10.1.1.7.6
-- 1.3.6.1.4.1.37950.1.1.5.10.1.1.7.6
-- 1.3.6.1.4.1.37950.1.1.5.10.1.1.7.6
-- 1.3.6.1.4.1.37950.1.1.5.10.1.1.7.6
-- 1.3.6.1.4.1.37950.1.1.5.10.1.1.7.6
		-- 1.3.6.1.4.1.37950.1.1.5.10.1.1.7.6
		uplinkPortPriorityS OBJECT-TYPE
			SYNTAX Integer32 (0..65535)
			MAX-ACCESS read-write
			STATUS current
			DESCRIPTION
				"Description."
			::= { uplinkPortAggregationCfg 6 }

		
--         1.3.6.1.4.1.37950.1.1.5.10.1.1.7.7
-- 1.3.6.1.4.1.37950.1.1.5.10.1.1.7.7
-- 1.3.6.1.4.1.37950.1.1.5.10.1.1.7.7
-- 1.3.6.1.4.1.37950.1.1.5.10.1.1.7.7
-- 1.3.6.1.4.1.37950.1.1.5.10.1.1.7.7
-- 1.3.6.1.4.1.37950.1.1.5.10.1.1.7.7
-- 1.3.6.1.4.1.37950.1.1.5.10.1.1.7.7
-- 1.3.6.1.4.1.37950.1.1.5.10.1.1.7.7
		-- 1.3.6.1.4.1.37950.1.1.5.10.1.1.7.7
		uplinkPortCfgAction OBJECT-TYPE
			SYNTAX INTEGER { submit(1) }
			MAX-ACCESS read-write
			STATUS current
			DESCRIPTION
				"Description."
			::= { uplinkPortAggregationCfg 7 }

		
--          1.3.6.1.4.1.37950.1.1.5.10.1.2
-- 1.3.6.1.4.1.37950.1.1.5.10.1.2
-- 1.3.6.1.4.1.37950.1.1.5.10.1.2
-- 1.3.6.1.4.1.37950.1.1.5.10.1.2
-- 1.3.6.1.4.1.37950.1.1.5.10.1.2
-- 1.3.6.1.4.1.37950.1.1.5.10.1.2
-- 1.3.6.1.4.1.37950.1.1.5.10.1.2
-- 1.3.6.1.4.1.37950.1.1.5.10.1.2
-- 1.3.6.1.4.1.37950.1.1.5.10.1.2
		-- 1.3.6.1.4.1.37950.1.1.5.10.1.2
		ponPort OBJECT IDENTIFIER ::= { v1600dPort 2 }

		
--          1.3.6.1.4.1.37950.1.1.5.10.1.2.1
-- 1.3.6.1.4.1.37950.1.1.5.10.1.2.1
-- 1.3.6.1.4.1.37950.1.1.5.10.1.2.1
-- 1.3.6.1.4.1.37950.1.1.5.10.1.2.1
-- 1.3.6.1.4.1.37950.1.1.5.10.1.2.1
-- 1.3.6.1.4.1.37950.1.1.5.10.1.2.1
-- 1.3.6.1.4.1.37950.1.1.5.10.1.2.1
-- 1.3.6.1.4.1.37950.1.1.5.10.1.2.1
-- 1.3.6.1.4.1.37950.1.1.5.10.1.2.1
		-- 1.3.6.1.4.1.37950.1.1.5.10.1.2.1
		ponPortConfigTable OBJECT-TYPE
			SYNTAX SEQUENCE OF PonPortConfigEntry
			MAX-ACCESS not-accessible
			STATUS current
			DESCRIPTION
				"Description."
			::= { ponPort 1 }

		
--          1.3.6.1.4.1.37950.1.1.5.10.1.2.1.1
-- 1.3.6.1.4.1.37950.1.1.5.10.1.2.1.1
-- 1.3.6.1.4.1.37950.1.1.5.10.1.2.1.1
-- 1.3.6.1.4.1.37950.1.1.5.10.1.2.1.1
-- 1.3.6.1.4.1.37950.1.1.5.10.1.2.1.1
-- 1.3.6.1.4.1.37950.1.1.5.10.1.2.1.1
-- 1.3.6.1.4.1.37950.1.1.5.10.1.2.1.1
-- 1.3.6.1.4.1.37950.1.1.5.10.1.2.1.1
-- 1.3.6.1.4.1.37950.1.1.5.10.1.2.1.1
		-- 1.3.6.1.4.1.37950.1.1.5.10.1.2.1.1
		ponPortConfigEntry OBJECT-TYPE
			SYNTAX PonPortConfigEntry
			MAX-ACCESS not-accessible
			STATUS current
			DESCRIPTION
				"Description."
			INDEX { ponPortIndex }
			::= { ponPortConfigTable 1 }

		
		PonPortConfigEntry ::=
			SEQUENCE { 
				ponPortIndex
					INTEGER,
				ponPortDescr
					OCTET STRING,
				ponPortAdminStatus
					INTEGER,
				ponPortFlowControl
					INTEGER,
				ponPortIngressRate
					INTEGER,
				ponPortEgressRate
					INTEGER,
				ponPortBCStormCtrl
					INTEGER,
				ponPortMCStromCtrl
					INTEGER,
				ponPortUCStromCtrl
					INTEGER,
				ponPortPriValue
					Integer32,
				ponPortPvid
					INTEGER,
				ponPortIsolate
					INTEGER,
				ponPortJumboFrameEn
					INTEGER,
				ponPortDescr2
					OCTET STRING,
				ponPortMode
					INTEGER,
				ponPortMacAddrLearnState
					INTEGER
			 }

--          1.3.6.1.4.1.37950.1.1.5.10.1.2.1.1.1
-- 1.3.6.1.4.1.37950.1.1.5.10.1.2.1.1.1
-- 1.3.6.1.4.1.37950.1.1.5.10.1.2.1.1.1
-- 1.3.6.1.4.1.37950.1.1.5.10.1.2.1.1.1
-- 1.3.6.1.4.1.37950.1.1.5.10.1.2.1.1.1
-- 1.3.6.1.4.1.37950.1.1.5.10.1.2.1.1.1
-- 1.3.6.1.4.1.37950.1.1.5.10.1.2.1.1.1
-- 1.3.6.1.4.1.37950.1.1.5.10.1.2.1.1.1
-- 1.3.6.1.4.1.37950.1.1.5.10.1.2.1.1.1
		-- 1.3.6.1.4.1.37950.1.1.5.10.1.2.1.1.1
		ponPortIndex OBJECT-TYPE
			SYNTAX INTEGER (1..16)
			MAX-ACCESS read-write
			STATUS current
			DESCRIPTION
				"Description."
			::= { ponPortConfigEntry 1 }

		
--          1.3.6.1.4.1.37950.1.1.5.10.1.2.1.1.2
-- 1.3.6.1.4.1.37950.1.1.5.10.1.2.1.1.2
-- 1.3.6.1.4.1.37950.1.1.5.10.1.2.1.1.2
-- 1.3.6.1.4.1.37950.1.1.5.10.1.2.1.1.2
-- 1.3.6.1.4.1.37950.1.1.5.10.1.2.1.1.2
-- 1.3.6.1.4.1.37950.1.1.5.10.1.2.1.1.2
-- 1.3.6.1.4.1.37950.1.1.5.10.1.2.1.1.2
-- 1.3.6.1.4.1.37950.1.1.5.10.1.2.1.1.2
-- 1.3.6.1.4.1.37950.1.1.5.10.1.2.1.1.2
		-- 1.3.6.1.4.1.37950.1.1.5.10.1.2.1.1.2
		ponPortDescr OBJECT-TYPE
			SYNTAX OCTET STRING
			MAX-ACCESS read-write
			STATUS current
			DESCRIPTION
				"Description."
			::= { ponPortConfigEntry 2 }

		
--          1.3.6.1.4.1.37950.1.1.5.10.1.2.1.1.3
-- 1.3.6.1.4.1.37950.1.1.5.10.1.2.1.1.3
-- 1.3.6.1.4.1.37950.1.1.5.10.1.2.1.1.3
-- 1.3.6.1.4.1.37950.1.1.5.10.1.2.1.1.3
-- 1.3.6.1.4.1.37950.1.1.5.10.1.2.1.1.3
-- 1.3.6.1.4.1.37950.1.1.5.10.1.2.1.1.3
-- 1.3.6.1.4.1.37950.1.1.5.10.1.2.1.1.3
-- 1.3.6.1.4.1.37950.1.1.5.10.1.2.1.1.3
-- 1.3.6.1.4.1.37950.1.1.5.10.1.2.1.1.3
		-- 1.3.6.1.4.1.37950.1.1.5.10.1.2.1.1.3
		ponPortAdminStatus OBJECT-TYPE
			SYNTAX INTEGER
				{
				disable(0),
				enable(1)
				}
			MAX-ACCESS read-write
			STATUS current
			DESCRIPTION
				"Description."
			::= { ponPortConfigEntry 3 }

		
--          1.3.6.1.4.1.37950.1.1.5.10.1.2.1.1.4
-- 1.3.6.1.4.1.37950.1.1.5.10.1.2.1.1.4
-- 1.3.6.1.4.1.37950.1.1.5.10.1.2.1.1.4
-- 1.3.6.1.4.1.37950.1.1.5.10.1.2.1.1.4
-- 1.3.6.1.4.1.37950.1.1.5.10.1.2.1.1.4
-- 1.3.6.1.4.1.37950.1.1.5.10.1.2.1.1.4
-- 1.3.6.1.4.1.37950.1.1.5.10.1.2.1.1.4
-- 1.3.6.1.4.1.37950.1.1.5.10.1.2.1.1.4
-- 1.3.6.1.4.1.37950.1.1.5.10.1.2.1.1.4
		-- 1.3.6.1.4.1.37950.1.1.5.10.1.2.1.1.4
		ponPortFlowControl OBJECT-TYPE
			SYNTAX INTEGER
				{
				disable(0),
				enable(1)
				}
			MAX-ACCESS read-write
			STATUS current
			DESCRIPTION
				"Description."
			::= { ponPortConfigEntry 4 }

		
--          1.3.6.1.4.1.37950.1.1.5.10.1.2.1.1.5
-- 1.3.6.1.4.1.37950.1.1.5.10.1.2.1.1.5
-- 1.3.6.1.4.1.37950.1.1.5.10.1.2.1.1.5
-- 1.3.6.1.4.1.37950.1.1.5.10.1.2.1.1.5
-- 1.3.6.1.4.1.37950.1.1.5.10.1.2.1.1.5
-- 1.3.6.1.4.1.37950.1.1.5.10.1.2.1.1.5
-- 1.3.6.1.4.1.37950.1.1.5.10.1.2.1.1.5
-- 1.3.6.1.4.1.37950.1.1.5.10.1.2.1.1.5
-- 1.3.6.1.4.1.37950.1.1.5.10.1.2.1.1.5
		-- 1.3.6.1.4.1.37950.1.1.5.10.1.2.1.1.5
		ponPortIngressRate OBJECT-TYPE
			SYNTAX INTEGER (0 | 64..1000000)
			MAX-ACCESS read-write
			STATUS current
			DESCRIPTION
				"Description."
			::= { ponPortConfigEntry 5 }

		
--          1.3.6.1.4.1.37950.1.1.5.10.1.2.1.1.6
-- 1.3.6.1.4.1.37950.1.1.5.10.1.2.1.1.6
-- 1.3.6.1.4.1.37950.1.1.5.10.1.2.1.1.6
-- 1.3.6.1.4.1.37950.1.1.5.10.1.2.1.1.6
-- 1.3.6.1.4.1.37950.1.1.5.10.1.2.1.1.6
-- 1.3.6.1.4.1.37950.1.1.5.10.1.2.1.1.6
-- 1.3.6.1.4.1.37950.1.1.5.10.1.2.1.1.6
-- 1.3.6.1.4.1.37950.1.1.5.10.1.2.1.1.6
-- 1.3.6.1.4.1.37950.1.1.5.10.1.2.1.1.6
		-- 1.3.6.1.4.1.37950.1.1.5.10.1.2.1.1.6
		ponPortEgressRate OBJECT-TYPE
			SYNTAX INTEGER (0 | 64..1000000)
			MAX-ACCESS read-write
			STATUS current
			DESCRIPTION
				"Description."
			::= { ponPortConfigEntry 6 }

		
--          1.3.6.1.4.1.37950.1.1.5.10.1.2.1.1.7
-- 1.3.6.1.4.1.37950.1.1.5.10.1.2.1.1.7
-- 1.3.6.1.4.1.37950.1.1.5.10.1.2.1.1.7
-- 1.3.6.1.4.1.37950.1.1.5.10.1.2.1.1.7
-- 1.3.6.1.4.1.37950.1.1.5.10.1.2.1.1.7
-- 1.3.6.1.4.1.37950.1.1.5.10.1.2.1.1.7
-- 1.3.6.1.4.1.37950.1.1.5.10.1.2.1.1.7
-- 1.3.6.1.4.1.37950.1.1.5.10.1.2.1.1.7
-- 1.3.6.1.4.1.37950.1.1.5.10.1.2.1.1.7
		-- 1.3.6.1.4.1.37950.1.1.5.10.1.2.1.1.7
		ponPortBCStormCtrl OBJECT-TYPE
			SYNTAX INTEGER (0 | 64..1000000)
			MAX-ACCESS read-write
			STATUS current
			DESCRIPTION
				"Description."
			::= { ponPortConfigEntry 7 }

		
--          1.3.6.1.4.1.37950.1.1.5.10.1.2.1.1.8
-- 1.3.6.1.4.1.37950.1.1.5.10.1.2.1.1.8
-- 1.3.6.1.4.1.37950.1.1.5.10.1.2.1.1.8
-- 1.3.6.1.4.1.37950.1.1.5.10.1.2.1.1.8
-- 1.3.6.1.4.1.37950.1.1.5.10.1.2.1.1.8
-- 1.3.6.1.4.1.37950.1.1.5.10.1.2.1.1.8
-- 1.3.6.1.4.1.37950.1.1.5.10.1.2.1.1.8
-- 1.3.6.1.4.1.37950.1.1.5.10.1.2.1.1.8
-- 1.3.6.1.4.1.37950.1.1.5.10.1.2.1.1.8
		-- 1.3.6.1.4.1.37950.1.1.5.10.1.2.1.1.8
		ponPortMCStromCtrl OBJECT-TYPE
			SYNTAX INTEGER (0 | 64..1000000)
			MAX-ACCESS read-write
			STATUS current
			DESCRIPTION
				"Description."
			::= { ponPortConfigEntry 8 }

		
--          1.3.6.1.4.1.37950.1.1.5.10.1.2.1.1.9
-- 1.3.6.1.4.1.37950.1.1.5.10.1.2.1.1.9
-- 1.3.6.1.4.1.37950.1.1.5.10.1.2.1.1.9
-- 1.3.6.1.4.1.37950.1.1.5.10.1.2.1.1.9
-- 1.3.6.1.4.1.37950.1.1.5.10.1.2.1.1.9
-- 1.3.6.1.4.1.37950.1.1.5.10.1.2.1.1.9
-- 1.3.6.1.4.1.37950.1.1.5.10.1.2.1.1.9
-- 1.3.6.1.4.1.37950.1.1.5.10.1.2.1.1.9
-- 1.3.6.1.4.1.37950.1.1.5.10.1.2.1.1.9
		-- 1.3.6.1.4.1.37950.1.1.5.10.1.2.1.1.9
		ponPortUCStromCtrl OBJECT-TYPE
			SYNTAX INTEGER (0 | 64..1000000)
			MAX-ACCESS read-write
			STATUS current
			DESCRIPTION
				"Description."
			::= { ponPortConfigEntry 9 }

		
--          1.3.6.1.4.1.37950.1.1.5.10.1.2.1.1.10
-- 1.3.6.1.4.1.37950.1.1.5.10.1.2.1.1.10
-- 1.3.6.1.4.1.37950.1.1.5.10.1.2.1.1.10
-- 1.3.6.1.4.1.37950.1.1.5.10.1.2.1.1.10
-- 1.3.6.1.4.1.37950.1.1.5.10.1.2.1.1.10
-- 1.3.6.1.4.1.37950.1.1.5.10.1.2.1.1.10
-- 1.3.6.1.4.1.37950.1.1.5.10.1.2.1.1.10
-- 1.3.6.1.4.1.37950.1.1.5.10.1.2.1.1.10
-- 1.3.6.1.4.1.37950.1.1.5.10.1.2.1.1.10
		-- 1.3.6.1.4.1.37950.1.1.5.10.1.2.1.1.10
		ponPortPriValue OBJECT-TYPE
			SYNTAX Integer32 (0..7)
			MAX-ACCESS read-write
			STATUS current
			DESCRIPTION
				"Description."
			::= { ponPortConfigEntry 10 }

		
--          1.3.6.1.4.1.37950.1.1.5.10.1.2.1.1.11
-- 1.3.6.1.4.1.37950.1.1.5.10.1.2.1.1.11
-- 1.3.6.1.4.1.37950.1.1.5.10.1.2.1.1.11
-- 1.3.6.1.4.1.37950.1.1.5.10.1.2.1.1.11
-- 1.3.6.1.4.1.37950.1.1.5.10.1.2.1.1.11
-- 1.3.6.1.4.1.37950.1.1.5.10.1.2.1.1.11
-- 1.3.6.1.4.1.37950.1.1.5.10.1.2.1.1.11
-- 1.3.6.1.4.1.37950.1.1.5.10.1.2.1.1.11
-- 1.3.6.1.4.1.37950.1.1.5.10.1.2.1.1.11
		-- 1.3.6.1.4.1.37950.1.1.5.10.1.2.1.1.11
		ponPortPvid OBJECT-TYPE
			SYNTAX INTEGER (1..4096)
			MAX-ACCESS read-write
			STATUS current
			DESCRIPTION
				"Description."
			::= { ponPortConfigEntry 11 }

		
--          1.3.6.1.4.1.37950.1.1.5.10.1.2.1.1.12
-- 1.3.6.1.4.1.37950.1.1.5.10.1.2.1.1.12
-- 1.3.6.1.4.1.37950.1.1.5.10.1.2.1.1.12
-- 1.3.6.1.4.1.37950.1.1.5.10.1.2.1.1.12
-- 1.3.6.1.4.1.37950.1.1.5.10.1.2.1.1.12
-- 1.3.6.1.4.1.37950.1.1.5.10.1.2.1.1.12
-- 1.3.6.1.4.1.37950.1.1.5.10.1.2.1.1.12
-- 1.3.6.1.4.1.37950.1.1.5.10.1.2.1.1.12
-- 1.3.6.1.4.1.37950.1.1.5.10.1.2.1.1.12
		-- 1.3.6.1.4.1.37950.1.1.5.10.1.2.1.1.12
		ponPortIsolate OBJECT-TYPE
			SYNTAX INTEGER
				{
				no-isolate(0),
				isolate(1)
				}
			MAX-ACCESS read-write
			STATUS current
			DESCRIPTION
				"Description."
			::= { ponPortConfigEntry 12 }

		
--          1.3.6.1.4.1.37950.1.1.5.10.1.2.1.1.13
-- 1.3.6.1.4.1.37950.1.1.5.10.1.2.1.1.13
-- 1.3.6.1.4.1.37950.1.1.5.10.1.2.1.1.13
-- 1.3.6.1.4.1.37950.1.1.5.10.1.2.1.1.13
-- 1.3.6.1.4.1.37950.1.1.5.10.1.2.1.1.13
-- 1.3.6.1.4.1.37950.1.1.5.10.1.2.1.1.13
-- 1.3.6.1.4.1.37950.1.1.5.10.1.2.1.1.13
-- 1.3.6.1.4.1.37950.1.1.5.10.1.2.1.1.13
-- 1.3.6.1.4.1.37950.1.1.5.10.1.2.1.1.13
		-- 1.3.6.1.4.1.37950.1.1.5.10.1.2.1.1.13
		ponPortJumboFrameEn OBJECT-TYPE
			SYNTAX INTEGER
				{
				disable(0),
				enable(1)
				}
			MAX-ACCESS read-write
			STATUS current
			DESCRIPTION
				"Description."
			::= { ponPortConfigEntry 13 }

		
--          1.3.6.1.4.1.37950.1.1.5.10.1.2.1.1.14
-- 1.3.6.1.4.1.37950.1.1.5.10.1.2.1.1.14
-- 1.3.6.1.4.1.37950.1.1.5.10.1.2.1.1.14
-- 1.3.6.1.4.1.37950.1.1.5.10.1.2.1.1.14
-- 1.3.6.1.4.1.37950.1.1.5.10.1.2.1.1.14
-- 1.3.6.1.4.1.37950.1.1.5.10.1.2.1.1.14
-- 1.3.6.1.4.1.37950.1.1.5.10.1.2.1.1.14
-- 1.3.6.1.4.1.37950.1.1.5.10.1.2.1.1.14
-- 1.3.6.1.4.1.37950.1.1.5.10.1.2.1.1.14
		-- 1.3.6.1.4.1.37950.1.1.5.10.1.2.1.1.14
		ponPortDescr2 OBJECT-TYPE
			SYNTAX OCTET STRING
			MAX-ACCESS read-write
			STATUS current
			DESCRIPTION
				"Description."
			::= { ponPortConfigEntry 14 }

		
--         1.3.6.1.4.1.37950.1.1.5.10.1.2.1.1.15
-- 1.3.6.1.4.1.37950.1.1.5.10.1.2.1.1.15
-- 1.3.6.1.4.1.37950.1.1.5.10.1.2.1.1.15
-- 1.3.6.1.4.1.37950.1.1.5.10.1.2.1.1.15
-- 1.3.6.1.4.1.37950.1.1.5.10.1.2.1.1.15
-- 1.3.6.1.4.1.37950.1.1.5.10.1.2.1.1.15
-- 1.3.6.1.4.1.37950.1.1.5.10.1.2.1.1.15
-- 1.3.6.1.4.1.37950.1.1.5.10.1.2.1.1.15
		-- 1.3.6.1.4.1.37950.1.1.5.10.1.2.1.1.15
		ponPortMode OBJECT-TYPE
			SYNTAX INTEGER
				{
				access(1),
				trunk(2),
				hybrid(3)
				}
			MAX-ACCESS read-write
			STATUS current
			DESCRIPTION
				"Description."
			::= { ponPortConfigEntry 15 }

		
--         1.3.6.1.4.1.37950.1.1.5.10.1.2.1.1.16
-- 1.3.6.1.4.1.37950.1.1.5.10.1.2.1.1.16
-- 1.3.6.1.4.1.37950.1.1.5.10.1.2.1.1.16
-- 1.3.6.1.4.1.37950.1.1.5.10.1.2.1.1.16
-- 1.3.6.1.4.1.37950.1.1.5.10.1.2.1.1.16
-- 1.3.6.1.4.1.37950.1.1.5.10.1.2.1.1.16
-- 1.3.6.1.4.1.37950.1.1.5.10.1.2.1.1.16
-- 1.3.6.1.4.1.37950.1.1.5.10.1.2.1.1.16
		-- 1.3.6.1.4.1.37950.1.1.5.10.1.2.1.1.16
		ponPortMacAddrLearnState OBJECT-TYPE
			SYNTAX INTEGER
				{
				disable(0),
				enable(1)
				}
			MAX-ACCESS read-write
			STATUS current
			DESCRIPTION
				"Description."
			::= { ponPortConfigEntry 16 }

		
--          1.3.6.1.4.1.37950.1.1.5.10.1.2.2
-- 1.3.6.1.4.1.37950.1.1.5.10.1.2.2
-- 1.3.6.1.4.1.37950.1.1.5.10.1.2.2
-- 1.3.6.1.4.1.37950.1.1.5.10.1.2.2
-- 1.3.6.1.4.1.37950.1.1.5.10.1.2.2
-- 1.3.6.1.4.1.37950.1.1.5.10.1.2.2
-- 1.3.6.1.4.1.37950.1.1.5.10.1.2.2
-- 1.3.6.1.4.1.37950.1.1.5.10.1.2.2
-- 1.3.6.1.4.1.37950.1.1.5.10.1.2.2
		-- 1.3.6.1.4.1.37950.1.1.5.10.1.2.2
		ponPortPerformanceDataTable OBJECT-TYPE
			SYNTAX SEQUENCE OF PonPortPerformanceDataEntry
			MAX-ACCESS not-accessible
			STATUS current
			DESCRIPTION
				"Description."
			::= { ponPort 2 }

		
--          1.3.6.1.4.1.37950.1.1.5.10.1.2.2.1
-- 1.3.6.1.4.1.37950.1.1.5.10.1.2.2.1
-- 1.3.6.1.4.1.37950.1.1.5.10.1.2.2.1
-- 1.3.6.1.4.1.37950.1.1.5.10.1.2.2.1
-- 1.3.6.1.4.1.37950.1.1.5.10.1.2.2.1
-- 1.3.6.1.4.1.37950.1.1.5.10.1.2.2.1
-- 1.3.6.1.4.1.37950.1.1.5.10.1.2.2.1
-- 1.3.6.1.4.1.37950.1.1.5.10.1.2.2.1
-- 1.3.6.1.4.1.37950.1.1.5.10.1.2.2.1
		-- 1.3.6.1.4.1.37950.1.1.5.10.1.2.2.1
		ponPortPerformanceDataEntry OBJECT-TYPE
			SYNTAX PonPortPerformanceDataEntry
			MAX-ACCESS not-accessible
			STATUS current
			DESCRIPTION
				"Description."
			INDEX { ponPIndex }
			::= { ponPortPerformanceDataTable 1 }

		
		PonPortPerformanceDataEntry ::=
			SEQUENCE { 
				ponPIndex
					INTEGER,
				ponPortUpOctets
					Counter32,
				ponPortUpSpeed
					Counter32,
				ponPortUpMaxBand
					Counter32,
				ponPortUpProportion
					Counter32,
				ponPortUpMPCP
					Counter32,
				ponPortTotalFrames
					Counter32,
				ponPortUpUnicastFrames
					Counter32,
				ponPortUpBroadcastFrames
					Counter32,
				ponPortUpMulticastFrames
					Counter32,
				ponPortUpCrc32Errors
					Counter32,
				ponPortUpUndersizeFrames
					Counter32,
				ponPortUpOversizeFrames
					Counter32,
				ponPortUpCollisions
					Counter32,
				ponPortUpFramesDropped
					Counter32,
				ponPortUp64OctetFrames
					Counter32,
				ponPortUp65To127OctetFrames
					Counter32,
				ponPortUp128To255OctetFrames
					Counter32,
				ponPortUp256To511OctetFrames
					Counter32,
				ponPortUp512To1023OctetFrames
					Counter32,
				ponPortUp1024To1518OctetFrames
					Counter32,
				ponPortUpOver1519OctetFrames
					Counter32,
				ponPortDownOctets
					Counter32,
				ponPortDownSpeed
					Counter32,
				ponPortDownMaxband
					Counter32,
				ponPortDownproportion
					Counter32,
				ponPortDownMPCP
					Counter32,
				ponPortDownTotalFrames
					Counter32,
				ponPortDownUnicastFrames
					Counter32,
				ponPortDownBroadcastFrames
					Counter32,
				ponPortDownMulticastFrames
					Counter32,
				ponPortDownCrc32Errors
					Counter32,
				ponPortDownUndersizeFrames
					Counter32,
				ponPortDownOversizeFrames
					Counter32,
				ponPortDownCollisions
					Counter32,
				ponPortDownFramesDropped
					Counter32,
				ponPortDown64OctetFrames
					Counter32,
				ponPortDown65To127OctetFrames
					Counter32,
				ponPortDown128To255OctetFrames
					Counter32,
				ponPortDown256To511OctetFrames
					Counter32,
				ponPortDown512To1023OctetFrames
					Counter32,
				ponPortDown1024To1518OctetFrames
					Counter32,
				ponPortDownOver1519OctetFrames
					Counter32,
				ponPortDownBytes
					Counter64,
				ponPortUpBytes
					Counter64
			 }

--          1.3.6.1.4.1.37950.1.1.5.10.1.2.2.1.1
-- 1.3.6.1.4.1.37950.1.1.5.10.1.2.2.1.1
-- 1.3.6.1.4.1.37950.1.1.5.10.1.2.2.1.1
-- 1.3.6.1.4.1.37950.1.1.5.10.1.2.2.1.1
-- 1.3.6.1.4.1.37950.1.1.5.10.1.2.2.1.1
-- 1.3.6.1.4.1.37950.1.1.5.10.1.2.2.1.1
-- 1.3.6.1.4.1.37950.1.1.5.10.1.2.2.1.1
-- 1.3.6.1.4.1.37950.1.1.5.10.1.2.2.1.1
-- 1.3.6.1.4.1.37950.1.1.5.10.1.2.2.1.1
		-- 1.3.6.1.4.1.37950.1.1.5.10.1.2.2.1.1
		ponPIndex OBJECT-TYPE
			SYNTAX INTEGER (1..16)
			MAX-ACCESS read-only
			STATUS current
			DESCRIPTION
				"Description."
			::= { ponPortPerformanceDataEntry 1 }

		
--          1.3.6.1.4.1.37950.1.1.5.10.1.2.2.1.2
-- 1.3.6.1.4.1.37950.1.1.5.10.1.2.2.1.2
-- 1.3.6.1.4.1.37950.1.1.5.10.1.2.2.1.2
-- 1.3.6.1.4.1.37950.1.1.5.10.1.2.2.1.2
-- 1.3.6.1.4.1.37950.1.1.5.10.1.2.2.1.2
-- 1.3.6.1.4.1.37950.1.1.5.10.1.2.2.1.2
-- 1.3.6.1.4.1.37950.1.1.5.10.1.2.2.1.2
-- 1.3.6.1.4.1.37950.1.1.5.10.1.2.2.1.2
-- 1.3.6.1.4.1.37950.1.1.5.10.1.2.2.1.2
		-- 1.3.6.1.4.1.37950.1.1.5.10.1.2.2.1.2
		ponPortUpOctets OBJECT-TYPE
			SYNTAX Counter32
			MAX-ACCESS read-only
			STATUS current
			DESCRIPTION
				"Description."
			::= { ponPortPerformanceDataEntry 2 }

		
--          1.3.6.1.4.1.37950.1.1.5.10.1.2.2.1.3
-- 1.3.6.1.4.1.37950.1.1.5.10.1.2.2.1.3
-- 1.3.6.1.4.1.37950.1.1.5.10.1.2.2.1.3
-- 1.3.6.1.4.1.37950.1.1.5.10.1.2.2.1.3
-- 1.3.6.1.4.1.37950.1.1.5.10.1.2.2.1.3
-- 1.3.6.1.4.1.37950.1.1.5.10.1.2.2.1.3
-- 1.3.6.1.4.1.37950.1.1.5.10.1.2.2.1.3
-- 1.3.6.1.4.1.37950.1.1.5.10.1.2.2.1.3
-- 1.3.6.1.4.1.37950.1.1.5.10.1.2.2.1.3
		-- 1.3.6.1.4.1.37950.1.1.5.10.1.2.2.1.3
		ponPortUpSpeed OBJECT-TYPE
			SYNTAX Counter32
			MAX-ACCESS read-only
			STATUS current
			DESCRIPTION
				"Description."
			::= { ponPortPerformanceDataEntry 3 }

		
--          1.3.6.1.4.1.37950.1.1.5.10.1.2.2.1.4
-- 1.3.6.1.4.1.37950.1.1.5.10.1.2.2.1.4
-- 1.3.6.1.4.1.37950.1.1.5.10.1.2.2.1.4
-- 1.3.6.1.4.1.37950.1.1.5.10.1.2.2.1.4
-- 1.3.6.1.4.1.37950.1.1.5.10.1.2.2.1.4
-- 1.3.6.1.4.1.37950.1.1.5.10.1.2.2.1.4
-- 1.3.6.1.4.1.37950.1.1.5.10.1.2.2.1.4
-- 1.3.6.1.4.1.37950.1.1.5.10.1.2.2.1.4
-- 1.3.6.1.4.1.37950.1.1.5.10.1.2.2.1.4
		-- 1.3.6.1.4.1.37950.1.1.5.10.1.2.2.1.4
		ponPortUpMaxBand OBJECT-TYPE
			SYNTAX Counter32
			MAX-ACCESS read-only
			STATUS current
			DESCRIPTION
				"Description."
			::= { ponPortPerformanceDataEntry 4 }

		
--          1.3.6.1.4.1.37950.1.1.5.10.1.2.2.1.5
-- 1.3.6.1.4.1.37950.1.1.5.10.1.2.2.1.5
-- 1.3.6.1.4.1.37950.1.1.5.10.1.2.2.1.5
-- 1.3.6.1.4.1.37950.1.1.5.10.1.2.2.1.5
-- 1.3.6.1.4.1.37950.1.1.5.10.1.2.2.1.5
-- 1.3.6.1.4.1.37950.1.1.5.10.1.2.2.1.5
-- 1.3.6.1.4.1.37950.1.1.5.10.1.2.2.1.5
-- 1.3.6.1.4.1.37950.1.1.5.10.1.2.2.1.5
-- 1.3.6.1.4.1.37950.1.1.5.10.1.2.2.1.5
		-- 1.3.6.1.4.1.37950.1.1.5.10.1.2.2.1.5
		ponPortUpProportion OBJECT-TYPE
			SYNTAX Counter32
			MAX-ACCESS read-only
			STATUS current
			DESCRIPTION
				"Description."
			::= { ponPortPerformanceDataEntry 5 }

		
--          1.3.6.1.4.1.37950.1.1.5.10.1.2.2.1.6
-- 1.3.6.1.4.1.37950.1.1.5.10.1.2.2.1.6
-- 1.3.6.1.4.1.37950.1.1.5.10.1.2.2.1.6
-- 1.3.6.1.4.1.37950.1.1.5.10.1.2.2.1.6
-- 1.3.6.1.4.1.37950.1.1.5.10.1.2.2.1.6
-- 1.3.6.1.4.1.37950.1.1.5.10.1.2.2.1.6
-- 1.3.6.1.4.1.37950.1.1.5.10.1.2.2.1.6
-- 1.3.6.1.4.1.37950.1.1.5.10.1.2.2.1.6
-- 1.3.6.1.4.1.37950.1.1.5.10.1.2.2.1.6
		-- 1.3.6.1.4.1.37950.1.1.5.10.1.2.2.1.6
		ponPortUpMPCP OBJECT-TYPE
			SYNTAX Counter32
			MAX-ACCESS read-only
			STATUS current
			DESCRIPTION
				"Description."
			::= { ponPortPerformanceDataEntry 6 }

		
--          1.3.6.1.4.1.37950.1.1.5.10.1.2.2.1.7
-- 1.3.6.1.4.1.37950.1.1.5.10.1.2.2.1.7
-- 1.3.6.1.4.1.37950.1.1.5.10.1.2.2.1.7
-- 1.3.6.1.4.1.37950.1.1.5.10.1.2.2.1.7
-- 1.3.6.1.4.1.37950.1.1.5.10.1.2.2.1.7
-- 1.3.6.1.4.1.37950.1.1.5.10.1.2.2.1.7
-- 1.3.6.1.4.1.37950.1.1.5.10.1.2.2.1.7
-- 1.3.6.1.4.1.37950.1.1.5.10.1.2.2.1.7
-- 1.3.6.1.4.1.37950.1.1.5.10.1.2.2.1.7
		-- 1.3.6.1.4.1.37950.1.1.5.10.1.2.2.1.7
		ponPortTotalFrames OBJECT-TYPE
			SYNTAX Counter32
			MAX-ACCESS read-only
			STATUS current
			DESCRIPTION
				"Description."
			::= { ponPortPerformanceDataEntry 7 }

		
--          1.3.6.1.4.1.37950.1.1.5.10.1.2.2.1.8
-- 1.3.6.1.4.1.37950.1.1.5.10.1.2.2.1.8
-- 1.3.6.1.4.1.37950.1.1.5.10.1.2.2.1.8
-- 1.3.6.1.4.1.37950.1.1.5.10.1.2.2.1.8
-- 1.3.6.1.4.1.37950.1.1.5.10.1.2.2.1.8
-- 1.3.6.1.4.1.37950.1.1.5.10.1.2.2.1.8
-- 1.3.6.1.4.1.37950.1.1.5.10.1.2.2.1.8
-- 1.3.6.1.4.1.37950.1.1.5.10.1.2.2.1.8
-- 1.3.6.1.4.1.37950.1.1.5.10.1.2.2.1.8
		-- 1.3.6.1.4.1.37950.1.1.5.10.1.2.2.1.8
		ponPortUpUnicastFrames OBJECT-TYPE
			SYNTAX Counter32
			MAX-ACCESS read-only
			STATUS current
			DESCRIPTION
				"Description."
			::= { ponPortPerformanceDataEntry 8 }

		
--          1.3.6.1.4.1.37950.1.1.5.10.1.2.2.1.9
-- 1.3.6.1.4.1.37950.1.1.5.10.1.2.2.1.9
-- 1.3.6.1.4.1.37950.1.1.5.10.1.2.2.1.9
-- 1.3.6.1.4.1.37950.1.1.5.10.1.2.2.1.9
-- 1.3.6.1.4.1.37950.1.1.5.10.1.2.2.1.9
-- 1.3.6.1.4.1.37950.1.1.5.10.1.2.2.1.9
-- 1.3.6.1.4.1.37950.1.1.5.10.1.2.2.1.9
-- 1.3.6.1.4.1.37950.1.1.5.10.1.2.2.1.9
-- 1.3.6.1.4.1.37950.1.1.5.10.1.2.2.1.9
		-- 1.3.6.1.4.1.37950.1.1.5.10.1.2.2.1.9
		ponPortUpBroadcastFrames OBJECT-TYPE
			SYNTAX Counter32
			MAX-ACCESS read-only
			STATUS current
			DESCRIPTION
				"Description."
			::= { ponPortPerformanceDataEntry 9 }

		
--          1.3.6.1.4.1.37950.1.1.5.10.1.2.2.1.10
-- 1.3.6.1.4.1.37950.1.1.5.10.1.2.2.1.10
-- 1.3.6.1.4.1.37950.1.1.5.10.1.2.2.1.10
-- 1.3.6.1.4.1.37950.1.1.5.10.1.2.2.1.10
-- 1.3.6.1.4.1.37950.1.1.5.10.1.2.2.1.10
-- 1.3.6.1.4.1.37950.1.1.5.10.1.2.2.1.10
-- 1.3.6.1.4.1.37950.1.1.5.10.1.2.2.1.10
-- 1.3.6.1.4.1.37950.1.1.5.10.1.2.2.1.10
-- 1.3.6.1.4.1.37950.1.1.5.10.1.2.2.1.10
		-- 1.3.6.1.4.1.37950.1.1.5.10.1.2.2.1.10
		ponPortUpMulticastFrames OBJECT-TYPE
			SYNTAX Counter32
			MAX-ACCESS read-only
			STATUS current
			DESCRIPTION
				"Description."
			::= { ponPortPerformanceDataEntry 10 }

		
--          1.3.6.1.4.1.37950.1.1.5.10.1.2.2.1.11
-- 1.3.6.1.4.1.37950.1.1.5.10.1.2.2.1.11
-- 1.3.6.1.4.1.37950.1.1.5.10.1.2.2.1.11
-- 1.3.6.1.4.1.37950.1.1.5.10.1.2.2.1.11
-- 1.3.6.1.4.1.37950.1.1.5.10.1.2.2.1.11
-- 1.3.6.1.4.1.37950.1.1.5.10.1.2.2.1.11
-- 1.3.6.1.4.1.37950.1.1.5.10.1.2.2.1.11
-- 1.3.6.1.4.1.37950.1.1.5.10.1.2.2.1.11
-- 1.3.6.1.4.1.37950.1.1.5.10.1.2.2.1.11
		-- 1.3.6.1.4.1.37950.1.1.5.10.1.2.2.1.11
		ponPortUpCrc32Errors OBJECT-TYPE
			SYNTAX Counter32
			MAX-ACCESS read-only
			STATUS current
			DESCRIPTION
				"Description."
			::= { ponPortPerformanceDataEntry 11 }

		
--          1.3.6.1.4.1.37950.1.1.5.10.1.2.2.1.12
-- 1.3.6.1.4.1.37950.1.1.5.10.1.2.2.1.12
-- 1.3.6.1.4.1.37950.1.1.5.10.1.2.2.1.12
-- 1.3.6.1.4.1.37950.1.1.5.10.1.2.2.1.12
-- 1.3.6.1.4.1.37950.1.1.5.10.1.2.2.1.12
-- 1.3.6.1.4.1.37950.1.1.5.10.1.2.2.1.12
-- 1.3.6.1.4.1.37950.1.1.5.10.1.2.2.1.12
-- 1.3.6.1.4.1.37950.1.1.5.10.1.2.2.1.12
-- 1.3.6.1.4.1.37950.1.1.5.10.1.2.2.1.12
		-- 1.3.6.1.4.1.37950.1.1.5.10.1.2.2.1.12
		ponPortUpUndersizeFrames OBJECT-TYPE
			SYNTAX Counter32
			MAX-ACCESS read-only
			STATUS current
			DESCRIPTION
				"Description."
			::= { ponPortPerformanceDataEntry 12 }

		
--          1.3.6.1.4.1.37950.1.1.5.10.1.2.2.1.13
-- 1.3.6.1.4.1.37950.1.1.5.10.1.2.2.1.13
-- 1.3.6.1.4.1.37950.1.1.5.10.1.2.2.1.13
-- 1.3.6.1.4.1.37950.1.1.5.10.1.2.2.1.13
-- 1.3.6.1.4.1.37950.1.1.5.10.1.2.2.1.13
-- 1.3.6.1.4.1.37950.1.1.5.10.1.2.2.1.13
-- 1.3.6.1.4.1.37950.1.1.5.10.1.2.2.1.13
-- 1.3.6.1.4.1.37950.1.1.5.10.1.2.2.1.13
-- 1.3.6.1.4.1.37950.1.1.5.10.1.2.2.1.13
		-- 1.3.6.1.4.1.37950.1.1.5.10.1.2.2.1.13
		ponPortUpOversizeFrames OBJECT-TYPE
			SYNTAX Counter32
			MAX-ACCESS read-only
			STATUS current
			DESCRIPTION
				"Description."
			::= { ponPortPerformanceDataEntry 13 }

		
--          1.3.6.1.4.1.37950.1.1.5.10.1.2.2.1.14
-- 1.3.6.1.4.1.37950.1.1.5.10.1.2.2.1.14
-- 1.3.6.1.4.1.37950.1.1.5.10.1.2.2.1.14
-- 1.3.6.1.4.1.37950.1.1.5.10.1.2.2.1.14
-- 1.3.6.1.4.1.37950.1.1.5.10.1.2.2.1.14
-- 1.3.6.1.4.1.37950.1.1.5.10.1.2.2.1.14
-- 1.3.6.1.4.1.37950.1.1.5.10.1.2.2.1.14
-- 1.3.6.1.4.1.37950.1.1.5.10.1.2.2.1.14
-- 1.3.6.1.4.1.37950.1.1.5.10.1.2.2.1.14
		-- 1.3.6.1.4.1.37950.1.1.5.10.1.2.2.1.14
		ponPortUpCollisions OBJECT-TYPE
			SYNTAX Counter32
			MAX-ACCESS read-only
			STATUS current
			DESCRIPTION
				"Description."
			::= { ponPortPerformanceDataEntry 14 }

		
--          1.3.6.1.4.1.37950.1.1.5.10.1.2.2.1.15
-- 1.3.6.1.4.1.37950.1.1.5.10.1.2.2.1.15
-- 1.3.6.1.4.1.37950.1.1.5.10.1.2.2.1.15
-- 1.3.6.1.4.1.37950.1.1.5.10.1.2.2.1.15
-- 1.3.6.1.4.1.37950.1.1.5.10.1.2.2.1.15
-- 1.3.6.1.4.1.37950.1.1.5.10.1.2.2.1.15
-- 1.3.6.1.4.1.37950.1.1.5.10.1.2.2.1.15
-- 1.3.6.1.4.1.37950.1.1.5.10.1.2.2.1.15
-- 1.3.6.1.4.1.37950.1.1.5.10.1.2.2.1.15
		-- 1.3.6.1.4.1.37950.1.1.5.10.1.2.2.1.15
		ponPortUpFramesDropped OBJECT-TYPE
			SYNTAX Counter32
			MAX-ACCESS read-only
			STATUS current
			DESCRIPTION
				"Description."
			::= { ponPortPerformanceDataEntry 15 }

		
--          1.3.6.1.4.1.37950.1.1.5.10.1.2.2.1.16
-- 1.3.6.1.4.1.37950.1.1.5.10.1.2.2.1.16
-- 1.3.6.1.4.1.37950.1.1.5.10.1.2.2.1.16
-- 1.3.6.1.4.1.37950.1.1.5.10.1.2.2.1.16
-- 1.3.6.1.4.1.37950.1.1.5.10.1.2.2.1.16
-- 1.3.6.1.4.1.37950.1.1.5.10.1.2.2.1.16
-- 1.3.6.1.4.1.37950.1.1.5.10.1.2.2.1.16
-- 1.3.6.1.4.1.37950.1.1.5.10.1.2.2.1.16
-- 1.3.6.1.4.1.37950.1.1.5.10.1.2.2.1.16
		-- 1.3.6.1.4.1.37950.1.1.5.10.1.2.2.1.16
		ponPortUp64OctetFrames OBJECT-TYPE
			SYNTAX Counter32
			MAX-ACCESS read-only
			STATUS current
			DESCRIPTION
				"Description."
			::= { ponPortPerformanceDataEntry 16 }

		
--          1.3.6.1.4.1.37950.1.1.5.10.1.2.2.1.17
-- 1.3.6.1.4.1.37950.1.1.5.10.1.2.2.1.17
-- 1.3.6.1.4.1.37950.1.1.5.10.1.2.2.1.17
-- 1.3.6.1.4.1.37950.1.1.5.10.1.2.2.1.17
-- 1.3.6.1.4.1.37950.1.1.5.10.1.2.2.1.17
-- 1.3.6.1.4.1.37950.1.1.5.10.1.2.2.1.17
-- 1.3.6.1.4.1.37950.1.1.5.10.1.2.2.1.17
-- 1.3.6.1.4.1.37950.1.1.5.10.1.2.2.1.17
-- 1.3.6.1.4.1.37950.1.1.5.10.1.2.2.1.17
		-- 1.3.6.1.4.1.37950.1.1.5.10.1.2.2.1.17
		ponPortUp65To127OctetFrames OBJECT-TYPE
			SYNTAX Counter32
			MAX-ACCESS read-only
			STATUS current
			DESCRIPTION
				"Description."
			::= { ponPortPerformanceDataEntry 17 }

		
--          1.3.6.1.4.1.37950.1.1.5.10.1.2.2.1.18
-- 1.3.6.1.4.1.37950.1.1.5.10.1.2.2.1.18
-- 1.3.6.1.4.1.37950.1.1.5.10.1.2.2.1.18
-- 1.3.6.1.4.1.37950.1.1.5.10.1.2.2.1.18
-- 1.3.6.1.4.1.37950.1.1.5.10.1.2.2.1.18
-- 1.3.6.1.4.1.37950.1.1.5.10.1.2.2.1.18
-- 1.3.6.1.4.1.37950.1.1.5.10.1.2.2.1.18
-- 1.3.6.1.4.1.37950.1.1.5.10.1.2.2.1.18
-- 1.3.6.1.4.1.37950.1.1.5.10.1.2.2.1.18
		-- 1.3.6.1.4.1.37950.1.1.5.10.1.2.2.1.18
		ponPortUp128To255OctetFrames OBJECT-TYPE
			SYNTAX Counter32
			MAX-ACCESS read-only
			STATUS current
			DESCRIPTION
				"Description."
			::= { ponPortPerformanceDataEntry 18 }

		
--          1.3.6.1.4.1.37950.1.1.5.10.1.2.2.1.19
-- 1.3.6.1.4.1.37950.1.1.5.10.1.2.2.1.19
-- 1.3.6.1.4.1.37950.1.1.5.10.1.2.2.1.19
-- 1.3.6.1.4.1.37950.1.1.5.10.1.2.2.1.19
-- 1.3.6.1.4.1.37950.1.1.5.10.1.2.2.1.19
-- 1.3.6.1.4.1.37950.1.1.5.10.1.2.2.1.19
-- 1.3.6.1.4.1.37950.1.1.5.10.1.2.2.1.19
-- 1.3.6.1.4.1.37950.1.1.5.10.1.2.2.1.19
-- 1.3.6.1.4.1.37950.1.1.5.10.1.2.2.1.19
		-- 1.3.6.1.4.1.37950.1.1.5.10.1.2.2.1.19
		ponPortUp256To511OctetFrames OBJECT-TYPE
			SYNTAX Counter32
			MAX-ACCESS read-only
			STATUS current
			DESCRIPTION
				"Description."
			::= { ponPortPerformanceDataEntry 19 }

		
--          1.3.6.1.4.1.37950.1.1.5.10.1.2.2.1.20
-- 1.3.6.1.4.1.37950.1.1.5.10.1.2.2.1.20
-- 1.3.6.1.4.1.37950.1.1.5.10.1.2.2.1.20
-- 1.3.6.1.4.1.37950.1.1.5.10.1.2.2.1.20
-- 1.3.6.1.4.1.37950.1.1.5.10.1.2.2.1.20
-- 1.3.6.1.4.1.37950.1.1.5.10.1.2.2.1.20
-- 1.3.6.1.4.1.37950.1.1.5.10.1.2.2.1.20
-- 1.3.6.1.4.1.37950.1.1.5.10.1.2.2.1.20
-- 1.3.6.1.4.1.37950.1.1.5.10.1.2.2.1.20
		-- 1.3.6.1.4.1.37950.1.1.5.10.1.2.2.1.20
		ponPortUp512To1023OctetFrames OBJECT-TYPE
			SYNTAX Counter32
			MAX-ACCESS read-only
			STATUS current
			DESCRIPTION
				"Description."
			::= { ponPortPerformanceDataEntry 20 }

		
--          1.3.6.1.4.1.37950.1.1.5.10.1.2.2.1.21
-- 1.3.6.1.4.1.37950.1.1.5.10.1.2.2.1.21
-- 1.3.6.1.4.1.37950.1.1.5.10.1.2.2.1.21
-- 1.3.6.1.4.1.37950.1.1.5.10.1.2.2.1.21
-- 1.3.6.1.4.1.37950.1.1.5.10.1.2.2.1.21
-- 1.3.6.1.4.1.37950.1.1.5.10.1.2.2.1.21
-- 1.3.6.1.4.1.37950.1.1.5.10.1.2.2.1.21
-- 1.3.6.1.4.1.37950.1.1.5.10.1.2.2.1.21
-- 1.3.6.1.4.1.37950.1.1.5.10.1.2.2.1.21
		-- 1.3.6.1.4.1.37950.1.1.5.10.1.2.2.1.21
		ponPortUp1024To1518OctetFrames OBJECT-TYPE
			SYNTAX Counter32
			MAX-ACCESS read-only
			STATUS current
			DESCRIPTION
				"Description."
			::= { ponPortPerformanceDataEntry 21 }

		
--          1.3.6.1.4.1.37950.1.1.5.10.1.2.2.1.22
-- 1.3.6.1.4.1.37950.1.1.5.10.1.2.2.1.22
-- 1.3.6.1.4.1.37950.1.1.5.10.1.2.2.1.22
-- 1.3.6.1.4.1.37950.1.1.5.10.1.2.2.1.22
-- 1.3.6.1.4.1.37950.1.1.5.10.1.2.2.1.22
-- 1.3.6.1.4.1.37950.1.1.5.10.1.2.2.1.22
-- 1.3.6.1.4.1.37950.1.1.5.10.1.2.2.1.22
-- 1.3.6.1.4.1.37950.1.1.5.10.1.2.2.1.22
-- 1.3.6.1.4.1.37950.1.1.5.10.1.2.2.1.22
		-- 1.3.6.1.4.1.37950.1.1.5.10.1.2.2.1.22
		ponPortUpOver1519OctetFrames OBJECT-TYPE
			SYNTAX Counter32
			MAX-ACCESS read-only
			STATUS current
			DESCRIPTION
				"Description."
			::= { ponPortPerformanceDataEntry 22 }

		
--          1.3.6.1.4.1.37950.1.1.5.10.1.2.2.1.23
-- 1.3.6.1.4.1.37950.1.1.5.10.1.2.2.1.23
-- 1.3.6.1.4.1.37950.1.1.5.10.1.2.2.1.23
-- 1.3.6.1.4.1.37950.1.1.5.10.1.2.2.1.23
-- 1.3.6.1.4.1.37950.1.1.5.10.1.2.2.1.23
-- 1.3.6.1.4.1.37950.1.1.5.10.1.2.2.1.23
-- 1.3.6.1.4.1.37950.1.1.5.10.1.2.2.1.23
-- 1.3.6.1.4.1.37950.1.1.5.10.1.2.2.1.23
-- 1.3.6.1.4.1.37950.1.1.5.10.1.2.2.1.23
		-- 1.3.6.1.4.1.37950.1.1.5.10.1.2.2.1.23
		ponPortDownOctets OBJECT-TYPE
			SYNTAX Counter32
			MAX-ACCESS read-only
			STATUS current
			DESCRIPTION
				"Description."
			::= { ponPortPerformanceDataEntry 23 }

		
--          1.3.6.1.4.1.37950.1.1.5.10.1.2.2.1.24
-- 1.3.6.1.4.1.37950.1.1.5.10.1.2.2.1.24
-- 1.3.6.1.4.1.37950.1.1.5.10.1.2.2.1.24
-- 1.3.6.1.4.1.37950.1.1.5.10.1.2.2.1.24
-- 1.3.6.1.4.1.37950.1.1.5.10.1.2.2.1.24
-- 1.3.6.1.4.1.37950.1.1.5.10.1.2.2.1.24
-- 1.3.6.1.4.1.37950.1.1.5.10.1.2.2.1.24
-- 1.3.6.1.4.1.37950.1.1.5.10.1.2.2.1.24
-- 1.3.6.1.4.1.37950.1.1.5.10.1.2.2.1.24
		-- 1.3.6.1.4.1.37950.1.1.5.10.1.2.2.1.24
		ponPortDownSpeed OBJECT-TYPE
			SYNTAX Counter32
			MAX-ACCESS read-only
			STATUS current
			DESCRIPTION
				"Description."
			::= { ponPortPerformanceDataEntry 24 }

		
--          1.3.6.1.4.1.37950.1.1.5.10.1.2.2.1.25
-- 1.3.6.1.4.1.37950.1.1.5.10.1.2.2.1.25
-- 1.3.6.1.4.1.37950.1.1.5.10.1.2.2.1.25
-- 1.3.6.1.4.1.37950.1.1.5.10.1.2.2.1.25
-- 1.3.6.1.4.1.37950.1.1.5.10.1.2.2.1.25
-- 1.3.6.1.4.1.37950.1.1.5.10.1.2.2.1.25
-- 1.3.6.1.4.1.37950.1.1.5.10.1.2.2.1.25
-- 1.3.6.1.4.1.37950.1.1.5.10.1.2.2.1.25
-- 1.3.6.1.4.1.37950.1.1.5.10.1.2.2.1.25
		-- 1.3.6.1.4.1.37950.1.1.5.10.1.2.2.1.25
		ponPortDownMaxband OBJECT-TYPE
			SYNTAX Counter32
			MAX-ACCESS read-only
			STATUS current
			DESCRIPTION
				"Description."
			::= { ponPortPerformanceDataEntry 25 }

		
--          1.3.6.1.4.1.37950.1.1.5.10.1.2.2.1.26
-- 1.3.6.1.4.1.37950.1.1.5.10.1.2.2.1.26
-- 1.3.6.1.4.1.37950.1.1.5.10.1.2.2.1.26
-- 1.3.6.1.4.1.37950.1.1.5.10.1.2.2.1.26
-- 1.3.6.1.4.1.37950.1.1.5.10.1.2.2.1.26
-- 1.3.6.1.4.1.37950.1.1.5.10.1.2.2.1.26
-- 1.3.6.1.4.1.37950.1.1.5.10.1.2.2.1.26
-- 1.3.6.1.4.1.37950.1.1.5.10.1.2.2.1.26
-- 1.3.6.1.4.1.37950.1.1.5.10.1.2.2.1.26
		-- 1.3.6.1.4.1.37950.1.1.5.10.1.2.2.1.26
		ponPortDownproportion OBJECT-TYPE
			SYNTAX Counter32
			MAX-ACCESS read-only
			STATUS current
			DESCRIPTION
				"Description."
			::= { ponPortPerformanceDataEntry 26 }

		
--          1.3.6.1.4.1.37950.1.1.5.10.1.2.2.1.27
-- 1.3.6.1.4.1.37950.1.1.5.10.1.2.2.1.27
-- 1.3.6.1.4.1.37950.1.1.5.10.1.2.2.1.27
-- 1.3.6.1.4.1.37950.1.1.5.10.1.2.2.1.27
-- 1.3.6.1.4.1.37950.1.1.5.10.1.2.2.1.27
-- 1.3.6.1.4.1.37950.1.1.5.10.1.2.2.1.27
-- 1.3.6.1.4.1.37950.1.1.5.10.1.2.2.1.27
-- 1.3.6.1.4.1.37950.1.1.5.10.1.2.2.1.27
-- 1.3.6.1.4.1.37950.1.1.5.10.1.2.2.1.27
		-- 1.3.6.1.4.1.37950.1.1.5.10.1.2.2.1.27
		ponPortDownMPCP OBJECT-TYPE
			SYNTAX Counter32
			MAX-ACCESS read-only
			STATUS current
			DESCRIPTION
				"Description."
			::= { ponPortPerformanceDataEntry 27 }

		
--          1.3.6.1.4.1.37950.1.1.5.10.1.2.2.1.28
-- 1.3.6.1.4.1.37950.1.1.5.10.1.2.2.1.28
-- 1.3.6.1.4.1.37950.1.1.5.10.1.2.2.1.28
-- 1.3.6.1.4.1.37950.1.1.5.10.1.2.2.1.28
-- 1.3.6.1.4.1.37950.1.1.5.10.1.2.2.1.28
-- 1.3.6.1.4.1.37950.1.1.5.10.1.2.2.1.28
-- 1.3.6.1.4.1.37950.1.1.5.10.1.2.2.1.28
-- 1.3.6.1.4.1.37950.1.1.5.10.1.2.2.1.28
-- 1.3.6.1.4.1.37950.1.1.5.10.1.2.2.1.28
		-- 1.3.6.1.4.1.37950.1.1.5.10.1.2.2.1.28
		ponPortDownTotalFrames OBJECT-TYPE
			SYNTAX Counter32
			MAX-ACCESS read-only
			STATUS current
			DESCRIPTION
				"Description."
			::= { ponPortPerformanceDataEntry 28 }

		
--          1.3.6.1.4.1.37950.1.1.5.10.1.2.2.1.29
-- 1.3.6.1.4.1.37950.1.1.5.10.1.2.2.1.29
-- 1.3.6.1.4.1.37950.1.1.5.10.1.2.2.1.29
-- 1.3.6.1.4.1.37950.1.1.5.10.1.2.2.1.29
-- 1.3.6.1.4.1.37950.1.1.5.10.1.2.2.1.29
-- 1.3.6.1.4.1.37950.1.1.5.10.1.2.2.1.29
-- 1.3.6.1.4.1.37950.1.1.5.10.1.2.2.1.29
-- 1.3.6.1.4.1.37950.1.1.5.10.1.2.2.1.29
-- 1.3.6.1.4.1.37950.1.1.5.10.1.2.2.1.29
		-- 1.3.6.1.4.1.37950.1.1.5.10.1.2.2.1.29
		ponPortDownUnicastFrames OBJECT-TYPE
			SYNTAX Counter32
			MAX-ACCESS read-only
			STATUS current
			DESCRIPTION
				"Description."
			::= { ponPortPerformanceDataEntry 29 }

		
--          1.3.6.1.4.1.37950.1.1.5.10.1.2.2.1.30
-- 1.3.6.1.4.1.37950.1.1.5.10.1.2.2.1.30
-- 1.3.6.1.4.1.37950.1.1.5.10.1.2.2.1.30
-- 1.3.6.1.4.1.37950.1.1.5.10.1.2.2.1.30
-- 1.3.6.1.4.1.37950.1.1.5.10.1.2.2.1.30
-- 1.3.6.1.4.1.37950.1.1.5.10.1.2.2.1.30
-- 1.3.6.1.4.1.37950.1.1.5.10.1.2.2.1.30
-- 1.3.6.1.4.1.37950.1.1.5.10.1.2.2.1.30
-- 1.3.6.1.4.1.37950.1.1.5.10.1.2.2.1.30
		-- 1.3.6.1.4.1.37950.1.1.5.10.1.2.2.1.30
		ponPortDownBroadcastFrames OBJECT-TYPE
			SYNTAX Counter32
			MAX-ACCESS read-only
			STATUS current
			DESCRIPTION
				"Description."
			::= { ponPortPerformanceDataEntry 30 }

		
--          1.3.6.1.4.1.37950.1.1.5.10.1.2.2.1.31
-- 1.3.6.1.4.1.37950.1.1.5.10.1.2.2.1.31
-- 1.3.6.1.4.1.37950.1.1.5.10.1.2.2.1.31
-- 1.3.6.1.4.1.37950.1.1.5.10.1.2.2.1.31
-- 1.3.6.1.4.1.37950.1.1.5.10.1.2.2.1.31
-- 1.3.6.1.4.1.37950.1.1.5.10.1.2.2.1.31
-- 1.3.6.1.4.1.37950.1.1.5.10.1.2.2.1.31
-- 1.3.6.1.4.1.37950.1.1.5.10.1.2.2.1.31
-- 1.3.6.1.4.1.37950.1.1.5.10.1.2.2.1.31
		-- 1.3.6.1.4.1.37950.1.1.5.10.1.2.2.1.31
		ponPortDownMulticastFrames OBJECT-TYPE
			SYNTAX Counter32
			MAX-ACCESS read-only
			STATUS current
			DESCRIPTION
				"Description."
			::= { ponPortPerformanceDataEntry 31 }

		
--          1.3.6.1.4.1.37950.1.1.5.10.1.2.2.1.32
-- 1.3.6.1.4.1.37950.1.1.5.10.1.2.2.1.32
-- 1.3.6.1.4.1.37950.1.1.5.10.1.2.2.1.32
-- 1.3.6.1.4.1.37950.1.1.5.10.1.2.2.1.32
-- 1.3.6.1.4.1.37950.1.1.5.10.1.2.2.1.32
-- 1.3.6.1.4.1.37950.1.1.5.10.1.2.2.1.32
-- 1.3.6.1.4.1.37950.1.1.5.10.1.2.2.1.32
-- 1.3.6.1.4.1.37950.1.1.5.10.1.2.2.1.32
-- 1.3.6.1.4.1.37950.1.1.5.10.1.2.2.1.32
		-- 1.3.6.1.4.1.37950.1.1.5.10.1.2.2.1.32
		ponPortDownCrc32Errors OBJECT-TYPE
			SYNTAX Counter32
			MAX-ACCESS read-only
			STATUS current
			DESCRIPTION
				"Description."
			::= { ponPortPerformanceDataEntry 32 }

		
--          1.3.6.1.4.1.37950.1.1.5.10.1.2.2.1.33
-- 1.3.6.1.4.1.37950.1.1.5.10.1.2.2.1.33
-- 1.3.6.1.4.1.37950.1.1.5.10.1.2.2.1.33
-- 1.3.6.1.4.1.37950.1.1.5.10.1.2.2.1.33
-- 1.3.6.1.4.1.37950.1.1.5.10.1.2.2.1.33
-- 1.3.6.1.4.1.37950.1.1.5.10.1.2.2.1.33
-- 1.3.6.1.4.1.37950.1.1.5.10.1.2.2.1.33
-- 1.3.6.1.4.1.37950.1.1.5.10.1.2.2.1.33
-- 1.3.6.1.4.1.37950.1.1.5.10.1.2.2.1.33
		-- 1.3.6.1.4.1.37950.1.1.5.10.1.2.2.1.33
		ponPortDownUndersizeFrames OBJECT-TYPE
			SYNTAX Counter32
			MAX-ACCESS read-only
			STATUS current
			DESCRIPTION
				"Description."
			::= { ponPortPerformanceDataEntry 33 }

		
--          1.3.6.1.4.1.37950.1.1.5.10.1.2.2.1.34
-- 1.3.6.1.4.1.37950.1.1.5.10.1.2.2.1.34
-- 1.3.6.1.4.1.37950.1.1.5.10.1.2.2.1.34
-- 1.3.6.1.4.1.37950.1.1.5.10.1.2.2.1.34
-- 1.3.6.1.4.1.37950.1.1.5.10.1.2.2.1.34
-- 1.3.6.1.4.1.37950.1.1.5.10.1.2.2.1.34
-- 1.3.6.1.4.1.37950.1.1.5.10.1.2.2.1.34
-- 1.3.6.1.4.1.37950.1.1.5.10.1.2.2.1.34
-- 1.3.6.1.4.1.37950.1.1.5.10.1.2.2.1.34
		-- 1.3.6.1.4.1.37950.1.1.5.10.1.2.2.1.34
		ponPortDownOversizeFrames OBJECT-TYPE
			SYNTAX Counter32
			MAX-ACCESS read-only
			STATUS current
			DESCRIPTION
				"Description."
			::= { ponPortPerformanceDataEntry 34 }

		
--          1.3.6.1.4.1.37950.1.1.5.10.1.2.2.1.35
-- 1.3.6.1.4.1.37950.1.1.5.10.1.2.2.1.35
-- 1.3.6.1.4.1.37950.1.1.5.10.1.2.2.1.35
-- 1.3.6.1.4.1.37950.1.1.5.10.1.2.2.1.35
-- 1.3.6.1.4.1.37950.1.1.5.10.1.2.2.1.35
-- 1.3.6.1.4.1.37950.1.1.5.10.1.2.2.1.35
-- 1.3.6.1.4.1.37950.1.1.5.10.1.2.2.1.35
-- 1.3.6.1.4.1.37950.1.1.5.10.1.2.2.1.35
-- 1.3.6.1.4.1.37950.1.1.5.10.1.2.2.1.35
		-- 1.3.6.1.4.1.37950.1.1.5.10.1.2.2.1.35
		ponPortDownCollisions OBJECT-TYPE
			SYNTAX Counter32
			MAX-ACCESS read-only
			STATUS current
			DESCRIPTION
				"Description."
			::= { ponPortPerformanceDataEntry 35 }

		
--          1.3.6.1.4.1.37950.1.1.5.10.1.2.2.1.36
-- 1.3.6.1.4.1.37950.1.1.5.10.1.2.2.1.36
-- 1.3.6.1.4.1.37950.1.1.5.10.1.2.2.1.36
-- 1.3.6.1.4.1.37950.1.1.5.10.1.2.2.1.36
-- 1.3.6.1.4.1.37950.1.1.5.10.1.2.2.1.36
-- 1.3.6.1.4.1.37950.1.1.5.10.1.2.2.1.36
-- 1.3.6.1.4.1.37950.1.1.5.10.1.2.2.1.36
-- 1.3.6.1.4.1.37950.1.1.5.10.1.2.2.1.36
-- 1.3.6.1.4.1.37950.1.1.5.10.1.2.2.1.36
		-- 1.3.6.1.4.1.37950.1.1.5.10.1.2.2.1.36
		ponPortDownFramesDropped OBJECT-TYPE
			SYNTAX Counter32
			MAX-ACCESS read-only
			STATUS current
			DESCRIPTION
				"Description."
			::= { ponPortPerformanceDataEntry 36 }

		
--          1.3.6.1.4.1.37950.1.1.5.10.1.2.2.1.37
-- 1.3.6.1.4.1.37950.1.1.5.10.1.2.2.1.37
-- 1.3.6.1.4.1.37950.1.1.5.10.1.2.2.1.37
-- 1.3.6.1.4.1.37950.1.1.5.10.1.2.2.1.37
-- 1.3.6.1.4.1.37950.1.1.5.10.1.2.2.1.37
-- 1.3.6.1.4.1.37950.1.1.5.10.1.2.2.1.37
-- 1.3.6.1.4.1.37950.1.1.5.10.1.2.2.1.37
-- 1.3.6.1.4.1.37950.1.1.5.10.1.2.2.1.37
-- 1.3.6.1.4.1.37950.1.1.5.10.1.2.2.1.37
		-- 1.3.6.1.4.1.37950.1.1.5.10.1.2.2.1.37
		ponPortDown64OctetFrames OBJECT-TYPE
			SYNTAX Counter32
			MAX-ACCESS read-only
			STATUS current
			DESCRIPTION
				"Description."
			::= { ponPortPerformanceDataEntry 37 }

		
--          1.3.6.1.4.1.37950.1.1.5.10.1.2.2.1.38
-- 1.3.6.1.4.1.37950.1.1.5.10.1.2.2.1.38
-- 1.3.6.1.4.1.37950.1.1.5.10.1.2.2.1.38
-- 1.3.6.1.4.1.37950.1.1.5.10.1.2.2.1.38
-- 1.3.6.1.4.1.37950.1.1.5.10.1.2.2.1.38
-- 1.3.6.1.4.1.37950.1.1.5.10.1.2.2.1.38
-- 1.3.6.1.4.1.37950.1.1.5.10.1.2.2.1.38
-- 1.3.6.1.4.1.37950.1.1.5.10.1.2.2.1.38
-- 1.3.6.1.4.1.37950.1.1.5.10.1.2.2.1.38
		-- 1.3.6.1.4.1.37950.1.1.5.10.1.2.2.1.38
		ponPortDown65To127OctetFrames OBJECT-TYPE
			SYNTAX Counter32
			MAX-ACCESS read-only
			STATUS current
			DESCRIPTION
				"Description."
			::= { ponPortPerformanceDataEntry 38 }

		
--          1.3.6.1.4.1.37950.1.1.5.10.1.2.2.1.39
-- 1.3.6.1.4.1.37950.1.1.5.10.1.2.2.1.39
-- 1.3.6.1.4.1.37950.1.1.5.10.1.2.2.1.39
-- 1.3.6.1.4.1.37950.1.1.5.10.1.2.2.1.39
-- 1.3.6.1.4.1.37950.1.1.5.10.1.2.2.1.39
-- 1.3.6.1.4.1.37950.1.1.5.10.1.2.2.1.39
-- 1.3.6.1.4.1.37950.1.1.5.10.1.2.2.1.39
-- 1.3.6.1.4.1.37950.1.1.5.10.1.2.2.1.39
-- 1.3.6.1.4.1.37950.1.1.5.10.1.2.2.1.39
		-- 1.3.6.1.4.1.37950.1.1.5.10.1.2.2.1.39
		ponPortDown128To255OctetFrames OBJECT-TYPE
			SYNTAX Counter32
			MAX-ACCESS read-only
			STATUS current
			DESCRIPTION
				"Description."
			::= { ponPortPerformanceDataEntry 39 }

		
--          1.3.6.1.4.1.37950.1.1.5.10.1.2.2.1.40
-- 1.3.6.1.4.1.37950.1.1.5.10.1.2.2.1.40
-- 1.3.6.1.4.1.37950.1.1.5.10.1.2.2.1.40
-- 1.3.6.1.4.1.37950.1.1.5.10.1.2.2.1.40
-- 1.3.6.1.4.1.37950.1.1.5.10.1.2.2.1.40
-- 1.3.6.1.4.1.37950.1.1.5.10.1.2.2.1.40
-- 1.3.6.1.4.1.37950.1.1.5.10.1.2.2.1.40
-- 1.3.6.1.4.1.37950.1.1.5.10.1.2.2.1.40
-- 1.3.6.1.4.1.37950.1.1.5.10.1.2.2.1.40
		-- 1.3.6.1.4.1.37950.1.1.5.10.1.2.2.1.40
		ponPortDown256To511OctetFrames OBJECT-TYPE
			SYNTAX Counter32
			MAX-ACCESS read-only
			STATUS current
			DESCRIPTION
				"Description."
			::= { ponPortPerformanceDataEntry 40 }

		
--          1.3.6.1.4.1.37950.1.1.5.10.1.2.2.1.41
-- 1.3.6.1.4.1.37950.1.1.5.10.1.2.2.1.41
-- 1.3.6.1.4.1.37950.1.1.5.10.1.2.2.1.41
-- 1.3.6.1.4.1.37950.1.1.5.10.1.2.2.1.41
-- 1.3.6.1.4.1.37950.1.1.5.10.1.2.2.1.41
-- 1.3.6.1.4.1.37950.1.1.5.10.1.2.2.1.41
-- 1.3.6.1.4.1.37950.1.1.5.10.1.2.2.1.41
-- 1.3.6.1.4.1.37950.1.1.5.10.1.2.2.1.41
-- 1.3.6.1.4.1.37950.1.1.5.10.1.2.2.1.41
		-- 1.3.6.1.4.1.37950.1.1.5.10.1.2.2.1.41
		ponPortDown512To1023OctetFrames OBJECT-TYPE
			SYNTAX Counter32
			MAX-ACCESS read-only
			STATUS current
			DESCRIPTION
				"Description."
			::= { ponPortPerformanceDataEntry 41 }

		
--          1.3.6.1.4.1.37950.1.1.5.10.1.2.2.1.42
-- 1.3.6.1.4.1.37950.1.1.5.10.1.2.2.1.42
-- 1.3.6.1.4.1.37950.1.1.5.10.1.2.2.1.42
-- 1.3.6.1.4.1.37950.1.1.5.10.1.2.2.1.42
-- 1.3.6.1.4.1.37950.1.1.5.10.1.2.2.1.42
-- 1.3.6.1.4.1.37950.1.1.5.10.1.2.2.1.42
-- 1.3.6.1.4.1.37950.1.1.5.10.1.2.2.1.42
-- 1.3.6.1.4.1.37950.1.1.5.10.1.2.2.1.42
-- 1.3.6.1.4.1.37950.1.1.5.10.1.2.2.1.42
		-- 1.3.6.1.4.1.37950.1.1.5.10.1.2.2.1.42
		ponPortDown1024To1518OctetFrames OBJECT-TYPE
			SYNTAX Counter32
			MAX-ACCESS read-only
			STATUS current
			DESCRIPTION
				"Description."
			::= { ponPortPerformanceDataEntry 42 }

		
--          1.3.6.1.4.1.37950.1.1.5.10.1.2.2.1.43
-- 1.3.6.1.4.1.37950.1.1.5.10.1.2.2.1.43
-- 1.3.6.1.4.1.37950.1.1.5.10.1.2.2.1.43
-- 1.3.6.1.4.1.37950.1.1.5.10.1.2.2.1.43
-- 1.3.6.1.4.1.37950.1.1.5.10.1.2.2.1.43
-- 1.3.6.1.4.1.37950.1.1.5.10.1.2.2.1.43
-- 1.3.6.1.4.1.37950.1.1.5.10.1.2.2.1.43
-- 1.3.6.1.4.1.37950.1.1.5.10.1.2.2.1.43
-- 1.3.6.1.4.1.37950.1.1.5.10.1.2.2.1.43
		-- 1.3.6.1.4.1.37950.1.1.5.10.1.2.2.1.43
		ponPortDownOver1519OctetFrames OBJECT-TYPE
			SYNTAX Counter32
			MAX-ACCESS read-only
			STATUS current
			DESCRIPTION
				"Description."
			::= { ponPortPerformanceDataEntry 43 }

		
--          1.3.6.1.4.1.37950.1.1.5.10.1.2.2.1.44
-- 1.3.6.1.4.1.37950.1.1.5.10.1.2.2.1.44
-- 1.3.6.1.4.1.37950.1.1.5.10.1.2.2.1.44
-- 1.3.6.1.4.1.37950.1.1.5.10.1.2.2.1.44
-- 1.3.6.1.4.1.37950.1.1.5.10.1.2.2.1.44
-- 1.3.6.1.4.1.37950.1.1.5.10.1.2.2.1.44
-- 1.3.6.1.4.1.37950.1.1.5.10.1.2.2.1.44
-- 1.3.6.1.4.1.37950.1.1.5.10.1.2.2.1.44
-- 1.3.6.1.4.1.37950.1.1.5.10.1.2.2.1.44
		-- 1.3.6.1.4.1.37950.1.1.5.10.1.2.2.1.44
		ponPortDownBytes OBJECT-TYPE
			SYNTAX Counter64
			MAX-ACCESS read-only
			STATUS current
			DESCRIPTION
				"Description."
			::= { ponPortPerformanceDataEntry 44 }

		
--          1.3.6.1.4.1.37950.1.1.5.10.1.2.2.1.45
-- 1.3.6.1.4.1.37950.1.1.5.10.1.2.2.1.45
-- 1.3.6.1.4.1.37950.1.1.5.10.1.2.2.1.45
-- 1.3.6.1.4.1.37950.1.1.5.10.1.2.2.1.45
-- 1.3.6.1.4.1.37950.1.1.5.10.1.2.2.1.45
-- 1.3.6.1.4.1.37950.1.1.5.10.1.2.2.1.45
-- 1.3.6.1.4.1.37950.1.1.5.10.1.2.2.1.45
-- 1.3.6.1.4.1.37950.1.1.5.10.1.2.2.1.45
-- 1.3.6.1.4.1.37950.1.1.5.10.1.2.2.1.45
		-- 1.3.6.1.4.1.37950.1.1.5.10.1.2.2.1.45
		ponPortUpBytes OBJECT-TYPE
			SYNTAX Counter64
			MAX-ACCESS read-only
			STATUS current
			DESCRIPTION
				"Description."
			::= { ponPortPerformanceDataEntry 45 }

		
--          1.3.6.1.4.1.37950.1.1.5.10.1.2.3
-- 1.3.6.1.4.1.37950.1.1.5.10.1.2.3
-- 1.3.6.1.4.1.37950.1.1.5.10.1.2.3
-- 1.3.6.1.4.1.37950.1.1.5.10.1.2.3
-- 1.3.6.1.4.1.37950.1.1.5.10.1.2.3
-- 1.3.6.1.4.1.37950.1.1.5.10.1.2.3
-- 1.3.6.1.4.1.37950.1.1.5.10.1.2.3
-- 1.3.6.1.4.1.37950.1.1.5.10.1.2.3
-- 1.3.6.1.4.1.37950.1.1.5.10.1.2.3
		-- 1.3.6.1.4.1.37950.1.1.5.10.1.2.3
		ponPortLinkTable OBJECT-TYPE
			SYNTAX SEQUENCE OF PonPortLinkEntry
			MAX-ACCESS not-accessible
			STATUS current
			DESCRIPTION
				"Description."
			::= { ponPort 3 }

		
--          1.3.6.1.4.1.37950.1.1.5.10.1.2.3.1
-- 1.3.6.1.4.1.37950.1.1.5.10.1.2.3.1
-- 1.3.6.1.4.1.37950.1.1.5.10.1.2.3.1
-- 1.3.6.1.4.1.37950.1.1.5.10.1.2.3.1
-- 1.3.6.1.4.1.37950.1.1.5.10.1.2.3.1
-- 1.3.6.1.4.1.37950.1.1.5.10.1.2.3.1
-- 1.3.6.1.4.1.37950.1.1.5.10.1.2.3.1
-- 1.3.6.1.4.1.37950.1.1.5.10.1.2.3.1
-- 1.3.6.1.4.1.37950.1.1.5.10.1.2.3.1
		-- 1.3.6.1.4.1.37950.1.1.5.10.1.2.3.1
		ponPortLinkEntry OBJECT-TYPE
			SYNTAX PonPortLinkEntry
			MAX-ACCESS not-accessible
			STATUS current
			DESCRIPTION
				"Description."
			INDEX { ponPortLinkIndex }
			::= { ponPortLinkTable 1 }

		
		PonPortLinkEntry ::=
			SEQUENCE { 
				ponPortLinkIndex
					INTEGER,
				ponPortLinkStatus
					INTEGER,
				ponPortLinkSpeed
					OCTET STRING
			 }

--          1.3.6.1.4.1.37950.1.1.5.10.1.2.3.1.1
-- 1.3.6.1.4.1.37950.1.1.5.10.1.2.3.1.1
-- 1.3.6.1.4.1.37950.1.1.5.10.1.2.3.1.1
-- 1.3.6.1.4.1.37950.1.1.5.10.1.2.3.1.1
-- 1.3.6.1.4.1.37950.1.1.5.10.1.2.3.1.1
-- 1.3.6.1.4.1.37950.1.1.5.10.1.2.3.1.1
-- 1.3.6.1.4.1.37950.1.1.5.10.1.2.3.1.1
-- 1.3.6.1.4.1.37950.1.1.5.10.1.2.3.1.1
-- 1.3.6.1.4.1.37950.1.1.5.10.1.2.3.1.1
		-- 1.3.6.1.4.1.37950.1.1.5.10.1.2.3.1.1
		ponPortLinkIndex OBJECT-TYPE
			SYNTAX INTEGER (1..16)
			MAX-ACCESS read-only
			STATUS current
			DESCRIPTION
				"Description."
			::= { ponPortLinkEntry 1 }

		
--          1.3.6.1.4.1.37950.1.1.5.10.1.2.3.1.2
-- 1.3.6.1.4.1.37950.1.1.5.10.1.2.3.1.2
-- 1.3.6.1.4.1.37950.1.1.5.10.1.2.3.1.2
-- 1.3.6.1.4.1.37950.1.1.5.10.1.2.3.1.2
-- 1.3.6.1.4.1.37950.1.1.5.10.1.2.3.1.2
-- 1.3.6.1.4.1.37950.1.1.5.10.1.2.3.1.2
-- 1.3.6.1.4.1.37950.1.1.5.10.1.2.3.1.2
-- 1.3.6.1.4.1.37950.1.1.5.10.1.2.3.1.2
-- 1.3.6.1.4.1.37950.1.1.5.10.1.2.3.1.2
		-- 1.3.6.1.4.1.37950.1.1.5.10.1.2.3.1.2
		ponPortLinkStatus OBJECT-TYPE
			SYNTAX INTEGER
				{
				down(0),
				up(1)
				}
			MAX-ACCESS read-only
			STATUS current
			DESCRIPTION
				"Description."
			::= { ponPortLinkEntry 2 }

		
--          1.3.6.1.4.1.37950.1.1.5.10.1.2.3.1.3
-- 1.3.6.1.4.1.37950.1.1.5.10.1.2.3.1.3
-- 1.3.6.1.4.1.37950.1.1.5.10.1.2.3.1.3
-- 1.3.6.1.4.1.37950.1.1.5.10.1.2.3.1.3
-- 1.3.6.1.4.1.37950.1.1.5.10.1.2.3.1.3
-- 1.3.6.1.4.1.37950.1.1.5.10.1.2.3.1.3
-- 1.3.6.1.4.1.37950.1.1.5.10.1.2.3.1.3
-- 1.3.6.1.4.1.37950.1.1.5.10.1.2.3.1.3
-- 1.3.6.1.4.1.37950.1.1.5.10.1.2.3.1.3
		-- 1.3.6.1.4.1.37950.1.1.5.10.1.2.3.1.3
		ponPortLinkSpeed OBJECT-TYPE
			SYNTAX OCTET STRING
			MAX-ACCESS read-only
			STATUS current
			DESCRIPTION
				"Description."
			::= { ponPortLinkEntry 3 }

		
--          1.3.6.1.4.1.37950.1.1.5.10.1.2.4
-- 1.3.6.1.4.1.37950.1.1.5.10.1.2.4
-- 1.3.6.1.4.1.37950.1.1.5.10.1.2.4
-- 1.3.6.1.4.1.37950.1.1.5.10.1.2.4
-- 1.3.6.1.4.1.37950.1.1.5.10.1.2.4
-- 1.3.6.1.4.1.37950.1.1.5.10.1.2.4
-- 1.3.6.1.4.1.37950.1.1.5.10.1.2.4
-- 1.3.6.1.4.1.37950.1.1.5.10.1.2.4
-- 1.3.6.1.4.1.37950.1.1.5.10.1.2.4
		-- 1.3.6.1.4.1.37950.1.1.5.10.1.2.4
		ponConfigTable OBJECT-TYPE
			SYNTAX SEQUENCE OF PonConfigEntry
			MAX-ACCESS not-accessible
			STATUS current
			DESCRIPTION
				"Description."
			::= { ponPort 4 }

		
--          1.3.6.1.4.1.37950.1.1.5.10.1.2.4.1
-- 1.3.6.1.4.1.37950.1.1.5.10.1.2.4.1
-- 1.3.6.1.4.1.37950.1.1.5.10.1.2.4.1
-- 1.3.6.1.4.1.37950.1.1.5.10.1.2.4.1
-- 1.3.6.1.4.1.37950.1.1.5.10.1.2.4.1
-- 1.3.6.1.4.1.37950.1.1.5.10.1.2.4.1
-- 1.3.6.1.4.1.37950.1.1.5.10.1.2.4.1
-- 1.3.6.1.4.1.37950.1.1.5.10.1.2.4.1
-- 1.3.6.1.4.1.37950.1.1.5.10.1.2.4.1
		-- 1.3.6.1.4.1.37950.1.1.5.10.1.2.4.1
		ponConfigEntry OBJECT-TYPE
			SYNTAX PonConfigEntry
			MAX-ACCESS not-accessible
			STATUS current
			DESCRIPTION
				"Description."
			INDEX { ponIndex }
			::= { ponConfigTable 1 }

		
		PonConfigEntry ::=
			SEQUENCE { 
				ponIndex
					INTEGER,
				ponStauts
					INTEGER,
				ponEncrytionTime
					INTEGER,
				ponMaxRtt
					INTEGER,
				ponP2pEnable
					INTEGER
			 }

--          1.3.6.1.4.1.37950.1.1.5.10.1.2.4.1.1
-- 1.3.6.1.4.1.37950.1.1.5.10.1.2.4.1.1
-- 1.3.6.1.4.1.37950.1.1.5.10.1.2.4.1.1
-- 1.3.6.1.4.1.37950.1.1.5.10.1.2.4.1.1
-- 1.3.6.1.4.1.37950.1.1.5.10.1.2.4.1.1
-- 1.3.6.1.4.1.37950.1.1.5.10.1.2.4.1.1
-- 1.3.6.1.4.1.37950.1.1.5.10.1.2.4.1.1
-- 1.3.6.1.4.1.37950.1.1.5.10.1.2.4.1.1
-- 1.3.6.1.4.1.37950.1.1.5.10.1.2.4.1.1
		-- 1.3.6.1.4.1.37950.1.1.5.10.1.2.4.1.1
		ponIndex OBJECT-TYPE
			SYNTAX INTEGER (1..16)
			MAX-ACCESS read-write
			STATUS current
			DESCRIPTION
				"Description."
			::= { ponConfigEntry 1 }

		
--          1.3.6.1.4.1.37950.1.1.5.10.1.2.4.1.2
-- 1.3.6.1.4.1.37950.1.1.5.10.1.2.4.1.2
-- 1.3.6.1.4.1.37950.1.1.5.10.1.2.4.1.2
-- 1.3.6.1.4.1.37950.1.1.5.10.1.2.4.1.2
-- 1.3.6.1.4.1.37950.1.1.5.10.1.2.4.1.2
-- 1.3.6.1.4.1.37950.1.1.5.10.1.2.4.1.2
-- 1.3.6.1.4.1.37950.1.1.5.10.1.2.4.1.2
-- 1.3.6.1.4.1.37950.1.1.5.10.1.2.4.1.2
-- 1.3.6.1.4.1.37950.1.1.5.10.1.2.4.1.2
		-- 1.3.6.1.4.1.37950.1.1.5.10.1.2.4.1.2
		ponStauts OBJECT-TYPE
			SYNTAX INTEGER
				{
				disable(0),
				enable(1)
				}
			MAX-ACCESS read-write
			STATUS current
			DESCRIPTION
				"Description."
			::= { ponConfigEntry 2 }

		
--          1.3.6.1.4.1.37950.1.1.5.10.1.2.4.1.3
-- 1.3.6.1.4.1.37950.1.1.5.10.1.2.4.1.3
-- 1.3.6.1.4.1.37950.1.1.5.10.1.2.4.1.3
-- 1.3.6.1.4.1.37950.1.1.5.10.1.2.4.1.3
-- 1.3.6.1.4.1.37950.1.1.5.10.1.2.4.1.3
-- 1.3.6.1.4.1.37950.1.1.5.10.1.2.4.1.3
-- 1.3.6.1.4.1.37950.1.1.5.10.1.2.4.1.3
-- 1.3.6.1.4.1.37950.1.1.5.10.1.2.4.1.3
-- 1.3.6.1.4.1.37950.1.1.5.10.1.2.4.1.3
		-- 1.3.6.1.4.1.37950.1.1.5.10.1.2.4.1.3
		ponEncrytionTime OBJECT-TYPE
			SYNTAX INTEGER (0 | 774..786426)
			MAX-ACCESS read-write
			STATUS current
			DESCRIPTION
				"Description."
			::= { ponConfigEntry 3 }

		
--          1.3.6.1.4.1.37950.1.1.5.10.1.2.4.1.4
-- 1.3.6.1.4.1.37950.1.1.5.10.1.2.4.1.4
-- 1.3.6.1.4.1.37950.1.1.5.10.1.2.4.1.4
-- 1.3.6.1.4.1.37950.1.1.5.10.1.2.4.1.4
-- 1.3.6.1.4.1.37950.1.1.5.10.1.2.4.1.4
-- 1.3.6.1.4.1.37950.1.1.5.10.1.2.4.1.4
-- 1.3.6.1.4.1.37950.1.1.5.10.1.2.4.1.4
-- 1.3.6.1.4.1.37950.1.1.5.10.1.2.4.1.4
-- 1.3.6.1.4.1.37950.1.1.5.10.1.2.4.1.4
		-- 1.3.6.1.4.1.37950.1.1.5.10.1.2.4.1.4
		ponMaxRtt OBJECT-TYPE
			SYNTAX INTEGER (2000..32000)
			MAX-ACCESS read-write
			STATUS current
			DESCRIPTION
				"Description."
			::= { ponConfigEntry 4 }

		
--          1.3.6.1.4.1.37950.1.1.5.10.1.2.4.1.5
-- 1.3.6.1.4.1.37950.1.1.5.10.1.2.4.1.5
-- 1.3.6.1.4.1.37950.1.1.5.10.1.2.4.1.5
-- 1.3.6.1.4.1.37950.1.1.5.10.1.2.4.1.5
-- 1.3.6.1.4.1.37950.1.1.5.10.1.2.4.1.5
-- 1.3.6.1.4.1.37950.1.1.5.10.1.2.4.1.5
-- 1.3.6.1.4.1.37950.1.1.5.10.1.2.4.1.5
-- 1.3.6.1.4.1.37950.1.1.5.10.1.2.4.1.5
-- 1.3.6.1.4.1.37950.1.1.5.10.1.2.4.1.5
		-- 1.3.6.1.4.1.37950.1.1.5.10.1.2.4.1.5
		ponP2pEnable OBJECT-TYPE
			SYNTAX INTEGER
				{
				disable(0),
				enable(1)
				}
			MAX-ACCESS read-write
			STATUS current
			DESCRIPTION
				"Description."
			::= { ponConfigEntry 5 }

		
--          1.3.6.1.4.1.37950.1.1.5.10.1.3
-- 1.3.6.1.4.1.37950.1.1.5.10.1.3
-- 1.3.6.1.4.1.37950.1.1.5.10.1.3
-- 1.3.6.1.4.1.37950.1.1.5.10.1.3
-- 1.3.6.1.4.1.37950.1.1.5.10.1.3
-- 1.3.6.1.4.1.37950.1.1.5.10.1.3
-- 1.3.6.1.4.1.37950.1.1.5.10.1.3
-- 1.3.6.1.4.1.37950.1.1.5.10.1.3
-- 1.3.6.1.4.1.37950.1.1.5.10.1.3
		-- 1.3.6.1.4.1.37950.1.1.5.10.1.3
		portMirror OBJECT IDENTIFIER ::= { v1600dPort 3 }

		
--          1.3.6.1.4.1.37950.1.1.5.10.1.3.1
-- 1.3.6.1.4.1.37950.1.1.5.10.1.3.1
-- 1.3.6.1.4.1.37950.1.1.5.10.1.3.1
-- 1.3.6.1.4.1.37950.1.1.5.10.1.3.1
-- 1.3.6.1.4.1.37950.1.1.5.10.1.3.1
-- 1.3.6.1.4.1.37950.1.1.5.10.1.3.1
-- 1.3.6.1.4.1.37950.1.1.5.10.1.3.1
-- 1.3.6.1.4.1.37950.1.1.5.10.1.3.1
-- 1.3.6.1.4.1.37950.1.1.5.10.1.3.1
		-- 1.3.6.1.4.1.37950.1.1.5.10.1.3.1
		mirrorSession OBJECT-TYPE
			SYNTAX INTEGER (1..4)
			MAX-ACCESS read-write
			STATUS current
			DESCRIPTION
				"Description."
			::= { portMirror 1 }

		
--          1.3.6.1.4.1.37950.1.1.5.10.1.3.2
-- 1.3.6.1.4.1.37950.1.1.5.10.1.3.2
-- 1.3.6.1.4.1.37950.1.1.5.10.1.3.2
-- 1.3.6.1.4.1.37950.1.1.5.10.1.3.2
-- 1.3.6.1.4.1.37950.1.1.5.10.1.3.2
-- 1.3.6.1.4.1.37950.1.1.5.10.1.3.2
-- 1.3.6.1.4.1.37950.1.1.5.10.1.3.2
-- 1.3.6.1.4.1.37950.1.1.5.10.1.3.2
-- 1.3.6.1.4.1.37950.1.1.5.10.1.3.2
		-- 1.3.6.1.4.1.37950.1.1.5.10.1.3.2
		mirrorDstPort OBJECT-TYPE
			SYNTAX INTEGER (1..28)
			MAX-ACCESS read-write
			STATUS current
			DESCRIPTION
				"Description."
			::= { portMirror 2 }

		
--          1.3.6.1.4.1.37950.1.1.5.10.1.3.3
-- 1.3.6.1.4.1.37950.1.1.5.10.1.3.3
-- 1.3.6.1.4.1.37950.1.1.5.10.1.3.3
-- 1.3.6.1.4.1.37950.1.1.5.10.1.3.3
-- 1.3.6.1.4.1.37950.1.1.5.10.1.3.3
-- 1.3.6.1.4.1.37950.1.1.5.10.1.3.3
-- 1.3.6.1.4.1.37950.1.1.5.10.1.3.3
-- 1.3.6.1.4.1.37950.1.1.5.10.1.3.3
-- 1.3.6.1.4.1.37950.1.1.5.10.1.3.3
		-- 1.3.6.1.4.1.37950.1.1.5.10.1.3.3
		mirrorSrcPort OBJECT-TYPE
			SYNTAX INTEGER (1..28)
			MAX-ACCESS read-write
			STATUS current
			DESCRIPTION
				"Description."
			::= { portMirror 3 }

		
--          1.3.6.1.4.1.37950.1.1.5.10.1.3.4
-- 1.3.6.1.4.1.37950.1.1.5.10.1.3.4
-- 1.3.6.1.4.1.37950.1.1.5.10.1.3.4
-- 1.3.6.1.4.1.37950.1.1.5.10.1.3.4
-- 1.3.6.1.4.1.37950.1.1.5.10.1.3.4
-- 1.3.6.1.4.1.37950.1.1.5.10.1.3.4
-- 1.3.6.1.4.1.37950.1.1.5.10.1.3.4
-- 1.3.6.1.4.1.37950.1.1.5.10.1.3.4
-- 1.3.6.1.4.1.37950.1.1.5.10.1.3.4
		-- 1.3.6.1.4.1.37950.1.1.5.10.1.3.4
		mirrorType OBJECT-TYPE
			SYNTAX INTEGER
				{
				both(1),
				rx(2),
				tx(3)
				}
			MAX-ACCESS read-write
			STATUS current
			DESCRIPTION
				"Description."
			::= { portMirror 4 }

		
--          1.3.6.1.4.1.37950.1.1.5.10.1.3.5
-- 1.3.6.1.4.1.37950.1.1.5.10.1.3.5
-- 1.3.6.1.4.1.37950.1.1.5.10.1.3.5
-- 1.3.6.1.4.1.37950.1.1.5.10.1.3.5
-- 1.3.6.1.4.1.37950.1.1.5.10.1.3.5
-- 1.3.6.1.4.1.37950.1.1.5.10.1.3.5
-- 1.3.6.1.4.1.37950.1.1.5.10.1.3.5
-- 1.3.6.1.4.1.37950.1.1.5.10.1.3.5
-- 1.3.6.1.4.1.37950.1.1.5.10.1.3.5
		-- 1.3.6.1.4.1.37950.1.1.5.10.1.3.5
		mirrorAction OBJECT-TYPE
			SYNTAX INTEGER
				{
				add(1),
				delete(2),
				clear(3),
				clearAll(4)
				}
			MAX-ACCESS read-write
			STATUS current
			DESCRIPTION
				"Description."
			::= { portMirror 5 }

		
--          1.3.6.1.4.1.37950.1.1.5.10.1.4
-- 1.3.6.1.4.1.37950.1.1.5.10.1.4
-- 1.3.6.1.4.1.37950.1.1.5.10.1.4
-- 1.3.6.1.4.1.37950.1.1.5.10.1.4
-- 1.3.6.1.4.1.37950.1.1.5.10.1.4
-- 1.3.6.1.4.1.37950.1.1.5.10.1.4
-- 1.3.6.1.4.1.37950.1.1.5.10.1.4
-- 1.3.6.1.4.1.37950.1.1.5.10.1.4
-- 1.3.6.1.4.1.37950.1.1.5.10.1.4
		-- 1.3.6.1.4.1.37950.1.1.5.10.1.4
		portMirrorTable OBJECT-TYPE
			SYNTAX SEQUENCE OF PortMirrorEntry
			MAX-ACCESS not-accessible
			STATUS current
			DESCRIPTION
				"Description."
			::= { v1600dPort 4 }

		
--          1.3.6.1.4.1.37950.1.1.5.10.1.4.1
-- 1.3.6.1.4.1.37950.1.1.5.10.1.4.1
-- 1.3.6.1.4.1.37950.1.1.5.10.1.4.1
-- 1.3.6.1.4.1.37950.1.1.5.10.1.4.1
-- 1.3.6.1.4.1.37950.1.1.5.10.1.4.1
-- 1.3.6.1.4.1.37950.1.1.5.10.1.4.1
-- 1.3.6.1.4.1.37950.1.1.5.10.1.4.1
-- 1.3.6.1.4.1.37950.1.1.5.10.1.4.1
-- 1.3.6.1.4.1.37950.1.1.5.10.1.4.1
		-- 1.3.6.1.4.1.37950.1.1.5.10.1.4.1
		portMirrorEntry OBJECT-TYPE
			SYNTAX PortMirrorEntry
			MAX-ACCESS not-accessible
			STATUS current
			DESCRIPTION
				"Description."
			INDEX { portMirrorIndex }
			::= { portMirrorTable 1 }

		
		PortMirrorEntry ::=
			SEQUENCE { 
				portMirrorIndex
					INTEGER,
				portMirrorsession
					INTEGER,
				portMirrorDstPort
					Integer32,
				portMirrorSrcPort
					Integer32,
				portMirrorType
					INTEGER
			 }

--          1.3.6.1.4.1.37950.1.1.5.10.1.4.1.1
-- 1.3.6.1.4.1.37950.1.1.5.10.1.4.1.1
-- 1.3.6.1.4.1.37950.1.1.5.10.1.4.1.1
-- 1.3.6.1.4.1.37950.1.1.5.10.1.4.1.1
-- 1.3.6.1.4.1.37950.1.1.5.10.1.4.1.1
-- 1.3.6.1.4.1.37950.1.1.5.10.1.4.1.1
-- 1.3.6.1.4.1.37950.1.1.5.10.1.4.1.1
-- 1.3.6.1.4.1.37950.1.1.5.10.1.4.1.1
-- 1.3.6.1.4.1.37950.1.1.5.10.1.4.1.1
		-- 1.3.6.1.4.1.37950.1.1.5.10.1.4.1.1
		portMirrorIndex OBJECT-TYPE
			SYNTAX INTEGER (1..16)
			MAX-ACCESS read-only
			STATUS current
			DESCRIPTION
				"Description."
			::= { portMirrorEntry 1 }

		
--          1.3.6.1.4.1.37950.1.1.5.10.1.4.1.2
-- 1.3.6.1.4.1.37950.1.1.5.10.1.4.1.2
-- 1.3.6.1.4.1.37950.1.1.5.10.1.4.1.2
-- 1.3.6.1.4.1.37950.1.1.5.10.1.4.1.2
-- 1.3.6.1.4.1.37950.1.1.5.10.1.4.1.2
-- 1.3.6.1.4.1.37950.1.1.5.10.1.4.1.2
-- 1.3.6.1.4.1.37950.1.1.5.10.1.4.1.2
-- 1.3.6.1.4.1.37950.1.1.5.10.1.4.1.2
-- 1.3.6.1.4.1.37950.1.1.5.10.1.4.1.2
		-- 1.3.6.1.4.1.37950.1.1.5.10.1.4.1.2
		portMirrorsession OBJECT-TYPE
			SYNTAX INTEGER (1..4)
			MAX-ACCESS read-only
			STATUS current
			DESCRIPTION
				"Description."
			::= { portMirrorEntry 2 }

		
--          1.3.6.1.4.1.37950.1.1.5.10.1.4.1.3
-- 1.3.6.1.4.1.37950.1.1.5.10.1.4.1.3
-- 1.3.6.1.4.1.37950.1.1.5.10.1.4.1.3
-- 1.3.6.1.4.1.37950.1.1.5.10.1.4.1.3
-- 1.3.6.1.4.1.37950.1.1.5.10.1.4.1.3
-- 1.3.6.1.4.1.37950.1.1.5.10.1.4.1.3
-- 1.3.6.1.4.1.37950.1.1.5.10.1.4.1.3
-- 1.3.6.1.4.1.37950.1.1.5.10.1.4.1.3
-- 1.3.6.1.4.1.37950.1.1.5.10.1.4.1.3
		-- 1.3.6.1.4.1.37950.1.1.5.10.1.4.1.3
		portMirrorDstPort OBJECT-TYPE
			SYNTAX Integer32
			MAX-ACCESS read-only
			STATUS current
			DESCRIPTION
				"Description."
			::= { portMirrorEntry 3 }

		
--          1.3.6.1.4.1.37950.1.1.5.10.1.4.1.4
-- 1.3.6.1.4.1.37950.1.1.5.10.1.4.1.4
-- 1.3.6.1.4.1.37950.1.1.5.10.1.4.1.4
-- 1.3.6.1.4.1.37950.1.1.5.10.1.4.1.4
-- 1.3.6.1.4.1.37950.1.1.5.10.1.4.1.4
-- 1.3.6.1.4.1.37950.1.1.5.10.1.4.1.4
-- 1.3.6.1.4.1.37950.1.1.5.10.1.4.1.4
-- 1.3.6.1.4.1.37950.1.1.5.10.1.4.1.4
-- 1.3.6.1.4.1.37950.1.1.5.10.1.4.1.4
		-- 1.3.6.1.4.1.37950.1.1.5.10.1.4.1.4
		portMirrorSrcPort OBJECT-TYPE
			SYNTAX Integer32
			MAX-ACCESS read-only
			STATUS current
			DESCRIPTION
				"Description."
			::= { portMirrorEntry 4 }

		
--          1.3.6.1.4.1.37950.1.1.5.10.1.4.1.5
-- 1.3.6.1.4.1.37950.1.1.5.10.1.4.1.5
-- 1.3.6.1.4.1.37950.1.1.5.10.1.4.1.5
-- 1.3.6.1.4.1.37950.1.1.5.10.1.4.1.5
-- 1.3.6.1.4.1.37950.1.1.5.10.1.4.1.5
-- 1.3.6.1.4.1.37950.1.1.5.10.1.4.1.5
-- 1.3.6.1.4.1.37950.1.1.5.10.1.4.1.5
-- 1.3.6.1.4.1.37950.1.1.5.10.1.4.1.5
-- 1.3.6.1.4.1.37950.1.1.5.10.1.4.1.5
		-- 1.3.6.1.4.1.37950.1.1.5.10.1.4.1.5
		portMirrorType OBJECT-TYPE
			SYNTAX INTEGER
				{
				both(1),
				rx(2),
				tx(3)
				}
			MAX-ACCESS read-write
			STATUS current
			DESCRIPTION
				"Description."
			::= { portMirrorEntry 5 }

		
--          1.3.6.1.4.1.37950.1.1.5.10.1.5
-- 1.3.6.1.4.1.37950.1.1.5.10.1.5
-- 1.3.6.1.4.1.37950.1.1.5.10.1.5
-- 1.3.6.1.4.1.37950.1.1.5.10.1.5
-- 1.3.6.1.4.1.37950.1.1.5.10.1.5
-- 1.3.6.1.4.1.37950.1.1.5.10.1.5
-- 1.3.6.1.4.1.37950.1.1.5.10.1.5
-- 1.3.6.1.4.1.37950.1.1.5.10.1.5
-- 1.3.6.1.4.1.37950.1.1.5.10.1.5
		-- 1.3.6.1.4.1.37950.1.1.5.10.1.5
		portCountersClear OBJECT-TYPE
			SYNTAX INTEGER { clear(1) }
			MAX-ACCESS read-write
			STATUS current
			DESCRIPTION
				"Description."
			::= { v1600dPort 5 }

		
--          1.3.6.1.4.1.37950.1.1.5.10.1.6
-- 1.3.6.1.4.1.37950.1.1.5.10.1.6
-- 1.3.6.1.4.1.37950.1.1.5.10.1.6
-- 1.3.6.1.4.1.37950.1.1.5.10.1.6
-- 1.3.6.1.4.1.37950.1.1.5.10.1.6
-- 1.3.6.1.4.1.37950.1.1.5.10.1.6
-- 1.3.6.1.4.1.37950.1.1.5.10.1.6
-- 1.3.6.1.4.1.37950.1.1.5.10.1.6
-- 1.3.6.1.4.1.37950.1.1.5.10.1.6
		-- 1.3.6.1.4.1.37950.1.1.5.10.1.6
		portLookbackDetect OBJECT-TYPE
			SYNTAX INTEGER
				{
				disable(0),
				enable(1)
				}
			MAX-ACCESS read-write
			STATUS current
			DESCRIPTION
				"Description."
			::= { v1600dPort 6 }

		
--          1.3.6.1.4.1.37950.1.1.5.10.1.7
-- 1.3.6.1.4.1.37950.1.1.5.10.1.7
-- 1.3.6.1.4.1.37950.1.1.5.10.1.7
-- 1.3.6.1.4.1.37950.1.1.5.10.1.7
-- 1.3.6.1.4.1.37950.1.1.5.10.1.7
-- 1.3.6.1.4.1.37950.1.1.5.10.1.7
-- 1.3.6.1.4.1.37950.1.1.5.10.1.7
-- 1.3.6.1.4.1.37950.1.1.5.10.1.7
-- 1.3.6.1.4.1.37950.1.1.5.10.1.7
		-- 1.3.6.1.4.1.37950.1.1.5.10.1.7
		portChannelGroup OBJECT IDENTIFIER ::= { v1600dPort 7 }

		
--          1.3.6.1.4.1.37950.1.1.5.10.1.7.1
-- 1.3.6.1.4.1.37950.1.1.5.10.1.7.1
-- 1.3.6.1.4.1.37950.1.1.5.10.1.7.1
-- 1.3.6.1.4.1.37950.1.1.5.10.1.7.1
-- 1.3.6.1.4.1.37950.1.1.5.10.1.7.1
-- 1.3.6.1.4.1.37950.1.1.5.10.1.7.1
-- 1.3.6.1.4.1.37950.1.1.5.10.1.7.1
-- 1.3.6.1.4.1.37950.1.1.5.10.1.7.1
-- 1.3.6.1.4.1.37950.1.1.5.10.1.7.1
		-- 1.3.6.1.4.1.37950.1.1.5.10.1.7.1
		portChannelGroupCfg OBJECT IDENTIFIER ::= { portChannelGroup 1 }

		
--          1.3.6.1.4.1.37950.1.1.5.10.1.7.1.1
-- 1.3.6.1.4.1.37950.1.1.5.10.1.7.1.1
-- 1.3.6.1.4.1.37950.1.1.5.10.1.7.1.1
-- 1.3.6.1.4.1.37950.1.1.5.10.1.7.1.1
-- 1.3.6.1.4.1.37950.1.1.5.10.1.7.1.1
-- 1.3.6.1.4.1.37950.1.1.5.10.1.7.1.1
-- 1.3.6.1.4.1.37950.1.1.5.10.1.7.1.1
-- 1.3.6.1.4.1.37950.1.1.5.10.1.7.1.1
-- 1.3.6.1.4.1.37950.1.1.5.10.1.7.1.1
		-- 1.3.6.1.4.1.37950.1.1.5.10.1.7.1.1
		portChannelGroupIndex OBJECT-TYPE
			SYNTAX Integer32 (1..16)
			MAX-ACCESS read-write
			STATUS current
			DESCRIPTION
				"Description."
			::= { portChannelGroupCfg 1 }

		
--          1.3.6.1.4.1.37950.1.1.5.10.1.7.1.2
-- 1.3.6.1.4.1.37950.1.1.5.10.1.7.1.2
-- 1.3.6.1.4.1.37950.1.1.5.10.1.7.1.2
-- 1.3.6.1.4.1.37950.1.1.5.10.1.7.1.2
-- 1.3.6.1.4.1.37950.1.1.5.10.1.7.1.2
-- 1.3.6.1.4.1.37950.1.1.5.10.1.7.1.2
-- 1.3.6.1.4.1.37950.1.1.5.10.1.7.1.2
-- 1.3.6.1.4.1.37950.1.1.5.10.1.7.1.2
-- 1.3.6.1.4.1.37950.1.1.5.10.1.7.1.2
		-- 1.3.6.1.4.1.37950.1.1.5.10.1.7.1.2
		portChannelLoadBalance OBJECT-TYPE
			SYNTAX INTEGER
				{
				smac(1),
				dmac(2),
				sdmac(3),
				sip(4),
				dip(5),
				sdip(6)
				}
			MAX-ACCESS read-write
			STATUS current
			DESCRIPTION
				"Description."
			::= { portChannelGroupCfg 2 }

		
--          1.3.6.1.4.1.37950.1.1.5.10.1.7.1.3
-- 1.3.6.1.4.1.37950.1.1.5.10.1.7.1.3
-- 1.3.6.1.4.1.37950.1.1.5.10.1.7.1.3
-- 1.3.6.1.4.1.37950.1.1.5.10.1.7.1.3
-- 1.3.6.1.4.1.37950.1.1.5.10.1.7.1.3
-- 1.3.6.1.4.1.37950.1.1.5.10.1.7.1.3
-- 1.3.6.1.4.1.37950.1.1.5.10.1.7.1.3
-- 1.3.6.1.4.1.37950.1.1.5.10.1.7.1.3
-- 1.3.6.1.4.1.37950.1.1.5.10.1.7.1.3
		-- 1.3.6.1.4.1.37950.1.1.5.10.1.7.1.3
		portChannelPortId1 OBJECT-TYPE
			SYNTAX INTEGER (0..16)
			MAX-ACCESS read-write
			STATUS current
			DESCRIPTION
				"Description."
			DEFVAL { 0 }
			::= { portChannelGroupCfg 3 }

		
--          1.3.6.1.4.1.37950.1.1.5.10.1.7.1.4
-- 1.3.6.1.4.1.37950.1.1.5.10.1.7.1.4
-- 1.3.6.1.4.1.37950.1.1.5.10.1.7.1.4
-- 1.3.6.1.4.1.37950.1.1.5.10.1.7.1.4
-- 1.3.6.1.4.1.37950.1.1.5.10.1.7.1.4
-- 1.3.6.1.4.1.37950.1.1.5.10.1.7.1.4
-- 1.3.6.1.4.1.37950.1.1.5.10.1.7.1.4
-- 1.3.6.1.4.1.37950.1.1.5.10.1.7.1.4
-- 1.3.6.1.4.1.37950.1.1.5.10.1.7.1.4
		-- 1.3.6.1.4.1.37950.1.1.5.10.1.7.1.4
		portChannelPortId2 OBJECT-TYPE
			SYNTAX INTEGER (0..16)
			MAX-ACCESS read-write
			STATUS current
			DESCRIPTION
				"Description."
			DEFVAL { 0 }
			::= { portChannelGroupCfg 4 }

		
--          1.3.6.1.4.1.37950.1.1.5.10.1.7.1.5
-- 1.3.6.1.4.1.37950.1.1.5.10.1.7.1.5
-- 1.3.6.1.4.1.37950.1.1.5.10.1.7.1.5
-- 1.3.6.1.4.1.37950.1.1.5.10.1.7.1.5
-- 1.3.6.1.4.1.37950.1.1.5.10.1.7.1.5
-- 1.3.6.1.4.1.37950.1.1.5.10.1.7.1.5
-- 1.3.6.1.4.1.37950.1.1.5.10.1.7.1.5
-- 1.3.6.1.4.1.37950.1.1.5.10.1.7.1.5
-- 1.3.6.1.4.1.37950.1.1.5.10.1.7.1.5
		-- 1.3.6.1.4.1.37950.1.1.5.10.1.7.1.5
		portChannelPortId3 OBJECT-TYPE
			SYNTAX INTEGER (0..16)
			MAX-ACCESS read-write
			STATUS current
			DESCRIPTION
				"Description."
			DEFVAL { 0 }
			::= { portChannelGroupCfg 5 }

		
--          1.3.6.1.4.1.37950.1.1.5.10.1.7.1.6
-- 1.3.6.1.4.1.37950.1.1.5.10.1.7.1.6
-- 1.3.6.1.4.1.37950.1.1.5.10.1.7.1.6
-- 1.3.6.1.4.1.37950.1.1.5.10.1.7.1.6
-- 1.3.6.1.4.1.37950.1.1.5.10.1.7.1.6
-- 1.3.6.1.4.1.37950.1.1.5.10.1.7.1.6
-- 1.3.6.1.4.1.37950.1.1.5.10.1.7.1.6
-- 1.3.6.1.4.1.37950.1.1.5.10.1.7.1.6
-- 1.3.6.1.4.1.37950.1.1.5.10.1.7.1.6
		-- 1.3.6.1.4.1.37950.1.1.5.10.1.7.1.6
		portChannelPortId4 OBJECT-TYPE
			SYNTAX INTEGER (0..16)
			MAX-ACCESS read-write
			STATUS current
			DESCRIPTION
				"Description."
			DEFVAL { 0 }
			::= { portChannelGroupCfg 6 }

		
--          1.3.6.1.4.1.37950.1.1.5.10.1.7.1.7
-- 1.3.6.1.4.1.37950.1.1.5.10.1.7.1.7
-- 1.3.6.1.4.1.37950.1.1.5.10.1.7.1.7
-- 1.3.6.1.4.1.37950.1.1.5.10.1.7.1.7
-- 1.3.6.1.4.1.37950.1.1.5.10.1.7.1.7
-- 1.3.6.1.4.1.37950.1.1.5.10.1.7.1.7
-- 1.3.6.1.4.1.37950.1.1.5.10.1.7.1.7
-- 1.3.6.1.4.1.37950.1.1.5.10.1.7.1.7
-- 1.3.6.1.4.1.37950.1.1.5.10.1.7.1.7
		-- 1.3.6.1.4.1.37950.1.1.5.10.1.7.1.7
		portChannelAction OBJECT-TYPE
			SYNTAX INTEGER
				{
				create(1),
				delete(2)
				}
			MAX-ACCESS read-write
			STATUS current
			DESCRIPTION
				"Description."
			::= { portChannelGroupCfg 7 }

		
--         1.3.6.1.4.1.37950.1.1.5.10.1.7.1.8
-- 1.3.6.1.4.1.37950.1.1.5.10.1.7.1.8
-- 1.3.6.1.4.1.37950.1.1.5.10.1.7.1.8
-- 1.3.6.1.4.1.37950.1.1.5.10.1.7.1.8
-- 1.3.6.1.4.1.37950.1.1.5.10.1.7.1.8
-- 1.3.6.1.4.1.37950.1.1.5.10.1.7.1.8
-- 1.3.6.1.4.1.37950.1.1.5.10.1.7.1.8
-- 1.3.6.1.4.1.37950.1.1.5.10.1.7.1.8
		-- 1.3.6.1.4.1.37950.1.1.5.10.1.7.1.8
		portChannelType OBJECT-TYPE
			SYNTAX INTEGER
				{
				manual(0),
				static(1),
				dynamic(2)
				}
			MAX-ACCESS read-write
			STATUS current
			DESCRIPTION
				"Description."
			::= { portChannelGroupCfg 8 }

		
--          1.3.6.1.4.1.37950.1.1.5.10.1.7.2
-- 1.3.6.1.4.1.37950.1.1.5.10.1.7.2
-- 1.3.6.1.4.1.37950.1.1.5.10.1.7.2
-- 1.3.6.1.4.1.37950.1.1.5.10.1.7.2
-- 1.3.6.1.4.1.37950.1.1.5.10.1.7.2
-- 1.3.6.1.4.1.37950.1.1.5.10.1.7.2
-- 1.3.6.1.4.1.37950.1.1.5.10.1.7.2
-- 1.3.6.1.4.1.37950.1.1.5.10.1.7.2
-- 1.3.6.1.4.1.37950.1.1.5.10.1.7.2
		-- 1.3.6.1.4.1.37950.1.1.5.10.1.7.2
		portChannelGroupTable OBJECT-TYPE
			SYNTAX SEQUENCE OF PortChannelGroupEntry
			MAX-ACCESS not-accessible
			STATUS current
			DESCRIPTION
				"Description."
			::= { portChannelGroup 2 }

		
--          1.3.6.1.4.1.37950.1.1.5.10.1.7.2.1
-- 1.3.6.1.4.1.37950.1.1.5.10.1.7.2.1
-- 1.3.6.1.4.1.37950.1.1.5.10.1.7.2.1
-- 1.3.6.1.4.1.37950.1.1.5.10.1.7.2.1
-- 1.3.6.1.4.1.37950.1.1.5.10.1.7.2.1
-- 1.3.6.1.4.1.37950.1.1.5.10.1.7.2.1
-- 1.3.6.1.4.1.37950.1.1.5.10.1.7.2.1
-- 1.3.6.1.4.1.37950.1.1.5.10.1.7.2.1
-- 1.3.6.1.4.1.37950.1.1.5.10.1.7.2.1
		-- 1.3.6.1.4.1.37950.1.1.5.10.1.7.2.1
		portChannelGroupEntry OBJECT-TYPE
			SYNTAX PortChannelGroupEntry
			MAX-ACCESS not-accessible
			STATUS current
			DESCRIPTION
				"Description."
			INDEX { portChannelGroupId }
			::= { portChannelGroupTable 1 }

		
		PortChannelGroupEntry ::=
			SEQUENCE { 
				portChannelGroupId
					Integer32,
				portChannelGroupLoadBalance
					INTEGER,
				portChannelGroupPortIdx1
					Integer32,
				portChannelGroupPortIdx2
					INTEGER,
				portChannelGroupPortIdx3
					INTEGER,
				portChannelGroupPortIdx4
					INTEGER,
				portChannelGroupType
					INTEGER
			 }

--          1.3.6.1.4.1.37950.1.1.5.10.1.7.2.1.1
-- 1.3.6.1.4.1.37950.1.1.5.10.1.7.2.1.1
-- 1.3.6.1.4.1.37950.1.1.5.10.1.7.2.1.1
-- 1.3.6.1.4.1.37950.1.1.5.10.1.7.2.1.1
-- 1.3.6.1.4.1.37950.1.1.5.10.1.7.2.1.1
-- 1.3.6.1.4.1.37950.1.1.5.10.1.7.2.1.1
-- 1.3.6.1.4.1.37950.1.1.5.10.1.7.2.1.1
-- 1.3.6.1.4.1.37950.1.1.5.10.1.7.2.1.1
-- 1.3.6.1.4.1.37950.1.1.5.10.1.7.2.1.1
		-- 1.3.6.1.4.1.37950.1.1.5.10.1.7.2.1.1
		portChannelGroupId OBJECT-TYPE
			SYNTAX Integer32
			MAX-ACCESS read-only
			STATUS current
			DESCRIPTION
				"Description."
			::= { portChannelGroupEntry 1 }

		
--          1.3.6.1.4.1.37950.1.1.5.10.1.7.2.1.2
-- 1.3.6.1.4.1.37950.1.1.5.10.1.7.2.1.2
-- 1.3.6.1.4.1.37950.1.1.5.10.1.7.2.1.2
-- 1.3.6.1.4.1.37950.1.1.5.10.1.7.2.1.2
-- 1.3.6.1.4.1.37950.1.1.5.10.1.7.2.1.2
-- 1.3.6.1.4.1.37950.1.1.5.10.1.7.2.1.2
-- 1.3.6.1.4.1.37950.1.1.5.10.1.7.2.1.2
-- 1.3.6.1.4.1.37950.1.1.5.10.1.7.2.1.2
-- 1.3.6.1.4.1.37950.1.1.5.10.1.7.2.1.2
		-- 1.3.6.1.4.1.37950.1.1.5.10.1.7.2.1.2
		portChannelGroupLoadBalance OBJECT-TYPE
			SYNTAX INTEGER
				{
				smac(1),
				dmac(2),
				sdmac(3),
				sip(4),
				dip(5),
				sdip(6)
				}
			MAX-ACCESS read-only
			STATUS current
			DESCRIPTION
				"Description."
			::= { portChannelGroupEntry 2 }

		
--          1.3.6.1.4.1.37950.1.1.5.10.1.7.2.1.3
-- 1.3.6.1.4.1.37950.1.1.5.10.1.7.2.1.3
-- 1.3.6.1.4.1.37950.1.1.5.10.1.7.2.1.3
-- 1.3.6.1.4.1.37950.1.1.5.10.1.7.2.1.3
-- 1.3.6.1.4.1.37950.1.1.5.10.1.7.2.1.3
-- 1.3.6.1.4.1.37950.1.1.5.10.1.7.2.1.3
-- 1.3.6.1.4.1.37950.1.1.5.10.1.7.2.1.3
-- 1.3.6.1.4.1.37950.1.1.5.10.1.7.2.1.3
-- 1.3.6.1.4.1.37950.1.1.5.10.1.7.2.1.3
		-- 1.3.6.1.4.1.37950.1.1.5.10.1.7.2.1.3
		portChannelGroupPortIdx1 OBJECT-TYPE
			SYNTAX Integer32 (0..16)
			MAX-ACCESS read-only
			STATUS current
			DESCRIPTION
				"Description."
			::= { portChannelGroupEntry 3 }

		
--          1.3.6.1.4.1.37950.1.1.5.10.1.7.2.1.4
-- 1.3.6.1.4.1.37950.1.1.5.10.1.7.2.1.4
-- 1.3.6.1.4.1.37950.1.1.5.10.1.7.2.1.4
-- 1.3.6.1.4.1.37950.1.1.5.10.1.7.2.1.4
-- 1.3.6.1.4.1.37950.1.1.5.10.1.7.2.1.4
-- 1.3.6.1.4.1.37950.1.1.5.10.1.7.2.1.4
-- 1.3.6.1.4.1.37950.1.1.5.10.1.7.2.1.4
-- 1.3.6.1.4.1.37950.1.1.5.10.1.7.2.1.4
-- 1.3.6.1.4.1.37950.1.1.5.10.1.7.2.1.4
		-- 1.3.6.1.4.1.37950.1.1.5.10.1.7.2.1.4
		portChannelGroupPortIdx2 OBJECT-TYPE
			SYNTAX INTEGER (0..16)
			MAX-ACCESS read-only
			STATUS current
			DESCRIPTION
				"Description."
			::= { portChannelGroupEntry 4 }

		
--          1.3.6.1.4.1.37950.1.1.5.10.1.7.2.1.5
-- 1.3.6.1.4.1.37950.1.1.5.10.1.7.2.1.5
-- 1.3.6.1.4.1.37950.1.1.5.10.1.7.2.1.5
-- 1.3.6.1.4.1.37950.1.1.5.10.1.7.2.1.5
-- 1.3.6.1.4.1.37950.1.1.5.10.1.7.2.1.5
-- 1.3.6.1.4.1.37950.1.1.5.10.1.7.2.1.5
-- 1.3.6.1.4.1.37950.1.1.5.10.1.7.2.1.5
-- 1.3.6.1.4.1.37950.1.1.5.10.1.7.2.1.5
-- 1.3.6.1.4.1.37950.1.1.5.10.1.7.2.1.5
		-- 1.3.6.1.4.1.37950.1.1.5.10.1.7.2.1.5
		portChannelGroupPortIdx3 OBJECT-TYPE
			SYNTAX INTEGER (0..16)
			MAX-ACCESS read-only
			STATUS current
			DESCRIPTION
				"Description."
			::= { portChannelGroupEntry 5 }

		
--          1.3.6.1.4.1.37950.1.1.5.10.1.7.2.1.6
-- 1.3.6.1.4.1.37950.1.1.5.10.1.7.2.1.6
-- 1.3.6.1.4.1.37950.1.1.5.10.1.7.2.1.6
-- 1.3.6.1.4.1.37950.1.1.5.10.1.7.2.1.6
-- 1.3.6.1.4.1.37950.1.1.5.10.1.7.2.1.6
-- 1.3.6.1.4.1.37950.1.1.5.10.1.7.2.1.6
-- 1.3.6.1.4.1.37950.1.1.5.10.1.7.2.1.6
-- 1.3.6.1.4.1.37950.1.1.5.10.1.7.2.1.6
-- 1.3.6.1.4.1.37950.1.1.5.10.1.7.2.1.6
		-- 1.3.6.1.4.1.37950.1.1.5.10.1.7.2.1.6
		portChannelGroupPortIdx4 OBJECT-TYPE
			SYNTAX INTEGER (0..16)
			MAX-ACCESS read-only
			STATUS current
			DESCRIPTION
				"Description."
			::= { portChannelGroupEntry 6 }

		
--         1.3.6.1.4.1.37950.1.1.5.10.1.7.2.1.7
-- 1.3.6.1.4.1.37950.1.1.5.10.1.7.2.1.7
-- 1.3.6.1.4.1.37950.1.1.5.10.1.7.2.1.7
-- 1.3.6.1.4.1.37950.1.1.5.10.1.7.2.1.7
-- 1.3.6.1.4.1.37950.1.1.5.10.1.7.2.1.7
-- 1.3.6.1.4.1.37950.1.1.5.10.1.7.2.1.7
-- 1.3.6.1.4.1.37950.1.1.5.10.1.7.2.1.7
-- 1.3.6.1.4.1.37950.1.1.5.10.1.7.2.1.7
		-- 1.3.6.1.4.1.37950.1.1.5.10.1.7.2.1.7
		portChannelGroupType OBJECT-TYPE
			SYNTAX INTEGER
				{
				manual(0),
				static(1),
				dynamic(2)
				}
			MAX-ACCESS read-only
			STATUS current
			DESCRIPTION
				"Description."
			::= { portChannelGroupEntry 7 }

		
--          1.3.6.1.4.1.37950.1.1.5.10.1.8
-- 1.3.6.1.4.1.37950.1.1.5.10.1.8
-- 1.3.6.1.4.1.37950.1.1.5.10.1.8
-- 1.3.6.1.4.1.37950.1.1.5.10.1.8
-- 1.3.6.1.4.1.37950.1.1.5.10.1.8
-- 1.3.6.1.4.1.37950.1.1.5.10.1.8
-- 1.3.6.1.4.1.37950.1.1.5.10.1.8
-- 1.3.6.1.4.1.37950.1.1.5.10.1.8
-- 1.3.6.1.4.1.37950.1.1.5.10.1.8
		-- 1.3.6.1.4.1.37950.1.1.5.10.1.8
		portCountersClean OBJECT IDENTIFIER ::= { v1600dPort 8 }

		
--          1.3.6.1.4.1.37950.1.1.5.10.1.8.1
-- 1.3.6.1.4.1.37950.1.1.5.10.1.8.1
-- 1.3.6.1.4.1.37950.1.1.5.10.1.8.1
-- 1.3.6.1.4.1.37950.1.1.5.10.1.8.1
-- 1.3.6.1.4.1.37950.1.1.5.10.1.8.1
-- 1.3.6.1.4.1.37950.1.1.5.10.1.8.1
-- 1.3.6.1.4.1.37950.1.1.5.10.1.8.1
-- 1.3.6.1.4.1.37950.1.1.5.10.1.8.1
-- 1.3.6.1.4.1.37950.1.1.5.10.1.8.1
		-- 1.3.6.1.4.1.37950.1.1.5.10.1.8.1
		portCountersCleanIndex OBJECT-TYPE
			SYNTAX INTEGER (1..28)
			MAX-ACCESS read-write
			STATUS current
			DESCRIPTION
				"Description."
			::= { portCountersClean 1 }

		
--          1.3.6.1.4.1.37950.1.1.5.10.1.8.2
-- 1.3.6.1.4.1.37950.1.1.5.10.1.8.2
-- 1.3.6.1.4.1.37950.1.1.5.10.1.8.2
-- 1.3.6.1.4.1.37950.1.1.5.10.1.8.2
-- 1.3.6.1.4.1.37950.1.1.5.10.1.8.2
-- 1.3.6.1.4.1.37950.1.1.5.10.1.8.2
-- 1.3.6.1.4.1.37950.1.1.5.10.1.8.2
-- 1.3.6.1.4.1.37950.1.1.5.10.1.8.2
-- 1.3.6.1.4.1.37950.1.1.5.10.1.8.2
		-- 1.3.6.1.4.1.37950.1.1.5.10.1.8.2
		portCountersCleanAction OBJECT-TYPE
			SYNTAX INTEGER { clear(1) }
			MAX-ACCESS read-write
			STATUS current
			DESCRIPTION
				"Description."
			::= { portCountersClean 2 }

		
--          1.3.6.1.4.1.37950.1.1.5.10.2
-- 1.3.6.1.4.1.37950.1.1.5.10.2
-- 1.3.6.1.4.1.37950.1.1.5.10.2
-- 1.3.6.1.4.1.37950.1.1.5.10.2
-- 1.3.6.1.4.1.37950.1.1.5.10.2
-- 1.3.6.1.4.1.37950.1.1.5.10.2
-- 1.3.6.1.4.1.37950.1.1.5.10.2
-- 1.3.6.1.4.1.37950.1.1.5.10.2
-- 1.3.6.1.4.1.37950.1.1.5.10.2
		-- 1.3.6.1.4.1.37950.1.1.5.10.2
		v1600dVLAN OBJECT IDENTIFIER ::= { v1600dSwitch 2 }

		
--          1.3.6.1.4.1.37950.1.1.5.10.2.1
-- 1.3.6.1.4.1.37950.1.1.5.10.2.1
-- 1.3.6.1.4.1.37950.1.1.5.10.2.1
-- 1.3.6.1.4.1.37950.1.1.5.10.2.1
-- 1.3.6.1.4.1.37950.1.1.5.10.2.1
-- 1.3.6.1.4.1.37950.1.1.5.10.2.1
-- 1.3.6.1.4.1.37950.1.1.5.10.2.1
-- 1.3.6.1.4.1.37950.1.1.5.10.2.1
-- 1.3.6.1.4.1.37950.1.1.5.10.2.1
		-- 1.3.6.1.4.1.37950.1.1.5.10.2.1
		vlanCfg OBJECT IDENTIFIER ::= { v1600dVLAN 1 }

		
--          1.3.6.1.4.1.37950.1.1.5.10.2.1.1
-- 1.3.6.1.4.1.37950.1.1.5.10.2.1.1
-- 1.3.6.1.4.1.37950.1.1.5.10.2.1.1
-- 1.3.6.1.4.1.37950.1.1.5.10.2.1.1
-- 1.3.6.1.4.1.37950.1.1.5.10.2.1.1
-- 1.3.6.1.4.1.37950.1.1.5.10.2.1.1
-- 1.3.6.1.4.1.37950.1.1.5.10.2.1.1
-- 1.3.6.1.4.1.37950.1.1.5.10.2.1.1
-- 1.3.6.1.4.1.37950.1.1.5.10.2.1.1
		-- 1.3.6.1.4.1.37950.1.1.5.10.2.1.1
		vlanCfgItem OBJECT-TYPE
			SYNTAX INTEGER
			MAX-ACCESS read-write
			STATUS current
			DESCRIPTION
				"Description."
			::= { vlanCfg 1 }

		
--          1.3.6.1.4.1.37950.1.1.5.10.2.1.2
-- 1.3.6.1.4.1.37950.1.1.5.10.2.1.2
-- 1.3.6.1.4.1.37950.1.1.5.10.2.1.2
-- 1.3.6.1.4.1.37950.1.1.5.10.2.1.2
-- 1.3.6.1.4.1.37950.1.1.5.10.2.1.2
-- 1.3.6.1.4.1.37950.1.1.5.10.2.1.2
-- 1.3.6.1.4.1.37950.1.1.5.10.2.1.2
-- 1.3.6.1.4.1.37950.1.1.5.10.2.1.2
-- 1.3.6.1.4.1.37950.1.1.5.10.2.1.2
		-- 1.3.6.1.4.1.37950.1.1.5.10.2.1.2
		serviceName OBJECT-TYPE
			SYNTAX OCTET STRING
			MAX-ACCESS read-write
			STATUS current
			DESCRIPTION
				"Description."
			::= { vlanCfg 2 }

		
--          1.3.6.1.4.1.37950.1.1.5.10.2.1.3
-- 1.3.6.1.4.1.37950.1.1.5.10.2.1.3
-- 1.3.6.1.4.1.37950.1.1.5.10.2.1.3
-- 1.3.6.1.4.1.37950.1.1.5.10.2.1.3
-- 1.3.6.1.4.1.37950.1.1.5.10.2.1.3
-- 1.3.6.1.4.1.37950.1.1.5.10.2.1.3
-- 1.3.6.1.4.1.37950.1.1.5.10.2.1.3
-- 1.3.6.1.4.1.37950.1.1.5.10.2.1.3
-- 1.3.6.1.4.1.37950.1.1.5.10.2.1.3
		-- 1.3.6.1.4.1.37950.1.1.5.10.2.1.3
		startVid OBJECT-TYPE
			SYNTAX INTEGER (1..4094)
			MAX-ACCESS read-write
			STATUS current
			DESCRIPTION
				"Description."
			::= { vlanCfg 3 }

		
--          1.3.6.1.4.1.37950.1.1.5.10.2.1.4
-- 1.3.6.1.4.1.37950.1.1.5.10.2.1.4
-- 1.3.6.1.4.1.37950.1.1.5.10.2.1.4
-- 1.3.6.1.4.1.37950.1.1.5.10.2.1.4
-- 1.3.6.1.4.1.37950.1.1.5.10.2.1.4
-- 1.3.6.1.4.1.37950.1.1.5.10.2.1.4
-- 1.3.6.1.4.1.37950.1.1.5.10.2.1.4
-- 1.3.6.1.4.1.37950.1.1.5.10.2.1.4
-- 1.3.6.1.4.1.37950.1.1.5.10.2.1.4
		-- 1.3.6.1.4.1.37950.1.1.5.10.2.1.4
		endVid OBJECT-TYPE
			SYNTAX INTEGER (1..4094)
			MAX-ACCESS read-write
			STATUS current
			DESCRIPTION
				"Description."
			::= { vlanCfg 4 }

		
--          1.3.6.1.4.1.37950.1.1.5.10.2.1.5
-- 1.3.6.1.4.1.37950.1.1.5.10.2.1.5
-- 1.3.6.1.4.1.37950.1.1.5.10.2.1.5
-- 1.3.6.1.4.1.37950.1.1.5.10.2.1.5
-- 1.3.6.1.4.1.37950.1.1.5.10.2.1.5
-- 1.3.6.1.4.1.37950.1.1.5.10.2.1.5
-- 1.3.6.1.4.1.37950.1.1.5.10.2.1.5
-- 1.3.6.1.4.1.37950.1.1.5.10.2.1.5
-- 1.3.6.1.4.1.37950.1.1.5.10.2.1.5
		-- 1.3.6.1.4.1.37950.1.1.5.10.2.1.5
		upLinkPortNo OBJECT-TYPE
			SYNTAX INTEGER (1..28)
			MAX-ACCESS read-write
			STATUS current
			DESCRIPTION
				"Description."
			::= { vlanCfg 5 }

		
--          1.3.6.1.4.1.37950.1.1.5.10.2.1.6
-- 1.3.6.1.4.1.37950.1.1.5.10.2.1.6
-- 1.3.6.1.4.1.37950.1.1.5.10.2.1.6
-- 1.3.6.1.4.1.37950.1.1.5.10.2.1.6
-- 1.3.6.1.4.1.37950.1.1.5.10.2.1.6
-- 1.3.6.1.4.1.37950.1.1.5.10.2.1.6
-- 1.3.6.1.4.1.37950.1.1.5.10.2.1.6
-- 1.3.6.1.4.1.37950.1.1.5.10.2.1.6
-- 1.3.6.1.4.1.37950.1.1.5.10.2.1.6
		-- 1.3.6.1.4.1.37950.1.1.5.10.2.1.6
		vlanTag OBJECT-TYPE
			SYNTAX INTEGER
				{
				untagged(0),
				tagged(1)
				}
			MAX-ACCESS read-write
			STATUS current
			DESCRIPTION
				"Description."
			::= { vlanCfg 6 }

		
--          1.3.6.1.4.1.37950.1.1.5.10.2.1.7
-- 1.3.6.1.4.1.37950.1.1.5.10.2.1.7
-- 1.3.6.1.4.1.37950.1.1.5.10.2.1.7
-- 1.3.6.1.4.1.37950.1.1.5.10.2.1.7
-- 1.3.6.1.4.1.37950.1.1.5.10.2.1.7
-- 1.3.6.1.4.1.37950.1.1.5.10.2.1.7
-- 1.3.6.1.4.1.37950.1.1.5.10.2.1.7
-- 1.3.6.1.4.1.37950.1.1.5.10.2.1.7
-- 1.3.6.1.4.1.37950.1.1.5.10.2.1.7
		-- 1.3.6.1.4.1.37950.1.1.5.10.2.1.7
		vlanAction OBJECT-TYPE
			SYNTAX INTEGER
				{
				add(1),
				delete(2)
				}
			MAX-ACCESS read-write
			STATUS current
			DESCRIPTION
				"Description."
			::= { vlanCfg 7 }

		
--          1.3.6.1.4.1.37950.1.1.5.10.2.2
-- 1.3.6.1.4.1.37950.1.1.5.10.2.2
-- 1.3.6.1.4.1.37950.1.1.5.10.2.2
-- 1.3.6.1.4.1.37950.1.1.5.10.2.2
-- 1.3.6.1.4.1.37950.1.1.5.10.2.2
-- 1.3.6.1.4.1.37950.1.1.5.10.2.2
-- 1.3.6.1.4.1.37950.1.1.5.10.2.2
-- 1.3.6.1.4.1.37950.1.1.5.10.2.2
-- 1.3.6.1.4.1.37950.1.1.5.10.2.2
		-- 1.3.6.1.4.1.37950.1.1.5.10.2.2
		vlanCfgTable OBJECT-TYPE
			SYNTAX SEQUENCE OF VlanCfgEntry
			MAX-ACCESS not-accessible
			STATUS current
			DESCRIPTION
				"Description."
			::= { v1600dVLAN 2 }

		
--          1.3.6.1.4.1.37950.1.1.5.10.2.2.1
-- 1.3.6.1.4.1.37950.1.1.5.10.2.2.1
-- 1.3.6.1.4.1.37950.1.1.5.10.2.2.1
-- 1.3.6.1.4.1.37950.1.1.5.10.2.2.1
-- 1.3.6.1.4.1.37950.1.1.5.10.2.2.1
-- 1.3.6.1.4.1.37950.1.1.5.10.2.2.1
-- 1.3.6.1.4.1.37950.1.1.5.10.2.2.1
-- 1.3.6.1.4.1.37950.1.1.5.10.2.2.1
-- 1.3.6.1.4.1.37950.1.1.5.10.2.2.1
		-- 1.3.6.1.4.1.37950.1.1.5.10.2.2.1
		vlanCfgEntry OBJECT-TYPE
			SYNTAX VlanCfgEntry
			MAX-ACCESS not-accessible
			STATUS current
			DESCRIPTION
				"Description."
			INDEX { vlanConfigIndex }
			::= { vlanCfgTable 1 }

		
		VlanCfgEntry ::=
			SEQUENCE { 
				vlanConfigIndex
					INTEGER,
				vlanCfgServiceName
					OCTET STRING,
				vlanCfgStartVid
					INTEGER,
				vlanCfgEndVid
					INTEGER,
				vlanCfgUplinkPortNo
					INTEGER,
				vlanCfgTagMode
					INTEGER
			 }

--          1.3.6.1.4.1.37950.1.1.5.10.2.2.1.1
-- 1.3.6.1.4.1.37950.1.1.5.10.2.2.1.1
-- 1.3.6.1.4.1.37950.1.1.5.10.2.2.1.1
-- 1.3.6.1.4.1.37950.1.1.5.10.2.2.1.1
-- 1.3.6.1.4.1.37950.1.1.5.10.2.2.1.1
-- 1.3.6.1.4.1.37950.1.1.5.10.2.2.1.1
-- 1.3.6.1.4.1.37950.1.1.5.10.2.2.1.1
-- 1.3.6.1.4.1.37950.1.1.5.10.2.2.1.1
-- 1.3.6.1.4.1.37950.1.1.5.10.2.2.1.1
		-- 1.3.6.1.4.1.37950.1.1.5.10.2.2.1.1
		vlanConfigIndex OBJECT-TYPE
			SYNTAX INTEGER (1..4094)
			MAX-ACCESS read-only
			STATUS current
			DESCRIPTION
				"Description."
			::= { vlanCfgEntry 1 }

		
--          1.3.6.1.4.1.37950.1.1.5.10.2.2.1.2
-- 1.3.6.1.4.1.37950.1.1.5.10.2.2.1.2
-- 1.3.6.1.4.1.37950.1.1.5.10.2.2.1.2
-- 1.3.6.1.4.1.37950.1.1.5.10.2.2.1.2
-- 1.3.6.1.4.1.37950.1.1.5.10.2.2.1.2
-- 1.3.6.1.4.1.37950.1.1.5.10.2.2.1.2
-- 1.3.6.1.4.1.37950.1.1.5.10.2.2.1.2
-- 1.3.6.1.4.1.37950.1.1.5.10.2.2.1.2
-- 1.3.6.1.4.1.37950.1.1.5.10.2.2.1.2
		-- 1.3.6.1.4.1.37950.1.1.5.10.2.2.1.2
		vlanCfgServiceName OBJECT-TYPE
			SYNTAX OCTET STRING
			MAX-ACCESS read-write
			STATUS current
			DESCRIPTION
				"Description."
			::= { vlanCfgEntry 2 }

		
--          1.3.6.1.4.1.37950.1.1.5.10.2.2.1.3
-- 1.3.6.1.4.1.37950.1.1.5.10.2.2.1.3
-- 1.3.6.1.4.1.37950.1.1.5.10.2.2.1.3
-- 1.3.6.1.4.1.37950.1.1.5.10.2.2.1.3
-- 1.3.6.1.4.1.37950.1.1.5.10.2.2.1.3
-- 1.3.6.1.4.1.37950.1.1.5.10.2.2.1.3
-- 1.3.6.1.4.1.37950.1.1.5.10.2.2.1.3
-- 1.3.6.1.4.1.37950.1.1.5.10.2.2.1.3
-- 1.3.6.1.4.1.37950.1.1.5.10.2.2.1.3
		-- 1.3.6.1.4.1.37950.1.1.5.10.2.2.1.3
		vlanCfgStartVid OBJECT-TYPE
			SYNTAX INTEGER (1..4094)
			MAX-ACCESS read-write
			STATUS current
			DESCRIPTION
				"Description."
			::= { vlanCfgEntry 3 }

		
--          1.3.6.1.4.1.37950.1.1.5.10.2.2.1.4
-- 1.3.6.1.4.1.37950.1.1.5.10.2.2.1.4
-- 1.3.6.1.4.1.37950.1.1.5.10.2.2.1.4
-- 1.3.6.1.4.1.37950.1.1.5.10.2.2.1.4
-- 1.3.6.1.4.1.37950.1.1.5.10.2.2.1.4
-- 1.3.6.1.4.1.37950.1.1.5.10.2.2.1.4
-- 1.3.6.1.4.1.37950.1.1.5.10.2.2.1.4
-- 1.3.6.1.4.1.37950.1.1.5.10.2.2.1.4
-- 1.3.6.1.4.1.37950.1.1.5.10.2.2.1.4
		-- 1.3.6.1.4.1.37950.1.1.5.10.2.2.1.4
		vlanCfgEndVid OBJECT-TYPE
			SYNTAX INTEGER (1..4094)
			MAX-ACCESS read-write
			STATUS current
			DESCRIPTION
				"Description."
			::= { vlanCfgEntry 4 }

		
--          1.3.6.1.4.1.37950.1.1.5.10.2.2.1.5
-- 1.3.6.1.4.1.37950.1.1.5.10.2.2.1.5
-- 1.3.6.1.4.1.37950.1.1.5.10.2.2.1.5
-- 1.3.6.1.4.1.37950.1.1.5.10.2.2.1.5
-- 1.3.6.1.4.1.37950.1.1.5.10.2.2.1.5
-- 1.3.6.1.4.1.37950.1.1.5.10.2.2.1.5
-- 1.3.6.1.4.1.37950.1.1.5.10.2.2.1.5
-- 1.3.6.1.4.1.37950.1.1.5.10.2.2.1.5
-- 1.3.6.1.4.1.37950.1.1.5.10.2.2.1.5
		-- 1.3.6.1.4.1.37950.1.1.5.10.2.2.1.5
		vlanCfgUplinkPortNo OBJECT-TYPE
			SYNTAX INTEGER (1..28)
			MAX-ACCESS read-write
			STATUS current
			DESCRIPTION
				"Description."
			::= { vlanCfgEntry 5 }

		
--          1.3.6.1.4.1.37950.1.1.5.10.2.2.1.6
-- 1.3.6.1.4.1.37950.1.1.5.10.2.2.1.6
-- 1.3.6.1.4.1.37950.1.1.5.10.2.2.1.6
-- 1.3.6.1.4.1.37950.1.1.5.10.2.2.1.6
-- 1.3.6.1.4.1.37950.1.1.5.10.2.2.1.6
-- 1.3.6.1.4.1.37950.1.1.5.10.2.2.1.6
-- 1.3.6.1.4.1.37950.1.1.5.10.2.2.1.6
-- 1.3.6.1.4.1.37950.1.1.5.10.2.2.1.6
-- 1.3.6.1.4.1.37950.1.1.5.10.2.2.1.6
		-- 1.3.6.1.4.1.37950.1.1.5.10.2.2.1.6
		vlanCfgTagMode OBJECT-TYPE
			SYNTAX INTEGER
				{
				untagged(0),
				tagged(1)
				}
			MAX-ACCESS read-write
			STATUS current
			DESCRIPTION
				"Description."
			::= { vlanCfgEntry 6 }

		
--          1.3.6.1.4.1.37950.1.1.5.10.2.3
-- 1.3.6.1.4.1.37950.1.1.5.10.2.3
-- 1.3.6.1.4.1.37950.1.1.5.10.2.3
-- 1.3.6.1.4.1.37950.1.1.5.10.2.3
-- 1.3.6.1.4.1.37950.1.1.5.10.2.3
-- 1.3.6.1.4.1.37950.1.1.5.10.2.3
-- 1.3.6.1.4.1.37950.1.1.5.10.2.3
-- 1.3.6.1.4.1.37950.1.1.5.10.2.3
-- 1.3.6.1.4.1.37950.1.1.5.10.2.3
		-- 1.3.6.1.4.1.37950.1.1.5.10.2.3
		vlanIPCfg OBJECT IDENTIFIER ::= { v1600dVLAN 3 }

		
--          1.3.6.1.4.1.37950.1.1.5.10.2.3.1
-- 1.3.6.1.4.1.37950.1.1.5.10.2.3.1
-- 1.3.6.1.4.1.37950.1.1.5.10.2.3.1
-- 1.3.6.1.4.1.37950.1.1.5.10.2.3.1
-- 1.3.6.1.4.1.37950.1.1.5.10.2.3.1
-- 1.3.6.1.4.1.37950.1.1.5.10.2.3.1
-- 1.3.6.1.4.1.37950.1.1.5.10.2.3.1
-- 1.3.6.1.4.1.37950.1.1.5.10.2.3.1
-- 1.3.6.1.4.1.37950.1.1.5.10.2.3.1
		-- 1.3.6.1.4.1.37950.1.1.5.10.2.3.1
		vlanId OBJECT-TYPE
			SYNTAX INTEGER (1..4094)
			MAX-ACCESS read-write
			STATUS current
			DESCRIPTION
				"Description."
			::= { vlanIPCfg 1 }

		
--          1.3.6.1.4.1.37950.1.1.5.10.2.3.2
-- 1.3.6.1.4.1.37950.1.1.5.10.2.3.2
-- 1.3.6.1.4.1.37950.1.1.5.10.2.3.2
-- 1.3.6.1.4.1.37950.1.1.5.10.2.3.2
-- 1.3.6.1.4.1.37950.1.1.5.10.2.3.2
-- 1.3.6.1.4.1.37950.1.1.5.10.2.3.2
-- 1.3.6.1.4.1.37950.1.1.5.10.2.3.2
-- 1.3.6.1.4.1.37950.1.1.5.10.2.3.2
-- 1.3.6.1.4.1.37950.1.1.5.10.2.3.2
		-- 1.3.6.1.4.1.37950.1.1.5.10.2.3.2
		vlanIP OBJECT-TYPE
			SYNTAX IpAddress
			MAX-ACCESS read-write
			STATUS current
			DESCRIPTION
				"Description."
			::= { vlanIPCfg 2 }

		
--          1.3.6.1.4.1.37950.1.1.5.10.2.3.3
-- 1.3.6.1.4.1.37950.1.1.5.10.2.3.3
-- 1.3.6.1.4.1.37950.1.1.5.10.2.3.3
-- 1.3.6.1.4.1.37950.1.1.5.10.2.3.3
-- 1.3.6.1.4.1.37950.1.1.5.10.2.3.3
-- 1.3.6.1.4.1.37950.1.1.5.10.2.3.3
-- 1.3.6.1.4.1.37950.1.1.5.10.2.3.3
-- 1.3.6.1.4.1.37950.1.1.5.10.2.3.3
-- 1.3.6.1.4.1.37950.1.1.5.10.2.3.3
		-- 1.3.6.1.4.1.37950.1.1.5.10.2.3.3
		vlanIPMask OBJECT-TYPE
			SYNTAX IpAddress
			MAX-ACCESS read-write
			STATUS current
			DESCRIPTION
				"Description."
			::= { vlanIPCfg 3 }

		
--          1.3.6.1.4.1.37950.1.1.5.10.2.3.4
-- 1.3.6.1.4.1.37950.1.1.5.10.2.3.4
-- 1.3.6.1.4.1.37950.1.1.5.10.2.3.4
-- 1.3.6.1.4.1.37950.1.1.5.10.2.3.4
-- 1.3.6.1.4.1.37950.1.1.5.10.2.3.4
-- 1.3.6.1.4.1.37950.1.1.5.10.2.3.4
-- 1.3.6.1.4.1.37950.1.1.5.10.2.3.4
-- 1.3.6.1.4.1.37950.1.1.5.10.2.3.4
-- 1.3.6.1.4.1.37950.1.1.5.10.2.3.4
		-- 1.3.6.1.4.1.37950.1.1.5.10.2.3.4
		vlanIPAction OBJECT-TYPE
			SYNTAX INTEGER
				{
				add(1),
				delete(2)
				}
			MAX-ACCESS read-write
			STATUS current
			DESCRIPTION
				"Description."
			::= { vlanIPCfg 4 }

		
--          1.3.6.1.4.1.37950.1.1.5.10.2.4
-- 1.3.6.1.4.1.37950.1.1.5.10.2.4
-- 1.3.6.1.4.1.37950.1.1.5.10.2.4
-- 1.3.6.1.4.1.37950.1.1.5.10.2.4
-- 1.3.6.1.4.1.37950.1.1.5.10.2.4
-- 1.3.6.1.4.1.37950.1.1.5.10.2.4
-- 1.3.6.1.4.1.37950.1.1.5.10.2.4
-- 1.3.6.1.4.1.37950.1.1.5.10.2.4
-- 1.3.6.1.4.1.37950.1.1.5.10.2.4
		-- 1.3.6.1.4.1.37950.1.1.5.10.2.4
		vlanIPTable OBJECT-TYPE
			SYNTAX SEQUENCE OF VlanIPEntry
			MAX-ACCESS not-accessible
			STATUS current
			DESCRIPTION
				"Description."
			::= { v1600dVLAN 4 }

		
--          1.3.6.1.4.1.37950.1.1.5.10.2.4.1
-- 1.3.6.1.4.1.37950.1.1.5.10.2.4.1
-- 1.3.6.1.4.1.37950.1.1.5.10.2.4.1
-- 1.3.6.1.4.1.37950.1.1.5.10.2.4.1
-- 1.3.6.1.4.1.37950.1.1.5.10.2.4.1
-- 1.3.6.1.4.1.37950.1.1.5.10.2.4.1
-- 1.3.6.1.4.1.37950.1.1.5.10.2.4.1
-- 1.3.6.1.4.1.37950.1.1.5.10.2.4.1
-- 1.3.6.1.4.1.37950.1.1.5.10.2.4.1
		-- 1.3.6.1.4.1.37950.1.1.5.10.2.4.1
		vlanIPEntry OBJECT-TYPE
			SYNTAX VlanIPEntry
			MAX-ACCESS not-accessible
			STATUS current
			DESCRIPTION
				"Description."
			INDEX { vlanIdIndex }
			::= { vlanIPTable 1 }

		
		VlanIPEntry ::=
			SEQUENCE { 
				vlanIdIndex
					Integer32,
				vlanIPAddr
					IpAddress,
				vlanIPMaskAddr
					IpAddress
			 }

--          1.3.6.1.4.1.37950.1.1.5.10.2.4.1.1
-- 1.3.6.1.4.1.37950.1.1.5.10.2.4.1.1
-- 1.3.6.1.4.1.37950.1.1.5.10.2.4.1.1
-- 1.3.6.1.4.1.37950.1.1.5.10.2.4.1.1
-- 1.3.6.1.4.1.37950.1.1.5.10.2.4.1.1
-- 1.3.6.1.4.1.37950.1.1.5.10.2.4.1.1
-- 1.3.6.1.4.1.37950.1.1.5.10.2.4.1.1
-- 1.3.6.1.4.1.37950.1.1.5.10.2.4.1.1
-- 1.3.6.1.4.1.37950.1.1.5.10.2.4.1.1
		-- 1.3.6.1.4.1.37950.1.1.5.10.2.4.1.1
		vlanIdIndex OBJECT-TYPE
			SYNTAX Integer32 (1..4094)
			MAX-ACCESS read-only
			STATUS current
			DESCRIPTION
				"Description."
			::= { vlanIPEntry 1 }

		
--          1.3.6.1.4.1.37950.1.1.5.10.2.4.1.2
-- 1.3.6.1.4.1.37950.1.1.5.10.2.4.1.2
-- 1.3.6.1.4.1.37950.1.1.5.10.2.4.1.2
-- 1.3.6.1.4.1.37950.1.1.5.10.2.4.1.2
-- 1.3.6.1.4.1.37950.1.1.5.10.2.4.1.2
-- 1.3.6.1.4.1.37950.1.1.5.10.2.4.1.2
-- 1.3.6.1.4.1.37950.1.1.5.10.2.4.1.2
-- 1.3.6.1.4.1.37950.1.1.5.10.2.4.1.2
-- 1.3.6.1.4.1.37950.1.1.5.10.2.4.1.2
		-- 1.3.6.1.4.1.37950.1.1.5.10.2.4.1.2
		vlanIPAddr OBJECT-TYPE
			SYNTAX IpAddress
			MAX-ACCESS read-only
			STATUS current
			DESCRIPTION
				"Description."
			::= { vlanIPEntry 2 }

		
--          1.3.6.1.4.1.37950.1.1.5.10.2.4.1.3
-- 1.3.6.1.4.1.37950.1.1.5.10.2.4.1.3
-- 1.3.6.1.4.1.37950.1.1.5.10.2.4.1.3
-- 1.3.6.1.4.1.37950.1.1.5.10.2.4.1.3
-- 1.3.6.1.4.1.37950.1.1.5.10.2.4.1.3
-- 1.3.6.1.4.1.37950.1.1.5.10.2.4.1.3
-- 1.3.6.1.4.1.37950.1.1.5.10.2.4.1.3
-- 1.3.6.1.4.1.37950.1.1.5.10.2.4.1.3
-- 1.3.6.1.4.1.37950.1.1.5.10.2.4.1.3
		-- 1.3.6.1.4.1.37950.1.1.5.10.2.4.1.3
		vlanIPMaskAddr OBJECT-TYPE
			SYNTAX IpAddress
			MAX-ACCESS read-only
			STATUS current
			DESCRIPTION
				"Description."
			::= { vlanIPEntry 3 }

		
--          1.3.6.1.4.1.37950.1.1.5.10.2.5
-- 1.3.6.1.4.1.37950.1.1.5.10.2.5
-- 1.3.6.1.4.1.37950.1.1.5.10.2.5
-- 1.3.6.1.4.1.37950.1.1.5.10.2.5
-- 1.3.6.1.4.1.37950.1.1.5.10.2.5
-- 1.3.6.1.4.1.37950.1.1.5.10.2.5
-- 1.3.6.1.4.1.37950.1.1.5.10.2.5
-- 1.3.6.1.4.1.37950.1.1.5.10.2.5
-- 1.3.6.1.4.1.37950.1.1.5.10.2.5
		-- 1.3.6.1.4.1.37950.1.1.5.10.2.5
		vlanQinq OBJECT IDENTIFIER ::= { v1600dVLAN 5 }

		
--          1.3.6.1.4.1.37950.1.1.5.10.2.5.1
-- 1.3.6.1.4.1.37950.1.1.5.10.2.5.1
-- 1.3.6.1.4.1.37950.1.1.5.10.2.5.1
-- 1.3.6.1.4.1.37950.1.1.5.10.2.5.1
-- 1.3.6.1.4.1.37950.1.1.5.10.2.5.1
-- 1.3.6.1.4.1.37950.1.1.5.10.2.5.1
-- 1.3.6.1.4.1.37950.1.1.5.10.2.5.1
-- 1.3.6.1.4.1.37950.1.1.5.10.2.5.1
-- 1.3.6.1.4.1.37950.1.1.5.10.2.5.1
		-- 1.3.6.1.4.1.37950.1.1.5.10.2.5.1
		vlanQinqEn OBJECT-TYPE
			SYNTAX INTEGER
				{
				disable(0),
				enable(1)
				}
			MAX-ACCESS read-write
			STATUS current
			DESCRIPTION
				"Description."
			::= { vlanQinq 1 }

		
--          1.3.6.1.4.1.37950.1.1.5.10.2.5.2
-- 1.3.6.1.4.1.37950.1.1.5.10.2.5.2
-- 1.3.6.1.4.1.37950.1.1.5.10.2.5.2
-- 1.3.6.1.4.1.37950.1.1.5.10.2.5.2
-- 1.3.6.1.4.1.37950.1.1.5.10.2.5.2
-- 1.3.6.1.4.1.37950.1.1.5.10.2.5.2
-- 1.3.6.1.4.1.37950.1.1.5.10.2.5.2
-- 1.3.6.1.4.1.37950.1.1.5.10.2.5.2
-- 1.3.6.1.4.1.37950.1.1.5.10.2.5.2
		-- 1.3.6.1.4.1.37950.1.1.5.10.2.5.2
		vlanQinqSetting OBJECT IDENTIFIER ::= { vlanQinq 2 }

		
--          1.3.6.1.4.1.37950.1.1.5.10.2.5.2.1
-- 1.3.6.1.4.1.37950.1.1.5.10.2.5.2.1
-- 1.3.6.1.4.1.37950.1.1.5.10.2.5.2.1
-- 1.3.6.1.4.1.37950.1.1.5.10.2.5.2.1
-- 1.3.6.1.4.1.37950.1.1.5.10.2.5.2.1
-- 1.3.6.1.4.1.37950.1.1.5.10.2.5.2.1
-- 1.3.6.1.4.1.37950.1.1.5.10.2.5.2.1
-- 1.3.6.1.4.1.37950.1.1.5.10.2.5.2.1
-- 1.3.6.1.4.1.37950.1.1.5.10.2.5.2.1
		-- 1.3.6.1.4.1.37950.1.1.5.10.2.5.2.1
		qinqPortId OBJECT-TYPE
			SYNTAX INTEGER (1..28)
			MAX-ACCESS read-write
			STATUS current
			DESCRIPTION
				"Description."
			::= { vlanQinqSetting 1 }

		
--          1.3.6.1.4.1.37950.1.1.5.10.2.5.2.2
-- 1.3.6.1.4.1.37950.1.1.5.10.2.5.2.2
-- 1.3.6.1.4.1.37950.1.1.5.10.2.5.2.2
-- 1.3.6.1.4.1.37950.1.1.5.10.2.5.2.2
-- 1.3.6.1.4.1.37950.1.1.5.10.2.5.2.2
-- 1.3.6.1.4.1.37950.1.1.5.10.2.5.2.2
-- 1.3.6.1.4.1.37950.1.1.5.10.2.5.2.2
-- 1.3.6.1.4.1.37950.1.1.5.10.2.5.2.2
-- 1.3.6.1.4.1.37950.1.1.5.10.2.5.2.2
		-- 1.3.6.1.4.1.37950.1.1.5.10.2.5.2.2
		qinqCVlanId OBJECT-TYPE
			SYNTAX Integer32 (1..4094)
			MAX-ACCESS read-write
			STATUS current
			DESCRIPTION
				"Description."
			::= { vlanQinqSetting 2 }

		
--          1.3.6.1.4.1.37950.1.1.5.10.2.5.2.3
-- 1.3.6.1.4.1.37950.1.1.5.10.2.5.2.3
-- 1.3.6.1.4.1.37950.1.1.5.10.2.5.2.3
-- 1.3.6.1.4.1.37950.1.1.5.10.2.5.2.3
-- 1.3.6.1.4.1.37950.1.1.5.10.2.5.2.3
-- 1.3.6.1.4.1.37950.1.1.5.10.2.5.2.3
-- 1.3.6.1.4.1.37950.1.1.5.10.2.5.2.3
-- 1.3.6.1.4.1.37950.1.1.5.10.2.5.2.3
-- 1.3.6.1.4.1.37950.1.1.5.10.2.5.2.3
		-- 1.3.6.1.4.1.37950.1.1.5.10.2.5.2.3
		qinqSVlanId OBJECT-TYPE
			SYNTAX Integer32 (1..4094)
			MAX-ACCESS read-write
			STATUS current
			DESCRIPTION
				"Description."
			::= { vlanQinqSetting 3 }

		
--          1.3.6.1.4.1.37950.1.1.5.10.2.5.2.4
-- 1.3.6.1.4.1.37950.1.1.5.10.2.5.2.4
-- 1.3.6.1.4.1.37950.1.1.5.10.2.5.2.4
-- 1.3.6.1.4.1.37950.1.1.5.10.2.5.2.4
-- 1.3.6.1.4.1.37950.1.1.5.10.2.5.2.4
-- 1.3.6.1.4.1.37950.1.1.5.10.2.5.2.4
-- 1.3.6.1.4.1.37950.1.1.5.10.2.5.2.4
-- 1.3.6.1.4.1.37950.1.1.5.10.2.5.2.4
-- 1.3.6.1.4.1.37950.1.1.5.10.2.5.2.4
		-- 1.3.6.1.4.1.37950.1.1.5.10.2.5.2.4
		qinqModeSelect OBJECT-TYPE
			SYNTAX INTEGER
				{
				translation(1),
				qinq(2),
				qinqrange(3)
				}
			MAX-ACCESS read-write
			STATUS current
			DESCRIPTION
				"Description."
			::= { vlanQinqSetting 4 }

		
--          1.3.6.1.4.1.37950.1.1.5.10.2.5.2.5
-- 1.3.6.1.4.1.37950.1.1.5.10.2.5.2.5
-- 1.3.6.1.4.1.37950.1.1.5.10.2.5.2.5
-- 1.3.6.1.4.1.37950.1.1.5.10.2.5.2.5
-- 1.3.6.1.4.1.37950.1.1.5.10.2.5.2.5
-- 1.3.6.1.4.1.37950.1.1.5.10.2.5.2.5
-- 1.3.6.1.4.1.37950.1.1.5.10.2.5.2.5
-- 1.3.6.1.4.1.37950.1.1.5.10.2.5.2.5
-- 1.3.6.1.4.1.37950.1.1.5.10.2.5.2.5
		-- 1.3.6.1.4.1.37950.1.1.5.10.2.5.2.5
		qinqAction OBJECT-TYPE
			SYNTAX INTEGER
				{
				add(1),
				delete(2)
				}
			MAX-ACCESS read-write
			STATUS current
			DESCRIPTION
				"Description."
			::= { vlanQinqSetting 5 }

		
--         1.3.6.1.4.1.37950.1.1.5.10.2.5.2.6
-- 1.3.6.1.4.1.37950.1.1.5.10.2.5.2.6
-- 1.3.6.1.4.1.37950.1.1.5.10.2.5.2.6
-- 1.3.6.1.4.1.37950.1.1.5.10.2.5.2.6
-- 1.3.6.1.4.1.37950.1.1.5.10.2.5.2.6
-- 1.3.6.1.4.1.37950.1.1.5.10.2.5.2.6
-- 1.3.6.1.4.1.37950.1.1.5.10.2.5.2.6
-- 1.3.6.1.4.1.37950.1.1.5.10.2.5.2.6
		-- 1.3.6.1.4.1.37950.1.1.5.10.2.5.2.6
		qinqCVlanIdRange OBJECT-TYPE
			SYNTAX OCTET STRING
			MAX-ACCESS read-write
			STATUS current
			DESCRIPTION
				"Description."
			::= { vlanQinqSetting 6 }

		
--          1.3.6.1.4.1.37950.1.1.5.10.2.5.3
-- 1.3.6.1.4.1.37950.1.1.5.10.2.5.3
-- 1.3.6.1.4.1.37950.1.1.5.10.2.5.3
-- 1.3.6.1.4.1.37950.1.1.5.10.2.5.3
-- 1.3.6.1.4.1.37950.1.1.5.10.2.5.3
-- 1.3.6.1.4.1.37950.1.1.5.10.2.5.3
-- 1.3.6.1.4.1.37950.1.1.5.10.2.5.3
-- 1.3.6.1.4.1.37950.1.1.5.10.2.5.3
-- 1.3.6.1.4.1.37950.1.1.5.10.2.5.3
		-- 1.3.6.1.4.1.37950.1.1.5.10.2.5.3
		vlanQinqTable OBJECT-TYPE
			SYNTAX SEQUENCE OF VlanQinqEntry
			MAX-ACCESS not-accessible
			STATUS current
			DESCRIPTION
				"Description."
			::= { vlanQinq 3 }

		
--          1.3.6.1.4.1.37950.1.1.5.10.2.5.3.1
-- 1.3.6.1.4.1.37950.1.1.5.10.2.5.3.1
-- 1.3.6.1.4.1.37950.1.1.5.10.2.5.3.1
-- 1.3.6.1.4.1.37950.1.1.5.10.2.5.3.1
-- 1.3.6.1.4.1.37950.1.1.5.10.2.5.3.1
-- 1.3.6.1.4.1.37950.1.1.5.10.2.5.3.1
-- 1.3.6.1.4.1.37950.1.1.5.10.2.5.3.1
-- 1.3.6.1.4.1.37950.1.1.5.10.2.5.3.1
-- 1.3.6.1.4.1.37950.1.1.5.10.2.5.3.1
		-- 1.3.6.1.4.1.37950.1.1.5.10.2.5.3.1
		vlanQinqEntry OBJECT-TYPE
			SYNTAX VlanQinqEntry
			MAX-ACCESS not-accessible
			STATUS current
			DESCRIPTION
				"Description."
			INDEX { qinqIndex }
			::= { vlanQinqTable 1 }

		
		VlanQinqEntry ::=
			SEQUENCE { 
				qinqIndex
					Integer32,
				qinqPortIndex
					Integer32,
				qinqCVlanIndex
					Integer32,
				qinqSVlanIndex
					Integer32,
				qinqMode
					INTEGER,
				qinqCVlanRange
					OCTET STRING
			 }

--          1.3.6.1.4.1.37950.1.1.5.10.2.5.3.1.1
-- 1.3.6.1.4.1.37950.1.1.5.10.2.5.3.1.1
-- 1.3.6.1.4.1.37950.1.1.5.10.2.5.3.1.1
-- 1.3.6.1.4.1.37950.1.1.5.10.2.5.3.1.1
-- 1.3.6.1.4.1.37950.1.1.5.10.2.5.3.1.1
-- 1.3.6.1.4.1.37950.1.1.5.10.2.5.3.1.1
-- 1.3.6.1.4.1.37950.1.1.5.10.2.5.3.1.1
-- 1.3.6.1.4.1.37950.1.1.5.10.2.5.3.1.1
-- 1.3.6.1.4.1.37950.1.1.5.10.2.5.3.1.1
		-- 1.3.6.1.4.1.37950.1.1.5.10.2.5.3.1.1
		qinqIndex OBJECT-TYPE
			SYNTAX Integer32
			MAX-ACCESS read-only
			STATUS current
			DESCRIPTION
				"Description."
			::= { vlanQinqEntry 1 }

		
--          1.3.6.1.4.1.37950.1.1.5.10.2.5.3.1.2
-- 1.3.6.1.4.1.37950.1.1.5.10.2.5.3.1.2
-- 1.3.6.1.4.1.37950.1.1.5.10.2.5.3.1.2
-- 1.3.6.1.4.1.37950.1.1.5.10.2.5.3.1.2
-- 1.3.6.1.4.1.37950.1.1.5.10.2.5.3.1.2
-- 1.3.6.1.4.1.37950.1.1.5.10.2.5.3.1.2
-- 1.3.6.1.4.1.37950.1.1.5.10.2.5.3.1.2
-- 1.3.6.1.4.1.37950.1.1.5.10.2.5.3.1.2
-- 1.3.6.1.4.1.37950.1.1.5.10.2.5.3.1.2
		-- 1.3.6.1.4.1.37950.1.1.5.10.2.5.3.1.2
		qinqPortIndex OBJECT-TYPE
			SYNTAX Integer32
			MAX-ACCESS read-only
			STATUS current
			DESCRIPTION
				"Description."
			::= { vlanQinqEntry 2 }

		
--          1.3.6.1.4.1.37950.1.1.5.10.2.5.3.1.3
-- 1.3.6.1.4.1.37950.1.1.5.10.2.5.3.1.3
-- 1.3.6.1.4.1.37950.1.1.5.10.2.5.3.1.3
-- 1.3.6.1.4.1.37950.1.1.5.10.2.5.3.1.3
-- 1.3.6.1.4.1.37950.1.1.5.10.2.5.3.1.3
-- 1.3.6.1.4.1.37950.1.1.5.10.2.5.3.1.3
-- 1.3.6.1.4.1.37950.1.1.5.10.2.5.3.1.3
-- 1.3.6.1.4.1.37950.1.1.5.10.2.5.3.1.3
-- 1.3.6.1.4.1.37950.1.1.5.10.2.5.3.1.3
		-- 1.3.6.1.4.1.37950.1.1.5.10.2.5.3.1.3
		qinqCVlanIndex OBJECT-TYPE
			SYNTAX Integer32
			MAX-ACCESS read-only
			STATUS current
			DESCRIPTION
				"Description."
			::= { vlanQinqEntry 3 }

		
--          1.3.6.1.4.1.37950.1.1.5.10.2.5.3.1.4
-- 1.3.6.1.4.1.37950.1.1.5.10.2.5.3.1.4
-- 1.3.6.1.4.1.37950.1.1.5.10.2.5.3.1.4
-- 1.3.6.1.4.1.37950.1.1.5.10.2.5.3.1.4
-- 1.3.6.1.4.1.37950.1.1.5.10.2.5.3.1.4
-- 1.3.6.1.4.1.37950.1.1.5.10.2.5.3.1.4
-- 1.3.6.1.4.1.37950.1.1.5.10.2.5.3.1.4
-- 1.3.6.1.4.1.37950.1.1.5.10.2.5.3.1.4
-- 1.3.6.1.4.1.37950.1.1.5.10.2.5.3.1.4
		-- 1.3.6.1.4.1.37950.1.1.5.10.2.5.3.1.4
		qinqSVlanIndex OBJECT-TYPE
			SYNTAX Integer32
			MAX-ACCESS read-only
			STATUS current
			DESCRIPTION
				"Description."
			::= { vlanQinqEntry 4 }

		
--          1.3.6.1.4.1.37950.1.1.5.10.2.5.3.1.5
-- 1.3.6.1.4.1.37950.1.1.5.10.2.5.3.1.5
-- 1.3.6.1.4.1.37950.1.1.5.10.2.5.3.1.5
-- 1.3.6.1.4.1.37950.1.1.5.10.2.5.3.1.5
-- 1.3.6.1.4.1.37950.1.1.5.10.2.5.3.1.5
-- 1.3.6.1.4.1.37950.1.1.5.10.2.5.3.1.5
-- 1.3.6.1.4.1.37950.1.1.5.10.2.5.3.1.5
-- 1.3.6.1.4.1.37950.1.1.5.10.2.5.3.1.5
-- 1.3.6.1.4.1.37950.1.1.5.10.2.5.3.1.5
		-- 1.3.6.1.4.1.37950.1.1.5.10.2.5.3.1.5
		qinqMode OBJECT-TYPE
			SYNTAX INTEGER
				{
				translation(1),
				qinq(2),
				qinqrange(3)
				}
			MAX-ACCESS read-only
			STATUS current
			DESCRIPTION
				"Description."
			::= { vlanQinqEntry 5 }

		
--         1.3.6.1.4.1.37950.1.1.5.10.2.5.3.1.6
-- 1.3.6.1.4.1.37950.1.1.5.10.2.5.3.1.6
-- 1.3.6.1.4.1.37950.1.1.5.10.2.5.3.1.6
-- 1.3.6.1.4.1.37950.1.1.5.10.2.5.3.1.6
-- 1.3.6.1.4.1.37950.1.1.5.10.2.5.3.1.6
-- 1.3.6.1.4.1.37950.1.1.5.10.2.5.3.1.6
-- 1.3.6.1.4.1.37950.1.1.5.10.2.5.3.1.6
-- 1.3.6.1.4.1.37950.1.1.5.10.2.5.3.1.6
		-- 1.3.6.1.4.1.37950.1.1.5.10.2.5.3.1.6
		qinqCVlanRange OBJECT-TYPE
			SYNTAX OCTET STRING
			MAX-ACCESS read-only
			STATUS current
			DESCRIPTION
				"Description."
			::= { vlanQinqEntry 6 }

		
--          1.3.6.1.4.1.37950.1.1.5.10.2.6
-- 1.3.6.1.4.1.37950.1.1.5.10.2.6
-- 1.3.6.1.4.1.37950.1.1.5.10.2.6
-- 1.3.6.1.4.1.37950.1.1.5.10.2.6
-- 1.3.6.1.4.1.37950.1.1.5.10.2.6
-- 1.3.6.1.4.1.37950.1.1.5.10.2.6
-- 1.3.6.1.4.1.37950.1.1.5.10.2.6
-- 1.3.6.1.4.1.37950.1.1.5.10.2.6
-- 1.3.6.1.4.1.37950.1.1.5.10.2.6
		-- 1.3.6.1.4.1.37950.1.1.5.10.2.6
		vlanTable OBJECT-TYPE
			SYNTAX SEQUENCE OF VlanEntry
			MAX-ACCESS not-accessible
			STATUS current
			DESCRIPTION
				"Description."
			::= { v1600dVLAN 6 }

		
--          1.3.6.1.4.1.37950.1.1.5.10.2.6.1
-- 1.3.6.1.4.1.37950.1.1.5.10.2.6.1
-- 1.3.6.1.4.1.37950.1.1.5.10.2.6.1
-- 1.3.6.1.4.1.37950.1.1.5.10.2.6.1
-- 1.3.6.1.4.1.37950.1.1.5.10.2.6.1
-- 1.3.6.1.4.1.37950.1.1.5.10.2.6.1
-- 1.3.6.1.4.1.37950.1.1.5.10.2.6.1
-- 1.3.6.1.4.1.37950.1.1.5.10.2.6.1
-- 1.3.6.1.4.1.37950.1.1.5.10.2.6.1
		-- 1.3.6.1.4.1.37950.1.1.5.10.2.6.1
		vlanEntry OBJECT-TYPE
			SYNTAX VlanEntry
			MAX-ACCESS not-accessible
			STATUS current
			DESCRIPTION
				"Description."
			INDEX { vlanVid }
			::= { vlanTable 1 }

		
		VlanEntry ::=
			SEQUENCE { 
				vlanVid
					Gauge32,
				vlanName
					OCTET STRING,
				vlanTagPort
					OCTET STRING,
				vlanUntagPort
					OCTET STRING,
				vlanRowStatus
					RowStatus,
				vlanDescr
					OCTET STRING
			 }

--          1.3.6.1.4.1.37950.1.1.5.10.2.6.1.1
-- 1.3.6.1.4.1.37950.1.1.5.10.2.6.1.1
-- 1.3.6.1.4.1.37950.1.1.5.10.2.6.1.1
-- 1.3.6.1.4.1.37950.1.1.5.10.2.6.1.1
-- 1.3.6.1.4.1.37950.1.1.5.10.2.6.1.1
-- 1.3.6.1.4.1.37950.1.1.5.10.2.6.1.1
-- 1.3.6.1.4.1.37950.1.1.5.10.2.6.1.1
-- 1.3.6.1.4.1.37950.1.1.5.10.2.6.1.1
-- 1.3.6.1.4.1.37950.1.1.5.10.2.6.1.1
		-- 1.3.6.1.4.1.37950.1.1.5.10.2.6.1.1
		vlanVid OBJECT-TYPE
			SYNTAX Gauge32 (1..4094)
			MAX-ACCESS read-write
			STATUS current
			DESCRIPTION
				"Description."
			::= { vlanEntry 1 }

		
--          1.3.6.1.4.1.37950.1.1.5.10.2.6.1.2
-- 1.3.6.1.4.1.37950.1.1.5.10.2.6.1.2
-- 1.3.6.1.4.1.37950.1.1.5.10.2.6.1.2
-- 1.3.6.1.4.1.37950.1.1.5.10.2.6.1.2
-- 1.3.6.1.4.1.37950.1.1.5.10.2.6.1.2
-- 1.3.6.1.4.1.37950.1.1.5.10.2.6.1.2
-- 1.3.6.1.4.1.37950.1.1.5.10.2.6.1.2
-- 1.3.6.1.4.1.37950.1.1.5.10.2.6.1.2
-- 1.3.6.1.4.1.37950.1.1.5.10.2.6.1.2
		-- 1.3.6.1.4.1.37950.1.1.5.10.2.6.1.2
		vlanName OBJECT-TYPE
			SYNTAX OCTET STRING
			MAX-ACCESS read-write
			STATUS current
			DESCRIPTION
				"Description."
			::= { vlanEntry 2 }

		
--          1.3.6.1.4.1.37950.1.1.5.10.2.6.1.3
-- 1.3.6.1.4.1.37950.1.1.5.10.2.6.1.3
-- 1.3.6.1.4.1.37950.1.1.5.10.2.6.1.3
-- 1.3.6.1.4.1.37950.1.1.5.10.2.6.1.3
-- 1.3.6.1.4.1.37950.1.1.5.10.2.6.1.3
-- 1.3.6.1.4.1.37950.1.1.5.10.2.6.1.3
-- 1.3.6.1.4.1.37950.1.1.5.10.2.6.1.3
-- 1.3.6.1.4.1.37950.1.1.5.10.2.6.1.3
-- 1.3.6.1.4.1.37950.1.1.5.10.2.6.1.3
		-- 1.3.6.1.4.1.37950.1.1.5.10.2.6.1.3
		vlanTagPort OBJECT-TYPE
			SYNTAX OCTET STRING
			MAX-ACCESS read-write
			STATUS current
			DESCRIPTION
				"Description."
			::= { vlanEntry 3 }

		
--          1.3.6.1.4.1.37950.1.1.5.10.2.6.1.4
-- 1.3.6.1.4.1.37950.1.1.5.10.2.6.1.4
-- 1.3.6.1.4.1.37950.1.1.5.10.2.6.1.4
-- 1.3.6.1.4.1.37950.1.1.5.10.2.6.1.4
-- 1.3.6.1.4.1.37950.1.1.5.10.2.6.1.4
-- 1.3.6.1.4.1.37950.1.1.5.10.2.6.1.4
-- 1.3.6.1.4.1.37950.1.1.5.10.2.6.1.4
-- 1.3.6.1.4.1.37950.1.1.5.10.2.6.1.4
-- 1.3.6.1.4.1.37950.1.1.5.10.2.6.1.4
		-- 1.3.6.1.4.1.37950.1.1.5.10.2.6.1.4
		vlanUntagPort OBJECT-TYPE
			SYNTAX OCTET STRING
			MAX-ACCESS read-write
			STATUS current
			DESCRIPTION
				"Description."
			::= { vlanEntry 4 }

		
--          1.3.6.1.4.1.37950.1.1.5.10.2.6.1.5
-- 1.3.6.1.4.1.37950.1.1.5.10.2.6.1.5
-- 1.3.6.1.4.1.37950.1.1.5.10.2.6.1.5
-- 1.3.6.1.4.1.37950.1.1.5.10.2.6.1.5
-- 1.3.6.1.4.1.37950.1.1.5.10.2.6.1.5
-- 1.3.6.1.4.1.37950.1.1.5.10.2.6.1.5
-- 1.3.6.1.4.1.37950.1.1.5.10.2.6.1.5
-- 1.3.6.1.4.1.37950.1.1.5.10.2.6.1.5
-- 1.3.6.1.4.1.37950.1.1.5.10.2.6.1.5
		-- 1.3.6.1.4.1.37950.1.1.5.10.2.6.1.5
		vlanRowStatus OBJECT-TYPE
			SYNTAX RowStatus
			MAX-ACCESS read-create
			STATUS current
			DESCRIPTION
				"Description."
			::= { vlanEntry 5 }

		
--          1.3.6.1.4.1.37950.1.1.5.10.2.6.1.6
-- 1.3.6.1.4.1.37950.1.1.5.10.2.6.1.6
-- 1.3.6.1.4.1.37950.1.1.5.10.2.6.1.6
-- 1.3.6.1.4.1.37950.1.1.5.10.2.6.1.6
-- 1.3.6.1.4.1.37950.1.1.5.10.2.6.1.6
-- 1.3.6.1.4.1.37950.1.1.5.10.2.6.1.6
-- 1.3.6.1.4.1.37950.1.1.5.10.2.6.1.6
-- 1.3.6.1.4.1.37950.1.1.5.10.2.6.1.6
-- 1.3.6.1.4.1.37950.1.1.5.10.2.6.1.6
		-- 1.3.6.1.4.1.37950.1.1.5.10.2.6.1.6
		vlanDescr OBJECT-TYPE
			SYNTAX OCTET STRING
			MAX-ACCESS read-write
			STATUS current
			DESCRIPTION
				"Description."
			::= { vlanEntry 6 }

		
--         1.3.6.1.4.1.37950.1.1.5.10.2.7
-- 1.3.6.1.4.1.37950.1.1.5.10.2.7
-- 1.3.6.1.4.1.37950.1.1.5.10.2.7
-- 1.3.6.1.4.1.37950.1.1.5.10.2.7
-- 1.3.6.1.4.1.37950.1.1.5.10.2.7
-- 1.3.6.1.4.1.37950.1.1.5.10.2.7
-- 1.3.6.1.4.1.37950.1.1.5.10.2.7
-- 1.3.6.1.4.1.37950.1.1.5.10.2.7
		-- 1.3.6.1.4.1.37950.1.1.5.10.2.7
		vlanIPv6Cfg OBJECT IDENTIFIER ::= { v1600dVLAN 7 }

		
--         1.3.6.1.4.1.37950.1.1.5.10.2.7.1
-- 1.3.6.1.4.1.37950.1.1.5.10.2.7.1
-- 1.3.6.1.4.1.37950.1.1.5.10.2.7.1
-- 1.3.6.1.4.1.37950.1.1.5.10.2.7.1
-- 1.3.6.1.4.1.37950.1.1.5.10.2.7.1
-- 1.3.6.1.4.1.37950.1.1.5.10.2.7.1
-- 1.3.6.1.4.1.37950.1.1.5.10.2.7.1
-- 1.3.6.1.4.1.37950.1.1.5.10.2.7.1
		-- 1.3.6.1.4.1.37950.1.1.5.10.2.7.1
		vlanid OBJECT-TYPE
			SYNTAX INTEGER (1..4094)
			MAX-ACCESS read-write
			STATUS current
			DESCRIPTION
				"Description."
			::= { vlanIPv6Cfg 1 }

		
--         1.3.6.1.4.1.37950.1.1.5.10.2.7.3
-- 1.3.6.1.4.1.37950.1.1.5.10.2.7.2
-- 1.3.6.1.4.1.37950.1.1.5.10.2.7.2
-- 1.3.6.1.4.1.37950.1.1.5.10.2.7.2
-- 1.3.6.1.4.1.37950.1.1.5.10.2.7.2
-- 1.3.6.1.4.1.37950.1.1.5.10.2.7.2
-- 1.3.6.1.4.1.37950.1.1.5.10.2.7.2
-- 1.3.6.1.4.1.37950.1.1.5.10.2.7.2
		-- 1.3.6.1.4.1.37950.1.1.5.10.2.7.2
		ipv6Addr OBJECT-TYPE
			SYNTAX OCTET STRING
			MAX-ACCESS read-write
			STATUS current
			DESCRIPTION
				"Description."
			::= { vlanIPv6Cfg 2 }

		
--         1.3.6.1.4.1.37950.1.1.5.10.2.7.4
-- 1.3.6.1.4.1.37950.1.1.5.10.2.7.3
-- 1.3.6.1.4.1.37950.1.1.5.10.2.7.3
-- 1.3.6.1.4.1.37950.1.1.5.10.2.7.3
-- 1.3.6.1.4.1.37950.1.1.5.10.2.7.3
-- 1.3.6.1.4.1.37950.1.1.5.10.2.7.3
-- 1.3.6.1.4.1.37950.1.1.5.10.2.7.3
-- 1.3.6.1.4.1.37950.1.1.5.10.2.7.3
		-- 1.3.6.1.4.1.37950.1.1.5.10.2.7.3
		ipv6AddrPlen OBJECT-TYPE
			SYNTAX Integer32
			MAX-ACCESS read-write
			STATUS current
			DESCRIPTION
				"Description."
			::= { vlanIPv6Cfg 3 }

		
--         1.3.6.1.4.1.37950.1.1.5.10.2.7.5
-- 1.3.6.1.4.1.37950.1.1.5.10.2.7.4
-- 1.3.6.1.4.1.37950.1.1.5.10.2.7.4
-- 1.3.6.1.4.1.37950.1.1.5.10.2.7.4
-- 1.3.6.1.4.1.37950.1.1.5.10.2.7.4
-- 1.3.6.1.4.1.37950.1.1.5.10.2.7.4
-- 1.3.6.1.4.1.37950.1.1.5.10.2.7.4
-- 1.3.6.1.4.1.37950.1.1.5.10.2.7.4
		-- 1.3.6.1.4.1.37950.1.1.5.10.2.7.4
		ipv6Addrtype OBJECT-TYPE
			SYNTAX INTEGER
				{
				global(0),
				link-local(1),
				eui-64(2)
				}
			MAX-ACCESS read-write
			STATUS current
			DESCRIPTION
				"Description."
			::= { vlanIPv6Cfg 4 }

		
--         1.3.6.1.4.1.37950.1.1.5.10.2.7.6
-- 1.3.6.1.4.1.37950.1.1.5.10.2.7.5
-- 1.3.6.1.4.1.37950.1.1.5.10.2.7.5
-- 1.3.6.1.4.1.37950.1.1.5.10.2.7.5
-- 1.3.6.1.4.1.37950.1.1.5.10.2.7.5
-- 1.3.6.1.4.1.37950.1.1.5.10.2.7.5
-- 1.3.6.1.4.1.37950.1.1.5.10.2.7.5
-- 1.3.6.1.4.1.37950.1.1.5.10.2.7.5
		-- 1.3.6.1.4.1.37950.1.1.5.10.2.7.5
		ipv6AddrAction OBJECT-TYPE
			SYNTAX INTEGER
				{
				add(1),
				delete(2)
				}
			MAX-ACCESS read-write
			STATUS current
			DESCRIPTION
				"Description."
			::= { vlanIPv6Cfg 5 }

		
--         1.3.6.1.4.1.37950.1.1.5.10.2.8
-- 1.3.6.1.4.1.37950.1.1.5.10.2.8
-- 1.3.6.1.4.1.37950.1.1.5.10.2.8
-- 1.3.6.1.4.1.37950.1.1.5.10.2.8
-- 1.3.6.1.4.1.37950.1.1.5.10.2.8
-- 1.3.6.1.4.1.37950.1.1.5.10.2.8
-- 1.3.6.1.4.1.37950.1.1.5.10.2.8
-- 1.3.6.1.4.1.37950.1.1.5.10.2.8
		-- 1.3.6.1.4.1.37950.1.1.5.10.2.8
		vlanIPv6Table OBJECT-TYPE
			SYNTAX SEQUENCE OF VlanIPv6Entry
			MAX-ACCESS not-accessible
			STATUS current
			DESCRIPTION
				"Description."
			::= { v1600dVLAN 8 }

		
--         1.3.6.1.4.1.37950.1.1.5.10.2.8.1
-- 1.3.6.1.4.1.37950.1.1.5.10.2.8.1
-- 1.3.6.1.4.1.37950.1.1.5.10.2.8.1
-- 1.3.6.1.4.1.37950.1.1.5.10.2.8.1
-- 1.3.6.1.4.1.37950.1.1.5.10.2.8.1
-- 1.3.6.1.4.1.37950.1.1.5.10.2.8.1
-- 1.3.6.1.4.1.37950.1.1.5.10.2.8.1
-- 1.3.6.1.4.1.37950.1.1.5.10.2.8.1
		-- 1.3.6.1.4.1.37950.1.1.5.10.2.8.1
		vlanIPv6Entry OBJECT-TYPE
			SYNTAX VlanIPv6Entry
			MAX-ACCESS not-accessible
			STATUS current
			DESCRIPTION
				"Description."
			INDEX { ipv6Vlanid, ipv6AddrIndex }
			::= { vlanIPv6Table 1 }

		
		VlanIPv6Entry ::=
			SEQUENCE { 
				ipv6Vlanid
					Integer32,
				ipv6AddrIndex
					Integer32,
				ipv6Address
					OCTET STRING,
				ipv6AddrPfxLen
					INTEGER,
				ipv6AddrPrefixDescr
					OCTET STRING
			 }

--         1.3.6.1.4.1.37950.1.1.5.10.2.8.1.1
-- 1.3.6.1.4.1.37950.1.1.5.10.2.8.1.1
-- 1.3.6.1.4.1.37950.1.1.5.10.2.8.1.1
-- 1.3.6.1.4.1.37950.1.1.5.10.2.8.1.1
-- 1.3.6.1.4.1.37950.1.1.5.10.2.8.1.1
-- 1.3.6.1.4.1.37950.1.1.5.10.2.8.1.1
-- 1.3.6.1.4.1.37950.1.1.5.10.2.8.1.1
-- 1.3.6.1.4.1.37950.1.1.5.10.2.8.1.1
		-- 1.3.6.1.4.1.37950.1.1.5.10.2.8.1.1
		ipv6Vlanid OBJECT-TYPE
			SYNTAX Integer32
			MAX-ACCESS read-only
			STATUS current
			DESCRIPTION
				"Description."
			::= { vlanIPv6Entry 1 }

		
--         1.3.6.1.4.1.37950.1.1.5.10.2.8.1.2
-- 1.3.6.1.4.1.37950.1.1.5.10.2.8.1.2
-- 1.3.6.1.4.1.37950.1.1.5.10.2.8.1.2
-- 1.3.6.1.4.1.37950.1.1.5.10.2.8.1.2
-- 1.3.6.1.4.1.37950.1.1.5.10.2.8.1.2
-- 1.3.6.1.4.1.37950.1.1.5.10.2.8.1.2
-- 1.3.6.1.4.1.37950.1.1.5.10.2.8.1.2
-- 1.3.6.1.4.1.37950.1.1.5.10.2.8.1.2
		-- 1.3.6.1.4.1.37950.1.1.5.10.2.8.1.2
		ipv6AddrIndex OBJECT-TYPE
			SYNTAX Integer32
			MAX-ACCESS read-only
			STATUS current
			DESCRIPTION
				"Description."
			::= { vlanIPv6Entry 2 }

		
--         1.3.6.1.4.1.37950.1.1.5.10.2.8.1.3
-- 1.3.6.1.4.1.37950.1.1.5.10.2.8.1.3
-- 1.3.6.1.4.1.37950.1.1.5.10.2.8.1.3
-- 1.3.6.1.4.1.37950.1.1.5.10.2.8.1.3
-- 1.3.6.1.4.1.37950.1.1.5.10.2.8.1.3
-- 1.3.6.1.4.1.37950.1.1.5.10.2.8.1.3
-- 1.3.6.1.4.1.37950.1.1.5.10.2.8.1.3
-- 1.3.6.1.4.1.37950.1.1.5.10.2.8.1.3
		-- 1.3.6.1.4.1.37950.1.1.5.10.2.8.1.3
		ipv6Address OBJECT-TYPE
			SYNTAX OCTET STRING
			MAX-ACCESS read-only
			STATUS current
			DESCRIPTION
				"Description."
			::= { vlanIPv6Entry 3 }

		
--         1.3.6.1.4.1.37950.1.1.5.10.2.8.1.4
-- 1.3.6.1.4.1.37950.1.1.5.10.2.8.1.4
-- 1.3.6.1.4.1.37950.1.1.5.10.2.8.1.4
-- 1.3.6.1.4.1.37950.1.1.5.10.2.8.1.4
-- 1.3.6.1.4.1.37950.1.1.5.10.2.8.1.4
-- 1.3.6.1.4.1.37950.1.1.5.10.2.8.1.4
-- 1.3.6.1.4.1.37950.1.1.5.10.2.8.1.4
-- 1.3.6.1.4.1.37950.1.1.5.10.2.8.1.4
		-- 1.3.6.1.4.1.37950.1.1.5.10.2.8.1.4
		ipv6AddrPfxLen OBJECT-TYPE
			SYNTAX INTEGER (0..128)
			MAX-ACCESS read-only
			STATUS current
			DESCRIPTION
				"Description."
			::= { vlanIPv6Entry 4 }

		
--         1.3.6.1.4.1.37950.1.1.5.10.2.8.1.5
-- 1.3.6.1.4.1.37950.1.1.5.10.2.8.1.5
-- 1.3.6.1.4.1.37950.1.1.5.10.2.8.1.5
-- 1.3.6.1.4.1.37950.1.1.5.10.2.8.1.5
-- 1.3.6.1.4.1.37950.1.1.5.10.2.8.1.5
-- 1.3.6.1.4.1.37950.1.1.5.10.2.8.1.5
-- 1.3.6.1.4.1.37950.1.1.5.10.2.8.1.5
-- 1.3.6.1.4.1.37950.1.1.5.10.2.8.1.5
		-- 1.3.6.1.4.1.37950.1.1.5.10.2.8.1.5
		ipv6AddrPrefixDescr OBJECT-TYPE
			SYNTAX OCTET STRING
			MAX-ACCESS read-only
			STATUS current
			DESCRIPTION
				"Description."
			::= { vlanIPv6Entry 5 }

		
--         1.3.6.1.4.1.37950.1.1.5.10.2.9
-- 1.3.6.1.4.1.37950.1.1.5.10.2.9
-- 1.3.6.1.4.1.37950.1.1.5.10.2.9
-- 1.3.6.1.4.1.37950.1.1.5.10.2.9
-- 1.3.6.1.4.1.37950.1.1.5.10.2.9
-- 1.3.6.1.4.1.37950.1.1.5.10.2.9
-- 1.3.6.1.4.1.37950.1.1.5.10.2.9
-- 1.3.6.1.4.1.37950.1.1.5.10.2.9
		-- 1.3.6.1.4.1.37950.1.1.5.10.2.9
		ipv6SlaacCfg OBJECT IDENTIFIER ::= { v1600dVLAN 9 }

		
--         1.3.6.1.4.1.37950.1.1.5.10.2.9.1
-- 1.3.6.1.4.1.37950.1.1.5.10.2.9.1
-- 1.3.6.1.4.1.37950.1.1.5.10.2.9.1
-- 1.3.6.1.4.1.37950.1.1.5.10.2.9.1
-- 1.3.6.1.4.1.37950.1.1.5.10.2.9.1
-- 1.3.6.1.4.1.37950.1.1.5.10.2.9.1
-- 1.3.6.1.4.1.37950.1.1.5.10.2.9.1
-- 1.3.6.1.4.1.37950.1.1.5.10.2.9.1
		-- 1.3.6.1.4.1.37950.1.1.5.10.2.9.1
		ipv6SlaacVlanId OBJECT-TYPE
			SYNTAX Integer32
			MAX-ACCESS read-write
			STATUS current
			DESCRIPTION
				"Description."
			::= { ipv6SlaacCfg 1 }

		
--         1.3.6.1.4.1.37950.1.1.5.10.2.9.2
-- 1.3.6.1.4.1.37950.1.1.5.10.2.9.2
-- 1.3.6.1.4.1.37950.1.1.5.10.2.9.2
-- 1.3.6.1.4.1.37950.1.1.5.10.2.9.2
-- 1.3.6.1.4.1.37950.1.1.5.10.2.9.2
-- 1.3.6.1.4.1.37950.1.1.5.10.2.9.2
-- 1.3.6.1.4.1.37950.1.1.5.10.2.9.2
-- 1.3.6.1.4.1.37950.1.1.5.10.2.9.2
		-- 1.3.6.1.4.1.37950.1.1.5.10.2.9.2
		ipv6SlaacSuppressRaEnable OBJECT-TYPE
			SYNTAX INTEGER
				{
				on(1),
				off(2)
				}
			MAX-ACCESS read-write
			STATUS current
			DESCRIPTION
				"Description."
			::= { ipv6SlaacCfg 2 }

		
--         1.3.6.1.4.1.37950.1.1.5.10.2.9.3
-- 1.3.6.1.4.1.37950.1.1.5.10.2.9.3
-- 1.3.6.1.4.1.37950.1.1.5.10.2.9.3
-- 1.3.6.1.4.1.37950.1.1.5.10.2.9.3
-- 1.3.6.1.4.1.37950.1.1.5.10.2.9.3
-- 1.3.6.1.4.1.37950.1.1.5.10.2.9.3
-- 1.3.6.1.4.1.37950.1.1.5.10.2.9.3
-- 1.3.6.1.4.1.37950.1.1.5.10.2.9.3
		-- 1.3.6.1.4.1.37950.1.1.5.10.2.9.3
		ipv6SlaacInterval OBJECT-TYPE
			SYNTAX Integer32 (1..1800)
			MAX-ACCESS read-write
			STATUS current
			DESCRIPTION
				"Description."
			DEFVAL { 0 }
			::= { ipv6SlaacCfg 3 }

		
--         1.3.6.1.4.1.37950.1.1.5.10.2.9.4
-- 1.3.6.1.4.1.37950.1.1.5.10.2.9.4
-- 1.3.6.1.4.1.37950.1.1.5.10.2.9.4
-- 1.3.6.1.4.1.37950.1.1.5.10.2.9.4
-- 1.3.6.1.4.1.37950.1.1.5.10.2.9.4
-- 1.3.6.1.4.1.37950.1.1.5.10.2.9.4
-- 1.3.6.1.4.1.37950.1.1.5.10.2.9.4
-- 1.3.6.1.4.1.37950.1.1.5.10.2.9.4
		-- 1.3.6.1.4.1.37950.1.1.5.10.2.9.4
		ipv6SlaacRALifetime OBJECT-TYPE
			SYNTAX Integer32 (0..9000)
			MAX-ACCESS read-write
			STATUS current
			DESCRIPTION
				"Description."
			DEFVAL { 600 }
			::= { ipv6SlaacCfg 4 }

		
--         1.3.6.1.4.1.37950.1.1.5.10.2.9.5
-- 1.3.6.1.4.1.37950.1.1.5.10.2.9.5
-- 1.3.6.1.4.1.37950.1.1.5.10.2.9.5
-- 1.3.6.1.4.1.37950.1.1.5.10.2.9.5
-- 1.3.6.1.4.1.37950.1.1.5.10.2.9.5
-- 1.3.6.1.4.1.37950.1.1.5.10.2.9.5
-- 1.3.6.1.4.1.37950.1.1.5.10.2.9.5
-- 1.3.6.1.4.1.37950.1.1.5.10.2.9.5
		-- 1.3.6.1.4.1.37950.1.1.5.10.2.9.5
		ipv6SlaacReachabletime OBJECT-TYPE
			SYNTAX Unsigned32 (0..3600000)
			MAX-ACCESS read-write
			STATUS current
			DESCRIPTION
				"Description."
			DEFVAL { 0 }
			::= { ipv6SlaacCfg 5 }

		
--         1.3.6.1.4.1.37950.1.1.5.10.2.9.6
-- 1.3.6.1.4.1.37950.1.1.5.10.2.9.6
-- 1.3.6.1.4.1.37950.1.1.5.10.2.9.6
-- 1.3.6.1.4.1.37950.1.1.5.10.2.9.6
-- 1.3.6.1.4.1.37950.1.1.5.10.2.9.6
-- 1.3.6.1.4.1.37950.1.1.5.10.2.9.6
-- 1.3.6.1.4.1.37950.1.1.5.10.2.9.6
-- 1.3.6.1.4.1.37950.1.1.5.10.2.9.6
		-- 1.3.6.1.4.1.37950.1.1.5.10.2.9.6
		ipv6SlaachomeAgentCfgFlag OBJECT-TYPE
			SYNTAX INTEGER
				{
				set(1),
				not-set(2)
				}
			MAX-ACCESS read-write
			STATUS current
			DESCRIPTION
				"Description."
			DEFVAL { not-set }
			::= { ipv6SlaacCfg 6 }

		
--         1.3.6.1.4.1.37950.1.1.5.10.2.9.7
-- 1.3.6.1.4.1.37950.1.1.5.10.2.9.7
-- 1.3.6.1.4.1.37950.1.1.5.10.2.9.7
-- 1.3.6.1.4.1.37950.1.1.5.10.2.9.7
-- 1.3.6.1.4.1.37950.1.1.5.10.2.9.7
-- 1.3.6.1.4.1.37950.1.1.5.10.2.9.7
-- 1.3.6.1.4.1.37950.1.1.5.10.2.9.7
-- 1.3.6.1.4.1.37950.1.1.5.10.2.9.7
		-- 1.3.6.1.4.1.37950.1.1.5.10.2.9.7
		ipv6SlaachomeAgentPreference OBJECT-TYPE
			SYNTAX Integer32
			MAX-ACCESS read-write
			STATUS current
			DESCRIPTION
				"Description."
			DEFVAL { 0 }
			::= { ipv6SlaacCfg 7 }

		
--         1.3.6.1.4.1.37950.1.1.5.10.2.9.8
-- 1.3.6.1.4.1.37950.1.1.5.10.2.9.8
-- 1.3.6.1.4.1.37950.1.1.5.10.2.9.8
-- 1.3.6.1.4.1.37950.1.1.5.10.2.9.8
-- 1.3.6.1.4.1.37950.1.1.5.10.2.9.8
-- 1.3.6.1.4.1.37950.1.1.5.10.2.9.8
-- 1.3.6.1.4.1.37950.1.1.5.10.2.9.8
-- 1.3.6.1.4.1.37950.1.1.5.10.2.9.8
		-- 1.3.6.1.4.1.37950.1.1.5.10.2.9.8
		ipv6SlaachomeAgentLifeTime OBJECT-TYPE
			SYNTAX Integer32 (0..65520)
			MAX-ACCESS read-write
			STATUS current
			DESCRIPTION
				"Description."
			DEFVAL { 1800 }
			::= { ipv6SlaacCfg 8 }

		
--         1.3.6.1.4.1.37950.1.1.5.10.2.9.9
-- 1.3.6.1.4.1.37950.1.1.5.10.2.9.9
-- 1.3.6.1.4.1.37950.1.1.5.10.2.9.9
-- 1.3.6.1.4.1.37950.1.1.5.10.2.9.9
-- 1.3.6.1.4.1.37950.1.1.5.10.2.9.9
-- 1.3.6.1.4.1.37950.1.1.5.10.2.9.9
-- 1.3.6.1.4.1.37950.1.1.5.10.2.9.9
-- 1.3.6.1.4.1.37950.1.1.5.10.2.9.9
		-- 1.3.6.1.4.1.37950.1.1.5.10.2.9.9
		ipv6SlaacAdvIntervalOption OBJECT-TYPE
			SYNTAX INTEGER
				{
				yes(1),
				no(2)
				}
			MAX-ACCESS read-write
			STATUS current
			DESCRIPTION
				"Description."
			DEFVAL { no }
			::= { ipv6SlaacCfg 9 }

		
--         1.3.6.1.4.1.37950.1.1.5.10.2.9.10
-- 1.3.6.1.4.1.37950.1.1.5.10.2.9.10
-- 1.3.6.1.4.1.37950.1.1.5.10.2.9.10
-- 1.3.6.1.4.1.37950.1.1.5.10.2.9.10
-- 1.3.6.1.4.1.37950.1.1.5.10.2.9.10
-- 1.3.6.1.4.1.37950.1.1.5.10.2.9.10
-- 1.3.6.1.4.1.37950.1.1.5.10.2.9.10
-- 1.3.6.1.4.1.37950.1.1.5.10.2.9.10
		-- 1.3.6.1.4.1.37950.1.1.5.10.2.9.10
		ipv6SlaacManaCfgFlag OBJECT-TYPE
			SYNTAX INTEGER
				{
				set(1),
				not-set(2)
				}
			MAX-ACCESS read-write
			STATUS current
			DESCRIPTION
				"Description."
			DEFVAL { not-set }
			::= { ipv6SlaacCfg 10 }

		
--         1.3.6.1.4.1.37950.1.1.5.10.2.9.11
-- 1.3.6.1.4.1.37950.1.1.5.10.2.9.11
-- 1.3.6.1.4.1.37950.1.1.5.10.2.9.11
-- 1.3.6.1.4.1.37950.1.1.5.10.2.9.11
-- 1.3.6.1.4.1.37950.1.1.5.10.2.9.11
-- 1.3.6.1.4.1.37950.1.1.5.10.2.9.11
-- 1.3.6.1.4.1.37950.1.1.5.10.2.9.11
-- 1.3.6.1.4.1.37950.1.1.5.10.2.9.11
		-- 1.3.6.1.4.1.37950.1.1.5.10.2.9.11
		ipv6SlaacOtherCfgFlag OBJECT-TYPE
			SYNTAX INTEGER
				{
				set(1),
				not-set(2)
				}
			MAX-ACCESS read-write
			STATUS current
			DESCRIPTION
				"Description."
			DEFVAL { not-set }
			::= { ipv6SlaacCfg 11 }

		
--         1.3.6.1.4.1.37950.1.1.5.10.2.9.12
-- 1.3.6.1.4.1.37950.1.1.5.10.2.9.12
-- 1.3.6.1.4.1.37950.1.1.5.10.2.9.12
-- 1.3.6.1.4.1.37950.1.1.5.10.2.9.12
-- 1.3.6.1.4.1.37950.1.1.5.10.2.9.12
-- 1.3.6.1.4.1.37950.1.1.5.10.2.9.12
-- 1.3.6.1.4.1.37950.1.1.5.10.2.9.12
-- 1.3.6.1.4.1.37950.1.1.5.10.2.9.12
		-- 1.3.6.1.4.1.37950.1.1.5.10.2.9.12
		ipv6SlaacAddrPrefix OBJECT-TYPE
			SYNTAX OCTET STRING
			MAX-ACCESS read-write
			STATUS current
			DESCRIPTION
				"Description."
			::= { ipv6SlaacCfg 12 }

		
--         1.3.6.1.4.1.37950.1.1.5.10.2.9.13
-- 1.3.6.1.4.1.37950.1.1.5.10.2.9.13
-- 1.3.6.1.4.1.37950.1.1.5.10.2.9.13
-- 1.3.6.1.4.1.37950.1.1.5.10.2.9.13
-- 1.3.6.1.4.1.37950.1.1.5.10.2.9.13
-- 1.3.6.1.4.1.37950.1.1.5.10.2.9.13
-- 1.3.6.1.4.1.37950.1.1.5.10.2.9.13
-- 1.3.6.1.4.1.37950.1.1.5.10.2.9.13
		-- 1.3.6.1.4.1.37950.1.1.5.10.2.9.13
		ipv6SlaacAddrPrefixLength OBJECT-TYPE
			SYNTAX Unsigned32
			MAX-ACCESS read-write
			STATUS current
			DESCRIPTION
				"Description."
			::= { ipv6SlaacCfg 13 }

		
--         1.3.6.1.4.1.37950.1.1.5.10.2.9.14
-- 1.3.6.1.4.1.37950.1.1.5.10.2.9.14
-- 1.3.6.1.4.1.37950.1.1.5.10.2.9.14
-- 1.3.6.1.4.1.37950.1.1.5.10.2.9.14
-- 1.3.6.1.4.1.37950.1.1.5.10.2.9.14
-- 1.3.6.1.4.1.37950.1.1.5.10.2.9.14
-- 1.3.6.1.4.1.37950.1.1.5.10.2.9.14
-- 1.3.6.1.4.1.37950.1.1.5.10.2.9.14
		-- 1.3.6.1.4.1.37950.1.1.5.10.2.9.14
		ipv6AddrPrefixValidLifeTime OBJECT-TYPE
			SYNTAX Unsigned32
			MAX-ACCESS read-write
			STATUS current
			DESCRIPTION
				"Description."
			DEFVAL { 0 }
			::= { ipv6SlaacCfg 14 }

		
--         1.3.6.1.4.1.37950.1.1.5.10.2.9.15
-- 1.3.6.1.4.1.37950.1.1.5.10.2.9.15
-- 1.3.6.1.4.1.37950.1.1.5.10.2.9.15
-- 1.3.6.1.4.1.37950.1.1.5.10.2.9.15
-- 1.3.6.1.4.1.37950.1.1.5.10.2.9.15
-- 1.3.6.1.4.1.37950.1.1.5.10.2.9.15
-- 1.3.6.1.4.1.37950.1.1.5.10.2.9.15
-- 1.3.6.1.4.1.37950.1.1.5.10.2.9.15
		-- 1.3.6.1.4.1.37950.1.1.5.10.2.9.15
		ipv6AddrPrefixPreferrefLifetime OBJECT-TYPE
			SYNTAX Unsigned32
			MAX-ACCESS read-write
			STATUS current
			DESCRIPTION
				"Description."
			DEFVAL { 0 }
			::= { ipv6SlaacCfg 15 }

		
--         1.3.6.1.4.1.37950.1.1.5.10.2.9.16
-- 1.3.6.1.4.1.37950.1.1.5.10.2.9.16
-- 1.3.6.1.4.1.37950.1.1.5.10.2.9.16
-- 1.3.6.1.4.1.37950.1.1.5.10.2.9.16
-- 1.3.6.1.4.1.37950.1.1.5.10.2.9.16
-- 1.3.6.1.4.1.37950.1.1.5.10.2.9.16
-- 1.3.6.1.4.1.37950.1.1.5.10.2.9.16
-- 1.3.6.1.4.1.37950.1.1.5.10.2.9.16
		-- 1.3.6.1.4.1.37950.1.1.5.10.2.9.16
		ipv6AddrPrefixOfflink OBJECT-TYPE
			SYNTAX INTEGER
				{
				set(1),
				not-set(2)
				}
			MAX-ACCESS read-write
			STATUS current
			DESCRIPTION
				"Description."
			DEFVAL { not-set }
			::= { ipv6SlaacCfg 16 }

		
--         1.3.6.1.4.1.37950.1.1.5.10.2.9.17
-- 1.3.6.1.4.1.37950.1.1.5.10.2.9.17
-- 1.3.6.1.4.1.37950.1.1.5.10.2.9.17
-- 1.3.6.1.4.1.37950.1.1.5.10.2.9.17
-- 1.3.6.1.4.1.37950.1.1.5.10.2.9.17
-- 1.3.6.1.4.1.37950.1.1.5.10.2.9.17
-- 1.3.6.1.4.1.37950.1.1.5.10.2.9.17
-- 1.3.6.1.4.1.37950.1.1.5.10.2.9.17
		-- 1.3.6.1.4.1.37950.1.1.5.10.2.9.17
		ipv6AddrPrefixPreNoAutoCfg OBJECT-TYPE
			SYNTAX INTEGER
				{
				set(1),
				not-set(2)
				}
			MAX-ACCESS read-write
			STATUS current
			DESCRIPTION
				"Description."
			DEFVAL { not-set }
			::= { ipv6SlaacCfg 17 }

		
--         1.3.6.1.4.1.37950.1.1.5.10.2.9.18
-- 1.3.6.1.4.1.37950.1.1.5.10.2.9.18
-- 1.3.6.1.4.1.37950.1.1.5.10.2.9.18
-- 1.3.6.1.4.1.37950.1.1.5.10.2.9.18
-- 1.3.6.1.4.1.37950.1.1.5.10.2.9.18
-- 1.3.6.1.4.1.37950.1.1.5.10.2.9.18
-- 1.3.6.1.4.1.37950.1.1.5.10.2.9.18
-- 1.3.6.1.4.1.37950.1.1.5.10.2.9.18
		-- 1.3.6.1.4.1.37950.1.1.5.10.2.9.18
		ipv6AddrPrefixRouterAddr OBJECT-TYPE
			SYNTAX INTEGER
				{
				set(1),
				not-set(2)
				}
			MAX-ACCESS read-write
			STATUS current
			DESCRIPTION
				"Description."
			DEFVAL { not-set }
			::= { ipv6SlaacCfg 18 }

		
--         1.3.6.1.4.1.37950.1.1.5.10.2.9.19
-- 1.3.6.1.4.1.37950.1.1.5.10.2.9.19
-- 1.3.6.1.4.1.37950.1.1.5.10.2.9.19
-- 1.3.6.1.4.1.37950.1.1.5.10.2.9.19
-- 1.3.6.1.4.1.37950.1.1.5.10.2.9.19
-- 1.3.6.1.4.1.37950.1.1.5.10.2.9.19
-- 1.3.6.1.4.1.37950.1.1.5.10.2.9.19
-- 1.3.6.1.4.1.37950.1.1.5.10.2.9.19
		-- 1.3.6.1.4.1.37950.1.1.5.10.2.9.19
		ipv6SlaacRouterPrefer OBJECT-TYPE
			SYNTAX INTEGER
				{
				high(1),
				medium(2),
				low(3),
				invalid(4),
				null(5)
				}
			MAX-ACCESS read-write
			STATUS current
			DESCRIPTION
				"Description."
			DEFVAL { medium }
			::= { ipv6SlaacCfg 19 }

		
--         1.3.6.1.4.1.37950.1.1.5.10.2.9.20
-- 1.3.6.1.4.1.37950.1.1.5.10.2.9.20
-- 1.3.6.1.4.1.37950.1.1.5.10.2.9.20
-- 1.3.6.1.4.1.37950.1.1.5.10.2.9.20
-- 1.3.6.1.4.1.37950.1.1.5.10.2.9.20
-- 1.3.6.1.4.1.37950.1.1.5.10.2.9.20
-- 1.3.6.1.4.1.37950.1.1.5.10.2.9.20
-- 1.3.6.1.4.1.37950.1.1.5.10.2.9.20
		-- 1.3.6.1.4.1.37950.1.1.5.10.2.9.20
		ipv6SlaacMTU OBJECT-TYPE
			SYNTAX Integer32 (1..65535)
			MAX-ACCESS read-write
			STATUS current
			DESCRIPTION
				"Description."
			DEFVAL { 0 }
			::= { ipv6SlaacCfg 20 }

		
--         1.3.6.1.4.1.37950.1.1.5.10.2.9.21
-- 1.3.6.1.4.1.37950.1.1.5.10.2.9.21
-- 1.3.6.1.4.1.37950.1.1.5.10.2.9.21
-- 1.3.6.1.4.1.37950.1.1.5.10.2.9.21
-- 1.3.6.1.4.1.37950.1.1.5.10.2.9.21
-- 1.3.6.1.4.1.37950.1.1.5.10.2.9.21
-- 1.3.6.1.4.1.37950.1.1.5.10.2.9.21
-- 1.3.6.1.4.1.37950.1.1.5.10.2.9.21
		-- 1.3.6.1.4.1.37950.1.1.5.10.2.9.21
		ipv6SlaacAction OBJECT-TYPE
			SYNTAX INTEGER
				{
				add(1),
				del-Interval(2),
				del-Ralifetime(3),
				del-ReachableTime(4),
				del-homeAgentPref(5),
				del-homeAgentLifetime(6),
				del-NDPrefix(7),
				del-MTU(8),
				delAll(9)
				}
			MAX-ACCESS read-write
			STATUS current
			DESCRIPTION
				"Description."
			::= { ipv6SlaacCfg 21 }

		
--         1.3.6.1.4.1.37950.1.1.5.10.2.10
-- 1.3.6.1.4.1.37950.1.1.5.10.2.10
-- 1.3.6.1.4.1.37950.1.1.5.10.2.10
-- 1.3.6.1.4.1.37950.1.1.5.10.2.10
-- 1.3.6.1.4.1.37950.1.1.5.10.2.10
-- 1.3.6.1.4.1.37950.1.1.5.10.2.10
-- 1.3.6.1.4.1.37950.1.1.5.10.2.10
-- 1.3.6.1.4.1.37950.1.1.5.10.2.10
		-- 1.3.6.1.4.1.37950.1.1.5.10.2.10
		ipv6SlaacTable OBJECT-TYPE
			SYNTAX SEQUENCE OF Ipv6SlaacEntry
			MAX-ACCESS not-accessible
			STATUS current
			DESCRIPTION
				"Description."
			::= { v1600dVLAN 10 }

		
--         1.3.6.1.4.1.37950.1.1.5.10.2.10.1
-- 1.3.6.1.4.1.37950.1.1.5.10.2.10.1
-- 1.3.6.1.4.1.37950.1.1.5.10.2.10.1
-- 1.3.6.1.4.1.37950.1.1.5.10.2.10.1
-- 1.3.6.1.4.1.37950.1.1.5.10.2.10.1
-- 1.3.6.1.4.1.37950.1.1.5.10.2.10.1
-- 1.3.6.1.4.1.37950.1.1.5.10.2.10.1
-- 1.3.6.1.4.1.37950.1.1.5.10.2.10.1
		-- 1.3.6.1.4.1.37950.1.1.5.10.2.10.1
		ipv6SlaacEntry OBJECT-TYPE
			SYNTAX Ipv6SlaacEntry
			MAX-ACCESS not-accessible
			STATUS current
			DESCRIPTION
				"Description."
			INDEX { ipv6SlaacIndex, ipv6SlaacVlanid }
			::= { ipv6SlaacTable 1 }

		
		Ipv6SlaacEntry ::=
			SEQUENCE { 
				ipv6SlaacVlanid
					Integer32,
				ipv6SlaacIndex
					Integer32,
				ipv6SlaacSuppressRaStatus
					INTEGER,
				ipv6SlaacRaInterval
					Integer32,
				ipv6SlaacRaLifetime
					Integer32,
				ipv6SlaacReachableTime
					Unsigned32,
				ipv6SlaachomeAgentCfgFg
					INTEGER,
				ipv6SlaachomeAgentPre
					Integer32,
				ipv6SlaachomeAgentLifetime
					Integer32,
				ipv6SlaacAdvIntervalOpt
					INTEGER,
				ipv6SlaacManaCfgFg
					INTEGER,
				ipv6SlaacOtherCfgFg
					INTEGER,
				ipv6SlaacPrefix
					OCTET STRING,
				ipv6AddrPfxAdvValidLifetime
					OCTET STRING,
				ipv6AddrPfxAdvPreferredLifetime
					OCTET STRING,
				ipv6AddrPfxOffLinkFlag
					INTEGER,
				ipv6AddrPfxAutonomousFlag
					INTEGER,
				ipv6AddrPfxRouterAddr
					INTEGER,
				ipv6AddrPfxRouterPreference
					INTEGER,
				ipv6AddrPfxMtu
					Integer32
			 }

--         1.3.6.1.4.1.37950.1.1.5.10.2.10.1.1
-- 1.3.6.1.4.1.37950.1.1.5.10.2.10.1.1
-- 1.3.6.1.4.1.37950.1.1.5.10.2.10.1.1
-- 1.3.6.1.4.1.37950.1.1.5.10.2.10.1.1
-- 1.3.6.1.4.1.37950.1.1.5.10.2.10.1.1
-- 1.3.6.1.4.1.37950.1.1.5.10.2.10.1.1
-- 1.3.6.1.4.1.37950.1.1.5.10.2.10.1.1
-- 1.3.6.1.4.1.37950.1.1.5.10.2.10.1.1
		-- 1.3.6.1.4.1.37950.1.1.5.10.2.10.1.1
		ipv6SlaacVlanid OBJECT-TYPE
			SYNTAX Integer32 (1..4094)
			MAX-ACCESS read-only
			STATUS current
			DESCRIPTION
				"Description."
			::= { ipv6SlaacEntry 1 }

		
--         1.3.6.1.4.1.37950.1.1.5.10.2.10.1.2
-- 1.3.6.1.4.1.37950.1.1.5.10.2.10.1.2
-- 1.3.6.1.4.1.37950.1.1.5.10.2.10.1.2
-- 1.3.6.1.4.1.37950.1.1.5.10.2.10.1.2
-- 1.3.6.1.4.1.37950.1.1.5.10.2.10.1.2
-- 1.3.6.1.4.1.37950.1.1.5.10.2.10.1.2
-- 1.3.6.1.4.1.37950.1.1.5.10.2.10.1.2
-- 1.3.6.1.4.1.37950.1.1.5.10.2.10.1.2
		-- 1.3.6.1.4.1.37950.1.1.5.10.2.10.1.2
		ipv6SlaacIndex OBJECT-TYPE
			SYNTAX Integer32
			MAX-ACCESS read-only
			STATUS current
			DESCRIPTION
				"Description."
			::= { ipv6SlaacEntry 2 }

		
--         1.3.6.1.4.1.37950.1.1.5.10.2.10.1.3
-- 1.3.6.1.4.1.37950.1.1.5.10.2.10.1.3
-- 1.3.6.1.4.1.37950.1.1.5.10.2.10.1.3
-- 1.3.6.1.4.1.37950.1.1.5.10.2.10.1.3
-- 1.3.6.1.4.1.37950.1.1.5.10.2.10.1.3
-- 1.3.6.1.4.1.37950.1.1.5.10.2.10.1.3
-- 1.3.6.1.4.1.37950.1.1.5.10.2.10.1.3
-- 1.3.6.1.4.1.37950.1.1.5.10.2.10.1.3
		-- 1.3.6.1.4.1.37950.1.1.5.10.2.10.1.3
		ipv6SlaacSuppressRaStatus OBJECT-TYPE
			SYNTAX INTEGER
				{
				on(1),
				off(2)
				}
			MAX-ACCESS read-only
			STATUS current
			DESCRIPTION
				"Description."
			::= { ipv6SlaacEntry 3 }

		
--         1.3.6.1.4.1.37950.1.1.5.10.2.10.1.4
-- 1.3.6.1.4.1.37950.1.1.5.10.2.10.1.4
-- 1.3.6.1.4.1.37950.1.1.5.10.2.10.1.4
-- 1.3.6.1.4.1.37950.1.1.5.10.2.10.1.4
-- 1.3.6.1.4.1.37950.1.1.5.10.2.10.1.4
-- 1.3.6.1.4.1.37950.1.1.5.10.2.10.1.4
-- 1.3.6.1.4.1.37950.1.1.5.10.2.10.1.4
-- 1.3.6.1.4.1.37950.1.1.5.10.2.10.1.4
		-- 1.3.6.1.4.1.37950.1.1.5.10.2.10.1.4
		ipv6SlaacRaInterval OBJECT-TYPE
			SYNTAX Integer32 (1..1800)
			MAX-ACCESS read-only
			STATUS current
			DESCRIPTION
				"Description."
			::= { ipv6SlaacEntry 4 }

		
--         1.3.6.1.4.1.37950.1.1.5.10.2.10.1.5
-- 1.3.6.1.4.1.37950.1.1.5.10.2.10.1.5
-- 1.3.6.1.4.1.37950.1.1.5.10.2.10.1.5
-- 1.3.6.1.4.1.37950.1.1.5.10.2.10.1.5
-- 1.3.6.1.4.1.37950.1.1.5.10.2.10.1.5
-- 1.3.6.1.4.1.37950.1.1.5.10.2.10.1.5
-- 1.3.6.1.4.1.37950.1.1.5.10.2.10.1.5
-- 1.3.6.1.4.1.37950.1.1.5.10.2.10.1.5
		-- 1.3.6.1.4.1.37950.1.1.5.10.2.10.1.5
		ipv6SlaacRaLifetime OBJECT-TYPE
			SYNTAX Integer32 (0..9000)
			MAX-ACCESS read-only
			STATUS current
			DESCRIPTION
				"Description."
			::= { ipv6SlaacEntry 5 }

		
--         1.3.6.1.4.1.37950.1.1.5.10.2.10.1.6
-- 1.3.6.1.4.1.37950.1.1.5.10.2.10.1.6
-- 1.3.6.1.4.1.37950.1.1.5.10.2.10.1.6
-- 1.3.6.1.4.1.37950.1.1.5.10.2.10.1.6
-- 1.3.6.1.4.1.37950.1.1.5.10.2.10.1.6
-- 1.3.6.1.4.1.37950.1.1.5.10.2.10.1.6
-- 1.3.6.1.4.1.37950.1.1.5.10.2.10.1.6
-- 1.3.6.1.4.1.37950.1.1.5.10.2.10.1.6
		-- 1.3.6.1.4.1.37950.1.1.5.10.2.10.1.6
		ipv6SlaacReachableTime OBJECT-TYPE
			SYNTAX Unsigned32 (1..3600000)
			MAX-ACCESS read-only
			STATUS current
			DESCRIPTION
				"Description."
			::= { ipv6SlaacEntry 6 }

		
--         1.3.6.1.4.1.37950.1.1.5.10.2.10.1.7
-- 1.3.6.1.4.1.37950.1.1.5.10.2.10.1.7
-- 1.3.6.1.4.1.37950.1.1.5.10.2.10.1.7
-- 1.3.6.1.4.1.37950.1.1.5.10.2.10.1.7
-- 1.3.6.1.4.1.37950.1.1.5.10.2.10.1.7
-- 1.3.6.1.4.1.37950.1.1.5.10.2.10.1.7
-- 1.3.6.1.4.1.37950.1.1.5.10.2.10.1.7
-- 1.3.6.1.4.1.37950.1.1.5.10.2.10.1.7
		-- 1.3.6.1.4.1.37950.1.1.5.10.2.10.1.7
		ipv6SlaachomeAgentCfgFg OBJECT-TYPE
			SYNTAX INTEGER
				{
				set(1),
				not-set(2)
				}
			MAX-ACCESS read-only
			STATUS current
			DESCRIPTION
				"Description."
			::= { ipv6SlaacEntry 7 }

		
--         1.3.6.1.4.1.37950.1.1.5.10.2.10.1.8
-- 1.3.6.1.4.1.37950.1.1.5.10.2.10.1.8
-- 1.3.6.1.4.1.37950.1.1.5.10.2.10.1.8
-- 1.3.6.1.4.1.37950.1.1.5.10.2.10.1.8
-- 1.3.6.1.4.1.37950.1.1.5.10.2.10.1.8
-- 1.3.6.1.4.1.37950.1.1.5.10.2.10.1.8
-- 1.3.6.1.4.1.37950.1.1.5.10.2.10.1.8
-- 1.3.6.1.4.1.37950.1.1.5.10.2.10.1.8
		-- 1.3.6.1.4.1.37950.1.1.5.10.2.10.1.8
		ipv6SlaachomeAgentPre OBJECT-TYPE
			SYNTAX Integer32 (0..65535)
			MAX-ACCESS read-only
			STATUS current
			DESCRIPTION
				"Description."
			::= { ipv6SlaacEntry 8 }

		
--         1.3.6.1.4.1.37950.1.1.5.10.2.10.1.9
-- 1.3.6.1.4.1.37950.1.1.5.10.2.10.1.9
-- 1.3.6.1.4.1.37950.1.1.5.10.2.10.1.9
-- 1.3.6.1.4.1.37950.1.1.5.10.2.10.1.9
-- 1.3.6.1.4.1.37950.1.1.5.10.2.10.1.9
-- 1.3.6.1.4.1.37950.1.1.5.10.2.10.1.9
-- 1.3.6.1.4.1.37950.1.1.5.10.2.10.1.9
-- 1.3.6.1.4.1.37950.1.1.5.10.2.10.1.9
		-- 1.3.6.1.4.1.37950.1.1.5.10.2.10.1.9
		ipv6SlaachomeAgentLifetime OBJECT-TYPE
			SYNTAX Integer32 (0..65520)
			MAX-ACCESS read-only
			STATUS current
			DESCRIPTION
				"Description."
			::= { ipv6SlaacEntry 9 }

		
--         1.3.6.1.4.1.37950.1.1.5.10.2.10.1.10
-- 1.3.6.1.4.1.37950.1.1.5.10.2.10.1.10
-- 1.3.6.1.4.1.37950.1.1.5.10.2.10.1.10
-- 1.3.6.1.4.1.37950.1.1.5.10.2.10.1.10
-- 1.3.6.1.4.1.37950.1.1.5.10.2.10.1.10
-- 1.3.6.1.4.1.37950.1.1.5.10.2.10.1.10
-- 1.3.6.1.4.1.37950.1.1.5.10.2.10.1.10
-- 1.3.6.1.4.1.37950.1.1.5.10.2.10.1.10
		-- 1.3.6.1.4.1.37950.1.1.5.10.2.10.1.10
		ipv6SlaacAdvIntervalOpt OBJECT-TYPE
			SYNTAX INTEGER
				{
				yes(1),
				no(2)
				}
			MAX-ACCESS read-only
			STATUS current
			DESCRIPTION
				"Description."
			::= { ipv6SlaacEntry 10 }

		
--         1.3.6.1.4.1.37950.1.1.5.10.2.10.1.11
-- 1.3.6.1.4.1.37950.1.1.5.10.2.10.1.11
-- 1.3.6.1.4.1.37950.1.1.5.10.2.10.1.11
-- 1.3.6.1.4.1.37950.1.1.5.10.2.10.1.11
-- 1.3.6.1.4.1.37950.1.1.5.10.2.10.1.11
-- 1.3.6.1.4.1.37950.1.1.5.10.2.10.1.11
-- 1.3.6.1.4.1.37950.1.1.5.10.2.10.1.11
-- 1.3.6.1.4.1.37950.1.1.5.10.2.10.1.11
		-- 1.3.6.1.4.1.37950.1.1.5.10.2.10.1.11
		ipv6SlaacManaCfgFg OBJECT-TYPE
			SYNTAX INTEGER
				{
				set(1),
				not-set(2)
				}
			MAX-ACCESS read-only
			STATUS current
			DESCRIPTION
				"Description."
			::= { ipv6SlaacEntry 11 }

		
--         1.3.6.1.4.1.37950.1.1.5.10.2.10.1.12
-- 1.3.6.1.4.1.37950.1.1.5.10.2.10.1.12
-- 1.3.6.1.4.1.37950.1.1.5.10.2.10.1.12
-- 1.3.6.1.4.1.37950.1.1.5.10.2.10.1.12
-- 1.3.6.1.4.1.37950.1.1.5.10.2.10.1.12
-- 1.3.6.1.4.1.37950.1.1.5.10.2.10.1.12
-- 1.3.6.1.4.1.37950.1.1.5.10.2.10.1.12
-- 1.3.6.1.4.1.37950.1.1.5.10.2.10.1.12
		-- 1.3.6.1.4.1.37950.1.1.5.10.2.10.1.12
		ipv6SlaacOtherCfgFg OBJECT-TYPE
			SYNTAX INTEGER
				{
				set(1),
				not-set(2)
				}
			MAX-ACCESS read-only
			STATUS current
			DESCRIPTION
				"Description."
			::= { ipv6SlaacEntry 12 }

		
--         1.3.6.1.4.1.37950.1.1.5.10.2.10.1.13
-- 1.3.6.1.4.1.37950.1.1.5.10.2.10.1.13
-- 1.3.6.1.4.1.37950.1.1.5.10.2.10.1.13
-- 1.3.6.1.4.1.37950.1.1.5.10.2.10.1.13
-- 1.3.6.1.4.1.37950.1.1.5.10.2.10.1.13
-- 1.3.6.1.4.1.37950.1.1.5.10.2.10.1.13
-- 1.3.6.1.4.1.37950.1.1.5.10.2.10.1.13
-- 1.3.6.1.4.1.37950.1.1.5.10.2.10.1.13
		-- 1.3.6.1.4.1.37950.1.1.5.10.2.10.1.13
		ipv6SlaacPrefix OBJECT-TYPE
			SYNTAX OCTET STRING
			MAX-ACCESS read-only
			STATUS current
			DESCRIPTION
				"Description."
			::= { ipv6SlaacEntry 13 }

		
--         1.3.6.1.4.1.37950.1.1.5.10.2.10.1.14
-- 1.3.6.1.4.1.37950.1.1.5.10.2.10.1.14
-- 1.3.6.1.4.1.37950.1.1.5.10.2.10.1.14
-- 1.3.6.1.4.1.37950.1.1.5.10.2.10.1.14
-- 1.3.6.1.4.1.37950.1.1.5.10.2.10.1.14
-- 1.3.6.1.4.1.37950.1.1.5.10.2.10.1.14
-- 1.3.6.1.4.1.37950.1.1.5.10.2.10.1.14
-- 1.3.6.1.4.1.37950.1.1.5.10.2.10.1.14
		-- 1.3.6.1.4.1.37950.1.1.5.10.2.10.1.14
		ipv6AddrPfxAdvValidLifetime OBJECT-TYPE
			SYNTAX OCTET STRING
			MAX-ACCESS read-only
			STATUS current
			DESCRIPTION
				"Description."
			::= { ipv6SlaacEntry 14 }

		
--         1.3.6.1.4.1.37950.1.1.5.10.2.10.1.15
-- 1.3.6.1.4.1.37950.1.1.5.10.2.10.1.15
-- 1.3.6.1.4.1.37950.1.1.5.10.2.10.1.15
-- 1.3.6.1.4.1.37950.1.1.5.10.2.10.1.15
-- 1.3.6.1.4.1.37950.1.1.5.10.2.10.1.15
-- 1.3.6.1.4.1.37950.1.1.5.10.2.10.1.15
-- 1.3.6.1.4.1.37950.1.1.5.10.2.10.1.15
-- 1.3.6.1.4.1.37950.1.1.5.10.2.10.1.15
		-- 1.3.6.1.4.1.37950.1.1.5.10.2.10.1.15
		ipv6AddrPfxAdvPreferredLifetime OBJECT-TYPE
			SYNTAX OCTET STRING
			MAX-ACCESS read-only
			STATUS current
			DESCRIPTION
				"Description."
			::= { ipv6SlaacEntry 15 }

		
--         1.3.6.1.4.1.37950.1.1.5.10.2.10.1.16
-- 1.3.6.1.4.1.37950.1.1.5.10.2.10.1.16
-- 1.3.6.1.4.1.37950.1.1.5.10.2.10.1.16
-- 1.3.6.1.4.1.37950.1.1.5.10.2.10.1.16
-- 1.3.6.1.4.1.37950.1.1.5.10.2.10.1.16
-- 1.3.6.1.4.1.37950.1.1.5.10.2.10.1.16
-- 1.3.6.1.4.1.37950.1.1.5.10.2.10.1.16
-- 1.3.6.1.4.1.37950.1.1.5.10.2.10.1.16
		-- 1.3.6.1.4.1.37950.1.1.5.10.2.10.1.16
		ipv6AddrPfxOffLinkFlag OBJECT-TYPE
			SYNTAX INTEGER
				{
				true(1),
				false(2)
				}
			MAX-ACCESS read-only
			STATUS current
			DESCRIPTION
				" "
			::= { ipv6SlaacEntry 16 }

		
--         1.3.6.1.4.1.37950.1.1.5.10.2.10.1.17
-- 1.3.6.1.4.1.37950.1.1.5.10.2.10.1.17
-- 1.3.6.1.4.1.37950.1.1.5.10.2.10.1.17
-- 1.3.6.1.4.1.37950.1.1.5.10.2.10.1.17
-- 1.3.6.1.4.1.37950.1.1.5.10.2.10.1.17
-- 1.3.6.1.4.1.37950.1.1.5.10.2.10.1.17
-- 1.3.6.1.4.1.37950.1.1.5.10.2.10.1.17
-- 1.3.6.1.4.1.37950.1.1.5.10.2.10.1.17
		-- 1.3.6.1.4.1.37950.1.1.5.10.2.10.1.17
		ipv6AddrPfxAutonomousFlag OBJECT-TYPE
			SYNTAX INTEGER
				{
				true(1),
				false(2)
				}
			MAX-ACCESS read-only
			STATUS current
			DESCRIPTION
				"Description."
			::= { ipv6SlaacEntry 17 }

		
--         1.3.6.1.4.1.37950.1.1.5.10.2.10.1.18
-- 1.3.6.1.4.1.37950.1.1.5.10.2.10.1.18
-- 1.3.6.1.4.1.37950.1.1.5.10.2.10.1.18
-- 1.3.6.1.4.1.37950.1.1.5.10.2.10.1.18
-- 1.3.6.1.4.1.37950.1.1.5.10.2.10.1.18
-- 1.3.6.1.4.1.37950.1.1.5.10.2.10.1.18
-- 1.3.6.1.4.1.37950.1.1.5.10.2.10.1.18
-- 1.3.6.1.4.1.37950.1.1.5.10.2.10.1.18
		-- 1.3.6.1.4.1.37950.1.1.5.10.2.10.1.18
		ipv6AddrPfxRouterAddr OBJECT-TYPE
			SYNTAX INTEGER
				{
				set(1),
				not-set(2)
				}
			MAX-ACCESS read-only
			STATUS current
			DESCRIPTION
				"Description."
			::= { ipv6SlaacEntry 18 }

		
--         1.3.6.1.4.1.37950.1.1.5.10.2.10.1.19
-- 1.3.6.1.4.1.37950.1.1.5.10.2.10.1.19
-- 1.3.6.1.4.1.37950.1.1.5.10.2.10.1.19
-- 1.3.6.1.4.1.37950.1.1.5.10.2.10.1.19
-- 1.3.6.1.4.1.37950.1.1.5.10.2.10.1.19
-- 1.3.6.1.4.1.37950.1.1.5.10.2.10.1.19
-- 1.3.6.1.4.1.37950.1.1.5.10.2.10.1.19
-- 1.3.6.1.4.1.37950.1.1.5.10.2.10.1.19
		-- 1.3.6.1.4.1.37950.1.1.5.10.2.10.1.19
		ipv6AddrPfxRouterPreference OBJECT-TYPE
			SYNTAX INTEGER
				{
				high(1),
				medium(2),
				low(3),
				invalid(4),
				null(5)
				}
			MAX-ACCESS read-only
			STATUS current
			DESCRIPTION
				"Description."
			::= { ipv6SlaacEntry 19 }

		
--         1.3.6.1.4.1.37950.1.1.5.10.2.10.1.20
-- 1.3.6.1.4.1.37950.1.1.5.10.2.10.1.20
-- 1.3.6.1.4.1.37950.1.1.5.10.2.10.1.20
-- 1.3.6.1.4.1.37950.1.1.5.10.2.10.1.20
-- 1.3.6.1.4.1.37950.1.1.5.10.2.10.1.20
-- 1.3.6.1.4.1.37950.1.1.5.10.2.10.1.20
-- 1.3.6.1.4.1.37950.1.1.5.10.2.10.1.20
-- 1.3.6.1.4.1.37950.1.1.5.10.2.10.1.20
		-- 1.3.6.1.4.1.37950.1.1.5.10.2.10.1.20
		ipv6AddrPfxMtu OBJECT-TYPE
			SYNTAX Integer32 (1..65535)
			MAX-ACCESS read-only
			STATUS current
			DESCRIPTION
				"Description."
			::= { ipv6SlaacEntry 20 }

		
--         1.3.6.1.4.1.37950.1.1.5.10.2.11
-- 1.3.6.1.4.1.37950.1.1.5.10.2.11
-- 1.3.6.1.4.1.37950.1.1.5.10.2.11
-- 1.3.6.1.4.1.37950.1.1.5.10.2.11
-- 1.3.6.1.4.1.37950.1.1.5.10.2.11
-- 1.3.6.1.4.1.37950.1.1.5.10.2.11
-- 1.3.6.1.4.1.37950.1.1.5.10.2.11
-- 1.3.6.1.4.1.37950.1.1.5.10.2.11
		-- 1.3.6.1.4.1.37950.1.1.5.10.2.11
		rdnssCfg OBJECT IDENTIFIER ::= { v1600dVLAN 11 }

		
--         1.3.6.1.4.1.37950.1.1.5.10.2.11.1
-- 1.3.6.1.4.1.37950.1.1.5.10.2.11.1
-- 1.3.6.1.4.1.37950.1.1.5.10.2.11.1
-- 1.3.6.1.4.1.37950.1.1.5.10.2.11.1
-- 1.3.6.1.4.1.37950.1.1.5.10.2.11.1
-- 1.3.6.1.4.1.37950.1.1.5.10.2.11.1
-- 1.3.6.1.4.1.37950.1.1.5.10.2.11.1
-- 1.3.6.1.4.1.37950.1.1.5.10.2.11.1
		-- 1.3.6.1.4.1.37950.1.1.5.10.2.11.1
		rdnssVlan OBJECT-TYPE
			SYNTAX Integer32 (1..4094)
			MAX-ACCESS read-write
			STATUS current
			DESCRIPTION
				"Description."
			::= { rdnssCfg 1 }

		
--         1.3.6.1.4.1.37950.1.1.5.10.2.11.2
-- 1.3.6.1.4.1.37950.1.1.5.10.2.11.2
-- 1.3.6.1.4.1.37950.1.1.5.10.2.11.2
-- 1.3.6.1.4.1.37950.1.1.5.10.2.11.2
-- 1.3.6.1.4.1.37950.1.1.5.10.2.11.2
-- 1.3.6.1.4.1.37950.1.1.5.10.2.11.2
-- 1.3.6.1.4.1.37950.1.1.5.10.2.11.2
-- 1.3.6.1.4.1.37950.1.1.5.10.2.11.2
		-- 1.3.6.1.4.1.37950.1.1.5.10.2.11.2
		rdnssSeq OBJECT-TYPE
			SYNTAX Integer32 (0..8)
			MAX-ACCESS read-write
			STATUS current
			DESCRIPTION
				"Description."
			DEFVAL { -1 }
			::= { rdnssCfg 2 }

		
--         1.3.6.1.4.1.37950.1.1.5.10.2.11.3
-- 1.3.6.1.4.1.37950.1.1.5.10.2.11.3
-- 1.3.6.1.4.1.37950.1.1.5.10.2.11.3
-- 1.3.6.1.4.1.37950.1.1.5.10.2.11.3
-- 1.3.6.1.4.1.37950.1.1.5.10.2.11.3
-- 1.3.6.1.4.1.37950.1.1.5.10.2.11.3
-- 1.3.6.1.4.1.37950.1.1.5.10.2.11.3
-- 1.3.6.1.4.1.37950.1.1.5.10.2.11.3
		-- 1.3.6.1.4.1.37950.1.1.5.10.2.11.3
		rdnssLifetime OBJECT-TYPE
			SYNTAX Unsigned32 (60..4294967295)
			MAX-ACCESS read-write
			STATUS current
			DESCRIPTION
				"Description."
			DEFVAL { 600 }
			::= { rdnssCfg 3 }

		
--         1.3.6.1.4.1.37950.1.1.5.10.2.11.4
-- 1.3.6.1.4.1.37950.1.1.5.10.2.11.4
-- 1.3.6.1.4.1.37950.1.1.5.10.2.11.4
-- 1.3.6.1.4.1.37950.1.1.5.10.2.11.4
-- 1.3.6.1.4.1.37950.1.1.5.10.2.11.4
-- 1.3.6.1.4.1.37950.1.1.5.10.2.11.4
-- 1.3.6.1.4.1.37950.1.1.5.10.2.11.4
-- 1.3.6.1.4.1.37950.1.1.5.10.2.11.4
		-- 1.3.6.1.4.1.37950.1.1.5.10.2.11.4
		rdnsServer1 OBJECT-TYPE
			SYNTAX OCTET STRING
			MAX-ACCESS read-write
			STATUS current
			DESCRIPTION
				"Description."
			::= { rdnssCfg 4 }

		
--         1.3.6.1.4.1.37950.1.1.5.10.2.11.5
-- 1.3.6.1.4.1.37950.1.1.5.10.2.11.5
-- 1.3.6.1.4.1.37950.1.1.5.10.2.11.5
-- 1.3.6.1.4.1.37950.1.1.5.10.2.11.5
-- 1.3.6.1.4.1.37950.1.1.5.10.2.11.5
-- 1.3.6.1.4.1.37950.1.1.5.10.2.11.5
-- 1.3.6.1.4.1.37950.1.1.5.10.2.11.5
-- 1.3.6.1.4.1.37950.1.1.5.10.2.11.5
		-- 1.3.6.1.4.1.37950.1.1.5.10.2.11.5
		rdnsServer2 OBJECT-TYPE
			SYNTAX OCTET STRING
			MAX-ACCESS read-write
			STATUS current
			DESCRIPTION
				"Description."
			::= { rdnssCfg 5 }

		
--         1.3.6.1.4.1.37950.1.1.5.10.2.11.6
-- 1.3.6.1.4.1.37950.1.1.5.10.2.11.6
-- 1.3.6.1.4.1.37950.1.1.5.10.2.11.6
-- 1.3.6.1.4.1.37950.1.1.5.10.2.11.6
-- 1.3.6.1.4.1.37950.1.1.5.10.2.11.6
-- 1.3.6.1.4.1.37950.1.1.5.10.2.11.6
-- 1.3.6.1.4.1.37950.1.1.5.10.2.11.6
-- 1.3.6.1.4.1.37950.1.1.5.10.2.11.6
		-- 1.3.6.1.4.1.37950.1.1.5.10.2.11.6
		rdnsServer3 OBJECT-TYPE
			SYNTAX OCTET STRING
			MAX-ACCESS read-write
			STATUS current
			DESCRIPTION
				"Description."
			::= { rdnssCfg 6 }

		
--         1.3.6.1.4.1.37950.1.1.5.10.2.11.7
-- 1.3.6.1.4.1.37950.1.1.5.10.2.11.7
-- 1.3.6.1.4.1.37950.1.1.5.10.2.11.7
-- 1.3.6.1.4.1.37950.1.1.5.10.2.11.7
-- 1.3.6.1.4.1.37950.1.1.5.10.2.11.7
-- 1.3.6.1.4.1.37950.1.1.5.10.2.11.7
-- 1.3.6.1.4.1.37950.1.1.5.10.2.11.7
-- 1.3.6.1.4.1.37950.1.1.5.10.2.11.7
		-- 1.3.6.1.4.1.37950.1.1.5.10.2.11.7
		rdnsAction OBJECT-TYPE
			SYNTAX INTEGER
				{
				add(0),
				del(1)
				}
			MAX-ACCESS read-write
			STATUS current
			DESCRIPTION
				"Description."
			::= { rdnssCfg 7 }

		
--         1.3.6.1.4.1.37950.1.1.5.10.2.11.8
-- 1.3.6.1.4.1.37950.1.1.5.10.2.11.8
-- 1.3.6.1.4.1.37950.1.1.5.10.2.11.8
-- 1.3.6.1.4.1.37950.1.1.5.10.2.11.8
-- 1.3.6.1.4.1.37950.1.1.5.10.2.11.8
-- 1.3.6.1.4.1.37950.1.1.5.10.2.11.8
-- 1.3.6.1.4.1.37950.1.1.5.10.2.11.8
-- 1.3.6.1.4.1.37950.1.1.5.10.2.11.8
		-- 1.3.6.1.4.1.37950.1.1.5.10.2.11.8
		rdnssSuppressSt OBJECT-TYPE
			SYNTAX INTEGER
				{
				off(0),
				on(1)
				}
			MAX-ACCESS read-write
			STATUS current
			DESCRIPTION
				"Description."
			DEFVAL { on }
			::= { rdnssCfg 8 }

		
--         1.3.6.1.4.1.37950.1.1.5.10.2.12
-- 1.3.6.1.4.1.37950.1.1.5.10.2.12
-- 1.3.6.1.4.1.37950.1.1.5.10.2.12
-- 1.3.6.1.4.1.37950.1.1.5.10.2.12
-- 1.3.6.1.4.1.37950.1.1.5.10.2.12
-- 1.3.6.1.4.1.37950.1.1.5.10.2.12
-- 1.3.6.1.4.1.37950.1.1.5.10.2.12
-- 1.3.6.1.4.1.37950.1.1.5.10.2.12
		-- 1.3.6.1.4.1.37950.1.1.5.10.2.12
		rdnssTable OBJECT-TYPE
			SYNTAX SEQUENCE OF RdnssEntry
			MAX-ACCESS not-accessible
			STATUS current
			DESCRIPTION
				"Description."
			::= { v1600dVLAN 12 }

		
--         1.3.6.1.4.1.37950.1.1.5.10.2.12.1
-- 1.3.6.1.4.1.37950.1.1.5.10.2.12.1
-- 1.3.6.1.4.1.37950.1.1.5.10.2.12.1
-- 1.3.6.1.4.1.37950.1.1.5.10.2.12.1
-- 1.3.6.1.4.1.37950.1.1.5.10.2.12.1
-- 1.3.6.1.4.1.37950.1.1.5.10.2.12.1
-- 1.3.6.1.4.1.37950.1.1.5.10.2.12.1
-- 1.3.6.1.4.1.37950.1.1.5.10.2.12.1
		-- 1.3.6.1.4.1.37950.1.1.5.10.2.12.1
		rdnssEntry OBJECT-TYPE
			SYNTAX RdnssEntry
			MAX-ACCESS not-accessible
			STATUS current
			DESCRIPTION
				"Description."
			INDEX { rdnssIdx, rdnssVlanId }
			::= { rdnssTable 1 }

		
		RdnssEntry ::=
			SEQUENCE { 
				rdnssIdx
					Integer32,
				rdnssVlanId
					Integer32,
				rdnssSequence
					Integer32,
				rDNSServer1
					OCTET STRING,
				rdnssServer2
					OCTET STRING,
				rdnssServer3
					OCTET STRING,
				rdnssLifeTime
					OCTET STRING,
				rdnssSuppressStatus
					INTEGER
			 }

--         1.3.6.1.4.1.37950.1.1.5.10.2.12.1.1
-- 1.3.6.1.4.1.37950.1.1.5.10.2.12.1.1
-- 1.3.6.1.4.1.37950.1.1.5.10.2.12.1.1
-- 1.3.6.1.4.1.37950.1.1.5.10.2.12.1.1
-- 1.3.6.1.4.1.37950.1.1.5.10.2.12.1.1
-- 1.3.6.1.4.1.37950.1.1.5.10.2.12.1.1
-- 1.3.6.1.4.1.37950.1.1.5.10.2.12.1.1
-- 1.3.6.1.4.1.37950.1.1.5.10.2.12.1.1
		-- 1.3.6.1.4.1.37950.1.1.5.10.2.12.1.1
		rdnssIdx OBJECT-TYPE
			SYNTAX Integer32
			MAX-ACCESS read-only
			STATUS current
			DESCRIPTION
				"Description."
			::= { rdnssEntry 1 }

		
--         1.3.6.1.4.1.37950.1.1.5.10.2.12.1.2
-- 1.3.6.1.4.1.37950.1.1.5.10.2.12.1.2
-- 1.3.6.1.4.1.37950.1.1.5.10.2.12.1.2
-- 1.3.6.1.4.1.37950.1.1.5.10.2.12.1.2
-- 1.3.6.1.4.1.37950.1.1.5.10.2.12.1.2
-- 1.3.6.1.4.1.37950.1.1.5.10.2.12.1.2
-- 1.3.6.1.4.1.37950.1.1.5.10.2.12.1.2
-- 1.3.6.1.4.1.37950.1.1.5.10.2.12.1.2
		-- 1.3.6.1.4.1.37950.1.1.5.10.2.12.1.2
		rdnssVlanId OBJECT-TYPE
			SYNTAX Integer32 (1..4094)
			MAX-ACCESS read-only
			STATUS current
			DESCRIPTION
				"Description."
			::= { rdnssEntry 2 }

		
--         1.3.6.1.4.1.37950.1.1.5.10.2.12.1.3
-- 1.3.6.1.4.1.37950.1.1.5.10.2.12.1.3
-- 1.3.6.1.4.1.37950.1.1.5.10.2.12.1.3
-- 1.3.6.1.4.1.37950.1.1.5.10.2.12.1.3
-- 1.3.6.1.4.1.37950.1.1.5.10.2.12.1.3
-- 1.3.6.1.4.1.37950.1.1.5.10.2.12.1.3
-- 1.3.6.1.4.1.37950.1.1.5.10.2.12.1.3
-- 1.3.6.1.4.1.37950.1.1.5.10.2.12.1.3
		-- 1.3.6.1.4.1.37950.1.1.5.10.2.12.1.3
		rdnssSequence OBJECT-TYPE
			SYNTAX Integer32 (0..8)
			MAX-ACCESS read-only
			STATUS current
			DESCRIPTION
				"Description."
			::= { rdnssEntry 3 }

		
--         1.3.6.1.4.1.37950.1.1.5.10.2.12.1.4
-- 1.3.6.1.4.1.37950.1.1.5.10.2.12.1.4
-- 1.3.6.1.4.1.37950.1.1.5.10.2.12.1.4
-- 1.3.6.1.4.1.37950.1.1.5.10.2.12.1.4
-- 1.3.6.1.4.1.37950.1.1.5.10.2.12.1.4
-- 1.3.6.1.4.1.37950.1.1.5.10.2.12.1.4
-- 1.3.6.1.4.1.37950.1.1.5.10.2.12.1.4
-- 1.3.6.1.4.1.37950.1.1.5.10.2.12.1.4
		-- 1.3.6.1.4.1.37950.1.1.5.10.2.12.1.4
		rDNSServer1 OBJECT-TYPE
			SYNTAX OCTET STRING
			MAX-ACCESS read-only
			STATUS current
			DESCRIPTION
				"Description."
			::= { rdnssEntry 4 }

		
--         1.3.6.1.4.1.37950.1.1.5.10.2.12.1.5
-- 1.3.6.1.4.1.37950.1.1.5.10.2.12.1.5
-- 1.3.6.1.4.1.37950.1.1.5.10.2.12.1.5
-- 1.3.6.1.4.1.37950.1.1.5.10.2.12.1.5
-- 1.3.6.1.4.1.37950.1.1.5.10.2.12.1.5
-- 1.3.6.1.4.1.37950.1.1.5.10.2.12.1.5
-- 1.3.6.1.4.1.37950.1.1.5.10.2.12.1.5
-- 1.3.6.1.4.1.37950.1.1.5.10.2.12.1.5
		-- 1.3.6.1.4.1.37950.1.1.5.10.2.12.1.5
		rdnssServer2 OBJECT-TYPE
			SYNTAX OCTET STRING
			MAX-ACCESS read-only
			STATUS current
			DESCRIPTION
				"Description."
			::= { rdnssEntry 5 }

		
--         1.3.6.1.4.1.37950.1.1.5.10.2.12.1.6
-- 1.3.6.1.4.1.37950.1.1.5.10.2.12.1.6
-- 1.3.6.1.4.1.37950.1.1.5.10.2.12.1.6
-- 1.3.6.1.4.1.37950.1.1.5.10.2.12.1.6
-- 1.3.6.1.4.1.37950.1.1.5.10.2.12.1.6
-- 1.3.6.1.4.1.37950.1.1.5.10.2.12.1.6
-- 1.3.6.1.4.1.37950.1.1.5.10.2.12.1.6
-- 1.3.6.1.4.1.37950.1.1.5.10.2.12.1.6
		-- 1.3.6.1.4.1.37950.1.1.5.10.2.12.1.6
		rdnssServer3 OBJECT-TYPE
			SYNTAX OCTET STRING
			MAX-ACCESS read-only
			STATUS current
			DESCRIPTION
				"Description."
			::= { rdnssEntry 6 }

		
--         1.3.6.1.4.1.37950.1.1.5.10.2.12.1.7
-- 1.3.6.1.4.1.37950.1.1.5.10.2.12.1.7
-- 1.3.6.1.4.1.37950.1.1.5.10.2.12.1.7
-- 1.3.6.1.4.1.37950.1.1.5.10.2.12.1.7
-- 1.3.6.1.4.1.37950.1.1.5.10.2.12.1.7
-- 1.3.6.1.4.1.37950.1.1.5.10.2.12.1.7
-- 1.3.6.1.4.1.37950.1.1.5.10.2.12.1.7
-- 1.3.6.1.4.1.37950.1.1.5.10.2.12.1.7
		-- 1.3.6.1.4.1.37950.1.1.5.10.2.12.1.7
		rdnssLifeTime OBJECT-TYPE
			SYNTAX OCTET STRING
			MAX-ACCESS read-only
			STATUS current
			DESCRIPTION
				"Description."
			::= { rdnssEntry 7 }

		
--         1.3.6.1.4.1.37950.1.1.5.10.2.12.1.8
-- 1.3.6.1.4.1.37950.1.1.5.10.2.12.1.8
-- 1.3.6.1.4.1.37950.1.1.5.10.2.12.1.8
-- 1.3.6.1.4.1.37950.1.1.5.10.2.12.1.8
-- 1.3.6.1.4.1.37950.1.1.5.10.2.12.1.8
-- 1.3.6.1.4.1.37950.1.1.5.10.2.12.1.8
-- 1.3.6.1.4.1.37950.1.1.5.10.2.12.1.8
-- 1.3.6.1.4.1.37950.1.1.5.10.2.12.1.8
		-- 1.3.6.1.4.1.37950.1.1.5.10.2.12.1.8
		rdnssSuppressStatus OBJECT-TYPE
			SYNTAX INTEGER
				{
				off(0),
				on(1)
				}
			MAX-ACCESS read-only
			STATUS current
			DESCRIPTION
				"Description."
			::= { rdnssEntry 8 }

		
--         1.3.6.1.4.1.37950.1.1.5.10.2.5
-- 1.3.6.1.4.1.37950.1.1.5.10.2.13
-- 1.3.6.1.4.1.37950.1.1.5.10.2.13
-- 1.3.6.1.4.1.37950.1.1.5.10.2.13
-- 1.3.6.1.4.1.37950.1.1.5.10.2.13
-- 1.3.6.1.4.1.37950.1.1.5.10.2.13
-- 1.3.6.1.4.1.37950.1.1.5.10.2.13
-- 1.3.6.1.4.1.37950.1.1.5.10.2.13
-- 1.3.6.1.4.1.37950.1.1.5.10.2.13
		-- 1.3.6.1.4.1.37950.1.1.5.10.2.13
		vlanPortModeRange OBJECT IDENTIFIER ::= { v1600dVLAN 13 }

		
--         1.3.6.1.4.1.37950.1.1.5.10.2.5.2
-- 1.3.6.1.4.1.37950.1.1.5.10.2.13.1
-- 1.3.6.1.4.1.37950.1.1.5.10.2.13.1
-- 1.3.6.1.4.1.37950.1.1.5.10.2.13.1
-- 1.3.6.1.4.1.37950.1.1.5.10.2.13.1
-- 1.3.6.1.4.1.37950.1.1.5.10.2.13.1
-- 1.3.6.1.4.1.37950.1.1.5.10.2.13.1
-- 1.3.6.1.4.1.37950.1.1.5.10.2.13.1
-- 1.3.6.1.4.1.37950.1.1.5.10.2.13.1
		-- 1.3.6.1.4.1.37950.1.1.5.10.2.13.1
		vlanPortModeCfg OBJECT IDENTIFIER ::= { vlanPortModeRange 1 }

		
--         1.3.6.1.4.1.37950.1.1.5.10.2.5.2.1
-- 1.3.6.1.4.1.37950.1.1.5.10.2.13.1.1
-- 1.3.6.1.4.1.37950.1.1.5.10.2.13.1.1
-- 1.3.6.1.4.1.37950.1.1.5.10.2.13.1.1
-- 1.3.6.1.4.1.37950.1.1.5.10.2.13.1.1
-- 1.3.6.1.4.1.37950.1.1.5.10.2.13.1.1
-- 1.3.6.1.4.1.37950.1.1.5.10.2.13.1.1
-- 1.3.6.1.4.1.37950.1.1.5.10.2.13.1.1
-- 1.3.6.1.4.1.37950.1.1.5.10.2.13.1.1
		-- 1.3.6.1.4.1.37950.1.1.5.10.2.13.1.1
		portIndex OBJECT-TYPE
			SYNTAX INTEGER (1..28)
			MAX-ACCESS read-write
			STATUS current
			DESCRIPTION
				"Description."
			::= { vlanPortModeCfg 1 }

		
--         1.3.6.1.4.1.37950.1.1.5.10.2.5.2.2
-- 1.3.6.1.4.1.37950.1.1.5.10.2.13.1.2
-- 1.3.6.1.4.1.37950.1.1.5.10.2.13.1.2
-- 1.3.6.1.4.1.37950.1.1.5.10.2.13.1.2
-- 1.3.6.1.4.1.37950.1.1.5.10.2.13.1.2
-- 1.3.6.1.4.1.37950.1.1.5.10.2.13.1.2
-- 1.3.6.1.4.1.37950.1.1.5.10.2.13.1.2
-- 1.3.6.1.4.1.37950.1.1.5.10.2.13.1.2
-- 1.3.6.1.4.1.37950.1.1.5.10.2.13.1.2
		-- 1.3.6.1.4.1.37950.1.1.5.10.2.13.1.2
		portTagMode OBJECT-TYPE
			SYNTAX INTEGER
				{
				access(0),
				hybrid(1),
				trunk(2)
				}
			MAX-ACCESS read-write
			STATUS current
			DESCRIPTION
				"Description."
			::= { vlanPortModeCfg 2 }

		
--         1.3.6.1.4.1.37950.1.1.5.10.2.5.2.3
-- 1.3.6.1.4.1.37950.1.1.5.10.2.13.1.3
-- 1.3.6.1.4.1.37950.1.1.5.10.2.13.1.3
-- 1.3.6.1.4.1.37950.1.1.5.10.2.13.1.3
-- 1.3.6.1.4.1.37950.1.1.5.10.2.13.1.3
-- 1.3.6.1.4.1.37950.1.1.5.10.2.13.1.3
-- 1.3.6.1.4.1.37950.1.1.5.10.2.13.1.3
-- 1.3.6.1.4.1.37950.1.1.5.10.2.13.1.3
-- 1.3.6.1.4.1.37950.1.1.5.10.2.13.1.3
		-- 1.3.6.1.4.1.37950.1.1.5.10.2.13.1.3
		portPvid OBJECT-TYPE
			SYNTAX INTEGER (1..4096)
			MAX-ACCESS read-write
			STATUS current
			DESCRIPTION
				"Description."
			::= { vlanPortModeCfg 3 }

		
--         1.3.6.1.4.1.37950.1.1.5.10.2.5.2.4
-- 1.3.6.1.4.1.37950.1.1.5.10.2.13.1.4
-- 1.3.6.1.4.1.37950.1.1.5.10.2.13.1.4
-- 1.3.6.1.4.1.37950.1.1.5.10.2.13.1.4
-- 1.3.6.1.4.1.37950.1.1.5.10.2.13.1.4
-- 1.3.6.1.4.1.37950.1.1.5.10.2.13.1.4
-- 1.3.6.1.4.1.37950.1.1.5.10.2.13.1.4
-- 1.3.6.1.4.1.37950.1.1.5.10.2.13.1.4
-- 1.3.6.1.4.1.37950.1.1.5.10.2.13.1.4
		-- 1.3.6.1.4.1.37950.1.1.5.10.2.13.1.4
		portTagRange OBJECT-TYPE
			SYNTAX OCTET STRING
			MAX-ACCESS read-write
			STATUS current
			DESCRIPTION
				"Description."
			::= { vlanPortModeCfg 4 }

		
--         1.3.6.1.4.1.37950.1.1.5.10.2.5.2.5
-- 1.3.6.1.4.1.37950.1.1.5.10.2.13.1.5
-- 1.3.6.1.4.1.37950.1.1.5.10.2.13.1.5
-- 1.3.6.1.4.1.37950.1.1.5.10.2.13.1.5
-- 1.3.6.1.4.1.37950.1.1.5.10.2.13.1.5
-- 1.3.6.1.4.1.37950.1.1.5.10.2.13.1.5
-- 1.3.6.1.4.1.37950.1.1.5.10.2.13.1.5
-- 1.3.6.1.4.1.37950.1.1.5.10.2.13.1.5
-- 1.3.6.1.4.1.37950.1.1.5.10.2.13.1.5
		-- 1.3.6.1.4.1.37950.1.1.5.10.2.13.1.5
		portUntagRange OBJECT-TYPE
			SYNTAX OCTET STRING
			MAX-ACCESS read-write
			STATUS current
			DESCRIPTION
				"Description."
			::= { vlanPortModeCfg 5 }

		
--         1.3.6.1.4.1.37950.1.1.5.10.2.13.1.6
-- 1.3.6.1.4.1.37950.1.1.5.10.2.13.1.6
-- 1.3.6.1.4.1.37950.1.1.5.10.2.13.1.6
-- 1.3.6.1.4.1.37950.1.1.5.10.2.13.1.6
-- 1.3.6.1.4.1.37950.1.1.5.10.2.13.1.6
-- 1.3.6.1.4.1.37950.1.1.5.10.2.13.1.6
-- 1.3.6.1.4.1.37950.1.1.5.10.2.13.1.6
-- 1.3.6.1.4.1.37950.1.1.5.10.2.13.1.6
		-- 1.3.6.1.4.1.37950.1.1.5.10.2.13.1.6
		portAction OBJECT-TYPE
			SYNTAX INTEGER { enable(1) }
			MAX-ACCESS read-write
			STATUS current
			DESCRIPTION
				"Description."
			::= { vlanPortModeCfg 6 }

		
--         1.3.6.1.4.1.37950.1.1.5.10.2.5.3
-- 1.3.6.1.4.1.37950.1.1.5.10.2.13.2
-- 1.3.6.1.4.1.37950.1.1.5.10.2.13.2
-- 1.3.6.1.4.1.37950.1.1.5.10.2.13.2
-- 1.3.6.1.4.1.37950.1.1.5.10.2.13.2
-- 1.3.6.1.4.1.37950.1.1.5.10.2.13.2
-- 1.3.6.1.4.1.37950.1.1.5.10.2.13.2
-- 1.3.6.1.4.1.37950.1.1.5.10.2.13.2
-- 1.3.6.1.4.1.37950.1.1.5.10.2.13.2
		-- 1.3.6.1.4.1.37950.1.1.5.10.2.13.2
		vlanPortModeTable OBJECT-TYPE
			SYNTAX SEQUENCE OF VlanPortModeEntry
			MAX-ACCESS not-accessible
			STATUS current
			DESCRIPTION
				"Description."
			::= { vlanPortModeRange 2 }

		
--         1.3.6.1.4.1.37950.1.1.5.10.2.5.3.1
-- 1.3.6.1.4.1.37950.1.1.5.10.2.13.2.1
-- 1.3.6.1.4.1.37950.1.1.5.10.2.13.2.1
-- 1.3.6.1.4.1.37950.1.1.5.10.2.13.2.1
-- 1.3.6.1.4.1.37950.1.1.5.10.2.13.2.1
-- 1.3.6.1.4.1.37950.1.1.5.10.2.13.2.1
-- 1.3.6.1.4.1.37950.1.1.5.10.2.13.2.1
-- 1.3.6.1.4.1.37950.1.1.5.10.2.13.2.1
-- 1.3.6.1.4.1.37950.1.1.5.10.2.13.2.1
		-- 1.3.6.1.4.1.37950.1.1.5.10.2.13.2.1
		vlanPortModeEntry OBJECT-TYPE
			SYNTAX VlanPortModeEntry
			MAX-ACCESS not-accessible
			STATUS current
			DESCRIPTION
				"Description."
			INDEX { portIndexS }
			::= { vlanPortModeTable 1 }

		
		VlanPortModeEntry ::=
			SEQUENCE { 
				portIndexS
					INTEGER,
				portIndexDescS
					OCTET STRING,
				portTagModeS
					OCTET STRING,
				portPvidS
					INTEGER,
				portTagRangeS
					OCTET STRING,
				portUntagRangeS
					OCTET STRING
			 }

--         1.3.6.1.4.1.37950.1.1.5.10.2.5.3.1.1
-- 1.3.6.1.4.1.37950.1.1.5.10.2.13.2.1.1
-- 1.3.6.1.4.1.37950.1.1.5.10.2.13.2.1.1
-- 1.3.6.1.4.1.37950.1.1.5.10.2.13.2.1.1
-- 1.3.6.1.4.1.37950.1.1.5.10.2.13.2.1.1
-- 1.3.6.1.4.1.37950.1.1.5.10.2.13.2.1.1
-- 1.3.6.1.4.1.37950.1.1.5.10.2.13.2.1.1
-- 1.3.6.1.4.1.37950.1.1.5.10.2.13.2.1.1
-- 1.3.6.1.4.1.37950.1.1.5.10.2.13.2.1.1
		-- 1.3.6.1.4.1.37950.1.1.5.10.2.13.2.1.1
		portIndexS OBJECT-TYPE
			SYNTAX INTEGER
			MAX-ACCESS read-only
			STATUS current
			DESCRIPTION
				"Description."
			::= { vlanPortModeEntry 1 }

		
--         1.3.6.1.4.1.37950.1.1.5.10.2.5.3.1.1
-- 1.3.6.1.4.1.37950.1.1.5.10.2.13.2.1.2
-- 1.3.6.1.4.1.37950.1.1.5.10.2.13.2.1.2
-- 1.3.6.1.4.1.37950.1.1.5.10.2.13.2.1.2
-- 1.3.6.1.4.1.37950.1.1.5.10.2.13.2.1.2
-- 1.3.6.1.4.1.37950.1.1.5.10.2.13.2.1.2
-- 1.3.6.1.4.1.37950.1.1.5.10.2.13.2.1.2
-- 1.3.6.1.4.1.37950.1.1.5.10.2.13.2.1.2
-- 1.3.6.1.4.1.37950.1.1.5.10.2.13.2.1.2
		-- 1.3.6.1.4.1.37950.1.1.5.10.2.13.2.1.2
		portIndexDescS OBJECT-TYPE
			SYNTAX OCTET STRING
			MAX-ACCESS read-only
			STATUS current
			DESCRIPTION
				"Description."
			::= { vlanPortModeEntry 2 }

		
--         1.3.6.1.4.1.37950.1.1.5.10.2.5.3.1.2
-- 1.3.6.1.4.1.37950.1.1.5.10.2.13.2.1.3
-- 1.3.6.1.4.1.37950.1.1.5.10.2.13.2.1.3
-- 1.3.6.1.4.1.37950.1.1.5.10.2.13.2.1.3
-- 1.3.6.1.4.1.37950.1.1.5.10.2.13.2.1.3
-- 1.3.6.1.4.1.37950.1.1.5.10.2.13.2.1.3
-- 1.3.6.1.4.1.37950.1.1.5.10.2.13.2.1.3
-- 1.3.6.1.4.1.37950.1.1.5.10.2.13.2.1.3
-- 1.3.6.1.4.1.37950.1.1.5.10.2.13.2.1.3
		-- 1.3.6.1.4.1.37950.1.1.5.10.2.13.2.1.3
		portTagModeS OBJECT-TYPE
			SYNTAX OCTET STRING
			MAX-ACCESS read-only
			STATUS current
			DESCRIPTION
				"Description."
			::= { vlanPortModeEntry 3 }

		
--         1.3.6.1.4.1.37950.1.1.5.10.2.5.3.1.3
-- 1.3.6.1.4.1.37950.1.1.5.10.2.13.2.1.4
-- 1.3.6.1.4.1.37950.1.1.5.10.2.13.2.1.4
-- 1.3.6.1.4.1.37950.1.1.5.10.2.13.2.1.4
-- 1.3.6.1.4.1.37950.1.1.5.10.2.13.2.1.4
-- 1.3.6.1.4.1.37950.1.1.5.10.2.13.2.1.4
-- 1.3.6.1.4.1.37950.1.1.5.10.2.13.2.1.4
-- 1.3.6.1.4.1.37950.1.1.5.10.2.13.2.1.4
-- 1.3.6.1.4.1.37950.1.1.5.10.2.13.2.1.4
		-- 1.3.6.1.4.1.37950.1.1.5.10.2.13.2.1.4
		portPvidS OBJECT-TYPE
			SYNTAX INTEGER
			MAX-ACCESS read-only
			STATUS current
			DESCRIPTION
				"Description."
			::= { vlanPortModeEntry 4 }

		
--         1.3.6.1.4.1.37950.1.1.5.10.2.5.3.1.4
-- 1.3.6.1.4.1.37950.1.1.5.10.2.13.2.1.5
-- 1.3.6.1.4.1.37950.1.1.5.10.2.13.2.1.5
-- 1.3.6.1.4.1.37950.1.1.5.10.2.13.2.1.5
-- 1.3.6.1.4.1.37950.1.1.5.10.2.13.2.1.5
-- 1.3.6.1.4.1.37950.1.1.5.10.2.13.2.1.5
-- 1.3.6.1.4.1.37950.1.1.5.10.2.13.2.1.5
-- 1.3.6.1.4.1.37950.1.1.5.10.2.13.2.1.5
-- 1.3.6.1.4.1.37950.1.1.5.10.2.13.2.1.5
		-- 1.3.6.1.4.1.37950.1.1.5.10.2.13.2.1.5
		portTagRangeS OBJECT-TYPE
			SYNTAX OCTET STRING
			MAX-ACCESS read-only
			STATUS current
			DESCRIPTION
				"Description."
			::= { vlanPortModeEntry 5 }

		
--         1.3.6.1.4.1.37950.1.1.5.10.2.5.3.1.5
-- 1.3.6.1.4.1.37950.1.1.5.10.2.13.2.1.6
-- 1.3.6.1.4.1.37950.1.1.5.10.2.13.2.1.6
-- 1.3.6.1.4.1.37950.1.1.5.10.2.13.2.1.6
-- 1.3.6.1.4.1.37950.1.1.5.10.2.13.2.1.6
-- 1.3.6.1.4.1.37950.1.1.5.10.2.13.2.1.6
-- 1.3.6.1.4.1.37950.1.1.5.10.2.13.2.1.6
-- 1.3.6.1.4.1.37950.1.1.5.10.2.13.2.1.6
-- 1.3.6.1.4.1.37950.1.1.5.10.2.13.2.1.6
		-- 1.3.6.1.4.1.37950.1.1.5.10.2.13.2.1.6
		portUntagRangeS OBJECT-TYPE
			SYNTAX OCTET STRING
			MAX-ACCESS read-only
			STATUS current
			DESCRIPTION
				"Description."
			::= { vlanPortModeEntry 6 }

		
--         1.3.6.1.4.1.37950.1.1.5.10.2.1
-- 1.3.6.1.4.1.37950.1.1.5.10.2.14
-- 1.3.6.1.4.1.37950.1.1.5.10.2.14
-- 1.3.6.1.4.1.37950.1.1.5.10.2.14
-- 1.3.6.1.4.1.37950.1.1.5.10.2.14
-- 1.3.6.1.4.1.37950.1.1.5.10.2.14
-- 1.3.6.1.4.1.37950.1.1.5.10.2.14
-- 1.3.6.1.4.1.37950.1.1.5.10.2.14
-- 1.3.6.1.4.1.37950.1.1.5.10.2.14
		-- 1.3.6.1.4.1.37950.1.1.5.10.2.14
		vlanRangeCfg OBJECT IDENTIFIER ::= { v1600dVLAN 14 }

		
--         1.3.6.1.4.1.37950.1.1.5.10.2.1.3
-- 1.3.6.1.4.1.37950.1.1.5.10.2.14.1
-- 1.3.6.1.4.1.37950.1.1.5.10.2.14.1
-- 1.3.6.1.4.1.37950.1.1.5.10.2.14.1
-- 1.3.6.1.4.1.37950.1.1.5.10.2.14.1
-- 1.3.6.1.4.1.37950.1.1.5.10.2.14.1
-- 1.3.6.1.4.1.37950.1.1.5.10.2.14.1
-- 1.3.6.1.4.1.37950.1.1.5.10.2.14.1
-- 1.3.6.1.4.1.37950.1.1.5.10.2.14.1
		-- 1.3.6.1.4.1.37950.1.1.5.10.2.14.1
		vlanRange OBJECT-TYPE
			SYNTAX OCTET STRING
			MAX-ACCESS read-write
			STATUS current
			DESCRIPTION
				"Description."
			::= { vlanRangeCfg 1 }

		
--         1.3.6.1.4.1.37950.1.1.5.10.2.1.7
-- 1.3.6.1.4.1.37950.1.1.5.10.2.14.2
-- 1.3.6.1.4.1.37950.1.1.5.10.2.14.2
-- 1.3.6.1.4.1.37950.1.1.5.10.2.14.2
-- 1.3.6.1.4.1.37950.1.1.5.10.2.14.2
-- 1.3.6.1.4.1.37950.1.1.5.10.2.14.2
-- 1.3.6.1.4.1.37950.1.1.5.10.2.14.2
-- 1.3.6.1.4.1.37950.1.1.5.10.2.14.2
-- 1.3.6.1.4.1.37950.1.1.5.10.2.14.2
		-- 1.3.6.1.4.1.37950.1.1.5.10.2.14.2
		vlanRangeAction OBJECT-TYPE
			SYNTAX INTEGER
				{
				add(1),
				delete(2)
				}
			MAX-ACCESS read-write
			STATUS current
			DESCRIPTION
				"Description."
			::= { vlanRangeCfg 2 }

		
--            1.3.6.1.4.1.37950.1.1.5.10.3
-- 1.3.6.1.4.1.37950.1.1.5.10.3
-- 1.3.6.1.4.1.37950.1.1.5.10.3
-- 1.3.6.1.4.1.37950.1.1.5.10.3
-- 1.3.6.1.4.1.37950.1.1.5.10.3
-- 1.3.6.1.4.1.37950.1.1.5.10.3
-- 1.3.6.1.4.1.37950.1.1.5.10.3
-- 1.3.6.1.4.1.37950.1.1.5.10.3
-- 1.3.6.1.4.1.37950.1.1.5.10.3
-- 1.3.6.1.4.1.37950.1.1.5.10.3
		-- 1.3.6.1.4.1.37950.1.1.5.10.3
		v1600dMacAddr OBJECT IDENTIFIER ::= { v1600dSwitch 3 }

		
--          1.3.6.1.4.1.37950.1.1.5.10.3.1
-- 1.3.6.1.4.1.37950.1.1.5.10.3.1
-- 1.3.6.1.4.1.37950.1.1.5.10.3.1
-- 1.3.6.1.4.1.37950.1.1.5.10.3.1
-- 1.3.6.1.4.1.37950.1.1.5.10.3.1
-- 1.3.6.1.4.1.37950.1.1.5.10.3.1
-- 1.3.6.1.4.1.37950.1.1.5.10.3.1
-- 1.3.6.1.4.1.37950.1.1.5.10.3.1
-- 1.3.6.1.4.1.37950.1.1.5.10.3.1
		-- 1.3.6.1.4.1.37950.1.1.5.10.3.1
		agingTimer OBJECT-TYPE
			SYNTAX INTEGER (0 | 10..1000000)
			MAX-ACCESS read-write
			STATUS current
			DESCRIPTION
				"Description."
			::= { v1600dMacAddr 1 }

		
--          1.3.6.1.4.1.37950.1.1.5.10.3.2
-- 1.3.6.1.4.1.37950.1.1.5.10.3.2
-- 1.3.6.1.4.1.37950.1.1.5.10.3.2
-- 1.3.6.1.4.1.37950.1.1.5.10.3.2
-- 1.3.6.1.4.1.37950.1.1.5.10.3.2
-- 1.3.6.1.4.1.37950.1.1.5.10.3.2
-- 1.3.6.1.4.1.37950.1.1.5.10.3.2
-- 1.3.6.1.4.1.37950.1.1.5.10.3.2
-- 1.3.6.1.4.1.37950.1.1.5.10.3.2
		-- 1.3.6.1.4.1.37950.1.1.5.10.3.2
		macAddrTable OBJECT-TYPE
			SYNTAX SEQUENCE OF MacAddrEntry
			MAX-ACCESS not-accessible
			STATUS current
			DESCRIPTION
				"Description."
			::= { v1600dMacAddr 2 }

		
--          1.3.6.1.4.1.37950.1.1.5.10.3.2.1
-- 1.3.6.1.4.1.37950.1.1.5.10.3.2.1
-- 1.3.6.1.4.1.37950.1.1.5.10.3.2.1
-- 1.3.6.1.4.1.37950.1.1.5.10.3.2.1
-- 1.3.6.1.4.1.37950.1.1.5.10.3.2.1
-- 1.3.6.1.4.1.37950.1.1.5.10.3.2.1
-- 1.3.6.1.4.1.37950.1.1.5.10.3.2.1
-- 1.3.6.1.4.1.37950.1.1.5.10.3.2.1
-- 1.3.6.1.4.1.37950.1.1.5.10.3.2.1
		-- 1.3.6.1.4.1.37950.1.1.5.10.3.2.1
		macAddrEntry OBJECT-TYPE
			SYNTAX MacAddrEntry
			MAX-ACCESS not-accessible
			STATUS current
			DESCRIPTION
				"Description."
			INDEX { macAddrIndex }
			::= { macAddrTable 1 }

		
		MacAddrEntry ::=
			SEQUENCE { 
				macAddrIndex
					Integer32,
				macVlanId
					Integer32,
				macAddr
					OCTET STRING,
				macType
					INTEGER,
				macPortId
					OCTET STRING
			 }

--          1.3.6.1.4.1.37950.1.1.5.10.3.2.1.1
-- 1.3.6.1.4.1.37950.1.1.5.10.3.2.1.1
-- 1.3.6.1.4.1.37950.1.1.5.10.3.2.1.1
-- 1.3.6.1.4.1.37950.1.1.5.10.3.2.1.1
-- 1.3.6.1.4.1.37950.1.1.5.10.3.2.1.1
-- 1.3.6.1.4.1.37950.1.1.5.10.3.2.1.1
-- 1.3.6.1.4.1.37950.1.1.5.10.3.2.1.1
-- 1.3.6.1.4.1.37950.1.1.5.10.3.2.1.1
-- 1.3.6.1.4.1.37950.1.1.5.10.3.2.1.1
		-- 1.3.6.1.4.1.37950.1.1.5.10.3.2.1.1
		macAddrIndex OBJECT-TYPE
			SYNTAX Integer32
			MAX-ACCESS read-only
			STATUS current
			DESCRIPTION
				"Description."
			::= { macAddrEntry 1 }

		
--          1.3.6.1.4.1.37950.1.1.5.10.3.2.1.2
-- 1.3.6.1.4.1.37950.1.1.5.10.3.2.1.2
-- 1.3.6.1.4.1.37950.1.1.5.10.3.2.1.2
-- 1.3.6.1.4.1.37950.1.1.5.10.3.2.1.2
-- 1.3.6.1.4.1.37950.1.1.5.10.3.2.1.2
-- 1.3.6.1.4.1.37950.1.1.5.10.3.2.1.2
-- 1.3.6.1.4.1.37950.1.1.5.10.3.2.1.2
-- 1.3.6.1.4.1.37950.1.1.5.10.3.2.1.2
-- 1.3.6.1.4.1.37950.1.1.5.10.3.2.1.2
		-- 1.3.6.1.4.1.37950.1.1.5.10.3.2.1.2
		macVlanId OBJECT-TYPE
			SYNTAX Integer32
			MAX-ACCESS read-only
			STATUS current
			DESCRIPTION
				"Description."
			::= { macAddrEntry 2 }

		
--          1.3.6.1.4.1.37950.1.1.5.10.3.2.1.3
-- 1.3.6.1.4.1.37950.1.1.5.10.3.2.1.3
-- 1.3.6.1.4.1.37950.1.1.5.10.3.2.1.3
-- 1.3.6.1.4.1.37950.1.1.5.10.3.2.1.3
-- 1.3.6.1.4.1.37950.1.1.5.10.3.2.1.3
-- 1.3.6.1.4.1.37950.1.1.5.10.3.2.1.3
-- 1.3.6.1.4.1.37950.1.1.5.10.3.2.1.3
-- 1.3.6.1.4.1.37950.1.1.5.10.3.2.1.3
-- 1.3.6.1.4.1.37950.1.1.5.10.3.2.1.3
		-- 1.3.6.1.4.1.37950.1.1.5.10.3.2.1.3
		macAddr OBJECT-TYPE
			SYNTAX OCTET STRING
			MAX-ACCESS read-only
			STATUS current
			DESCRIPTION
				"Description."
			::= { macAddrEntry 3 }

		
--          1.3.6.1.4.1.37950.1.1.5.10.3.2.1.4
-- 1.3.6.1.4.1.37950.1.1.5.10.3.2.1.4
-- 1.3.6.1.4.1.37950.1.1.5.10.3.2.1.4
-- 1.3.6.1.4.1.37950.1.1.5.10.3.2.1.4
-- 1.3.6.1.4.1.37950.1.1.5.10.3.2.1.4
-- 1.3.6.1.4.1.37950.1.1.5.10.3.2.1.4
-- 1.3.6.1.4.1.37950.1.1.5.10.3.2.1.4
-- 1.3.6.1.4.1.37950.1.1.5.10.3.2.1.4
-- 1.3.6.1.4.1.37950.1.1.5.10.3.2.1.4
		-- 1.3.6.1.4.1.37950.1.1.5.10.3.2.1.4
		macType OBJECT-TYPE
			SYNTAX INTEGER
				{
				static(0),
				dynamic(1)
				}
			MAX-ACCESS read-only
			STATUS current
			DESCRIPTION
				"Description."
			::= { macAddrEntry 4 }

		
--          1.3.6.1.4.1.37950.1.1.5.10.3.2.1.5
-- 1.3.6.1.4.1.37950.1.1.5.10.3.2.1.5
-- 1.3.6.1.4.1.37950.1.1.5.10.3.2.1.5
-- 1.3.6.1.4.1.37950.1.1.5.10.3.2.1.5
-- 1.3.6.1.4.1.37950.1.1.5.10.3.2.1.5
-- 1.3.6.1.4.1.37950.1.1.5.10.3.2.1.5
-- 1.3.6.1.4.1.37950.1.1.5.10.3.2.1.5
-- 1.3.6.1.4.1.37950.1.1.5.10.3.2.1.5
-- 1.3.6.1.4.1.37950.1.1.5.10.3.2.1.5
		-- 1.3.6.1.4.1.37950.1.1.5.10.3.2.1.5
		macPortId OBJECT-TYPE
			SYNTAX OCTET STRING
			MAX-ACCESS read-only
			STATUS current
			DESCRIPTION
				"Description."
			::= { macAddrEntry 5 }

		
--          1.3.6.1.4.1.37950.1.1.5.10.3.3
-- 1.3.6.1.4.1.37950.1.1.5.10.3.3
-- 1.3.6.1.4.1.37950.1.1.5.10.3.3
-- 1.3.6.1.4.1.37950.1.1.5.10.3.3
-- 1.3.6.1.4.1.37950.1.1.5.10.3.3
-- 1.3.6.1.4.1.37950.1.1.5.10.3.3
-- 1.3.6.1.4.1.37950.1.1.5.10.3.3
-- 1.3.6.1.4.1.37950.1.1.5.10.3.3
-- 1.3.6.1.4.1.37950.1.1.5.10.3.3
		-- 1.3.6.1.4.1.37950.1.1.5.10.3.3
		portMacAddrLimitTable OBJECT-TYPE
			SYNTAX SEQUENCE OF PortMacAddrLimitEntry
			MAX-ACCESS not-accessible
			STATUS current
			DESCRIPTION
				"Description."
			::= { v1600dMacAddr 3 }

		
--          1.3.6.1.4.1.37950.1.1.5.10.3.3.1
-- 1.3.6.1.4.1.37950.1.1.5.10.3.3.1
-- 1.3.6.1.4.1.37950.1.1.5.10.3.3.1
-- 1.3.6.1.4.1.37950.1.1.5.10.3.3.1
-- 1.3.6.1.4.1.37950.1.1.5.10.3.3.1
-- 1.3.6.1.4.1.37950.1.1.5.10.3.3.1
-- 1.3.6.1.4.1.37950.1.1.5.10.3.3.1
-- 1.3.6.1.4.1.37950.1.1.5.10.3.3.1
-- 1.3.6.1.4.1.37950.1.1.5.10.3.3.1
		-- 1.3.6.1.4.1.37950.1.1.5.10.3.3.1
		portMacAddrLimitEntry OBJECT-TYPE
			SYNTAX PortMacAddrLimitEntry
			MAX-ACCESS not-accessible
			STATUS current
			DESCRIPTION
				"Description."
			INDEX { portMacLimitIdx }
			::= { portMacAddrLimitTable 1 }

		
		PortMacAddrLimitEntry ::=
			SEQUENCE { 
				portMacLimitIdx
					INTEGER,
				portMacAddrLimit
					Integer32
			 }

--          1.3.6.1.4.1.37950.1.1.5.10.3.3.1.1
-- 1.3.6.1.4.1.37950.1.1.5.10.3.3.1.1
-- 1.3.6.1.4.1.37950.1.1.5.10.3.3.1.1
-- 1.3.6.1.4.1.37950.1.1.5.10.3.3.1.1
-- 1.3.6.1.4.1.37950.1.1.5.10.3.3.1.1
-- 1.3.6.1.4.1.37950.1.1.5.10.3.3.1.1
-- 1.3.6.1.4.1.37950.1.1.5.10.3.3.1.1
-- 1.3.6.1.4.1.37950.1.1.5.10.3.3.1.1
-- 1.3.6.1.4.1.37950.1.1.5.10.3.3.1.1
		-- 1.3.6.1.4.1.37950.1.1.5.10.3.3.1.1
		portMacLimitIdx OBJECT-TYPE
			SYNTAX INTEGER (1..28)
			MAX-ACCESS read-only
			STATUS current
			DESCRIPTION
				"Description."
			::= { portMacAddrLimitEntry 1 }

		
--          1.3.6.1.4.1.37950.1.1.5.10.3.3.1.2
-- 1.3.6.1.4.1.37950.1.1.5.10.3.3.1.2
-- 1.3.6.1.4.1.37950.1.1.5.10.3.3.1.2
-- 1.3.6.1.4.1.37950.1.1.5.10.3.3.1.2
-- 1.3.6.1.4.1.37950.1.1.5.10.3.3.1.2
-- 1.3.6.1.4.1.37950.1.1.5.10.3.3.1.2
-- 1.3.6.1.4.1.37950.1.1.5.10.3.3.1.2
-- 1.3.6.1.4.1.37950.1.1.5.10.3.3.1.2
-- 1.3.6.1.4.1.37950.1.1.5.10.3.3.1.2
		-- 1.3.6.1.4.1.37950.1.1.5.10.3.3.1.2
		portMacAddrLimit OBJECT-TYPE
			SYNTAX Integer32 (0..16384)
			MAX-ACCESS read-write
			STATUS current
			DESCRIPTION
				"Description."
			::= { portMacAddrLimitEntry 2 }

		
--         1.3.6.1.4.1.37950.1.1.5.10.3.4
-- 1.3.6.1.4.1.37950.1.1.5.10.3.4
-- 1.3.6.1.4.1.37950.1.1.5.10.3.4
-- 1.3.6.1.4.1.37950.1.1.5.10.3.4
-- 1.3.6.1.4.1.37950.1.1.5.10.3.4
-- 1.3.6.1.4.1.37950.1.1.5.10.3.4
-- 1.3.6.1.4.1.37950.1.1.5.10.3.4
-- 1.3.6.1.4.1.37950.1.1.5.10.3.4
		-- 1.3.6.1.4.1.37950.1.1.5.10.3.4
		macFlappingCfg OBJECT IDENTIFIER ::= { v1600dMacAddr 4 }

		
--         1.3.6.1.4.1.37950.1.1.5.10.3.4.1
-- 1.3.6.1.4.1.37950.1.1.5.10.3.4.1
-- 1.3.6.1.4.1.37950.1.1.5.10.3.4.1
-- 1.3.6.1.4.1.37950.1.1.5.10.3.4.1
-- 1.3.6.1.4.1.37950.1.1.5.10.3.4.1
-- 1.3.6.1.4.1.37950.1.1.5.10.3.4.1
-- 1.3.6.1.4.1.37950.1.1.5.10.3.4.1
-- 1.3.6.1.4.1.37950.1.1.5.10.3.4.1
		-- 1.3.6.1.4.1.37950.1.1.5.10.3.4.1
		macFlappingStatus OBJECT-TYPE
			SYNTAX INTEGER
				{
				disable(0),
				enable(1)
				}
			MAX-ACCESS read-write
			STATUS current
			DESCRIPTION
				"Description."
			::= { macFlappingCfg 1 }

		
--         1.3.6.1.4.1.37950.1.1.5.10.3.4.2
-- 1.3.6.1.4.1.37950.1.1.5.10.3.4.2
-- 1.3.6.1.4.1.37950.1.1.5.10.3.4.2
-- 1.3.6.1.4.1.37950.1.1.5.10.3.4.2
-- 1.3.6.1.4.1.37950.1.1.5.10.3.4.2
-- 1.3.6.1.4.1.37950.1.1.5.10.3.4.2
-- 1.3.6.1.4.1.37950.1.1.5.10.3.4.2
-- 1.3.6.1.4.1.37950.1.1.5.10.3.4.2
		-- 1.3.6.1.4.1.37950.1.1.5.10.3.4.2
		macPortRange OBJECT-TYPE
			SYNTAX INTEGER
				{
				uplink(0),
				pon(1),
				all(2)
				}
			MAX-ACCESS read-write
			STATUS current
			DESCRIPTION
				"Description."
			::= { macFlappingCfg 2 }

		
--         1.3.6.1.4.1.37950.1.1.5.10.3.4.3
-- 1.3.6.1.4.1.37950.1.1.5.10.3.4.3
-- 1.3.6.1.4.1.37950.1.1.5.10.3.4.3
-- 1.3.6.1.4.1.37950.1.1.5.10.3.4.3
-- 1.3.6.1.4.1.37950.1.1.5.10.3.4.3
-- 1.3.6.1.4.1.37950.1.1.5.10.3.4.3
-- 1.3.6.1.4.1.37950.1.1.5.10.3.4.3
-- 1.3.6.1.4.1.37950.1.1.5.10.3.4.3
		-- 1.3.6.1.4.1.37950.1.1.5.10.3.4.3
		macFlappingMode OBJECT-TYPE
			SYNTAX INTEGER
				{
				only-alarm(0),
				auto-recovery(1),
				manual-recovery(2)
				}
			MAX-ACCESS read-write
			STATUS current
			DESCRIPTION
				"Description."
			::= { macFlappingCfg 3 }

		
--         1.3.6.1.4.1.37950.1.1.5.10.3.4.4
-- 1.3.6.1.4.1.37950.1.1.5.10.3.4.4
-- 1.3.6.1.4.1.37950.1.1.5.10.3.4.4
-- 1.3.6.1.4.1.37950.1.1.5.10.3.4.4
-- 1.3.6.1.4.1.37950.1.1.5.10.3.4.4
-- 1.3.6.1.4.1.37950.1.1.5.10.3.4.4
-- 1.3.6.1.4.1.37950.1.1.5.10.3.4.4
-- 1.3.6.1.4.1.37950.1.1.5.10.3.4.4
		-- 1.3.6.1.4.1.37950.1.1.5.10.3.4.4
		macFlappingInterval OBJECT-TYPE
			SYNTAX INTEGER (10..3600)
			MAX-ACCESS read-write
			STATUS current
			DESCRIPTION
				"Description."
			::= { macFlappingCfg 4 }

		
--         1.3.6.1.4.1.37950.1.1.5.10.3.4.5
-- 1.3.6.1.4.1.37950.1.1.5.10.3.4.5
-- 1.3.6.1.4.1.37950.1.1.5.10.3.4.5
-- 1.3.6.1.4.1.37950.1.1.5.10.3.4.5
-- 1.3.6.1.4.1.37950.1.1.5.10.3.4.5
-- 1.3.6.1.4.1.37950.1.1.5.10.3.4.5
-- 1.3.6.1.4.1.37950.1.1.5.10.3.4.5
-- 1.3.6.1.4.1.37950.1.1.5.10.3.4.5
		-- 1.3.6.1.4.1.37950.1.1.5.10.3.4.5
		macFlappingSupThr OBJECT-TYPE
			SYNTAX INTEGER (1..256)
			MAX-ACCESS read-write
			STATUS current
			DESCRIPTION
				"Description."
			::= { macFlappingCfg 5 }

		
--         1.3.6.1.4.1.37950.1.1.5.10.3.4.6
-- 1.3.6.1.4.1.37950.1.1.5.10.3.4.6
-- 1.3.6.1.4.1.37950.1.1.5.10.3.4.6
-- 1.3.6.1.4.1.37950.1.1.5.10.3.4.6
-- 1.3.6.1.4.1.37950.1.1.5.10.3.4.6
-- 1.3.6.1.4.1.37950.1.1.5.10.3.4.6
-- 1.3.6.1.4.1.37950.1.1.5.10.3.4.6
-- 1.3.6.1.4.1.37950.1.1.5.10.3.4.6
		-- 1.3.6.1.4.1.37950.1.1.5.10.3.4.6
		macFlappingSupAgeTime OBJECT-TYPE
			SYNTAX INTEGER (10..3600)
			MAX-ACCESS read-write
			STATUS current
			DESCRIPTION
				"Description."
			::= { macFlappingCfg 6 }

		
--         1.3.6.1.4.1.37950.1.1.5.10.3.4.7
-- 1.3.6.1.4.1.37950.1.1.5.10.3.4.7
-- 1.3.6.1.4.1.37950.1.1.5.10.3.4.7
-- 1.3.6.1.4.1.37950.1.1.5.10.3.4.7
-- 1.3.6.1.4.1.37950.1.1.5.10.3.4.7
-- 1.3.6.1.4.1.37950.1.1.5.10.3.4.7
-- 1.3.6.1.4.1.37950.1.1.5.10.3.4.7
-- 1.3.6.1.4.1.37950.1.1.5.10.3.4.7
		-- 1.3.6.1.4.1.37950.1.1.5.10.3.4.7
		macFlappingInfoClean OBJECT-TYPE
			SYNTAX INTEGER { clean(1) }
			MAX-ACCESS read-write
			STATUS current
			DESCRIPTION
				"Description."
			::= { macFlappingCfg 7 }

		
--         1.3.6.1.4.1.37950.1.1.5.10.3.5
-- 1.3.6.1.4.1.37950.1.1.5.10.3.5
-- 1.3.6.1.4.1.37950.1.1.5.10.3.5
-- 1.3.6.1.4.1.37950.1.1.5.10.3.5
-- 1.3.6.1.4.1.37950.1.1.5.10.3.5
-- 1.3.6.1.4.1.37950.1.1.5.10.3.5
-- 1.3.6.1.4.1.37950.1.1.5.10.3.5
-- 1.3.6.1.4.1.37950.1.1.5.10.3.5
		-- 1.3.6.1.4.1.37950.1.1.5.10.3.5
		macFlappingTable OBJECT-TYPE
			SYNTAX SEQUENCE OF MacFlappingEntry
			MAX-ACCESS not-accessible
			STATUS current
			DESCRIPTION
				"Description."
			::= { v1600dMacAddr 5 }

		
--         1.3.6.1.4.1.37950.1.1.5.10.3.5.1
-- 1.3.6.1.4.1.37950.1.1.5.10.3.5.1
-- 1.3.6.1.4.1.37950.1.1.5.10.3.5.1
-- 1.3.6.1.4.1.37950.1.1.5.10.3.5.1
-- 1.3.6.1.4.1.37950.1.1.5.10.3.5.1
-- 1.3.6.1.4.1.37950.1.1.5.10.3.5.1
-- 1.3.6.1.4.1.37950.1.1.5.10.3.5.1
-- 1.3.6.1.4.1.37950.1.1.5.10.3.5.1
		-- 1.3.6.1.4.1.37950.1.1.5.10.3.5.1
		macFlappingEntry OBJECT-TYPE
			SYNTAX MacFlappingEntry
			MAX-ACCESS not-accessible
			STATUS current
			DESCRIPTION
				"Description."
			INDEX { macFlappingindex }
			::= { macFlappingTable 1 }

		
		MacFlappingEntry ::=
			SEQUENCE { 
				macFlappingindex
					Integer32,
				macFlappingMacAddr
					OCTET STRING,
				macFlappingVlanId
					Integer32,
				macFlappingSourcePort
					OCTET STRING,
				macFlappingCurrentPort
					OCTET STRING,
				macFlappingBeginTime
					OCTET STRING,
				macFlappingLastTime
					OCTET STRING,
				macFlappingTimes
					OCTET STRING
			 }

--         1.3.6.1.4.1.37950.1.1.5.10.3.5.1.1
-- 1.3.6.1.4.1.37950.1.1.5.10.3.5.1.1
-- 1.3.6.1.4.1.37950.1.1.5.10.3.5.1.1
-- 1.3.6.1.4.1.37950.1.1.5.10.3.5.1.1
-- 1.3.6.1.4.1.37950.1.1.5.10.3.5.1.1
-- 1.3.6.1.4.1.37950.1.1.5.10.3.5.1.1
-- 1.3.6.1.4.1.37950.1.1.5.10.3.5.1.1
-- 1.3.6.1.4.1.37950.1.1.5.10.3.5.1.1
		-- 1.3.6.1.4.1.37950.1.1.5.10.3.5.1.1
		macFlappingindex OBJECT-TYPE
			SYNTAX Integer32
			MAX-ACCESS read-only
			STATUS current
			DESCRIPTION
				"Description."
			::= { macFlappingEntry 1 }

		
--         1.3.6.1.4.1.37950.1.1.5.10.3.5.1.2
-- 1.3.6.1.4.1.37950.1.1.5.10.3.5.1.2
-- 1.3.6.1.4.1.37950.1.1.5.10.3.5.1.2
-- 1.3.6.1.4.1.37950.1.1.5.10.3.5.1.2
-- 1.3.6.1.4.1.37950.1.1.5.10.3.5.1.2
-- 1.3.6.1.4.1.37950.1.1.5.10.3.5.1.2
-- 1.3.6.1.4.1.37950.1.1.5.10.3.5.1.2
-- 1.3.6.1.4.1.37950.1.1.5.10.3.5.1.2
		-- 1.3.6.1.4.1.37950.1.1.5.10.3.5.1.2
		macFlappingMacAddr OBJECT-TYPE
			SYNTAX OCTET STRING
			MAX-ACCESS read-only
			STATUS current
			DESCRIPTION
				"Description."
			::= { macFlappingEntry 2 }

		
--         1.3.6.1.4.1.37950.1.1.5.10.3.5.1.3
-- 1.3.6.1.4.1.37950.1.1.5.10.3.5.1.3
-- 1.3.6.1.4.1.37950.1.1.5.10.3.5.1.3
-- 1.3.6.1.4.1.37950.1.1.5.10.3.5.1.3
-- 1.3.6.1.4.1.37950.1.1.5.10.3.5.1.3
-- 1.3.6.1.4.1.37950.1.1.5.10.3.5.1.3
-- 1.3.6.1.4.1.37950.1.1.5.10.3.5.1.3
-- 1.3.6.1.4.1.37950.1.1.5.10.3.5.1.3
		-- 1.3.6.1.4.1.37950.1.1.5.10.3.5.1.3
		macFlappingVlanId OBJECT-TYPE
			SYNTAX Integer32
			MAX-ACCESS read-only
			STATUS current
			DESCRIPTION
				"Description."
			::= { macFlappingEntry 3 }

		
--         1.3.6.1.4.1.37950.1.1.5.10.3.5.1.4
-- 1.3.6.1.4.1.37950.1.1.5.10.3.5.1.4
-- 1.3.6.1.4.1.37950.1.1.5.10.3.5.1.4
-- 1.3.6.1.4.1.37950.1.1.5.10.3.5.1.4
-- 1.3.6.1.4.1.37950.1.1.5.10.3.5.1.4
-- 1.3.6.1.4.1.37950.1.1.5.10.3.5.1.4
-- 1.3.6.1.4.1.37950.1.1.5.10.3.5.1.4
-- 1.3.6.1.4.1.37950.1.1.5.10.3.5.1.4
		-- 1.3.6.1.4.1.37950.1.1.5.10.3.5.1.4
		macFlappingSourcePort OBJECT-TYPE
			SYNTAX OCTET STRING
			MAX-ACCESS read-only
			STATUS current
			DESCRIPTION
				"Description."
			::= { macFlappingEntry 4 }

		
--         1.3.6.1.4.1.37950.1.1.5.10.3.5.1.5
-- 1.3.6.1.4.1.37950.1.1.5.10.3.5.1.5
-- 1.3.6.1.4.1.37950.1.1.5.10.3.5.1.5
-- 1.3.6.1.4.1.37950.1.1.5.10.3.5.1.5
-- 1.3.6.1.4.1.37950.1.1.5.10.3.5.1.5
-- 1.3.6.1.4.1.37950.1.1.5.10.3.5.1.5
-- 1.3.6.1.4.1.37950.1.1.5.10.3.5.1.5
-- 1.3.6.1.4.1.37950.1.1.5.10.3.5.1.5
		-- 1.3.6.1.4.1.37950.1.1.5.10.3.5.1.5
		macFlappingCurrentPort OBJECT-TYPE
			SYNTAX OCTET STRING
			MAX-ACCESS read-only
			STATUS current
			DESCRIPTION
				"Description."
			::= { macFlappingEntry 5 }

		
--         1.3.6.1.4.1.37950.1.1.5.10.3.5.1.6
-- 1.3.6.1.4.1.37950.1.1.5.10.3.5.1.6
-- 1.3.6.1.4.1.37950.1.1.5.10.3.5.1.6
-- 1.3.6.1.4.1.37950.1.1.5.10.3.5.1.6
-- 1.3.6.1.4.1.37950.1.1.5.10.3.5.1.6
-- 1.3.6.1.4.1.37950.1.1.5.10.3.5.1.6
-- 1.3.6.1.4.1.37950.1.1.5.10.3.5.1.6
-- 1.3.6.1.4.1.37950.1.1.5.10.3.5.1.6
		-- 1.3.6.1.4.1.37950.1.1.5.10.3.5.1.6
		macFlappingBeginTime OBJECT-TYPE
			SYNTAX OCTET STRING
			MAX-ACCESS read-only
			STATUS current
			DESCRIPTION
				"Description."
			::= { macFlappingEntry 6 }

		
--         1.3.6.1.4.1.37950.1.1.5.10.3.5.1.7
-- 1.3.6.1.4.1.37950.1.1.5.10.3.5.1.7
-- 1.3.6.1.4.1.37950.1.1.5.10.3.5.1.7
-- 1.3.6.1.4.1.37950.1.1.5.10.3.5.1.7
-- 1.3.6.1.4.1.37950.1.1.5.10.3.5.1.7
-- 1.3.6.1.4.1.37950.1.1.5.10.3.5.1.7
-- 1.3.6.1.4.1.37950.1.1.5.10.3.5.1.7
-- 1.3.6.1.4.1.37950.1.1.5.10.3.5.1.7
		-- 1.3.6.1.4.1.37950.1.1.5.10.3.5.1.7
		macFlappingLastTime OBJECT-TYPE
			SYNTAX OCTET STRING
			MAX-ACCESS read-only
			STATUS current
			DESCRIPTION
				"Description."
			::= { macFlappingEntry 7 }

		
--         1.3.6.1.4.1.37950.1.1.5.10.3.5.1.8
-- 1.3.6.1.4.1.37950.1.1.5.10.3.5.1.8
-- 1.3.6.1.4.1.37950.1.1.5.10.3.5.1.8
-- 1.3.6.1.4.1.37950.1.1.5.10.3.5.1.8
-- 1.3.6.1.4.1.37950.1.1.5.10.3.5.1.8
-- 1.3.6.1.4.1.37950.1.1.5.10.3.5.1.8
-- 1.3.6.1.4.1.37950.1.1.5.10.3.5.1.8
-- 1.3.6.1.4.1.37950.1.1.5.10.3.5.1.8
		-- 1.3.6.1.4.1.37950.1.1.5.10.3.5.1.8
		macFlappingTimes OBJECT-TYPE
			SYNTAX OCTET STRING
			MAX-ACCESS read-only
			STATUS current
			DESCRIPTION
				"Description."
			::= { macFlappingEntry 8 }

		
--         1.3.6.1.4.1.37950.1.1.5.10.3.6
-- 1.3.6.1.4.1.37950.1.1.5.10.3.6
-- 1.3.6.1.4.1.37950.1.1.5.10.3.6
-- 1.3.6.1.4.1.37950.1.1.5.10.3.6
-- 1.3.6.1.4.1.37950.1.1.5.10.3.6
-- 1.3.6.1.4.1.37950.1.1.5.10.3.6
-- 1.3.6.1.4.1.37950.1.1.5.10.3.6
-- 1.3.6.1.4.1.37950.1.1.5.10.3.6
		-- 1.3.6.1.4.1.37950.1.1.5.10.3.6
		macFlappingSuppressionTable OBJECT-TYPE
			SYNTAX SEQUENCE OF MacFlappingSuppressionEntry
			MAX-ACCESS not-accessible
			STATUS current
			DESCRIPTION
				"Description."
			::= { v1600dMacAddr 6 }

		
--         1.3.6.1.4.1.37950.1.1.5.10.3.6.1
-- 1.3.6.1.4.1.37950.1.1.5.10.3.6.1
-- 1.3.6.1.4.1.37950.1.1.5.10.3.6.1
-- 1.3.6.1.4.1.37950.1.1.5.10.3.6.1
-- 1.3.6.1.4.1.37950.1.1.5.10.3.6.1
-- 1.3.6.1.4.1.37950.1.1.5.10.3.6.1
-- 1.3.6.1.4.1.37950.1.1.5.10.3.6.1
-- 1.3.6.1.4.1.37950.1.1.5.10.3.6.1
		-- 1.3.6.1.4.1.37950.1.1.5.10.3.6.1
		macFlappingSuppressionEntry OBJECT-TYPE
			SYNTAX MacFlappingSuppressionEntry
			MAX-ACCESS not-accessible
			STATUS current
			DESCRIPTION
				"Description."
			INDEX { macFlappingSupIndex }
			::= { macFlappingSuppressionTable 1 }

		
		MacFlappingSuppressionEntry ::=
			SEQUENCE { 
				macFlappingSupIndex
					Integer32,
				macFlappingSupInterface
					OCTET STRING,
				macFlappingSupMode
					OCTET STRING,
				macFlappingSupTimes
					OCTET STRING,
				macFlappingSupSrcInterface
					OCTET STRING
			 }

--         1.3.6.1.4.1.37950.1.1.5.10.3.6.1.1
-- 1.3.6.1.4.1.37950.1.1.5.10.3.6.1.1
-- 1.3.6.1.4.1.37950.1.1.5.10.3.6.1.1
-- 1.3.6.1.4.1.37950.1.1.5.10.3.6.1.1
-- 1.3.6.1.4.1.37950.1.1.5.10.3.6.1.1
-- 1.3.6.1.4.1.37950.1.1.5.10.3.6.1.1
-- 1.3.6.1.4.1.37950.1.1.5.10.3.6.1.1
-- 1.3.6.1.4.1.37950.1.1.5.10.3.6.1.1
		-- 1.3.6.1.4.1.37950.1.1.5.10.3.6.1.1
		macFlappingSupIndex OBJECT-TYPE
			SYNTAX Integer32
			MAX-ACCESS read-only
			STATUS current
			DESCRIPTION
				"Description."
			::= { macFlappingSuppressionEntry 1 }

		
--         1.3.6.1.4.1.37950.1.1.5.10.3.6.1.2
-- 1.3.6.1.4.1.37950.1.1.5.10.3.6.1.2
-- 1.3.6.1.4.1.37950.1.1.5.10.3.6.1.2
-- 1.3.6.1.4.1.37950.1.1.5.10.3.6.1.2
-- 1.3.6.1.4.1.37950.1.1.5.10.3.6.1.2
-- 1.3.6.1.4.1.37950.1.1.5.10.3.6.1.2
-- 1.3.6.1.4.1.37950.1.1.5.10.3.6.1.2
-- 1.3.6.1.4.1.37950.1.1.5.10.3.6.1.2
		-- 1.3.6.1.4.1.37950.1.1.5.10.3.6.1.2
		macFlappingSupInterface OBJECT-TYPE
			SYNTAX OCTET STRING
			MAX-ACCESS read-only
			STATUS current
			DESCRIPTION
				"Description."
			::= { macFlappingSuppressionEntry 2 }

		
--         1.3.6.1.4.1.37950.1.1.5.10.3.6.1.3
-- 1.3.6.1.4.1.37950.1.1.5.10.3.6.1.3
-- 1.3.6.1.4.1.37950.1.1.5.10.3.6.1.3
-- 1.3.6.1.4.1.37950.1.1.5.10.3.6.1.3
-- 1.3.6.1.4.1.37950.1.1.5.10.3.6.1.3
-- 1.3.6.1.4.1.37950.1.1.5.10.3.6.1.3
-- 1.3.6.1.4.1.37950.1.1.5.10.3.6.1.3
-- 1.3.6.1.4.1.37950.1.1.5.10.3.6.1.3
		-- 1.3.6.1.4.1.37950.1.1.5.10.3.6.1.3
		macFlappingSupMode OBJECT-TYPE
			SYNTAX OCTET STRING
			MAX-ACCESS read-only
			STATUS current
			DESCRIPTION
				"Description."
			::= { macFlappingSuppressionEntry 3 }

		
--         1.3.6.1.4.1.37950.1.1.5.10.3.6.1.4
-- 1.3.6.1.4.1.37950.1.1.5.10.3.6.1.4
-- 1.3.6.1.4.1.37950.1.1.5.10.3.6.1.4
-- 1.3.6.1.4.1.37950.1.1.5.10.3.6.1.4
-- 1.3.6.1.4.1.37950.1.1.5.10.3.6.1.4
-- 1.3.6.1.4.1.37950.1.1.5.10.3.6.1.4
-- 1.3.6.1.4.1.37950.1.1.5.10.3.6.1.4
-- 1.3.6.1.4.1.37950.1.1.5.10.3.6.1.4
		-- 1.3.6.1.4.1.37950.1.1.5.10.3.6.1.4
		macFlappingSupTimes OBJECT-TYPE
			SYNTAX OCTET STRING
			MAX-ACCESS read-only
			STATUS current
			DESCRIPTION
				"Description."
			::= { macFlappingSuppressionEntry 4 }

		
--         1.3.6.1.4.1.37950.1.1.5.10.3.6.1.5
-- 1.3.6.1.4.1.37950.1.1.5.10.3.6.1.5
-- 1.3.6.1.4.1.37950.1.1.5.10.3.6.1.5
-- 1.3.6.1.4.1.37950.1.1.5.10.3.6.1.5
-- 1.3.6.1.4.1.37950.1.1.5.10.3.6.1.5
-- 1.3.6.1.4.1.37950.1.1.5.10.3.6.1.5
-- 1.3.6.1.4.1.37950.1.1.5.10.3.6.1.5
-- 1.3.6.1.4.1.37950.1.1.5.10.3.6.1.5
		-- 1.3.6.1.4.1.37950.1.1.5.10.3.6.1.5
		macFlappingSupSrcInterface OBJECT-TYPE
			SYNTAX OCTET STRING
			MAX-ACCESS read-only
			STATUS current
			DESCRIPTION
				"Description."
			::= { macFlappingSuppressionEntry 5 }

		
--         1.3.6.1.4.1.37950.1.1.5.10.3.7
-- 1.3.6.1.4.1.37950.1.1.5.10.3.7
-- 1.3.6.1.4.1.37950.1.1.5.10.3.7
-- 1.3.6.1.4.1.37950.1.1.5.10.3.7
-- 1.3.6.1.4.1.37950.1.1.5.10.3.7
-- 1.3.6.1.4.1.37950.1.1.5.10.3.7
-- 1.3.6.1.4.1.37950.1.1.5.10.3.7
-- 1.3.6.1.4.1.37950.1.1.5.10.3.7
		-- 1.3.6.1.4.1.37950.1.1.5.10.3.7
		macFlappingPortTable OBJECT-TYPE
			SYNTAX SEQUENCE OF MacFlappingPortEntry
			MAX-ACCESS not-accessible
			STATUS current
			DESCRIPTION
				"Description."
			::= { v1600dMacAddr 7 }

		
--         1.3.6.1.4.1.37950.1.1.5.10.3.7.1
-- 1.3.6.1.4.1.37950.1.1.5.10.3.7.1
-- 1.3.6.1.4.1.37950.1.1.5.10.3.7.1
-- 1.3.6.1.4.1.37950.1.1.5.10.3.7.1
-- 1.3.6.1.4.1.37950.1.1.5.10.3.7.1
-- 1.3.6.1.4.1.37950.1.1.5.10.3.7.1
-- 1.3.6.1.4.1.37950.1.1.5.10.3.7.1
-- 1.3.6.1.4.1.37950.1.1.5.10.3.7.1
		-- 1.3.6.1.4.1.37950.1.1.5.10.3.7.1
		macFlappingPortEntry OBJECT-TYPE
			SYNTAX MacFlappingPortEntry
			MAX-ACCESS not-accessible
			STATUS current
			DESCRIPTION
				"Description."
			INDEX { macFlappingPortId }
			::= { macFlappingPortTable 1 }

		
		MacFlappingPortEntry ::=
			SEQUENCE { 
				macFlappingPortId
					Integer32,
				macFlappingPortStatus
					INTEGER
			 }

--         1.3.6.1.4.1.37950.1.1.5.10.3.7.1.1
-- 1.3.6.1.4.1.37950.1.1.5.10.3.7.1.1
-- 1.3.6.1.4.1.37950.1.1.5.10.3.7.1.1
-- 1.3.6.1.4.1.37950.1.1.5.10.3.7.1.1
-- 1.3.6.1.4.1.37950.1.1.5.10.3.7.1.1
-- 1.3.6.1.4.1.37950.1.1.5.10.3.7.1.1
-- 1.3.6.1.4.1.37950.1.1.5.10.3.7.1.1
-- 1.3.6.1.4.1.37950.1.1.5.10.3.7.1.1
		-- 1.3.6.1.4.1.37950.1.1.5.10.3.7.1.1
		macFlappingPortId OBJECT-TYPE
			SYNTAX Integer32
			MAX-ACCESS read-only
			STATUS current
			DESCRIPTION
				"Description."
			::= { macFlappingPortEntry 1 }

		
--         1.3.6.1.4.1.37950.1.1.5.10.3.7.1.2
-- 1.3.6.1.4.1.37950.1.1.5.10.3.7.1.2
-- 1.3.6.1.4.1.37950.1.1.5.10.3.7.1.2
-- 1.3.6.1.4.1.37950.1.1.5.10.3.7.1.2
-- 1.3.6.1.4.1.37950.1.1.5.10.3.7.1.2
-- 1.3.6.1.4.1.37950.1.1.5.10.3.7.1.2
-- 1.3.6.1.4.1.37950.1.1.5.10.3.7.1.2
-- 1.3.6.1.4.1.37950.1.1.5.10.3.7.1.2
		-- 1.3.6.1.4.1.37950.1.1.5.10.3.7.1.2
		macFlappingPortStatus OBJECT-TYPE
			SYNTAX INTEGER
				{
				disable(0),
				enable(1)
				}
			MAX-ACCESS read-write
			STATUS current
			DESCRIPTION
				"Description."
			::= { macFlappingPortEntry 2 }

		
--         1.3.6.1.4.1.37950.1.1.5.10.3.8
-- 1.3.6.1.4.1.37950.1.1.5.10.3.8
-- 1.3.6.1.4.1.37950.1.1.5.10.3.8
-- 1.3.6.1.4.1.37950.1.1.5.10.3.8
-- 1.3.6.1.4.1.37950.1.1.5.10.3.8
-- 1.3.6.1.4.1.37950.1.1.5.10.3.8
-- 1.3.6.1.4.1.37950.1.1.5.10.3.8
-- 1.3.6.1.4.1.37950.1.1.5.10.3.8
		-- 1.3.6.1.4.1.37950.1.1.5.10.3.8
		macAddr1Table OBJECT-TYPE
			SYNTAX SEQUENCE OF MacAddr1Entry
			MAX-ACCESS not-accessible
			STATUS current
			DESCRIPTION
				"Description."
			::= { v1600dMacAddr 8 }

		
--         1.3.6.1.4.1.37950.1.1.5.10.3.8.1
-- 1.3.6.1.4.1.37950.1.1.5.10.3.8.1
-- 1.3.6.1.4.1.37950.1.1.5.10.3.8.1
-- 1.3.6.1.4.1.37950.1.1.5.10.3.8.1
-- 1.3.6.1.4.1.37950.1.1.5.10.3.8.1
-- 1.3.6.1.4.1.37950.1.1.5.10.3.8.1
-- 1.3.6.1.4.1.37950.1.1.5.10.3.8.1
-- 1.3.6.1.4.1.37950.1.1.5.10.3.8.1
		-- 1.3.6.1.4.1.37950.1.1.5.10.3.8.1
		macAddr1Entry OBJECT-TYPE
			SYNTAX MacAddr1Entry
			MAX-ACCESS not-accessible
			STATUS current
			DESCRIPTION
				"Description."
			INDEX { macAddr1 }
			::= { macAddr1Table 1 }

		
		MacAddr1Entry ::=
			SEQUENCE { 
				macAddr1
					OCTET STRING,
				macVlanId1
					Integer32,
				macType1
					INTEGER,
				macPortId1
					OCTET STRING
			 }

--         1.3.6.1.4.1.37950.1.1.5.10.3.8.1.1
-- 1.3.6.1.4.1.37950.1.1.5.10.3.8.1.1
-- 1.3.6.1.4.1.37950.1.1.5.10.3.8.1.1
-- 1.3.6.1.4.1.37950.1.1.5.10.3.8.1.1
-- 1.3.6.1.4.1.37950.1.1.5.10.3.8.1.1
-- 1.3.6.1.4.1.37950.1.1.5.10.3.8.1.1
-- 1.3.6.1.4.1.37950.1.1.5.10.3.8.1.1
-- 1.3.6.1.4.1.37950.1.1.5.10.3.8.1.1
		-- 1.3.6.1.4.1.37950.1.1.5.10.3.8.1.1
		macAddr1 OBJECT-TYPE
			SYNTAX OCTET STRING
			MAX-ACCESS read-only
			STATUS current
			DESCRIPTION
				"Description."
			::= { macAddr1Entry 1 }

		
--         1.3.6.1.4.1.37950.1.1.5.10.3.8.1.2
-- 1.3.6.1.4.1.37950.1.1.5.10.3.8.1.2
-- 1.3.6.1.4.1.37950.1.1.5.10.3.8.1.2
-- 1.3.6.1.4.1.37950.1.1.5.10.3.8.1.2
-- 1.3.6.1.4.1.37950.1.1.5.10.3.8.1.2
-- 1.3.6.1.4.1.37950.1.1.5.10.3.8.1.2
-- 1.3.6.1.4.1.37950.1.1.5.10.3.8.1.2
-- 1.3.6.1.4.1.37950.1.1.5.10.3.8.1.2
		-- 1.3.6.1.4.1.37950.1.1.5.10.3.8.1.2
		macVlanId1 OBJECT-TYPE
			SYNTAX Integer32
			MAX-ACCESS read-only
			STATUS current
			DESCRIPTION
				"Description."
			::= { macAddr1Entry 2 }

		
--         1.3.6.1.4.1.37950.1.1.5.10.3.8.1.3
-- 1.3.6.1.4.1.37950.1.1.5.10.3.8.1.3
-- 1.3.6.1.4.1.37950.1.1.5.10.3.8.1.3
-- 1.3.6.1.4.1.37950.1.1.5.10.3.8.1.3
-- 1.3.6.1.4.1.37950.1.1.5.10.3.8.1.3
-- 1.3.6.1.4.1.37950.1.1.5.10.3.8.1.3
-- 1.3.6.1.4.1.37950.1.1.5.10.3.8.1.3
-- 1.3.6.1.4.1.37950.1.1.5.10.3.8.1.3
		-- 1.3.6.1.4.1.37950.1.1.5.10.3.8.1.3
		macType1 OBJECT-TYPE
			SYNTAX INTEGER
				{
				static(0),
				dynamic(1)
				}
			MAX-ACCESS read-only
			STATUS current
			DESCRIPTION
				"Description."
			::= { macAddr1Entry 3 }

		
--         1.3.6.1.4.1.37950.1.1.5.10.3.8.1.4
-- 1.3.6.1.4.1.37950.1.1.5.10.3.8.1.4
-- 1.3.6.1.4.1.37950.1.1.5.10.3.8.1.4
-- 1.3.6.1.4.1.37950.1.1.5.10.3.8.1.4
-- 1.3.6.1.4.1.37950.1.1.5.10.3.8.1.4
-- 1.3.6.1.4.1.37950.1.1.5.10.3.8.1.4
-- 1.3.6.1.4.1.37950.1.1.5.10.3.8.1.4
-- 1.3.6.1.4.1.37950.1.1.5.10.3.8.1.4
		-- 1.3.6.1.4.1.37950.1.1.5.10.3.8.1.4
		macPortId1 OBJECT-TYPE
			SYNTAX OCTET STRING
			MAX-ACCESS read-only
			STATUS current
			DESCRIPTION
				"Description."
			::= { macAddr1Entry 4 }

		
--         1.3.6.1.4.1.37950.1.1.5.10.3.9
-- 1.3.6.1.4.1.37950.1.1.5.10.3.9
-- 1.3.6.1.4.1.37950.1.1.5.10.3.9
-- 1.3.6.1.4.1.37950.1.1.5.10.3.9
-- 1.3.6.1.4.1.37950.1.1.5.10.3.9
-- 1.3.6.1.4.1.37950.1.1.5.10.3.9
-- 1.3.6.1.4.1.37950.1.1.5.10.3.9
-- 1.3.6.1.4.1.37950.1.1.5.10.3.9
		-- 1.3.6.1.4.1.37950.1.1.5.10.3.9
		macAddrStrTable OBJECT-TYPE
			SYNTAX SEQUENCE OF MacAddrStrEntry
			MAX-ACCESS not-accessible
			STATUS current
			DESCRIPTION
				"Description."
			::= { v1600dMacAddr 9 }

		
--         1.3.6.1.4.1.37950.1.1.5.10.3.9.1
-- 1.3.6.1.4.1.37950.1.1.5.10.3.9.1
-- 1.3.6.1.4.1.37950.1.1.5.10.3.9.1
-- 1.3.6.1.4.1.37950.1.1.5.10.3.9.1
-- 1.3.6.1.4.1.37950.1.1.5.10.3.9.1
-- 1.3.6.1.4.1.37950.1.1.5.10.3.9.1
-- 1.3.6.1.4.1.37950.1.1.5.10.3.9.1
-- 1.3.6.1.4.1.37950.1.1.5.10.3.9.1
		-- 1.3.6.1.4.1.37950.1.1.5.10.3.9.1
		macAddrStrEntry OBJECT-TYPE
			SYNTAX MacAddrStrEntry
			MAX-ACCESS not-accessible
			STATUS current
			DESCRIPTION
				"Description."
			INDEX { macAddrStrIndex }
			::= { macAddrStrTable 1 }

		
		MacAddrStrEntry ::=
			SEQUENCE { 
				macAddrStrIndex
					Integer32,
				macVlanIdAddrTypePortId
					OCTET STRING
			 }

--         1.3.6.1.4.1.37950.1.1.5.10.3.9.1.1
-- 1.3.6.1.4.1.37950.1.1.5.10.3.9.1.1
-- 1.3.6.1.4.1.37950.1.1.5.10.3.9.1.1
-- 1.3.6.1.4.1.37950.1.1.5.10.3.9.1.1
-- 1.3.6.1.4.1.37950.1.1.5.10.3.9.1.1
-- 1.3.6.1.4.1.37950.1.1.5.10.3.9.1.1
-- 1.3.6.1.4.1.37950.1.1.5.10.3.9.1.1
-- 1.3.6.1.4.1.37950.1.1.5.10.3.9.1.1
		-- 1.3.6.1.4.1.37950.1.1.5.10.3.9.1.1
		macAddrStrIndex OBJECT-TYPE
			SYNTAX Integer32
			MAX-ACCESS read-only
			STATUS current
			DESCRIPTION
				"Description."
			::= { macAddrStrEntry 1 }

		
--         1.3.6.1.4.1.37950.1.1.5.10.3.9.1.2
-- 1.3.6.1.4.1.37950.1.1.5.10.3.9.1.2
-- 1.3.6.1.4.1.37950.1.1.5.10.3.9.1.2
-- 1.3.6.1.4.1.37950.1.1.5.10.3.9.1.2
-- 1.3.6.1.4.1.37950.1.1.5.10.3.9.1.2
-- 1.3.6.1.4.1.37950.1.1.5.10.3.9.1.2
-- 1.3.6.1.4.1.37950.1.1.5.10.3.9.1.2
-- 1.3.6.1.4.1.37950.1.1.5.10.3.9.1.2
		-- 1.3.6.1.4.1.37950.1.1.5.10.3.9.1.2
		macVlanIdAddrTypePortId OBJECT-TYPE
			SYNTAX OCTET STRING
			MAX-ACCESS read-only
			STATUS current
			DESCRIPTION
				"Description."
			::= { macAddrStrEntry 2 }

		
--        1.3.6.1.4.1.37950.1.1.5.10.3.10
-- 1.3.6.1.4.1.37950.1.1.5.10.3.10
-- 1.3.6.1.4.1.37950.1.1.5.10.3.10
-- 1.3.6.1.4.1.37950.1.1.5.10.3.10
-- 1.3.6.1.4.1.37950.1.1.5.10.3.10
-- 1.3.6.1.4.1.37950.1.1.5.10.3.10
-- 1.3.6.1.4.1.37950.1.1.5.10.3.10
		-- 1.3.6.1.4.1.37950.1.1.5.10.3.10
		macAddrCfg OBJECT IDENTIFIER ::= { v1600dMacAddr 10 }

		
--        1.3.6.1.4.1.37950.1.1.5.10.3.10.1
-- 1.3.6.1.4.1.37950.1.1.5.10.3.10.1
-- 1.3.6.1.4.1.37950.1.1.5.10.3.10.1
-- 1.3.6.1.4.1.37950.1.1.5.10.3.10.1
-- 1.3.6.1.4.1.37950.1.1.5.10.3.10.1
-- 1.3.6.1.4.1.37950.1.1.5.10.3.10.1
-- 1.3.6.1.4.1.37950.1.1.5.10.3.10.1
		-- 1.3.6.1.4.1.37950.1.1.5.10.3.10.1
		macAddrCfgVlanID OBJECT-TYPE
			SYNTAX INTEGER (1..4094)
			MAX-ACCESS read-write
			STATUS current
			DESCRIPTION
				"Description."
			::= { macAddrCfg 1 }

		
--        1.3.6.1.4.1.37950.1.1.5.10.3.10.2
-- 1.3.6.1.4.1.37950.1.1.5.10.3.10.2
-- 1.3.6.1.4.1.37950.1.1.5.10.3.10.2
-- 1.3.6.1.4.1.37950.1.1.5.10.3.10.2
-- 1.3.6.1.4.1.37950.1.1.5.10.3.10.2
-- 1.3.6.1.4.1.37950.1.1.5.10.3.10.2
-- 1.3.6.1.4.1.37950.1.1.5.10.3.10.2
		-- 1.3.6.1.4.1.37950.1.1.5.10.3.10.2
		macAddrCfgMacAddr OBJECT-TYPE
			SYNTAX OCTET STRING
			MAX-ACCESS read-write
			STATUS current
			DESCRIPTION
				"Description."
			::= { macAddrCfg 2 }

		
--        1.3.6.1.4.1.37950.1.1.5.10.3.10.3
-- 1.3.6.1.4.1.37950.1.1.5.10.3.10.3
-- 1.3.6.1.4.1.37950.1.1.5.10.3.10.3
-- 1.3.6.1.4.1.37950.1.1.5.10.3.10.3
-- 1.3.6.1.4.1.37950.1.1.5.10.3.10.3
-- 1.3.6.1.4.1.37950.1.1.5.10.3.10.3
-- 1.3.6.1.4.1.37950.1.1.5.10.3.10.3
		-- 1.3.6.1.4.1.37950.1.1.5.10.3.10.3
		macAddrCfgPortType OBJECT-TYPE
			SYNTAX INTEGER
				{
				dynamic(0),
				static(1)
				}
			MAX-ACCESS read-write
			STATUS current
			DESCRIPTION
				"Description."
			::= { macAddrCfg 3 }

		
--        1.3.6.1.4.1.37950.1.1.5.10.3.10.4
-- 1.3.6.1.4.1.37950.1.1.5.10.3.10.4
-- 1.3.6.1.4.1.37950.1.1.5.10.3.10.4
-- 1.3.6.1.4.1.37950.1.1.5.10.3.10.4
-- 1.3.6.1.4.1.37950.1.1.5.10.3.10.4
-- 1.3.6.1.4.1.37950.1.1.5.10.3.10.4
-- 1.3.6.1.4.1.37950.1.1.5.10.3.10.4
		-- 1.3.6.1.4.1.37950.1.1.5.10.3.10.4
		macAddrCfgPortID OBJECT-TYPE
			SYNTAX INTEGER
				{
				ge1(1),
				ge2(2),
				ge3(3),
				ge4(4),
				ge5(5),
				ge6(6),
				ge7(7),
				ge8(8),
				ge9(9),
				ge10(10),
				ge11(11),
				ge12(12),
				ge13(13),
				ge14(14),
				ge15(15),
				ge16(16),
				pon1(17),
				pon2(18),
				pon3(19),
				pon4(20),
				pon5(21),
				pon6(22),
				pon7(23),
				pon8(24),
				pon9(25),
				pon10(26),
				pon11(27),
				pon12(28),
				pon13(29),
				pon14(30),
				pon15(31),
				pon16(32)
				}
			MAX-ACCESS read-write
			STATUS current
			DESCRIPTION
				"Description."
			::= { macAddrCfg 4 }

		
--        1.3.6.1.4.1.37950.1.1.5.10.3.10.5
-- 1.3.6.1.4.1.37950.1.1.5.10.3.10.5
-- 1.3.6.1.4.1.37950.1.1.5.10.3.10.5
-- 1.3.6.1.4.1.37950.1.1.5.10.3.10.5
-- 1.3.6.1.4.1.37950.1.1.5.10.3.10.5
-- 1.3.6.1.4.1.37950.1.1.5.10.3.10.5
-- 1.3.6.1.4.1.37950.1.1.5.10.3.10.5
		-- 1.3.6.1.4.1.37950.1.1.5.10.3.10.5
		macAddrCfgAction OBJECT-TYPE
			SYNTAX INTEGER
				{
				submit(1),
				delete(2)
				}
			MAX-ACCESS read-write
			STATUS current
			DESCRIPTION
				"Description."
			::= { macAddrCfg 5 }

		
--               1.3.6.1.4.1.37950.1.1.5.10.4
-- 1.3.6.1.4.1.37950.1.1.5.10.4
-- 1.3.6.1.4.1.37950.1.1.5.10.4
-- 1.3.6.1.4.1.37950.1.1.5.10.4
-- 1.3.6.1.4.1.37950.1.1.5.10.4
-- 1.3.6.1.4.1.37950.1.1.5.10.4
-- 1.3.6.1.4.1.37950.1.1.5.10.4
-- 1.3.6.1.4.1.37950.1.1.5.10.4
-- 1.3.6.1.4.1.37950.1.1.5.10.4
-- 1.3.6.1.4.1.37950.1.1.5.10.4
-- 1.3.6.1.4.1.37950.1.1.5.10.4
-- 1.3.6.1.4.1.37950.1.1.5.10.4
-- 1.3.6.1.4.1.37950.1.1.5.10.4
-- 1.3.6.1.4.1.37950.1.1.5.10.4
		-- 1.3.6.1.4.1.37950.1.1.5.10.4
		v1600dQos OBJECT IDENTIFIER ::= { v1600dSwitch 4 }

		
--          1.3.6.1.4.1.37950.1.1.5.10.4.1
-- 1.3.6.1.4.1.37950.1.1.5.10.4.1
-- 1.3.6.1.4.1.37950.1.1.5.10.4.1
-- 1.3.6.1.4.1.37950.1.1.5.10.4.1
-- 1.3.6.1.4.1.37950.1.1.5.10.4.1
-- 1.3.6.1.4.1.37950.1.1.5.10.4.1
-- 1.3.6.1.4.1.37950.1.1.5.10.4.1
-- 1.3.6.1.4.1.37950.1.1.5.10.4.1
-- 1.3.6.1.4.1.37950.1.1.5.10.4.1
		-- 1.3.6.1.4.1.37950.1.1.5.10.4.1
		qosQueueScheduler OBJECT-TYPE
			SYNTAX INTEGER
				{
				strict-priority(1),
				wrr(2),
				sp-wrr(3)
				}
			MAX-ACCESS read-write
			STATUS current
			DESCRIPTION
				"Description."
			::= { v1600dQos 1 }

		
--          1.3.6.1.4.1.37950.1.1.5.10.4.2
-- 1.3.6.1.4.1.37950.1.1.5.10.4.2
-- 1.3.6.1.4.1.37950.1.1.5.10.4.2
-- 1.3.6.1.4.1.37950.1.1.5.10.4.2
-- 1.3.6.1.4.1.37950.1.1.5.10.4.2
-- 1.3.6.1.4.1.37950.1.1.5.10.4.2
-- 1.3.6.1.4.1.37950.1.1.5.10.4.2
-- 1.3.6.1.4.1.37950.1.1.5.10.4.2
-- 1.3.6.1.4.1.37950.1.1.5.10.4.2
		-- 1.3.6.1.4.1.37950.1.1.5.10.4.2
		wrrTable OBJECT-TYPE
			SYNTAX SEQUENCE OF WrrEntry
			MAX-ACCESS not-accessible
			STATUS current
			DESCRIPTION
				"Description."
			::= { v1600dQos 2 }

		
--          1.3.6.1.4.1.37950.1.1.5.10.4.2.1
-- 1.3.6.1.4.1.37950.1.1.5.10.4.2.1
-- 1.3.6.1.4.1.37950.1.1.5.10.4.2.1
-- 1.3.6.1.4.1.37950.1.1.5.10.4.2.1
-- 1.3.6.1.4.1.37950.1.1.5.10.4.2.1
-- 1.3.6.1.4.1.37950.1.1.5.10.4.2.1
-- 1.3.6.1.4.1.37950.1.1.5.10.4.2.1
-- 1.3.6.1.4.1.37950.1.1.5.10.4.2.1
-- 1.3.6.1.4.1.37950.1.1.5.10.4.2.1
		-- 1.3.6.1.4.1.37950.1.1.5.10.4.2.1
		wrrEntry OBJECT-TYPE
			SYNTAX WrrEntry
			MAX-ACCESS not-accessible
			STATUS current
			DESCRIPTION
				"Description."
			INDEX { wrrQueue }
			::= { wrrTable 1 }

		
		WrrEntry ::=
			SEQUENCE { 
				wrrQueue
					Gauge32,
				wrrWeight
					INTEGER
			 }

--          1.3.6.1.4.1.37950.1.1.5.10.4.2.1.1
-- 1.3.6.1.4.1.37950.1.1.5.10.4.2.1.1
-- 1.3.6.1.4.1.37950.1.1.5.10.4.2.1.1
-- 1.3.6.1.4.1.37950.1.1.5.10.4.2.1.1
-- 1.3.6.1.4.1.37950.1.1.5.10.4.2.1.1
-- 1.3.6.1.4.1.37950.1.1.5.10.4.2.1.1
-- 1.3.6.1.4.1.37950.1.1.5.10.4.2.1.1
-- 1.3.6.1.4.1.37950.1.1.5.10.4.2.1.1
-- 1.3.6.1.4.1.37950.1.1.5.10.4.2.1.1
		-- 1.3.6.1.4.1.37950.1.1.5.10.4.2.1.1
		wrrQueue OBJECT-TYPE
			SYNTAX Gauge32 (0..7)
			MAX-ACCESS read-only
			STATUS current
			DESCRIPTION
				"Description."
			::= { wrrEntry 1 }

		
--          1.3.6.1.4.1.37950.1.1.5.10.4.2.1.2
-- 1.3.6.1.4.1.37950.1.1.5.10.4.2.1.2
-- 1.3.6.1.4.1.37950.1.1.5.10.4.2.1.2
-- 1.3.6.1.4.1.37950.1.1.5.10.4.2.1.2
-- 1.3.6.1.4.1.37950.1.1.5.10.4.2.1.2
-- 1.3.6.1.4.1.37950.1.1.5.10.4.2.1.2
-- 1.3.6.1.4.1.37950.1.1.5.10.4.2.1.2
-- 1.3.6.1.4.1.37950.1.1.5.10.4.2.1.2
-- 1.3.6.1.4.1.37950.1.1.5.10.4.2.1.2
		-- 1.3.6.1.4.1.37950.1.1.5.10.4.2.1.2
		wrrWeight OBJECT-TYPE
			SYNTAX INTEGER (1..127)
			MAX-ACCESS read-write
			STATUS current
			DESCRIPTION
				"Description."
			::= { wrrEntry 2 }

		
--          1.3.6.1.4.1.37950.1.1.5.10.4.3
-- 1.3.6.1.4.1.37950.1.1.5.10.4.3
-- 1.3.6.1.4.1.37950.1.1.5.10.4.3
-- 1.3.6.1.4.1.37950.1.1.5.10.4.3
-- 1.3.6.1.4.1.37950.1.1.5.10.4.3
-- 1.3.6.1.4.1.37950.1.1.5.10.4.3
-- 1.3.6.1.4.1.37950.1.1.5.10.4.3
-- 1.3.6.1.4.1.37950.1.1.5.10.4.3
-- 1.3.6.1.4.1.37950.1.1.5.10.4.3
		-- 1.3.6.1.4.1.37950.1.1.5.10.4.3
		spWrrTable OBJECT-TYPE
			SYNTAX SEQUENCE OF SpWrrEntry
			MAX-ACCESS not-accessible
			STATUS current
			DESCRIPTION
				"Description."
			::= { v1600dQos 3 }

		
--          1.3.6.1.4.1.37950.1.1.5.10.4.3.1
-- 1.3.6.1.4.1.37950.1.1.5.10.4.3.1
-- 1.3.6.1.4.1.37950.1.1.5.10.4.3.1
-- 1.3.6.1.4.1.37950.1.1.5.10.4.3.1
-- 1.3.6.1.4.1.37950.1.1.5.10.4.3.1
-- 1.3.6.1.4.1.37950.1.1.5.10.4.3.1
-- 1.3.6.1.4.1.37950.1.1.5.10.4.3.1
-- 1.3.6.1.4.1.37950.1.1.5.10.4.3.1
-- 1.3.6.1.4.1.37950.1.1.5.10.4.3.1
		-- 1.3.6.1.4.1.37950.1.1.5.10.4.3.1
		spWrrEntry OBJECT-TYPE
			SYNTAX SpWrrEntry
			MAX-ACCESS not-accessible
			STATUS current
			DESCRIPTION
				"Description."
			INDEX { spWrrQueue }
			::= { spWrrTable 1 }

		
		SpWrrEntry ::=
			SEQUENCE { 
				spWrrQueue
					INTEGER,
				spWrrWeight
					INTEGER
			 }

--          1.3.6.1.4.1.37950.1.1.5.10.4.3.1.1
-- 1.3.6.1.4.1.37950.1.1.5.10.4.3.1.1
-- 1.3.6.1.4.1.37950.1.1.5.10.4.3.1.1
-- 1.3.6.1.4.1.37950.1.1.5.10.4.3.1.1
-- 1.3.6.1.4.1.37950.1.1.5.10.4.3.1.1
-- 1.3.6.1.4.1.37950.1.1.5.10.4.3.1.1
-- 1.3.6.1.4.1.37950.1.1.5.10.4.3.1.1
-- 1.3.6.1.4.1.37950.1.1.5.10.4.3.1.1
-- 1.3.6.1.4.1.37950.1.1.5.10.4.3.1.1
		-- 1.3.6.1.4.1.37950.1.1.5.10.4.3.1.1
		spWrrQueue OBJECT-TYPE
			SYNTAX INTEGER (0..7)
			MAX-ACCESS read-only
			STATUS current
			DESCRIPTION
				"Description."
			::= { spWrrEntry 1 }

		
--          1.3.6.1.4.1.37950.1.1.5.10.4.3.1.2
-- 1.3.6.1.4.1.37950.1.1.5.10.4.3.1.2
-- 1.3.6.1.4.1.37950.1.1.5.10.4.3.1.2
-- 1.3.6.1.4.1.37950.1.1.5.10.4.3.1.2
-- 1.3.6.1.4.1.37950.1.1.5.10.4.3.1.2
-- 1.3.6.1.4.1.37950.1.1.5.10.4.3.1.2
-- 1.3.6.1.4.1.37950.1.1.5.10.4.3.1.2
-- 1.3.6.1.4.1.37950.1.1.5.10.4.3.1.2
-- 1.3.6.1.4.1.37950.1.1.5.10.4.3.1.2
		-- 1.3.6.1.4.1.37950.1.1.5.10.4.3.1.2
		spWrrWeight OBJECT-TYPE
			SYNTAX INTEGER (0..127)
			MAX-ACCESS read-write
			STATUS current
			DESCRIPTION
				"Description."
			::= { spWrrEntry 2 }

		
--          1.3.6.1.4.1.37950.1.1.5.10.5
-- 1.3.6.1.4.1.37950.1.1.5.10.5
-- 1.3.6.1.4.1.37950.1.1.5.10.5
-- 1.3.6.1.4.1.37950.1.1.5.10.5
-- 1.3.6.1.4.1.37950.1.1.5.10.5
-- 1.3.6.1.4.1.37950.1.1.5.10.5
-- 1.3.6.1.4.1.37950.1.1.5.10.5
-- 1.3.6.1.4.1.37950.1.1.5.10.5
-- 1.3.6.1.4.1.37950.1.1.5.10.5
		-- 1.3.6.1.4.1.37950.1.1.5.10.5
		v1600dIgmpsnooping OBJECT IDENTIFIER ::= { v1600dSwitch 5 }

		
--          1.3.6.1.4.1.37950.1.1.5.10.5.1
-- 1.3.6.1.4.1.37950.1.1.5.10.5.1
-- 1.3.6.1.4.1.37950.1.1.5.10.5.1
-- 1.3.6.1.4.1.37950.1.1.5.10.5.1
-- 1.3.6.1.4.1.37950.1.1.5.10.5.1
-- 1.3.6.1.4.1.37950.1.1.5.10.5.1
-- 1.3.6.1.4.1.37950.1.1.5.10.5.1
-- 1.3.6.1.4.1.37950.1.1.5.10.5.1
-- 1.3.6.1.4.1.37950.1.1.5.10.5.1
		-- 1.3.6.1.4.1.37950.1.1.5.10.5.1
		igmpSnoopingEn OBJECT-TYPE
			SYNTAX INTEGER
				{
				disable(0),
				enable(1)
				}
			MAX-ACCESS read-write
			STATUS current
			DESCRIPTION
				"Description."
			::= { v1600dIgmpsnooping 1 }

		
--          1.3.6.1.4.1.37950.1.1.5.10.5.2
-- 1.3.6.1.4.1.37950.1.1.5.10.5.2
-- 1.3.6.1.4.1.37950.1.1.5.10.5.2
-- 1.3.6.1.4.1.37950.1.1.5.10.5.2
-- 1.3.6.1.4.1.37950.1.1.5.10.5.2
-- 1.3.6.1.4.1.37950.1.1.5.10.5.2
-- 1.3.6.1.4.1.37950.1.1.5.10.5.2
-- 1.3.6.1.4.1.37950.1.1.5.10.5.2
-- 1.3.6.1.4.1.37950.1.1.5.10.5.2
		-- 1.3.6.1.4.1.37950.1.1.5.10.5.2
		igmpMrouterPortCfg OBJECT IDENTIFIER ::= { v1600dIgmpsnooping 2 }

		
--          1.3.6.1.4.1.37950.1.1.5.10.5.2.1
-- 1.3.6.1.4.1.37950.1.1.5.10.5.2.1
-- 1.3.6.1.4.1.37950.1.1.5.10.5.2.1
-- 1.3.6.1.4.1.37950.1.1.5.10.5.2.1
-- 1.3.6.1.4.1.37950.1.1.5.10.5.2.1
-- 1.3.6.1.4.1.37950.1.1.5.10.5.2.1
-- 1.3.6.1.4.1.37950.1.1.5.10.5.2.1
-- 1.3.6.1.4.1.37950.1.1.5.10.5.2.1
-- 1.3.6.1.4.1.37950.1.1.5.10.5.2.1
		-- 1.3.6.1.4.1.37950.1.1.5.10.5.2.1
		mrouterPort OBJECT-TYPE
			SYNTAX INTEGER (1..16)
			MAX-ACCESS read-write
			STATUS current
			DESCRIPTION
				"Description."
			::= { igmpMrouterPortCfg 1 }

		
--          1.3.6.1.4.1.37950.1.1.5.10.5.2.2
-- 1.3.6.1.4.1.37950.1.1.5.10.5.2.2
-- 1.3.6.1.4.1.37950.1.1.5.10.5.2.2
-- 1.3.6.1.4.1.37950.1.1.5.10.5.2.2
-- 1.3.6.1.4.1.37950.1.1.5.10.5.2.2
-- 1.3.6.1.4.1.37950.1.1.5.10.5.2.2
-- 1.3.6.1.4.1.37950.1.1.5.10.5.2.2
-- 1.3.6.1.4.1.37950.1.1.5.10.5.2.2
-- 1.3.6.1.4.1.37950.1.1.5.10.5.2.2
		-- 1.3.6.1.4.1.37950.1.1.5.10.5.2.2
		mrouterVlan OBJECT-TYPE
			SYNTAX INTEGER (1..4094)
			MAX-ACCESS read-write
			STATUS current
			DESCRIPTION
				"Description."
			::= { igmpMrouterPortCfg 2 }

		
--          1.3.6.1.4.1.37950.1.1.5.10.5.2.3
-- 1.3.6.1.4.1.37950.1.1.5.10.5.2.3
-- 1.3.6.1.4.1.37950.1.1.5.10.5.2.3
-- 1.3.6.1.4.1.37950.1.1.5.10.5.2.3
-- 1.3.6.1.4.1.37950.1.1.5.10.5.2.3
-- 1.3.6.1.4.1.37950.1.1.5.10.5.2.3
-- 1.3.6.1.4.1.37950.1.1.5.10.5.2.3
-- 1.3.6.1.4.1.37950.1.1.5.10.5.2.3
-- 1.3.6.1.4.1.37950.1.1.5.10.5.2.3
		-- 1.3.6.1.4.1.37950.1.1.5.10.5.2.3
		mrouterAction OBJECT-TYPE
			SYNTAX INTEGER
				{
				add(1),
				delete(2)
				}
			MAX-ACCESS read-write
			STATUS current
			DESCRIPTION
				"Description."
			::= { igmpMrouterPortCfg 3 }

		
--          1.3.6.1.4.1.37950.1.1.5.10.5.3
-- 1.3.6.1.4.1.37950.1.1.5.10.5.3
-- 1.3.6.1.4.1.37950.1.1.5.10.5.3
-- 1.3.6.1.4.1.37950.1.1.5.10.5.3
-- 1.3.6.1.4.1.37950.1.1.5.10.5.3
-- 1.3.6.1.4.1.37950.1.1.5.10.5.3
-- 1.3.6.1.4.1.37950.1.1.5.10.5.3
-- 1.3.6.1.4.1.37950.1.1.5.10.5.3
-- 1.3.6.1.4.1.37950.1.1.5.10.5.3
		-- 1.3.6.1.4.1.37950.1.1.5.10.5.3
		igmpMrouterPortTable OBJECT-TYPE
			SYNTAX SEQUENCE OF IgmpMrouterPortEntry
			MAX-ACCESS not-accessible
			STATUS current
			DESCRIPTION
				"Description."
			::= { v1600dIgmpsnooping 3 }

		
--          1.3.6.1.4.1.37950.1.1.5.10.5.3.1
-- 1.3.6.1.4.1.37950.1.1.5.10.5.3.1
-- 1.3.6.1.4.1.37950.1.1.5.10.5.3.1
-- 1.3.6.1.4.1.37950.1.1.5.10.5.3.1
-- 1.3.6.1.4.1.37950.1.1.5.10.5.3.1
-- 1.3.6.1.4.1.37950.1.1.5.10.5.3.1
-- 1.3.6.1.4.1.37950.1.1.5.10.5.3.1
-- 1.3.6.1.4.1.37950.1.1.5.10.5.3.1
-- 1.3.6.1.4.1.37950.1.1.5.10.5.3.1
		-- 1.3.6.1.4.1.37950.1.1.5.10.5.3.1
		igmpMrouterPortEntry OBJECT-TYPE
			SYNTAX IgmpMrouterPortEntry
			MAX-ACCESS not-accessible
			STATUS current
			DESCRIPTION
				"Description."
			INDEX { igmpMrouterItem }
			::= { igmpMrouterPortTable 1 }

		
		IgmpMrouterPortEntry ::=
			SEQUENCE { 
				igmpMrouterItem
					Integer32,
				igmpMrouterPort
					INTEGER,
				igmpMrouterVlan
					Integer32
			 }

--          1.3.6.1.4.1.37950.1.1.5.10.5.3.1.1
-- 1.3.6.1.4.1.37950.1.1.5.10.5.3.1.1
-- 1.3.6.1.4.1.37950.1.1.5.10.5.3.1.1
-- 1.3.6.1.4.1.37950.1.1.5.10.5.3.1.1
-- 1.3.6.1.4.1.37950.1.1.5.10.5.3.1.1
-- 1.3.6.1.4.1.37950.1.1.5.10.5.3.1.1
-- 1.3.6.1.4.1.37950.1.1.5.10.5.3.1.1
-- 1.3.6.1.4.1.37950.1.1.5.10.5.3.1.1
-- 1.3.6.1.4.1.37950.1.1.5.10.5.3.1.1
		-- 1.3.6.1.4.1.37950.1.1.5.10.5.3.1.1
		igmpMrouterItem OBJECT-TYPE
			SYNTAX Integer32 (1..24)
			MAX-ACCESS read-write
			STATUS current
			DESCRIPTION
				"Description."
			::= { igmpMrouterPortEntry 1 }

		
--          1.3.6.1.4.1.37950.1.1.5.10.5.3.1.2
-- 1.3.6.1.4.1.37950.1.1.5.10.5.3.1.2
-- 1.3.6.1.4.1.37950.1.1.5.10.5.3.1.2
-- 1.3.6.1.4.1.37950.1.1.5.10.5.3.1.2
-- 1.3.6.1.4.1.37950.1.1.5.10.5.3.1.2
-- 1.3.6.1.4.1.37950.1.1.5.10.5.3.1.2
-- 1.3.6.1.4.1.37950.1.1.5.10.5.3.1.2
-- 1.3.6.1.4.1.37950.1.1.5.10.5.3.1.2
-- 1.3.6.1.4.1.37950.1.1.5.10.5.3.1.2
		-- 1.3.6.1.4.1.37950.1.1.5.10.5.3.1.2
		igmpMrouterPort OBJECT-TYPE
			SYNTAX INTEGER (1..16)
			MAX-ACCESS read-write
			STATUS current
			DESCRIPTION
				"Description."
			::= { igmpMrouterPortEntry 2 }

		
--          1.3.6.1.4.1.37950.1.1.5.10.5.3.1.3
-- 1.3.6.1.4.1.37950.1.1.5.10.5.3.1.3
-- 1.3.6.1.4.1.37950.1.1.5.10.5.3.1.3
-- 1.3.6.1.4.1.37950.1.1.5.10.5.3.1.3
-- 1.3.6.1.4.1.37950.1.1.5.10.5.3.1.3
-- 1.3.6.1.4.1.37950.1.1.5.10.5.3.1.3
-- 1.3.6.1.4.1.37950.1.1.5.10.5.3.1.3
-- 1.3.6.1.4.1.37950.1.1.5.10.5.3.1.3
-- 1.3.6.1.4.1.37950.1.1.5.10.5.3.1.3
		-- 1.3.6.1.4.1.37950.1.1.5.10.5.3.1.3
		igmpMrouterVlan OBJECT-TYPE
			SYNTAX Integer32
			MAX-ACCESS read-only
			STATUS current
			DESCRIPTION
				"Description."
			::= { igmpMrouterPortEntry 3 }

		
--          1.3.6.1.4.1.37950.1.1.5.10.5.4
-- 1.3.6.1.4.1.37950.1.1.5.10.5.4
-- 1.3.6.1.4.1.37950.1.1.5.10.5.4
-- 1.3.6.1.4.1.37950.1.1.5.10.5.4
-- 1.3.6.1.4.1.37950.1.1.5.10.5.4
-- 1.3.6.1.4.1.37950.1.1.5.10.5.4
-- 1.3.6.1.4.1.37950.1.1.5.10.5.4
-- 1.3.6.1.4.1.37950.1.1.5.10.5.4
-- 1.3.6.1.4.1.37950.1.1.5.10.5.4
		-- 1.3.6.1.4.1.37950.1.1.5.10.5.4
		igmpPortTable OBJECT-TYPE
			SYNTAX SEQUENCE OF IgmpPortEntry
			MAX-ACCESS not-accessible
			STATUS current
			DESCRIPTION
				"Description."
			::= { v1600dIgmpsnooping 4 }

		
--          1.3.6.1.4.1.37950.1.1.5.10.5.4.1
-- 1.3.6.1.4.1.37950.1.1.5.10.5.4.1
-- 1.3.6.1.4.1.37950.1.1.5.10.5.4.1
-- 1.3.6.1.4.1.37950.1.1.5.10.5.4.1
-- 1.3.6.1.4.1.37950.1.1.5.10.5.4.1
-- 1.3.6.1.4.1.37950.1.1.5.10.5.4.1
-- 1.3.6.1.4.1.37950.1.1.5.10.5.4.1
-- 1.3.6.1.4.1.37950.1.1.5.10.5.4.1
-- 1.3.6.1.4.1.37950.1.1.5.10.5.4.1
		-- 1.3.6.1.4.1.37950.1.1.5.10.5.4.1
		igmpPortEntry OBJECT-TYPE
			SYNTAX IgmpPortEntry
			MAX-ACCESS not-accessible
			STATUS current
			DESCRIPTION
				"Description."
			INDEX { igmpPortIndex }
			::= { igmpPortTable 1 }

		
		IgmpPortEntry ::=
			SEQUENCE { 
				igmpPortIndex
					Integer32,
				groupCount
					Integer32,
				tagstrip
					INTEGER,
				fastLeave
					INTEGER
			 }

--          1.3.6.1.4.1.37950.1.1.5.10.5.4.1.1
-- 1.3.6.1.4.1.37950.1.1.5.10.5.4.1.1
-- 1.3.6.1.4.1.37950.1.1.5.10.5.4.1.1
-- 1.3.6.1.4.1.37950.1.1.5.10.5.4.1.1
-- 1.3.6.1.4.1.37950.1.1.5.10.5.4.1.1
-- 1.3.6.1.4.1.37950.1.1.5.10.5.4.1.1
-- 1.3.6.1.4.1.37950.1.1.5.10.5.4.1.1
-- 1.3.6.1.4.1.37950.1.1.5.10.5.4.1.1
-- 1.3.6.1.4.1.37950.1.1.5.10.5.4.1.1
		-- 1.3.6.1.4.1.37950.1.1.5.10.5.4.1.1
		igmpPortIndex OBJECT-TYPE
			SYNTAX Integer32 (1..28)
			MAX-ACCESS read-only
			STATUS current
			DESCRIPTION
				"Description."
			::= { igmpPortEntry 1 }

		
--          1.3.6.1.4.1.37950.1.1.5.10.5.4.1.2
-- 1.3.6.1.4.1.37950.1.1.5.10.5.4.1.2
-- 1.3.6.1.4.1.37950.1.1.5.10.5.4.1.2
-- 1.3.6.1.4.1.37950.1.1.5.10.5.4.1.2
-- 1.3.6.1.4.1.37950.1.1.5.10.5.4.1.2
-- 1.3.6.1.4.1.37950.1.1.5.10.5.4.1.2
-- 1.3.6.1.4.1.37950.1.1.5.10.5.4.1.2
-- 1.3.6.1.4.1.37950.1.1.5.10.5.4.1.2
-- 1.3.6.1.4.1.37950.1.1.5.10.5.4.1.2
		-- 1.3.6.1.4.1.37950.1.1.5.10.5.4.1.2
		groupCount OBJECT-TYPE
			SYNTAX Integer32 (0..1024)
			MAX-ACCESS read-write
			STATUS current
			DESCRIPTION
				"Description."
			::= { igmpPortEntry 2 }

		
--          1.3.6.1.4.1.37950.1.1.5.10.5.4.1.3
-- 1.3.6.1.4.1.37950.1.1.5.10.5.4.1.3
-- 1.3.6.1.4.1.37950.1.1.5.10.5.4.1.3
-- 1.3.6.1.4.1.37950.1.1.5.10.5.4.1.3
-- 1.3.6.1.4.1.37950.1.1.5.10.5.4.1.3
-- 1.3.6.1.4.1.37950.1.1.5.10.5.4.1.3
-- 1.3.6.1.4.1.37950.1.1.5.10.5.4.1.3
-- 1.3.6.1.4.1.37950.1.1.5.10.5.4.1.3
-- 1.3.6.1.4.1.37950.1.1.5.10.5.4.1.3
		-- 1.3.6.1.4.1.37950.1.1.5.10.5.4.1.3
		tagstrip OBJECT-TYPE
			SYNTAX INTEGER
				{
				no-tagstrip(0),
				tagstrip(1)
				}
			MAX-ACCESS read-write
			STATUS current
			DESCRIPTION
				"Description."
			::= { igmpPortEntry 3 }

		
--          1.3.6.1.4.1.37950.1.1.5.10.5.4.1.4
-- 1.3.6.1.4.1.37950.1.1.5.10.5.4.1.4
-- 1.3.6.1.4.1.37950.1.1.5.10.5.4.1.4
-- 1.3.6.1.4.1.37950.1.1.5.10.5.4.1.4
-- 1.3.6.1.4.1.37950.1.1.5.10.5.4.1.4
-- 1.3.6.1.4.1.37950.1.1.5.10.5.4.1.4
-- 1.3.6.1.4.1.37950.1.1.5.10.5.4.1.4
-- 1.3.6.1.4.1.37950.1.1.5.10.5.4.1.4
-- 1.3.6.1.4.1.37950.1.1.5.10.5.4.1.4
		-- 1.3.6.1.4.1.37950.1.1.5.10.5.4.1.4
		fastLeave OBJECT-TYPE
			SYNTAX INTEGER
				{
				disable(0),
				enable(1)
				}
			MAX-ACCESS read-write
			STATUS current
			DESCRIPTION
				"Description."
			::= { igmpPortEntry 4 }

		
--          1.3.6.1.4.1.37950.1.1.5.10.5.5
-- 1.3.6.1.4.1.37950.1.1.5.10.5.5
-- 1.3.6.1.4.1.37950.1.1.5.10.5.5
-- 1.3.6.1.4.1.37950.1.1.5.10.5.5
-- 1.3.6.1.4.1.37950.1.1.5.10.5.5
-- 1.3.6.1.4.1.37950.1.1.5.10.5.5
-- 1.3.6.1.4.1.37950.1.1.5.10.5.5
-- 1.3.6.1.4.1.37950.1.1.5.10.5.5
-- 1.3.6.1.4.1.37950.1.1.5.10.5.5
		-- 1.3.6.1.4.1.37950.1.1.5.10.5.5
		userVlanConfig OBJECT IDENTIFIER ::= { v1600dIgmpsnooping 5 }

		
--          1.3.6.1.4.1.37950.1.1.5.10.5.5.1
-- 1.3.6.1.4.1.37950.1.1.5.10.5.5.1
-- 1.3.6.1.4.1.37950.1.1.5.10.5.5.1
-- 1.3.6.1.4.1.37950.1.1.5.10.5.5.1
-- 1.3.6.1.4.1.37950.1.1.5.10.5.5.1
-- 1.3.6.1.4.1.37950.1.1.5.10.5.5.1
-- 1.3.6.1.4.1.37950.1.1.5.10.5.5.1
-- 1.3.6.1.4.1.37950.1.1.5.10.5.5.1
-- 1.3.6.1.4.1.37950.1.1.5.10.5.5.1
		-- 1.3.6.1.4.1.37950.1.1.5.10.5.5.1
		userPort OBJECT-TYPE
			SYNTAX Integer32 (1..28)
			MAX-ACCESS read-write
			STATUS current
			DESCRIPTION
				"Description."
			::= { userVlanConfig 1 }

		
--          1.3.6.1.4.1.37950.1.1.5.10.5.5.2
-- 1.3.6.1.4.1.37950.1.1.5.10.5.5.2
-- 1.3.6.1.4.1.37950.1.1.5.10.5.5.2
-- 1.3.6.1.4.1.37950.1.1.5.10.5.5.2
-- 1.3.6.1.4.1.37950.1.1.5.10.5.5.2
-- 1.3.6.1.4.1.37950.1.1.5.10.5.5.2
-- 1.3.6.1.4.1.37950.1.1.5.10.5.5.2
-- 1.3.6.1.4.1.37950.1.1.5.10.5.5.2
-- 1.3.6.1.4.1.37950.1.1.5.10.5.5.2
		-- 1.3.6.1.4.1.37950.1.1.5.10.5.5.2
		userVlanId OBJECT-TYPE
			SYNTAX Integer32 (1..4094)
			MAX-ACCESS read-write
			STATUS current
			DESCRIPTION
				"Description."
			::= { userVlanConfig 2 }

		
--          1.3.6.1.4.1.37950.1.1.5.10.5.5.3
-- 1.3.6.1.4.1.37950.1.1.5.10.5.5.3
-- 1.3.6.1.4.1.37950.1.1.5.10.5.5.3
-- 1.3.6.1.4.1.37950.1.1.5.10.5.5.3
-- 1.3.6.1.4.1.37950.1.1.5.10.5.5.3
-- 1.3.6.1.4.1.37950.1.1.5.10.5.5.3
-- 1.3.6.1.4.1.37950.1.1.5.10.5.5.3
-- 1.3.6.1.4.1.37950.1.1.5.10.5.5.3
-- 1.3.6.1.4.1.37950.1.1.5.10.5.5.3
		-- 1.3.6.1.4.1.37950.1.1.5.10.5.5.3
		groupVlanId OBJECT-TYPE
			SYNTAX Integer32 (1..4094)
			MAX-ACCESS read-write
			STATUS current
			DESCRIPTION
				"Description."
			::= { userVlanConfig 3 }

		
--          1.3.6.1.4.1.37950.1.1.5.10.5.5.4
-- 1.3.6.1.4.1.37950.1.1.5.10.5.5.4
-- 1.3.6.1.4.1.37950.1.1.5.10.5.5.4
-- 1.3.6.1.4.1.37950.1.1.5.10.5.5.4
-- 1.3.6.1.4.1.37950.1.1.5.10.5.5.4
-- 1.3.6.1.4.1.37950.1.1.5.10.5.5.4
-- 1.3.6.1.4.1.37950.1.1.5.10.5.5.4
-- 1.3.6.1.4.1.37950.1.1.5.10.5.5.4
-- 1.3.6.1.4.1.37950.1.1.5.10.5.5.4
		-- 1.3.6.1.4.1.37950.1.1.5.10.5.5.4
		userAction OBJECT-TYPE
			SYNTAX INTEGER
				{
				add(1),
				delete(2)
				}
			MAX-ACCESS read-write
			STATUS current
			DESCRIPTION
				"Description."
			::= { userVlanConfig 4 }

		
--          1.3.6.1.4.1.37950.1.1.5.10.5.6
-- 1.3.6.1.4.1.37950.1.1.5.10.5.6
-- 1.3.6.1.4.1.37950.1.1.5.10.5.6
-- 1.3.6.1.4.1.37950.1.1.5.10.5.6
-- 1.3.6.1.4.1.37950.1.1.5.10.5.6
-- 1.3.6.1.4.1.37950.1.1.5.10.5.6
-- 1.3.6.1.4.1.37950.1.1.5.10.5.6
-- 1.3.6.1.4.1.37950.1.1.5.10.5.6
-- 1.3.6.1.4.1.37950.1.1.5.10.5.6
		-- 1.3.6.1.4.1.37950.1.1.5.10.5.6
		userVlanTable OBJECT-TYPE
			SYNTAX SEQUENCE OF UserVlanEntry
			MAX-ACCESS not-accessible
			STATUS current
			DESCRIPTION
				"Description."
			::= { v1600dIgmpsnooping 6 }

		
--          1.3.6.1.4.1.37950.1.1.5.10.5.6.1
-- 1.3.6.1.4.1.37950.1.1.5.10.5.6.1
-- 1.3.6.1.4.1.37950.1.1.5.10.5.6.1
-- 1.3.6.1.4.1.37950.1.1.5.10.5.6.1
-- 1.3.6.1.4.1.37950.1.1.5.10.5.6.1
-- 1.3.6.1.4.1.37950.1.1.5.10.5.6.1
-- 1.3.6.1.4.1.37950.1.1.5.10.5.6.1
-- 1.3.6.1.4.1.37950.1.1.5.10.5.6.1
-- 1.3.6.1.4.1.37950.1.1.5.10.5.6.1
		-- 1.3.6.1.4.1.37950.1.1.5.10.5.6.1
		userVlanEntry OBJECT-TYPE
			SYNTAX UserVlanEntry
			MAX-ACCESS not-accessible
			STATUS current
			DESCRIPTION
				"Description."
			INDEX { userVlanIndex }
			::= { userVlanTable 1 }

		
		UserVlanEntry ::=
			SEQUENCE { 
				userVlanIndex
					Integer32,
				userVlanPortIndex
					Integer32,
				userVlanIdIndex
					Integer32,
				groupVlanIdIndex
					Integer32
			 }

--          1.3.6.1.4.1.37950.1.1.5.10.5.6.1.1
-- 1.3.6.1.4.1.37950.1.1.5.10.5.6.1.1
-- 1.3.6.1.4.1.37950.1.1.5.10.5.6.1.1
-- 1.3.6.1.4.1.37950.1.1.5.10.5.6.1.1
-- 1.3.6.1.4.1.37950.1.1.5.10.5.6.1.1
-- 1.3.6.1.4.1.37950.1.1.5.10.5.6.1.1
-- 1.3.6.1.4.1.37950.1.1.5.10.5.6.1.1
-- 1.3.6.1.4.1.37950.1.1.5.10.5.6.1.1
-- 1.3.6.1.4.1.37950.1.1.5.10.5.6.1.1
		-- 1.3.6.1.4.1.37950.1.1.5.10.5.6.1.1
		userVlanIndex OBJECT-TYPE
			SYNTAX Integer32 (1..4094)
			MAX-ACCESS read-only
			STATUS current
			DESCRIPTION
				"Description."
			::= { userVlanEntry 1 }

		
--          1.3.6.1.4.1.37950.1.1.5.10.5.6.1.2
-- 1.3.6.1.4.1.37950.1.1.5.10.5.6.1.2
-- 1.3.6.1.4.1.37950.1.1.5.10.5.6.1.2
-- 1.3.6.1.4.1.37950.1.1.5.10.5.6.1.2
-- 1.3.6.1.4.1.37950.1.1.5.10.5.6.1.2
-- 1.3.6.1.4.1.37950.1.1.5.10.5.6.1.2
-- 1.3.6.1.4.1.37950.1.1.5.10.5.6.1.2
-- 1.3.6.1.4.1.37950.1.1.5.10.5.6.1.2
-- 1.3.6.1.4.1.37950.1.1.5.10.5.6.1.2
		-- 1.3.6.1.4.1.37950.1.1.5.10.5.6.1.2
		userVlanPortIndex OBJECT-TYPE
			SYNTAX Integer32
			MAX-ACCESS read-only
			STATUS current
			DESCRIPTION
				"Description."
			::= { userVlanEntry 2 }

		
--          1.3.6.1.4.1.37950.1.1.5.10.5.6.1.3
-- 1.3.6.1.4.1.37950.1.1.5.10.5.6.1.3
-- 1.3.6.1.4.1.37950.1.1.5.10.5.6.1.3
-- 1.3.6.1.4.1.37950.1.1.5.10.5.6.1.3
-- 1.3.6.1.4.1.37950.1.1.5.10.5.6.1.3
-- 1.3.6.1.4.1.37950.1.1.5.10.5.6.1.3
-- 1.3.6.1.4.1.37950.1.1.5.10.5.6.1.3
-- 1.3.6.1.4.1.37950.1.1.5.10.5.6.1.3
-- 1.3.6.1.4.1.37950.1.1.5.10.5.6.1.3
		-- 1.3.6.1.4.1.37950.1.1.5.10.5.6.1.3
		userVlanIdIndex OBJECT-TYPE
			SYNTAX Integer32
			MAX-ACCESS read-only
			STATUS current
			DESCRIPTION
				"Description."
			::= { userVlanEntry 3 }

		
--          1.3.6.1.4.1.37950.1.1.5.10.5.6.1.4
-- 1.3.6.1.4.1.37950.1.1.5.10.5.6.1.4
-- 1.3.6.1.4.1.37950.1.1.5.10.5.6.1.4
-- 1.3.6.1.4.1.37950.1.1.5.10.5.6.1.4
-- 1.3.6.1.4.1.37950.1.1.5.10.5.6.1.4
-- 1.3.6.1.4.1.37950.1.1.5.10.5.6.1.4
-- 1.3.6.1.4.1.37950.1.1.5.10.5.6.1.4
-- 1.3.6.1.4.1.37950.1.1.5.10.5.6.1.4
-- 1.3.6.1.4.1.37950.1.1.5.10.5.6.1.4
		-- 1.3.6.1.4.1.37950.1.1.5.10.5.6.1.4
		groupVlanIdIndex OBJECT-TYPE
			SYNTAX Integer32
			MAX-ACCESS read-only
			STATUS current
			DESCRIPTION
				"Description."
			::= { userVlanEntry 4 }

		
--          1.3.6.1.4.1.37950.1.1.5.10.5.7
-- 1.3.6.1.4.1.37950.1.1.5.10.5.7
-- 1.3.6.1.4.1.37950.1.1.5.10.5.7
-- 1.3.6.1.4.1.37950.1.1.5.10.5.7
-- 1.3.6.1.4.1.37950.1.1.5.10.5.7
-- 1.3.6.1.4.1.37950.1.1.5.10.5.7
-- 1.3.6.1.4.1.37950.1.1.5.10.5.7
-- 1.3.6.1.4.1.37950.1.1.5.10.5.7
-- 1.3.6.1.4.1.37950.1.1.5.10.5.7
		-- 1.3.6.1.4.1.37950.1.1.5.10.5.7
		igmpStaticGroupCfg OBJECT IDENTIFIER ::= { v1600dIgmpsnooping 7 }

		
--          1.3.6.1.4.1.37950.1.1.5.10.5.7.1
-- 1.3.6.1.4.1.37950.1.1.5.10.5.7.1
-- 1.3.6.1.4.1.37950.1.1.5.10.5.7.1
-- 1.3.6.1.4.1.37950.1.1.5.10.5.7.1
-- 1.3.6.1.4.1.37950.1.1.5.10.5.7.1
-- 1.3.6.1.4.1.37950.1.1.5.10.5.7.1
-- 1.3.6.1.4.1.37950.1.1.5.10.5.7.1
-- 1.3.6.1.4.1.37950.1.1.5.10.5.7.1
-- 1.3.6.1.4.1.37950.1.1.5.10.5.7.1
		-- 1.3.6.1.4.1.37950.1.1.5.10.5.7.1
		staticGroupPort OBJECT-TYPE
			SYNTAX Integer32 (1..28)
			MAX-ACCESS read-write
			STATUS current
			DESCRIPTION
				"Description."
			::= { igmpStaticGroupCfg 1 }

		
--          1.3.6.1.4.1.37950.1.1.5.10.5.7.2
-- 1.3.6.1.4.1.37950.1.1.5.10.5.7.2
-- 1.3.6.1.4.1.37950.1.1.5.10.5.7.2
-- 1.3.6.1.4.1.37950.1.1.5.10.5.7.2
-- 1.3.6.1.4.1.37950.1.1.5.10.5.7.2
-- 1.3.6.1.4.1.37950.1.1.5.10.5.7.2
-- 1.3.6.1.4.1.37950.1.1.5.10.5.7.2
-- 1.3.6.1.4.1.37950.1.1.5.10.5.7.2
-- 1.3.6.1.4.1.37950.1.1.5.10.5.7.2
		-- 1.3.6.1.4.1.37950.1.1.5.10.5.7.2
		staticGroupIp OBJECT-TYPE
			SYNTAX IpAddress
			MAX-ACCESS read-write
			STATUS current
			DESCRIPTION
				"Description."
			::= { igmpStaticGroupCfg 2 }

		
--          1.3.6.1.4.1.37950.1.1.5.10.5.7.3
-- 1.3.6.1.4.1.37950.1.1.5.10.5.7.3
-- 1.3.6.1.4.1.37950.1.1.5.10.5.7.3
-- 1.3.6.1.4.1.37950.1.1.5.10.5.7.3
-- 1.3.6.1.4.1.37950.1.1.5.10.5.7.3
-- 1.3.6.1.4.1.37950.1.1.5.10.5.7.3
-- 1.3.6.1.4.1.37950.1.1.5.10.5.7.3
-- 1.3.6.1.4.1.37950.1.1.5.10.5.7.3
-- 1.3.6.1.4.1.37950.1.1.5.10.5.7.3
		-- 1.3.6.1.4.1.37950.1.1.5.10.5.7.3
		staticGroupVlan OBJECT-TYPE
			SYNTAX Integer32 (1..4094)
			MAX-ACCESS read-write
			STATUS current
			DESCRIPTION
				"Description."
			::= { igmpStaticGroupCfg 3 }

		
--          1.3.6.1.4.1.37950.1.1.5.10.5.7.4
-- 1.3.6.1.4.1.37950.1.1.5.10.5.7.4
-- 1.3.6.1.4.1.37950.1.1.5.10.5.7.4
-- 1.3.6.1.4.1.37950.1.1.5.10.5.7.4
-- 1.3.6.1.4.1.37950.1.1.5.10.5.7.4
-- 1.3.6.1.4.1.37950.1.1.5.10.5.7.4
-- 1.3.6.1.4.1.37950.1.1.5.10.5.7.4
-- 1.3.6.1.4.1.37950.1.1.5.10.5.7.4
-- 1.3.6.1.4.1.37950.1.1.5.10.5.7.4
		-- 1.3.6.1.4.1.37950.1.1.5.10.5.7.4
		staticGroupAction OBJECT-TYPE
			SYNTAX INTEGER
				{
				add(1),
				delete(2)
				}
			MAX-ACCESS read-write
			STATUS current
			DESCRIPTION
				"Description."
			::= { igmpStaticGroupCfg 4 }

		
--          1.3.6.1.4.1.37950.1.1.5.10.5.8
-- 1.3.6.1.4.1.37950.1.1.5.10.5.8
-- 1.3.6.1.4.1.37950.1.1.5.10.5.8
-- 1.3.6.1.4.1.37950.1.1.5.10.5.8
-- 1.3.6.1.4.1.37950.1.1.5.10.5.8
-- 1.3.6.1.4.1.37950.1.1.5.10.5.8
-- 1.3.6.1.4.1.37950.1.1.5.10.5.8
-- 1.3.6.1.4.1.37950.1.1.5.10.5.8
-- 1.3.6.1.4.1.37950.1.1.5.10.5.8
		-- 1.3.6.1.4.1.37950.1.1.5.10.5.8
		igmpStaticGroupTable OBJECT-TYPE
			SYNTAX SEQUENCE OF IgmpStaticGroupEntry
			MAX-ACCESS not-accessible
			STATUS current
			DESCRIPTION
				"Description."
			::= { v1600dIgmpsnooping 8 }

		
--          1.3.6.1.4.1.37950.1.1.5.10.5.8.1
-- 1.3.6.1.4.1.37950.1.1.5.10.5.8.1
-- 1.3.6.1.4.1.37950.1.1.5.10.5.8.1
-- 1.3.6.1.4.1.37950.1.1.5.10.5.8.1
-- 1.3.6.1.4.1.37950.1.1.5.10.5.8.1
-- 1.3.6.1.4.1.37950.1.1.5.10.5.8.1
-- 1.3.6.1.4.1.37950.1.1.5.10.5.8.1
-- 1.3.6.1.4.1.37950.1.1.5.10.5.8.1
-- 1.3.6.1.4.1.37950.1.1.5.10.5.8.1
		-- 1.3.6.1.4.1.37950.1.1.5.10.5.8.1
		igmpStaticGroupEntry OBJECT-TYPE
			SYNTAX IgmpStaticGroupEntry
			MAX-ACCESS not-accessible
			STATUS current
			DESCRIPTION
				"Description."
			INDEX { igmpStaticItem }
			::= { igmpStaticGroupTable 1 }

		
		IgmpStaticGroupEntry ::=
			SEQUENCE { 
				igmpStaticItem
					Integer32,
				igmpStaticPort
					Integer32,
				igmpStaticGroupIp
					IpAddress,
				igmpStaticGroupVlan
					Integer32
			 }

--          1.3.6.1.4.1.37950.1.1.5.10.5.8.1.1
-- 1.3.6.1.4.1.37950.1.1.5.10.5.8.1.1
-- 1.3.6.1.4.1.37950.1.1.5.10.5.8.1.1
-- 1.3.6.1.4.1.37950.1.1.5.10.5.8.1.1
-- 1.3.6.1.4.1.37950.1.1.5.10.5.8.1.1
-- 1.3.6.1.4.1.37950.1.1.5.10.5.8.1.1
-- 1.3.6.1.4.1.37950.1.1.5.10.5.8.1.1
-- 1.3.6.1.4.1.37950.1.1.5.10.5.8.1.1
-- 1.3.6.1.4.1.37950.1.1.5.10.5.8.1.1
		-- 1.3.6.1.4.1.37950.1.1.5.10.5.8.1.1
		igmpStaticItem OBJECT-TYPE
			SYNTAX Integer32
			MAX-ACCESS read-only
			STATUS current
			DESCRIPTION
				"Description."
			::= { igmpStaticGroupEntry 1 }

		
--          1.3.6.1.4.1.37950.1.1.5.10.5.8.1.2
-- 1.3.6.1.4.1.37950.1.1.5.10.5.8.1.2
-- 1.3.6.1.4.1.37950.1.1.5.10.5.8.1.2
-- 1.3.6.1.4.1.37950.1.1.5.10.5.8.1.2
-- 1.3.6.1.4.1.37950.1.1.5.10.5.8.1.2
-- 1.3.6.1.4.1.37950.1.1.5.10.5.8.1.2
-- 1.3.6.1.4.1.37950.1.1.5.10.5.8.1.2
-- 1.3.6.1.4.1.37950.1.1.5.10.5.8.1.2
-- 1.3.6.1.4.1.37950.1.1.5.10.5.8.1.2
		-- 1.3.6.1.4.1.37950.1.1.5.10.5.8.1.2
		igmpStaticPort OBJECT-TYPE
			SYNTAX Integer32
			MAX-ACCESS read-only
			STATUS current
			DESCRIPTION
				"Description."
			::= { igmpStaticGroupEntry 2 }

		
--          1.3.6.1.4.1.37950.1.1.5.10.5.8.1.3
-- 1.3.6.1.4.1.37950.1.1.5.10.5.8.1.3
-- 1.3.6.1.4.1.37950.1.1.5.10.5.8.1.3
-- 1.3.6.1.4.1.37950.1.1.5.10.5.8.1.3
-- 1.3.6.1.4.1.37950.1.1.5.10.5.8.1.3
-- 1.3.6.1.4.1.37950.1.1.5.10.5.8.1.3
-- 1.3.6.1.4.1.37950.1.1.5.10.5.8.1.3
-- 1.3.6.1.4.1.37950.1.1.5.10.5.8.1.3
-- 1.3.6.1.4.1.37950.1.1.5.10.5.8.1.3
		-- 1.3.6.1.4.1.37950.1.1.5.10.5.8.1.3
		igmpStaticGroupIp OBJECT-TYPE
			SYNTAX IpAddress
			MAX-ACCESS read-only
			STATUS current
			DESCRIPTION
				"Description."
			::= { igmpStaticGroupEntry 3 }

		
--          1.3.6.1.4.1.37950.1.1.5.10.5.8.1.4
-- 1.3.6.1.4.1.37950.1.1.5.10.5.8.1.4
-- 1.3.6.1.4.1.37950.1.1.5.10.5.8.1.4
-- 1.3.6.1.4.1.37950.1.1.5.10.5.8.1.4
-- 1.3.6.1.4.1.37950.1.1.5.10.5.8.1.4
-- 1.3.6.1.4.1.37950.1.1.5.10.5.8.1.4
-- 1.3.6.1.4.1.37950.1.1.5.10.5.8.1.4
-- 1.3.6.1.4.1.37950.1.1.5.10.5.8.1.4
-- 1.3.6.1.4.1.37950.1.1.5.10.5.8.1.4
		-- 1.3.6.1.4.1.37950.1.1.5.10.5.8.1.4
		igmpStaticGroupVlan OBJECT-TYPE
			SYNTAX Integer32
			MAX-ACCESS read-write
			STATUS current
			DESCRIPTION
				"Description."
			::= { igmpStaticGroupEntry 4 }

		
--          1.3.6.1.4.1.37950.1.1.5.10.5.9
-- 1.3.6.1.4.1.37950.1.1.5.10.5.9
-- 1.3.6.1.4.1.37950.1.1.5.10.5.9
-- 1.3.6.1.4.1.37950.1.1.5.10.5.9
-- 1.3.6.1.4.1.37950.1.1.5.10.5.9
-- 1.3.6.1.4.1.37950.1.1.5.10.5.9
-- 1.3.6.1.4.1.37950.1.1.5.10.5.9
-- 1.3.6.1.4.1.37950.1.1.5.10.5.9
-- 1.3.6.1.4.1.37950.1.1.5.10.5.9
		-- 1.3.6.1.4.1.37950.1.1.5.10.5.9
		igmplastmemberCfg OBJECT IDENTIFIER ::= { v1600dIgmpsnooping 9 }

		
--          1.3.6.1.4.1.37950.1.1.5.10.5.9.1
-- 1.3.6.1.4.1.37950.1.1.5.10.5.9.1
-- 1.3.6.1.4.1.37950.1.1.5.10.5.9.1
-- 1.3.6.1.4.1.37950.1.1.5.10.5.9.1
-- 1.3.6.1.4.1.37950.1.1.5.10.5.9.1
-- 1.3.6.1.4.1.37950.1.1.5.10.5.9.1
-- 1.3.6.1.4.1.37950.1.1.5.10.5.9.1
-- 1.3.6.1.4.1.37950.1.1.5.10.5.9.1
-- 1.3.6.1.4.1.37950.1.1.5.10.5.9.1
		-- 1.3.6.1.4.1.37950.1.1.5.10.5.9.1
		querycount OBJECT-TYPE
			SYNTAX Integer32 (1..255)
			MAX-ACCESS read-write
			STATUS current
			DESCRIPTION
				"Description."
			::= { igmplastmemberCfg 1 }

		
--          1.3.6.1.4.1.37950.1.1.5.10.5.9.2
-- 1.3.6.1.4.1.37950.1.1.5.10.5.9.2
-- 1.3.6.1.4.1.37950.1.1.5.10.5.9.2
-- 1.3.6.1.4.1.37950.1.1.5.10.5.9.2
-- 1.3.6.1.4.1.37950.1.1.5.10.5.9.2
-- 1.3.6.1.4.1.37950.1.1.5.10.5.9.2
-- 1.3.6.1.4.1.37950.1.1.5.10.5.9.2
-- 1.3.6.1.4.1.37950.1.1.5.10.5.9.2
-- 1.3.6.1.4.1.37950.1.1.5.10.5.9.2
		-- 1.3.6.1.4.1.37950.1.1.5.10.5.9.2
		queryinterval OBJECT-TYPE
			SYNTAX Integer32 (1..255)
			MAX-ACCESS read-write
			STATUS current
			DESCRIPTION
				"Description."
			::= { igmplastmemberCfg 2 }

		
--          1.3.6.1.4.1.37950.1.1.5.10.5.9.3
-- 1.3.6.1.4.1.37950.1.1.5.10.5.9.3
-- 1.3.6.1.4.1.37950.1.1.5.10.5.9.3
-- 1.3.6.1.4.1.37950.1.1.5.10.5.9.3
-- 1.3.6.1.4.1.37950.1.1.5.10.5.9.3
-- 1.3.6.1.4.1.37950.1.1.5.10.5.9.3
-- 1.3.6.1.4.1.37950.1.1.5.10.5.9.3
-- 1.3.6.1.4.1.37950.1.1.5.10.5.9.3
-- 1.3.6.1.4.1.37950.1.1.5.10.5.9.3
		-- 1.3.6.1.4.1.37950.1.1.5.10.5.9.3
		queryresponse OBJECT-TYPE
			SYNTAX Integer32 (1..255)
			MAX-ACCESS read-write
			STATUS current
			DESCRIPTION
				"Description."
			::= { igmplastmemberCfg 3 }

		
--          1.3.6.1.4.1.37950.1.1.5.10.5.10
-- 1.3.6.1.4.1.37950.1.1.5.10.5.10
-- 1.3.6.1.4.1.37950.1.1.5.10.5.10
-- 1.3.6.1.4.1.37950.1.1.5.10.5.10
-- 1.3.6.1.4.1.37950.1.1.5.10.5.10
-- 1.3.6.1.4.1.37950.1.1.5.10.5.10
-- 1.3.6.1.4.1.37950.1.1.5.10.5.10
-- 1.3.6.1.4.1.37950.1.1.5.10.5.10
-- 1.3.6.1.4.1.37950.1.1.5.10.5.10
		-- 1.3.6.1.4.1.37950.1.1.5.10.5.10
		igmpGeneralCfg OBJECT IDENTIFIER ::= { v1600dIgmpsnooping 10 }

		
--          1.3.6.1.4.1.37950.1.1.5.10.5.10.1
-- 1.3.6.1.4.1.37950.1.1.5.10.5.10.1
-- 1.3.6.1.4.1.37950.1.1.5.10.5.10.1
-- 1.3.6.1.4.1.37950.1.1.5.10.5.10.1
-- 1.3.6.1.4.1.37950.1.1.5.10.5.10.1
-- 1.3.6.1.4.1.37950.1.1.5.10.5.10.1
-- 1.3.6.1.4.1.37950.1.1.5.10.5.10.1
-- 1.3.6.1.4.1.37950.1.1.5.10.5.10.1
-- 1.3.6.1.4.1.37950.1.1.5.10.5.10.1
		-- 1.3.6.1.4.1.37950.1.1.5.10.5.10.1
		queryPacket OBJECT-TYPE
			SYNTAX INTEGER
				{
				disable(0),
				enable(1)
				}
			MAX-ACCESS read-write
			STATUS current
			DESCRIPTION
				"Description."
			::= { igmpGeneralCfg 1 }

		
--          1.3.6.1.4.1.37950.1.1.5.10.5.10.2
-- 1.3.6.1.4.1.37950.1.1.5.10.5.10.2
-- 1.3.6.1.4.1.37950.1.1.5.10.5.10.2
-- 1.3.6.1.4.1.37950.1.1.5.10.5.10.2
-- 1.3.6.1.4.1.37950.1.1.5.10.5.10.2
-- 1.3.6.1.4.1.37950.1.1.5.10.5.10.2
-- 1.3.6.1.4.1.37950.1.1.5.10.5.10.2
-- 1.3.6.1.4.1.37950.1.1.5.10.5.10.2
-- 1.3.6.1.4.1.37950.1.1.5.10.5.10.2
		-- 1.3.6.1.4.1.37950.1.1.5.10.5.10.2
		queryTime OBJECT-TYPE
			SYNTAX Integer32 (10..255)
			MAX-ACCESS read-write
			STATUS current
			DESCRIPTION
				"Description."
			::= { igmpGeneralCfg 2 }

		
--          1.3.6.1.4.1.37950.1.1.5.10.5.11
-- 1.3.6.1.4.1.37950.1.1.5.10.5.11
-- 1.3.6.1.4.1.37950.1.1.5.10.5.11
-- 1.3.6.1.4.1.37950.1.1.5.10.5.11
-- 1.3.6.1.4.1.37950.1.1.5.10.5.11
-- 1.3.6.1.4.1.37950.1.1.5.10.5.11
-- 1.3.6.1.4.1.37950.1.1.5.10.5.11
-- 1.3.6.1.4.1.37950.1.1.5.10.5.11
-- 1.3.6.1.4.1.37950.1.1.5.10.5.11
		-- 1.3.6.1.4.1.37950.1.1.5.10.5.11
		igmpSourceIpCfg OBJECT IDENTIFIER ::= { v1600dIgmpsnooping 11 }

		
--          1.3.6.1.4.1.37950.1.1.5.10.5.11.1
-- 1.3.6.1.4.1.37950.1.1.5.10.5.11.1
-- 1.3.6.1.4.1.37950.1.1.5.10.5.11.1
-- 1.3.6.1.4.1.37950.1.1.5.10.5.11.1
-- 1.3.6.1.4.1.37950.1.1.5.10.5.11.1
-- 1.3.6.1.4.1.37950.1.1.5.10.5.11.1
-- 1.3.6.1.4.1.37950.1.1.5.10.5.11.1
-- 1.3.6.1.4.1.37950.1.1.5.10.5.11.1
-- 1.3.6.1.4.1.37950.1.1.5.10.5.11.1
		-- 1.3.6.1.4.1.37950.1.1.5.10.5.11.1
		sourceip OBJECT-TYPE
			SYNTAX OCTET STRING
			MAX-ACCESS read-write
			STATUS current
			DESCRIPTION
				"Description."
			::= { igmpSourceIpCfg 1 }

		
--          1.3.6.1.4.1.37950.1.1.5.10.5.12
-- 1.3.6.1.4.1.37950.1.1.5.10.5.12
-- 1.3.6.1.4.1.37950.1.1.5.10.5.12
-- 1.3.6.1.4.1.37950.1.1.5.10.5.12
-- 1.3.6.1.4.1.37950.1.1.5.10.5.12
-- 1.3.6.1.4.1.37950.1.1.5.10.5.12
-- 1.3.6.1.4.1.37950.1.1.5.10.5.12
-- 1.3.6.1.4.1.37950.1.1.5.10.5.12
-- 1.3.6.1.4.1.37950.1.1.5.10.5.12
		-- 1.3.6.1.4.1.37950.1.1.5.10.5.12
		igmpGroupMemberTable OBJECT-TYPE
			SYNTAX SEQUENCE OF IgmpGroupMemberEntry
			MAX-ACCESS not-accessible
			STATUS current
			DESCRIPTION
				"Description."
			::= { v1600dIgmpsnooping 12 }

		
--          1.3.6.1.4.1.37950.1.1.5.10.5.12.1
-- 1.3.6.1.4.1.37950.1.1.5.10.5.12.1
-- 1.3.6.1.4.1.37950.1.1.5.10.5.12.1
-- 1.3.6.1.4.1.37950.1.1.5.10.5.12.1
-- 1.3.6.1.4.1.37950.1.1.5.10.5.12.1
-- 1.3.6.1.4.1.37950.1.1.5.10.5.12.1
-- 1.3.6.1.4.1.37950.1.1.5.10.5.12.1
-- 1.3.6.1.4.1.37950.1.1.5.10.5.12.1
-- 1.3.6.1.4.1.37950.1.1.5.10.5.12.1
		-- 1.3.6.1.4.1.37950.1.1.5.10.5.12.1
		igmpGroupMemberEntry OBJECT-TYPE
			SYNTAX IgmpGroupMemberEntry
			MAX-ACCESS not-accessible
			STATUS current
			DESCRIPTION
				"Description."
			INDEX { igmpGroupMemberItem }
			::= { igmpGroupMemberTable 1 }

		
		IgmpGroupMemberEntry ::=
			SEQUENCE { 
				igmpGroupMemberItem
					Integer32,
				igmpGroupMemberGVlan
					INTEGER,
				igmpGroupMemberIp
					IpAddress,
				igmpGroupMemberPort
					OCTET STRING,
				igmpGroupMembeType
					INTEGER,
				igmpGroupMemberUserVlan
					INTEGER
			 }

--          1.3.6.1.4.1.37950.1.1.5.10.5.12.1.1
-- 1.3.6.1.4.1.37950.1.1.5.10.5.12.1.1
-- 1.3.6.1.4.1.37950.1.1.5.10.5.12.1.1
-- 1.3.6.1.4.1.37950.1.1.5.10.5.12.1.1
-- 1.3.6.1.4.1.37950.1.1.5.10.5.12.1.1
-- 1.3.6.1.4.1.37950.1.1.5.10.5.12.1.1
-- 1.3.6.1.4.1.37950.1.1.5.10.5.12.1.1
-- 1.3.6.1.4.1.37950.1.1.5.10.5.12.1.1
-- 1.3.6.1.4.1.37950.1.1.5.10.5.12.1.1
		-- 1.3.6.1.4.1.37950.1.1.5.10.5.12.1.1
		igmpGroupMemberItem OBJECT-TYPE
			SYNTAX Integer32
			MAX-ACCESS read-write
			STATUS current
			DESCRIPTION
				"Description."
			::= { igmpGroupMemberEntry 1 }

		
--          1.3.6.1.4.1.37950.1.1.5.10.5.12.1.2
-- 1.3.6.1.4.1.37950.1.1.5.10.5.12.1.2
-- 1.3.6.1.4.1.37950.1.1.5.10.5.12.1.2
-- 1.3.6.1.4.1.37950.1.1.5.10.5.12.1.2
-- 1.3.6.1.4.1.37950.1.1.5.10.5.12.1.2
-- 1.3.6.1.4.1.37950.1.1.5.10.5.12.1.2
-- 1.3.6.1.4.1.37950.1.1.5.10.5.12.1.2
-- 1.3.6.1.4.1.37950.1.1.5.10.5.12.1.2
-- 1.3.6.1.4.1.37950.1.1.5.10.5.12.1.2
		-- 1.3.6.1.4.1.37950.1.1.5.10.5.12.1.2
		igmpGroupMemberGVlan OBJECT-TYPE
			SYNTAX INTEGER (1..4094)
			MAX-ACCESS read-write
			STATUS current
			DESCRIPTION
				"Description."
			::= { igmpGroupMemberEntry 2 }

		
--          1.3.6.1.4.1.37950.1.1.5.10.5.12.1.3
-- 1.3.6.1.4.1.37950.1.1.5.10.5.12.1.3
-- 1.3.6.1.4.1.37950.1.1.5.10.5.12.1.3
-- 1.3.6.1.4.1.37950.1.1.5.10.5.12.1.3
-- 1.3.6.1.4.1.37950.1.1.5.10.5.12.1.3
-- 1.3.6.1.4.1.37950.1.1.5.10.5.12.1.3
-- 1.3.6.1.4.1.37950.1.1.5.10.5.12.1.3
-- 1.3.6.1.4.1.37950.1.1.5.10.5.12.1.3
-- 1.3.6.1.4.1.37950.1.1.5.10.5.12.1.3
		-- 1.3.6.1.4.1.37950.1.1.5.10.5.12.1.3
		igmpGroupMemberIp OBJECT-TYPE
			SYNTAX IpAddress
			MAX-ACCESS read-write
			STATUS current
			DESCRIPTION
				"Description."
			::= { igmpGroupMemberEntry 3 }

		
--          1.3.6.1.4.1.37950.1.1.5.10.5.12.1.4
-- 1.3.6.1.4.1.37950.1.1.5.10.5.12.1.4
-- 1.3.6.1.4.1.37950.1.1.5.10.5.12.1.4
-- 1.3.6.1.4.1.37950.1.1.5.10.5.12.1.4
-- 1.3.6.1.4.1.37950.1.1.5.10.5.12.1.4
-- 1.3.6.1.4.1.37950.1.1.5.10.5.12.1.4
-- 1.3.6.1.4.1.37950.1.1.5.10.5.12.1.4
-- 1.3.6.1.4.1.37950.1.1.5.10.5.12.1.4
-- 1.3.6.1.4.1.37950.1.1.5.10.5.12.1.4
		-- 1.3.6.1.4.1.37950.1.1.5.10.5.12.1.4
		igmpGroupMemberPort OBJECT-TYPE
			SYNTAX OCTET STRING
			MAX-ACCESS read-write
			STATUS current
			DESCRIPTION
				"Description."
			::= { igmpGroupMemberEntry 4 }

		
--          1.3.6.1.4.1.37950.1.1.5.10.5.12.1.5
-- 1.3.6.1.4.1.37950.1.1.5.10.5.12.1.5
-- 1.3.6.1.4.1.37950.1.1.5.10.5.12.1.5
-- 1.3.6.1.4.1.37950.1.1.5.10.5.12.1.5
-- 1.3.6.1.4.1.37950.1.1.5.10.5.12.1.5
-- 1.3.6.1.4.1.37950.1.1.5.10.5.12.1.5
-- 1.3.6.1.4.1.37950.1.1.5.10.5.12.1.5
-- 1.3.6.1.4.1.37950.1.1.5.10.5.12.1.5
-- 1.3.6.1.4.1.37950.1.1.5.10.5.12.1.5
		-- 1.3.6.1.4.1.37950.1.1.5.10.5.12.1.5
		igmpGroupMembeType OBJECT-TYPE
			SYNTAX INTEGER
				{
				static(1),
				router(2),
				dynamic(3)
				}
			MAX-ACCESS read-write
			STATUS current
			DESCRIPTION
				"Description."
			::= { igmpGroupMemberEntry 5 }

		
--          1.3.6.1.4.1.37950.1.1.5.10.5.12.1.6
-- 1.3.6.1.4.1.37950.1.1.5.10.5.12.1.6
-- 1.3.6.1.4.1.37950.1.1.5.10.5.12.1.6
-- 1.3.6.1.4.1.37950.1.1.5.10.5.12.1.6
-- 1.3.6.1.4.1.37950.1.1.5.10.5.12.1.6
-- 1.3.6.1.4.1.37950.1.1.5.10.5.12.1.6
-- 1.3.6.1.4.1.37950.1.1.5.10.5.12.1.6
-- 1.3.6.1.4.1.37950.1.1.5.10.5.12.1.6
-- 1.3.6.1.4.1.37950.1.1.5.10.5.12.1.6
		-- 1.3.6.1.4.1.37950.1.1.5.10.5.12.1.6
		igmpGroupMemberUserVlan OBJECT-TYPE
			SYNTAX INTEGER (1..4094)
			MAX-ACCESS read-write
			STATUS current
			DESCRIPTION
				"Description."
			::= { igmpGroupMemberEntry 6 }

		
--       1.3.6.1.4.1.37950.1.1.5.10.5.13
-- 1.3.6.1.4.1.37950.1.1.5.10.5.13
-- 1.3.6.1.4.1.37950.1.1.5.10.5.13
-- 1.3.6.1.4.1.37950.1.1.5.10.5.13
-- 1.3.6.1.4.1.37950.1.1.5.10.5.13
-- 1.3.6.1.4.1.37950.1.1.5.10.5.13
		-- 1.3.6.1.4.1.37950.1.1.5.10.5.13
		igmpGlobalTimeCfg OBJECT IDENTIFIER ::= { v1600dIgmpsnooping 13 }

		
--       1.3.6.1.4.1.37950.1.1.5.10.5.13.1
-- 1.3.6.1.4.1.37950.1.1.5.10.5.13.1
-- 1.3.6.1.4.1.37950.1.1.5.10.5.13.1
-- 1.3.6.1.4.1.37950.1.1.5.10.5.13.1
-- 1.3.6.1.4.1.37950.1.1.5.10.5.13.1
-- 1.3.6.1.4.1.37950.1.1.5.10.5.13.1
		-- 1.3.6.1.4.1.37950.1.1.5.10.5.13.1
		memberPortTimeout OBJECT-TYPE
			SYNTAX Integer32 (10..3600)
			MAX-ACCESS read-write
			STATUS current
			DESCRIPTION
				"Description."
			::= { igmpGlobalTimeCfg 1 }

		
--       1.3.6.1.4.1.37950.1.1.5.10.5.13.2
-- 1.3.6.1.4.1.37950.1.1.5.10.5.13.2
-- 1.3.6.1.4.1.37950.1.1.5.10.5.13.2
-- 1.3.6.1.4.1.37950.1.1.5.10.5.13.2
-- 1.3.6.1.4.1.37950.1.1.5.10.5.13.2
-- 1.3.6.1.4.1.37950.1.1.5.10.5.13.2
		-- 1.3.6.1.4.1.37950.1.1.5.10.5.13.2
		queryResponseTime OBJECT-TYPE
			SYNTAX Integer32 (10..3600)
			MAX-ACCESS read-write
			STATUS current
			DESCRIPTION
				"Description."
			::= { igmpGlobalTimeCfg 2 }

		
--       1.3.6.1.4.1.37950.1.1.5.10.5.14
-- 1.3.6.1.4.1.37950.1.1.5.10.5.14
-- 1.3.6.1.4.1.37950.1.1.5.10.5.14
-- 1.3.6.1.4.1.37950.1.1.5.10.5.14
-- 1.3.6.1.4.1.37950.1.1.5.10.5.14
-- 1.3.6.1.4.1.37950.1.1.5.10.5.14
		-- 1.3.6.1.4.1.37950.1.1.5.10.5.14
		defaultVlanConfig OBJECT IDENTIFIER ::= { v1600dIgmpsnooping 14 }

		
--       1.3.6.1.4.1.37950.1.1.5.10.5.14.1
-- 1.3.6.1.4.1.37950.1.1.5.10.5.14.1
-- 1.3.6.1.4.1.37950.1.1.5.10.5.14.1
-- 1.3.6.1.4.1.37950.1.1.5.10.5.14.1
-- 1.3.6.1.4.1.37950.1.1.5.10.5.14.1
-- 1.3.6.1.4.1.37950.1.1.5.10.5.14.1
		-- 1.3.6.1.4.1.37950.1.1.5.10.5.14.1
		defaultVlanId OBJECT-TYPE
			SYNTAX Integer32 (1..4094)
			MAX-ACCESS read-write
			STATUS current
			DESCRIPTION
				"Description."
			::= { defaultVlanConfig 1 }

		
--       1.3.6.1.4.1.37950.1.1.5.10.5.14.2
-- 1.3.6.1.4.1.37950.1.1.5.10.5.14.2
-- 1.3.6.1.4.1.37950.1.1.5.10.5.14.2
-- 1.3.6.1.4.1.37950.1.1.5.10.5.14.2
-- 1.3.6.1.4.1.37950.1.1.5.10.5.14.2
-- 1.3.6.1.4.1.37950.1.1.5.10.5.14.2
		-- 1.3.6.1.4.1.37950.1.1.5.10.5.14.2
		defaultVlanAction OBJECT-TYPE
			SYNTAX INTEGER
				{
				add(1),
				delete(2)
				}
			MAX-ACCESS read-write
			STATUS current
			DESCRIPTION
				"Description."
			::= { defaultVlanConfig 2 }

		
--          1.3.6.1.4.1.37950.1.1.5.10.6
-- 1.3.6.1.4.1.37950.1.1.5.10.6
-- 1.3.6.1.4.1.37950.1.1.5.10.6
-- 1.3.6.1.4.1.37950.1.1.5.10.6
-- 1.3.6.1.4.1.37950.1.1.5.10.6
-- 1.3.6.1.4.1.37950.1.1.5.10.6
-- 1.3.6.1.4.1.37950.1.1.5.10.6
-- 1.3.6.1.4.1.37950.1.1.5.10.6
-- 1.3.6.1.4.1.37950.1.1.5.10.6
		-- 1.3.6.1.4.1.37950.1.1.5.10.6
		v1600dARPProxy OBJECT IDENTIFIER ::= { v1600dSwitch 6 }

		
--          1.3.6.1.4.1.37950.1.1.5.10.6.1
-- 1.3.6.1.4.1.37950.1.1.5.10.6.1
-- 1.3.6.1.4.1.37950.1.1.5.10.6.1
-- 1.3.6.1.4.1.37950.1.1.5.10.6.1
-- 1.3.6.1.4.1.37950.1.1.5.10.6.1
-- 1.3.6.1.4.1.37950.1.1.5.10.6.1
-- 1.3.6.1.4.1.37950.1.1.5.10.6.1
-- 1.3.6.1.4.1.37950.1.1.5.10.6.1
-- 1.3.6.1.4.1.37950.1.1.5.10.6.1
		-- 1.3.6.1.4.1.37950.1.1.5.10.6.1
		arpProxyCfg OBJECT IDENTIFIER ::= { v1600dARPProxy 1 }

		
--          1.3.6.1.4.1.37950.1.1.5.10.6.1.1
-- 1.3.6.1.4.1.37950.1.1.5.10.6.1.1
-- 1.3.6.1.4.1.37950.1.1.5.10.6.1.1
-- 1.3.6.1.4.1.37950.1.1.5.10.6.1.1
-- 1.3.6.1.4.1.37950.1.1.5.10.6.1.1
-- 1.3.6.1.4.1.37950.1.1.5.10.6.1.1
-- 1.3.6.1.4.1.37950.1.1.5.10.6.1.1
-- 1.3.6.1.4.1.37950.1.1.5.10.6.1.1
-- 1.3.6.1.4.1.37950.1.1.5.10.6.1.1
		-- 1.3.6.1.4.1.37950.1.1.5.10.6.1.1
		arpProxyVlan OBJECT-TYPE
			SYNTAX Integer32 (1..4095)
			MAX-ACCESS read-write
			STATUS current
			DESCRIPTION
				"Description."
			::= { arpProxyCfg 1 }

		
--          1.3.6.1.4.1.37950.1.1.5.10.6.1.2
-- 1.3.6.1.4.1.37950.1.1.5.10.6.1.2
-- 1.3.6.1.4.1.37950.1.1.5.10.6.1.2
-- 1.3.6.1.4.1.37950.1.1.5.10.6.1.2
-- 1.3.6.1.4.1.37950.1.1.5.10.6.1.2
-- 1.3.6.1.4.1.37950.1.1.5.10.6.1.2
-- 1.3.6.1.4.1.37950.1.1.5.10.6.1.2
-- 1.3.6.1.4.1.37950.1.1.5.10.6.1.2
-- 1.3.6.1.4.1.37950.1.1.5.10.6.1.2
		-- 1.3.6.1.4.1.37950.1.1.5.10.6.1.2
		arpProxyConfig OBJECT-TYPE
			SYNTAX INTEGER
				{
				enable(1),
				disable(2)
				}
			MAX-ACCESS read-write
			STATUS current
			DESCRIPTION
				"Description."
			::= { arpProxyCfg 2 }

		
--          1.3.6.1.4.1.37950.1.1.5.10.6.2
-- 1.3.6.1.4.1.37950.1.1.5.10.6.2
-- 1.3.6.1.4.1.37950.1.1.5.10.6.2
-- 1.3.6.1.4.1.37950.1.1.5.10.6.2
-- 1.3.6.1.4.1.37950.1.1.5.10.6.2
-- 1.3.6.1.4.1.37950.1.1.5.10.6.2
-- 1.3.6.1.4.1.37950.1.1.5.10.6.2
-- 1.3.6.1.4.1.37950.1.1.5.10.6.2
-- 1.3.6.1.4.1.37950.1.1.5.10.6.2
		-- 1.3.6.1.4.1.37950.1.1.5.10.6.2
		arpProxyTable OBJECT-TYPE
			SYNTAX SEQUENCE OF ArpProxyEntry
			MAX-ACCESS not-accessible
			STATUS current
			DESCRIPTION
				"Description."
			::= { v1600dARPProxy 2 }

		
--          1.3.6.1.4.1.37950.1.1.5.10.6.2.1
-- 1.3.6.1.4.1.37950.1.1.5.10.6.2.1
-- 1.3.6.1.4.1.37950.1.1.5.10.6.2.1
-- 1.3.6.1.4.1.37950.1.1.5.10.6.2.1
-- 1.3.6.1.4.1.37950.1.1.5.10.6.2.1
-- 1.3.6.1.4.1.37950.1.1.5.10.6.2.1
-- 1.3.6.1.4.1.37950.1.1.5.10.6.2.1
-- 1.3.6.1.4.1.37950.1.1.5.10.6.2.1
-- 1.3.6.1.4.1.37950.1.1.5.10.6.2.1
		-- 1.3.6.1.4.1.37950.1.1.5.10.6.2.1
		arpProxyEntry OBJECT-TYPE
			SYNTAX ArpProxyEntry
			MAX-ACCESS not-accessible
			STATUS current
			DESCRIPTION
				"Description."
			INDEX { arpProxyVlanId }
			::= { arpProxyTable 1 }

		
		ArpProxyEntry ::=
			SEQUENCE { 
				arpProxyVlanId
					Integer32,
				arpProxyState
					INTEGER
			 }

--          1.3.6.1.4.1.37950.1.1.5.10.6.2.1.1
-- 1.3.6.1.4.1.37950.1.1.5.10.6.2.1.1
-- 1.3.6.1.4.1.37950.1.1.5.10.6.2.1.1
-- 1.3.6.1.4.1.37950.1.1.5.10.6.2.1.1
-- 1.3.6.1.4.1.37950.1.1.5.10.6.2.1.1
-- 1.3.6.1.4.1.37950.1.1.5.10.6.2.1.1
-- 1.3.6.1.4.1.37950.1.1.5.10.6.2.1.1
-- 1.3.6.1.4.1.37950.1.1.5.10.6.2.1.1
-- 1.3.6.1.4.1.37950.1.1.5.10.6.2.1.1
		-- 1.3.6.1.4.1.37950.1.1.5.10.6.2.1.1
		arpProxyVlanId OBJECT-TYPE
			SYNTAX Integer32
			MAX-ACCESS read-only
			STATUS current
			DESCRIPTION
				"Description."
			::= { arpProxyEntry 1 }

		
--          1.3.6.1.4.1.37950.1.1.5.10.6.2.1.2
-- 1.3.6.1.4.1.37950.1.1.5.10.6.2.1.2
-- 1.3.6.1.4.1.37950.1.1.5.10.6.2.1.2
-- 1.3.6.1.4.1.37950.1.1.5.10.6.2.1.2
-- 1.3.6.1.4.1.37950.1.1.5.10.6.2.1.2
-- 1.3.6.1.4.1.37950.1.1.5.10.6.2.1.2
-- 1.3.6.1.4.1.37950.1.1.5.10.6.2.1.2
-- 1.3.6.1.4.1.37950.1.1.5.10.6.2.1.2
-- 1.3.6.1.4.1.37950.1.1.5.10.6.2.1.2
		-- 1.3.6.1.4.1.37950.1.1.5.10.6.2.1.2
		arpProxyState OBJECT-TYPE
			SYNTAX INTEGER
				{
				enable(1),
				disable(2)
				}
			MAX-ACCESS read-only
			STATUS current
			DESCRIPTION
				"Description."
			::= { arpProxyEntry 2 }

		
--          1.3.6.1.4.1.37950.1.1.5.10.7
-- 1.3.6.1.4.1.37950.1.1.5.10.7
-- 1.3.6.1.4.1.37950.1.1.5.10.7
-- 1.3.6.1.4.1.37950.1.1.5.10.7
-- 1.3.6.1.4.1.37950.1.1.5.10.7
-- 1.3.6.1.4.1.37950.1.1.5.10.7
-- 1.3.6.1.4.1.37950.1.1.5.10.7
-- 1.3.6.1.4.1.37950.1.1.5.10.7
-- 1.3.6.1.4.1.37950.1.1.5.10.7
		-- 1.3.6.1.4.1.37950.1.1.5.10.7
		v1600dDHCP OBJECT IDENTIFIER ::= { v1600dSwitch 7 }

		
--          1.3.6.1.4.1.37950.1.1.5.10.7.1
-- 1.3.6.1.4.1.37950.1.1.5.10.7.1
-- 1.3.6.1.4.1.37950.1.1.5.10.7.1
-- 1.3.6.1.4.1.37950.1.1.5.10.7.1
-- 1.3.6.1.4.1.37950.1.1.5.10.7.1
-- 1.3.6.1.4.1.37950.1.1.5.10.7.1
-- 1.3.6.1.4.1.37950.1.1.5.10.7.1
-- 1.3.6.1.4.1.37950.1.1.5.10.7.1
-- 1.3.6.1.4.1.37950.1.1.5.10.7.1
		-- 1.3.6.1.4.1.37950.1.1.5.10.7.1
		dhcpServer OBJECT IDENTIFIER ::= { v1600dDHCP 1 }

		
--          1.3.6.1.4.1.37950.1.1.5.10.7.1.1
-- 1.3.6.1.4.1.37950.1.1.5.10.7.1.1
-- 1.3.6.1.4.1.37950.1.1.5.10.7.1.1
-- 1.3.6.1.4.1.37950.1.1.5.10.7.1.1
-- 1.3.6.1.4.1.37950.1.1.5.10.7.1.1
-- 1.3.6.1.4.1.37950.1.1.5.10.7.1.1
-- 1.3.6.1.4.1.37950.1.1.5.10.7.1.1
-- 1.3.6.1.4.1.37950.1.1.5.10.7.1.1
-- 1.3.6.1.4.1.37950.1.1.5.10.7.1.1
		-- 1.3.6.1.4.1.37950.1.1.5.10.7.1.1
		dhcpCurrentState OBJECT-TYPE
			SYNTAX INTEGER
				{
				enable(1),
				disable(2)
				}
			MAX-ACCESS read-only
			STATUS current
			DESCRIPTION
				"Description."
			::= { dhcpServer 1 }

		
--          1.3.6.1.4.1.37950.1.1.5.10.7.1.2
-- 1.3.6.1.4.1.37950.1.1.5.10.7.1.2
-- 1.3.6.1.4.1.37950.1.1.5.10.7.1.2
-- 1.3.6.1.4.1.37950.1.1.5.10.7.1.2
-- 1.3.6.1.4.1.37950.1.1.5.10.7.1.2
-- 1.3.6.1.4.1.37950.1.1.5.10.7.1.2
-- 1.3.6.1.4.1.37950.1.1.5.10.7.1.2
-- 1.3.6.1.4.1.37950.1.1.5.10.7.1.2
-- 1.3.6.1.4.1.37950.1.1.5.10.7.1.2
		-- 1.3.6.1.4.1.37950.1.1.5.10.7.1.2
		dhcpStartIP OBJECT-TYPE
			SYNTAX IpAddress
			MAX-ACCESS read-write
			STATUS current
			DESCRIPTION
				"Description."
			::= { dhcpServer 2 }

		
--          1.3.6.1.4.1.37950.1.1.5.10.7.1.3
-- 1.3.6.1.4.1.37950.1.1.5.10.7.1.3
-- 1.3.6.1.4.1.37950.1.1.5.10.7.1.3
-- 1.3.6.1.4.1.37950.1.1.5.10.7.1.3
-- 1.3.6.1.4.1.37950.1.1.5.10.7.1.3
-- 1.3.6.1.4.1.37950.1.1.5.10.7.1.3
-- 1.3.6.1.4.1.37950.1.1.5.10.7.1.3
-- 1.3.6.1.4.1.37950.1.1.5.10.7.1.3
-- 1.3.6.1.4.1.37950.1.1.5.10.7.1.3
		-- 1.3.6.1.4.1.37950.1.1.5.10.7.1.3
		dhcpEndIP OBJECT-TYPE
			SYNTAX IpAddress
			MAX-ACCESS read-write
			STATUS current
			DESCRIPTION
				"Description."
			::= { dhcpServer 3 }

		
--          1.3.6.1.4.1.37950.1.1.5.10.7.1.4
-- 1.3.6.1.4.1.37950.1.1.5.10.7.1.4
-- 1.3.6.1.4.1.37950.1.1.5.10.7.1.4
-- 1.3.6.1.4.1.37950.1.1.5.10.7.1.4
-- 1.3.6.1.4.1.37950.1.1.5.10.7.1.4
-- 1.3.6.1.4.1.37950.1.1.5.10.7.1.4
-- 1.3.6.1.4.1.37950.1.1.5.10.7.1.4
-- 1.3.6.1.4.1.37950.1.1.5.10.7.1.4
-- 1.3.6.1.4.1.37950.1.1.5.10.7.1.4
		-- 1.3.6.1.4.1.37950.1.1.5.10.7.1.4
		dhcpSubNetMask OBJECT-TYPE
			SYNTAX IpAddress
			MAX-ACCESS read-write
			STATUS current
			DESCRIPTION
				"Description."
			::= { dhcpServer 4 }

		
--          1.3.6.1.4.1.37950.1.1.5.10.7.1.5
-- 1.3.6.1.4.1.37950.1.1.5.10.7.1.5
-- 1.3.6.1.4.1.37950.1.1.5.10.7.1.5
-- 1.3.6.1.4.1.37950.1.1.5.10.7.1.5
-- 1.3.6.1.4.1.37950.1.1.5.10.7.1.5
-- 1.3.6.1.4.1.37950.1.1.5.10.7.1.5
-- 1.3.6.1.4.1.37950.1.1.5.10.7.1.5
-- 1.3.6.1.4.1.37950.1.1.5.10.7.1.5
-- 1.3.6.1.4.1.37950.1.1.5.10.7.1.5
		-- 1.3.6.1.4.1.37950.1.1.5.10.7.1.5
		dhcpGateWay OBJECT-TYPE
			SYNTAX IpAddress
			MAX-ACCESS read-write
			STATUS current
			DESCRIPTION
				"Description."
			::= { dhcpServer 5 }

		
--          1.3.6.1.4.1.37950.1.1.5.10.7.1.6
-- 1.3.6.1.4.1.37950.1.1.5.10.7.1.6
-- 1.3.6.1.4.1.37950.1.1.5.10.7.1.6
-- 1.3.6.1.4.1.37950.1.1.5.10.7.1.6
-- 1.3.6.1.4.1.37950.1.1.5.10.7.1.6
-- 1.3.6.1.4.1.37950.1.1.5.10.7.1.6
-- 1.3.6.1.4.1.37950.1.1.5.10.7.1.6
-- 1.3.6.1.4.1.37950.1.1.5.10.7.1.6
-- 1.3.6.1.4.1.37950.1.1.5.10.7.1.6
		-- 1.3.6.1.4.1.37950.1.1.5.10.7.1.6
		dhcpDNS1 OBJECT-TYPE
			SYNTAX IpAddress
			MAX-ACCESS read-write
			STATUS current
			DESCRIPTION
				"Description."
			::= { dhcpServer 6 }

		
--          1.3.6.1.4.1.37950.1.1.5.10.7.1.7
-- 1.3.6.1.4.1.37950.1.1.5.10.7.1.7
-- 1.3.6.1.4.1.37950.1.1.5.10.7.1.7
-- 1.3.6.1.4.1.37950.1.1.5.10.7.1.7
-- 1.3.6.1.4.1.37950.1.1.5.10.7.1.7
-- 1.3.6.1.4.1.37950.1.1.5.10.7.1.7
-- 1.3.6.1.4.1.37950.1.1.5.10.7.1.7
-- 1.3.6.1.4.1.37950.1.1.5.10.7.1.7
-- 1.3.6.1.4.1.37950.1.1.5.10.7.1.7
		-- 1.3.6.1.4.1.37950.1.1.5.10.7.1.7
		dhcpDNS2 OBJECT-TYPE
			SYNTAX IpAddress
			MAX-ACCESS read-write
			STATUS current
			DESCRIPTION
				"Description."
			::= { dhcpServer 7 }

		
--          1.3.6.1.4.1.37950.1.1.5.10.7.1.8
-- 1.3.6.1.4.1.37950.1.1.5.10.7.1.8
-- 1.3.6.1.4.1.37950.1.1.5.10.7.1.8
-- 1.3.6.1.4.1.37950.1.1.5.10.7.1.8
-- 1.3.6.1.4.1.37950.1.1.5.10.7.1.8
-- 1.3.6.1.4.1.37950.1.1.5.10.7.1.8
-- 1.3.6.1.4.1.37950.1.1.5.10.7.1.8
-- 1.3.6.1.4.1.37950.1.1.5.10.7.1.8
-- 1.3.6.1.4.1.37950.1.1.5.10.7.1.8
		-- 1.3.6.1.4.1.37950.1.1.5.10.7.1.8
		dhcpDNS3 OBJECT-TYPE
			SYNTAX IpAddress
			MAX-ACCESS read-write
			STATUS current
			DESCRIPTION
				"Description."
			::= { dhcpServer 8 }

		
--          1.3.6.1.4.1.37950.1.1.5.10.7.1.9
-- 1.3.6.1.4.1.37950.1.1.5.10.7.1.9
-- 1.3.6.1.4.1.37950.1.1.5.10.7.1.9
-- 1.3.6.1.4.1.37950.1.1.5.10.7.1.9
-- 1.3.6.1.4.1.37950.1.1.5.10.7.1.9
-- 1.3.6.1.4.1.37950.1.1.5.10.7.1.9
-- 1.3.6.1.4.1.37950.1.1.5.10.7.1.9
-- 1.3.6.1.4.1.37950.1.1.5.10.7.1.9
-- 1.3.6.1.4.1.37950.1.1.5.10.7.1.9
		-- 1.3.6.1.4.1.37950.1.1.5.10.7.1.9
		dhcpWins OBJECT-TYPE
			SYNTAX IpAddress
			MAX-ACCESS read-write
			STATUS current
			DESCRIPTION
				"Description."
			::= { dhcpServer 9 }

		
--          1.3.6.1.4.1.37950.1.1.5.10.7.1.10
-- 1.3.6.1.4.1.37950.1.1.5.10.7.1.10
-- 1.3.6.1.4.1.37950.1.1.5.10.7.1.10
-- 1.3.6.1.4.1.37950.1.1.5.10.7.1.10
-- 1.3.6.1.4.1.37950.1.1.5.10.7.1.10
-- 1.3.6.1.4.1.37950.1.1.5.10.7.1.10
-- 1.3.6.1.4.1.37950.1.1.5.10.7.1.10
-- 1.3.6.1.4.1.37950.1.1.5.10.7.1.10
-- 1.3.6.1.4.1.37950.1.1.5.10.7.1.10
		-- 1.3.6.1.4.1.37950.1.1.5.10.7.1.10
		dhcpLeaseTime OBJECT-TYPE
			SYNTAX Integer32 (60..864000)
			MAX-ACCESS read-write
			STATUS current
			DESCRIPTION
				"Description."
			::= { dhcpServer 10 }

		
--          1.3.6.1.4.1.37950.1.1.5.10.7.1.11
-- 1.3.6.1.4.1.37950.1.1.5.10.7.1.11
-- 1.3.6.1.4.1.37950.1.1.5.10.7.1.11
-- 1.3.6.1.4.1.37950.1.1.5.10.7.1.11
-- 1.3.6.1.4.1.37950.1.1.5.10.7.1.11
-- 1.3.6.1.4.1.37950.1.1.5.10.7.1.11
-- 1.3.6.1.4.1.37950.1.1.5.10.7.1.11
-- 1.3.6.1.4.1.37950.1.1.5.10.7.1.11
-- 1.3.6.1.4.1.37950.1.1.5.10.7.1.11
		-- 1.3.6.1.4.1.37950.1.1.5.10.7.1.11
		dhcpInterfaceVlan OBJECT-TYPE
			SYNTAX Integer32 (1..4095)
			MAX-ACCESS read-write
			STATUS current
			DESCRIPTION
				"Description."
			::= { dhcpServer 11 }

		
--          1.3.6.1.4.1.37950.1.1.5.10.7.1.12
-- 1.3.6.1.4.1.37950.1.1.5.10.7.1.12
-- 1.3.6.1.4.1.37950.1.1.5.10.7.1.12
-- 1.3.6.1.4.1.37950.1.1.5.10.7.1.12
-- 1.3.6.1.4.1.37950.1.1.5.10.7.1.12
-- 1.3.6.1.4.1.37950.1.1.5.10.7.1.12
-- 1.3.6.1.4.1.37950.1.1.5.10.7.1.12
-- 1.3.6.1.4.1.37950.1.1.5.10.7.1.12
-- 1.3.6.1.4.1.37950.1.1.5.10.7.1.12
		-- 1.3.6.1.4.1.37950.1.1.5.10.7.1.12
		dhcpControl OBJECT-TYPE
			SYNTAX INTEGER
				{
				enable(1),
				disable(2)
				}
			MAX-ACCESS read-write
			STATUS current
			DESCRIPTION
				"Description."
			::= { dhcpServer 12 }

		
--          1.3.6.1.4.1.37950.1.1.5.10.7.1.13
-- 1.3.6.1.4.1.37950.1.1.5.10.7.1.13
-- 1.3.6.1.4.1.37950.1.1.5.10.7.1.13
-- 1.3.6.1.4.1.37950.1.1.5.10.7.1.13
-- 1.3.6.1.4.1.37950.1.1.5.10.7.1.13
-- 1.3.6.1.4.1.37950.1.1.5.10.7.1.13
-- 1.3.6.1.4.1.37950.1.1.5.10.7.1.13
-- 1.3.6.1.4.1.37950.1.1.5.10.7.1.13
-- 1.3.6.1.4.1.37950.1.1.5.10.7.1.13
		-- 1.3.6.1.4.1.37950.1.1.5.10.7.1.13
		dhcpCommit OBJECT-TYPE
			SYNTAX INTEGER { commit(1) }
			MAX-ACCESS read-write
			STATUS current
			DESCRIPTION
				"Description."
			::= { dhcpServer 13 }

		
--          1.3.6.1.4.1.37950.1.1.5.10.7.1.14
-- 1.3.6.1.4.1.37950.1.1.5.10.7.1.14
-- 1.3.6.1.4.1.37950.1.1.5.10.7.1.14
-- 1.3.6.1.4.1.37950.1.1.5.10.7.1.14
-- 1.3.6.1.4.1.37950.1.1.5.10.7.1.14
-- 1.3.6.1.4.1.37950.1.1.5.10.7.1.14
-- 1.3.6.1.4.1.37950.1.1.5.10.7.1.14
-- 1.3.6.1.4.1.37950.1.1.5.10.7.1.14
-- 1.3.6.1.4.1.37950.1.1.5.10.7.1.14
		-- 1.3.6.1.4.1.37950.1.1.5.10.7.1.14
		dhcpLeaseTable OBJECT-TYPE
			SYNTAX SEQUENCE OF DhcpLeaseEntry
			MAX-ACCESS not-accessible
			STATUS current
			DESCRIPTION
				"Description."
			::= { dhcpServer 14 }

		
--          1.3.6.1.4.1.37950.1.1.5.10.7.1.14.1
-- 1.3.6.1.4.1.37950.1.1.5.10.7.1.14.1
-- 1.3.6.1.4.1.37950.1.1.5.10.7.1.14.1
-- 1.3.6.1.4.1.37950.1.1.5.10.7.1.14.1
-- 1.3.6.1.4.1.37950.1.1.5.10.7.1.14.1
-- 1.3.6.1.4.1.37950.1.1.5.10.7.1.14.1
-- 1.3.6.1.4.1.37950.1.1.5.10.7.1.14.1
-- 1.3.6.1.4.1.37950.1.1.5.10.7.1.14.1
-- 1.3.6.1.4.1.37950.1.1.5.10.7.1.14.1
		-- 1.3.6.1.4.1.37950.1.1.5.10.7.1.14.1
		dhcpLeaseEntry OBJECT-TYPE
			SYNTAX DhcpLeaseEntry
			MAX-ACCESS not-accessible
			STATUS current
			DESCRIPTION
				"Description."
			INDEX { dhcpLeaseIndex }
			::= { dhcpLeaseTable 1 }

		
		DhcpLeaseEntry ::=
			SEQUENCE { 
				dhcpLeaseIndex
					Integer32,
				dhcpLeaseIP
					IpAddress,
				dhcpLeaseMACAddr
					OCTET STRING,
				dhcpLeaseTimeValue
					Integer32
			 }

--          1.3.6.1.4.1.37950.1.1.5.10.7.1.14.1.1
-- 1.3.6.1.4.1.37950.1.1.5.10.7.1.14.1.1
-- 1.3.6.1.4.1.37950.1.1.5.10.7.1.14.1.1
-- 1.3.6.1.4.1.37950.1.1.5.10.7.1.14.1.1
-- 1.3.6.1.4.1.37950.1.1.5.10.7.1.14.1.1
-- 1.3.6.1.4.1.37950.1.1.5.10.7.1.14.1.1
-- 1.3.6.1.4.1.37950.1.1.5.10.7.1.14.1.1
-- 1.3.6.1.4.1.37950.1.1.5.10.7.1.14.1.1
-- 1.3.6.1.4.1.37950.1.1.5.10.7.1.14.1.1
		-- 1.3.6.1.4.1.37950.1.1.5.10.7.1.14.1.1
		dhcpLeaseIndex OBJECT-TYPE
			SYNTAX Integer32
			MAX-ACCESS read-only
			STATUS current
			DESCRIPTION
				"Description."
			::= { dhcpLeaseEntry 1 }

		
--          1.3.6.1.4.1.37950.1.1.5.10.7.1.14.1.2
-- 1.3.6.1.4.1.37950.1.1.5.10.7.1.14.1.2
-- 1.3.6.1.4.1.37950.1.1.5.10.7.1.14.1.2
-- 1.3.6.1.4.1.37950.1.1.5.10.7.1.14.1.2
-- 1.3.6.1.4.1.37950.1.1.5.10.7.1.14.1.2
-- 1.3.6.1.4.1.37950.1.1.5.10.7.1.14.1.2
-- 1.3.6.1.4.1.37950.1.1.5.10.7.1.14.1.2
-- 1.3.6.1.4.1.37950.1.1.5.10.7.1.14.1.2
-- 1.3.6.1.4.1.37950.1.1.5.10.7.1.14.1.2
		-- 1.3.6.1.4.1.37950.1.1.5.10.7.1.14.1.2
		dhcpLeaseIP OBJECT-TYPE
			SYNTAX IpAddress
			MAX-ACCESS read-only
			STATUS current
			DESCRIPTION
				"Description."
			::= { dhcpLeaseEntry 2 }

		
--          1.3.6.1.4.1.37950.1.1.5.10.7.1.14.1.3
-- 1.3.6.1.4.1.37950.1.1.5.10.7.1.14.1.3
-- 1.3.6.1.4.1.37950.1.1.5.10.7.1.14.1.3
-- 1.3.6.1.4.1.37950.1.1.5.10.7.1.14.1.3
-- 1.3.6.1.4.1.37950.1.1.5.10.7.1.14.1.3
-- 1.3.6.1.4.1.37950.1.1.5.10.7.1.14.1.3
-- 1.3.6.1.4.1.37950.1.1.5.10.7.1.14.1.3
-- 1.3.6.1.4.1.37950.1.1.5.10.7.1.14.1.3
-- 1.3.6.1.4.1.37950.1.1.5.10.7.1.14.1.3
		-- 1.3.6.1.4.1.37950.1.1.5.10.7.1.14.1.3
		dhcpLeaseMACAddr OBJECT-TYPE
			SYNTAX OCTET STRING
			MAX-ACCESS read-only
			STATUS current
			DESCRIPTION
				"Description."
			::= { dhcpLeaseEntry 3 }

		
--          1.3.6.1.4.1.37950.1.1.5.10.7.1.14.1.4
-- 1.3.6.1.4.1.37950.1.1.5.10.7.1.14.1.4
-- 1.3.6.1.4.1.37950.1.1.5.10.7.1.14.1.4
-- 1.3.6.1.4.1.37950.1.1.5.10.7.1.14.1.4
-- 1.3.6.1.4.1.37950.1.1.5.10.7.1.14.1.4
-- 1.3.6.1.4.1.37950.1.1.5.10.7.1.14.1.4
-- 1.3.6.1.4.1.37950.1.1.5.10.7.1.14.1.4
-- 1.3.6.1.4.1.37950.1.1.5.10.7.1.14.1.4
-- 1.3.6.1.4.1.37950.1.1.5.10.7.1.14.1.4
		-- 1.3.6.1.4.1.37950.1.1.5.10.7.1.14.1.4
		dhcpLeaseTimeValue OBJECT-TYPE
			SYNTAX Integer32
			MAX-ACCESS read-only
			STATUS current
			DESCRIPTION
				"Description."
			::= { dhcpLeaseEntry 4 }

		
--          1.3.6.1.4.1.37950.1.1.5.10.7.2
-- 1.3.6.1.4.1.37950.1.1.5.10.7.2
-- 1.3.6.1.4.1.37950.1.1.5.10.7.2
-- 1.3.6.1.4.1.37950.1.1.5.10.7.2
-- 1.3.6.1.4.1.37950.1.1.5.10.7.2
-- 1.3.6.1.4.1.37950.1.1.5.10.7.2
-- 1.3.6.1.4.1.37950.1.1.5.10.7.2
-- 1.3.6.1.4.1.37950.1.1.5.10.7.2
-- 1.3.6.1.4.1.37950.1.1.5.10.7.2
		-- 1.3.6.1.4.1.37950.1.1.5.10.7.2
		dhcpRelay OBJECT IDENTIFIER ::= { v1600dDHCP 2 }

		
--          1.3.6.1.4.1.37950.1.1.5.10.7.2.1
-- 1.3.6.1.4.1.37950.1.1.5.10.7.2.1
-- 1.3.6.1.4.1.37950.1.1.5.10.7.2.1
-- 1.3.6.1.4.1.37950.1.1.5.10.7.2.1
-- 1.3.6.1.4.1.37950.1.1.5.10.7.2.1
-- 1.3.6.1.4.1.37950.1.1.5.10.7.2.1
-- 1.3.6.1.4.1.37950.1.1.5.10.7.2.1
-- 1.3.6.1.4.1.37950.1.1.5.10.7.2.1
-- 1.3.6.1.4.1.37950.1.1.5.10.7.2.1
		-- 1.3.6.1.4.1.37950.1.1.5.10.7.2.1
		relayServerConfig OBJECT IDENTIFIER ::= { dhcpRelay 1 }

		
--          1.3.6.1.4.1.37950.1.1.5.10.7.2.1.1
-- 1.3.6.1.4.1.37950.1.1.5.10.7.2.1.1
-- 1.3.6.1.4.1.37950.1.1.5.10.7.2.1.1
-- 1.3.6.1.4.1.37950.1.1.5.10.7.2.1.1
-- 1.3.6.1.4.1.37950.1.1.5.10.7.2.1.1
-- 1.3.6.1.4.1.37950.1.1.5.10.7.2.1.1
-- 1.3.6.1.4.1.37950.1.1.5.10.7.2.1.1
-- 1.3.6.1.4.1.37950.1.1.5.10.7.2.1.1
-- 1.3.6.1.4.1.37950.1.1.5.10.7.2.1.1
		-- 1.3.6.1.4.1.37950.1.1.5.10.7.2.1.1
		relayVlan OBJECT-TYPE
			SYNTAX Integer32 (1..4095)
			MAX-ACCESS read-write
			STATUS current
			DESCRIPTION
				"Description."
			::= { relayServerConfig 1 }

		
--          1.3.6.1.4.1.37950.1.1.5.10.7.2.1.2
-- 1.3.6.1.4.1.37950.1.1.5.10.7.2.1.2
-- 1.3.6.1.4.1.37950.1.1.5.10.7.2.1.2
-- 1.3.6.1.4.1.37950.1.1.5.10.7.2.1.2
-- 1.3.6.1.4.1.37950.1.1.5.10.7.2.1.2
-- 1.3.6.1.4.1.37950.1.1.5.10.7.2.1.2
-- 1.3.6.1.4.1.37950.1.1.5.10.7.2.1.2
-- 1.3.6.1.4.1.37950.1.1.5.10.7.2.1.2
-- 1.3.6.1.4.1.37950.1.1.5.10.7.2.1.2
		-- 1.3.6.1.4.1.37950.1.1.5.10.7.2.1.2
		relayServerIP OBJECT-TYPE
			SYNTAX IpAddress
			MAX-ACCESS read-write
			STATUS current
			DESCRIPTION
				"Description."
			::= { relayServerConfig 2 }

		
--          1.3.6.1.4.1.37950.1.1.5.10.7.2.1.3
-- 1.3.6.1.4.1.37950.1.1.5.10.7.2.1.3
-- 1.3.6.1.4.1.37950.1.1.5.10.7.2.1.3
-- 1.3.6.1.4.1.37950.1.1.5.10.7.2.1.3
-- 1.3.6.1.4.1.37950.1.1.5.10.7.2.1.3
-- 1.3.6.1.4.1.37950.1.1.5.10.7.2.1.3
-- 1.3.6.1.4.1.37950.1.1.5.10.7.2.1.3
-- 1.3.6.1.4.1.37950.1.1.5.10.7.2.1.3
-- 1.3.6.1.4.1.37950.1.1.5.10.7.2.1.3
		-- 1.3.6.1.4.1.37950.1.1.5.10.7.2.1.3
		relayServerAction OBJECT-TYPE
			SYNTAX INTEGER
				{
				add(1),
				delete(2)
				}
			MAX-ACCESS read-write
			STATUS current
			DESCRIPTION
				"Description."
			::= { relayServerConfig 3 }

		
--          1.3.6.1.4.1.37950.1.1.5.10.7.2.2
-- 1.3.6.1.4.1.37950.1.1.5.10.7.2.2
-- 1.3.6.1.4.1.37950.1.1.5.10.7.2.2
-- 1.3.6.1.4.1.37950.1.1.5.10.7.2.2
-- 1.3.6.1.4.1.37950.1.1.5.10.7.2.2
-- 1.3.6.1.4.1.37950.1.1.5.10.7.2.2
-- 1.3.6.1.4.1.37950.1.1.5.10.7.2.2
-- 1.3.6.1.4.1.37950.1.1.5.10.7.2.2
-- 1.3.6.1.4.1.37950.1.1.5.10.7.2.2
		-- 1.3.6.1.4.1.37950.1.1.5.10.7.2.2
		relayServerTable OBJECT-TYPE
			SYNTAX SEQUENCE OF RelayServerEntry
			MAX-ACCESS not-accessible
			STATUS current
			DESCRIPTION
				"Description."
			::= { dhcpRelay 2 }

		
--          1.3.6.1.4.1.37950.1.1.5.10.7.2.2.1
-- 1.3.6.1.4.1.37950.1.1.5.10.7.2.2.1
-- 1.3.6.1.4.1.37950.1.1.5.10.7.2.2.1
-- 1.3.6.1.4.1.37950.1.1.5.10.7.2.2.1
-- 1.3.6.1.4.1.37950.1.1.5.10.7.2.2.1
-- 1.3.6.1.4.1.37950.1.1.5.10.7.2.2.1
-- 1.3.6.1.4.1.37950.1.1.5.10.7.2.2.1
-- 1.3.6.1.4.1.37950.1.1.5.10.7.2.2.1
-- 1.3.6.1.4.1.37950.1.1.5.10.7.2.2.1
		-- 1.3.6.1.4.1.37950.1.1.5.10.7.2.2.1
		relayServerEntry OBJECT-TYPE
			SYNTAX RelayServerEntry
			MAX-ACCESS not-accessible
			STATUS current
			DESCRIPTION
				"Description."
			INDEX { relayServerVlan }
			::= { relayServerTable 1 }

		
		RelayServerEntry ::=
			SEQUENCE { 
				relayServerVlan
					Integer32,
				relayServerIPAddrList
					OCTET STRING
			 }

--          1.3.6.1.4.1.37950.1.1.5.10.7.2.2.1.1
-- 1.3.6.1.4.1.37950.1.1.5.10.7.2.2.1.1
-- 1.3.6.1.4.1.37950.1.1.5.10.7.2.2.1.1
-- 1.3.6.1.4.1.37950.1.1.5.10.7.2.2.1.1
-- 1.3.6.1.4.1.37950.1.1.5.10.7.2.2.1.1
-- 1.3.6.1.4.1.37950.1.1.5.10.7.2.2.1.1
-- 1.3.6.1.4.1.37950.1.1.5.10.7.2.2.1.1
-- 1.3.6.1.4.1.37950.1.1.5.10.7.2.2.1.1
-- 1.3.6.1.4.1.37950.1.1.5.10.7.2.2.1.1
		-- 1.3.6.1.4.1.37950.1.1.5.10.7.2.2.1.1
		relayServerVlan OBJECT-TYPE
			SYNTAX Integer32
			MAX-ACCESS read-only
			STATUS current
			DESCRIPTION
				"Description."
			::= { relayServerEntry 1 }

		
--          1.3.6.1.4.1.37950.1.1.5.10.7.2.2.1.2
-- 1.3.6.1.4.1.37950.1.1.5.10.7.2.2.1.2
-- 1.3.6.1.4.1.37950.1.1.5.10.7.2.2.1.2
-- 1.3.6.1.4.1.37950.1.1.5.10.7.2.2.1.2
-- 1.3.6.1.4.1.37950.1.1.5.10.7.2.2.1.2
-- 1.3.6.1.4.1.37950.1.1.5.10.7.2.2.1.2
-- 1.3.6.1.4.1.37950.1.1.5.10.7.2.2.1.2
-- 1.3.6.1.4.1.37950.1.1.5.10.7.2.2.1.2
-- 1.3.6.1.4.1.37950.1.1.5.10.7.2.2.1.2
		-- 1.3.6.1.4.1.37950.1.1.5.10.7.2.2.1.2
		relayServerIPAddrList OBJECT-TYPE
			SYNTAX OCTET STRING
			MAX-ACCESS read-only
			STATUS current
			DESCRIPTION
				"Description."
			::= { relayServerEntry 2 }

		
--          1.3.6.1.4.1.37950.1.1.5.10.7.3
-- 1.3.6.1.4.1.37950.1.1.5.10.7.3
-- 1.3.6.1.4.1.37950.1.1.5.10.7.3
-- 1.3.6.1.4.1.37950.1.1.5.10.7.3
-- 1.3.6.1.4.1.37950.1.1.5.10.7.3
-- 1.3.6.1.4.1.37950.1.1.5.10.7.3
-- 1.3.6.1.4.1.37950.1.1.5.10.7.3
-- 1.3.6.1.4.1.37950.1.1.5.10.7.3
-- 1.3.6.1.4.1.37950.1.1.5.10.7.3
		-- 1.3.6.1.4.1.37950.1.1.5.10.7.3
		dhcpSnooping OBJECT IDENTIFIER ::= { v1600dDHCP 3 }

		
--          1.3.6.1.4.1.37950.1.1.5.10.7.3.1
-- 1.3.6.1.4.1.37950.1.1.5.10.7.3.1
-- 1.3.6.1.4.1.37950.1.1.5.10.7.3.1
-- 1.3.6.1.4.1.37950.1.1.5.10.7.3.1
-- 1.3.6.1.4.1.37950.1.1.5.10.7.3.1
-- 1.3.6.1.4.1.37950.1.1.5.10.7.3.1
-- 1.3.6.1.4.1.37950.1.1.5.10.7.3.1
-- 1.3.6.1.4.1.37950.1.1.5.10.7.3.1
-- 1.3.6.1.4.1.37950.1.1.5.10.7.3.1
		-- 1.3.6.1.4.1.37950.1.1.5.10.7.3.1
		dhcpSNControl OBJECT-TYPE
			SYNTAX INTEGER
				{
				enable(1),
				disable(2)
				}
			MAX-ACCESS read-write
			STATUS current
			DESCRIPTION
				"Description."
			::= { dhcpSnooping 1 }

		
--          1.3.6.1.4.1.37950.1.1.5.10.7.3.2
-- 1.3.6.1.4.1.37950.1.1.5.10.7.3.2
-- 1.3.6.1.4.1.37950.1.1.5.10.7.3.2
-- 1.3.6.1.4.1.37950.1.1.5.10.7.3.2
-- 1.3.6.1.4.1.37950.1.1.5.10.7.3.2
-- 1.3.6.1.4.1.37950.1.1.5.10.7.3.2
-- 1.3.6.1.4.1.37950.1.1.5.10.7.3.2
-- 1.3.6.1.4.1.37950.1.1.5.10.7.3.2
-- 1.3.6.1.4.1.37950.1.1.5.10.7.3.2
		-- 1.3.6.1.4.1.37950.1.1.5.10.7.3.2
		dhcpSNVlan OBJECT IDENTIFIER ::= { dhcpSnooping 2 }

		
--          1.3.6.1.4.1.37950.1.1.5.10.7.3.2.1
-- 1.3.6.1.4.1.37950.1.1.5.10.7.3.2.1
-- 1.3.6.1.4.1.37950.1.1.5.10.7.3.2.1
-- 1.3.6.1.4.1.37950.1.1.5.10.7.3.2.1
-- 1.3.6.1.4.1.37950.1.1.5.10.7.3.2.1
-- 1.3.6.1.4.1.37950.1.1.5.10.7.3.2.1
-- 1.3.6.1.4.1.37950.1.1.5.10.7.3.2.1
-- 1.3.6.1.4.1.37950.1.1.5.10.7.3.2.1
-- 1.3.6.1.4.1.37950.1.1.5.10.7.3.2.1
		-- 1.3.6.1.4.1.37950.1.1.5.10.7.3.2.1
		dhcpSNVlanId OBJECT-TYPE
			SYNTAX Integer32 (1..4095)
			MAX-ACCESS read-write
			STATUS current
			DESCRIPTION
				"Description."
			::= { dhcpSNVlan 1 }

		
--          1.3.6.1.4.1.37950.1.1.5.10.7.3.2.2
-- 1.3.6.1.4.1.37950.1.1.5.10.7.3.2.2
-- 1.3.6.1.4.1.37950.1.1.5.10.7.3.2.2
-- 1.3.6.1.4.1.37950.1.1.5.10.7.3.2.2
-- 1.3.6.1.4.1.37950.1.1.5.10.7.3.2.2
-- 1.3.6.1.4.1.37950.1.1.5.10.7.3.2.2
-- 1.3.6.1.4.1.37950.1.1.5.10.7.3.2.2
-- 1.3.6.1.4.1.37950.1.1.5.10.7.3.2.2
-- 1.3.6.1.4.1.37950.1.1.5.10.7.3.2.2
		-- 1.3.6.1.4.1.37950.1.1.5.10.7.3.2.2
		dhcpSNVlanAction OBJECT-TYPE
			SYNTAX INTEGER
				{
				add(1),
				delete(2)
				}
			MAX-ACCESS read-write
			STATUS current
			DESCRIPTION
				"Description."
			::= { dhcpSNVlan 2 }

		
--          1.3.6.1.4.1.37950.1.1.5.10.7.3.2.3
-- 1.3.6.1.4.1.37950.1.1.5.10.7.3.2.3
-- 1.3.6.1.4.1.37950.1.1.5.10.7.3.2.3
-- 1.3.6.1.4.1.37950.1.1.5.10.7.3.2.3
-- 1.3.6.1.4.1.37950.1.1.5.10.7.3.2.3
-- 1.3.6.1.4.1.37950.1.1.5.10.7.3.2.3
-- 1.3.6.1.4.1.37950.1.1.5.10.7.3.2.3
-- 1.3.6.1.4.1.37950.1.1.5.10.7.3.2.3
-- 1.3.6.1.4.1.37950.1.1.5.10.7.3.2.3
		-- 1.3.6.1.4.1.37950.1.1.5.10.7.3.2.3
		dhcpSNVlanList OBJECT-TYPE
			SYNTAX OCTET STRING
			MAX-ACCESS read-only
			STATUS current
			DESCRIPTION
				"Description."
			::= { dhcpSNVlan 3 }

		
--          1.3.6.1.4.1.37950.1.1.5.10.7.3.3
-- 1.3.6.1.4.1.37950.1.1.5.10.7.3.3
-- 1.3.6.1.4.1.37950.1.1.5.10.7.3.3
-- 1.3.6.1.4.1.37950.1.1.5.10.7.3.3
-- 1.3.6.1.4.1.37950.1.1.5.10.7.3.3
-- 1.3.6.1.4.1.37950.1.1.5.10.7.3.3
-- 1.3.6.1.4.1.37950.1.1.5.10.7.3.3
-- 1.3.6.1.4.1.37950.1.1.5.10.7.3.3
-- 1.3.6.1.4.1.37950.1.1.5.10.7.3.3
		-- 1.3.6.1.4.1.37950.1.1.5.10.7.3.3
		dhcpSNOption82 OBJECT IDENTIFIER ::= { dhcpSnooping 3 }

		
--          1.3.6.1.4.1.37950.1.1.5.10.7.3.3.1
-- 1.3.6.1.4.1.37950.1.1.5.10.7.3.3.1
-- 1.3.6.1.4.1.37950.1.1.5.10.7.3.3.1
-- 1.3.6.1.4.1.37950.1.1.5.10.7.3.3.1
-- 1.3.6.1.4.1.37950.1.1.5.10.7.3.3.1
-- 1.3.6.1.4.1.37950.1.1.5.10.7.3.3.1
-- 1.3.6.1.4.1.37950.1.1.5.10.7.3.3.1
-- 1.3.6.1.4.1.37950.1.1.5.10.7.3.3.1
-- 1.3.6.1.4.1.37950.1.1.5.10.7.3.3.1
		-- 1.3.6.1.4.1.37950.1.1.5.10.7.3.3.1
		snOption82Control OBJECT-TYPE
			SYNTAX INTEGER
				{
				enable(1),
				disable(2)
				}
			MAX-ACCESS read-write
			STATUS current
			DESCRIPTION
				"Description."
			::= { dhcpSNOption82 1 }

		
--          1.3.6.1.4.1.37950.1.1.5.10.7.3.3.2
-- 1.3.6.1.4.1.37950.1.1.5.10.7.3.3.2
-- 1.3.6.1.4.1.37950.1.1.5.10.7.3.3.2
-- 1.3.6.1.4.1.37950.1.1.5.10.7.3.3.2
-- 1.3.6.1.4.1.37950.1.1.5.10.7.3.3.2
-- 1.3.6.1.4.1.37950.1.1.5.10.7.3.3.2
-- 1.3.6.1.4.1.37950.1.1.5.10.7.3.3.2
-- 1.3.6.1.4.1.37950.1.1.5.10.7.3.3.2
-- 1.3.6.1.4.1.37950.1.1.5.10.7.3.3.2
		-- 1.3.6.1.4.1.37950.1.1.5.10.7.3.3.2
		snOption82Strategy OBJECT-TYPE
			SYNTAX INTEGER
				{
				drop(0),
				keep(1),
				replace(2)
				}
			MAX-ACCESS read-write
			STATUS current
			DESCRIPTION
				"Description."
			::= { dhcpSNOption82 2 }

		
--          1.3.6.1.4.1.37950.1.1.5.10.7.3.4
-- 1.3.6.1.4.1.37950.1.1.5.10.7.3.4
-- 1.3.6.1.4.1.37950.1.1.5.10.7.3.4
-- 1.3.6.1.4.1.37950.1.1.5.10.7.3.4
-- 1.3.6.1.4.1.37950.1.1.5.10.7.3.4
-- 1.3.6.1.4.1.37950.1.1.5.10.7.3.4
-- 1.3.6.1.4.1.37950.1.1.5.10.7.3.4
-- 1.3.6.1.4.1.37950.1.1.5.10.7.3.4
-- 1.3.6.1.4.1.37950.1.1.5.10.7.3.4
		-- 1.3.6.1.4.1.37950.1.1.5.10.7.3.4
		dhcpSNPortCfgTable OBJECT-TYPE
			SYNTAX SEQUENCE OF DhcpSNPortCfgEntry
			MAX-ACCESS not-accessible
			STATUS current
			DESCRIPTION
				"Description."
			::= { dhcpSnooping 4 }

		
--          1.3.6.1.4.1.37950.1.1.5.10.7.3.4.1
-- 1.3.6.1.4.1.37950.1.1.5.10.7.3.4.1
-- 1.3.6.1.4.1.37950.1.1.5.10.7.3.4.1
-- 1.3.6.1.4.1.37950.1.1.5.10.7.3.4.1
-- 1.3.6.1.4.1.37950.1.1.5.10.7.3.4.1
-- 1.3.6.1.4.1.37950.1.1.5.10.7.3.4.1
-- 1.3.6.1.4.1.37950.1.1.5.10.7.3.4.1
-- 1.3.6.1.4.1.37950.1.1.5.10.7.3.4.1
-- 1.3.6.1.4.1.37950.1.1.5.10.7.3.4.1
		-- 1.3.6.1.4.1.37950.1.1.5.10.7.3.4.1
		dhcpSNPortCfgEntry OBJECT-TYPE
			SYNTAX DhcpSNPortCfgEntry
			MAX-ACCESS not-accessible
			STATUS current
			DESCRIPTION
				"Description."
			INDEX { snPortIndex }
			::= { dhcpSNPortCfgTable 1 }

		
		DhcpSNPortCfgEntry ::=
			SEQUENCE { 
				snPortIndex
					Integer32,
				snPortType
					INTEGER,
				snPortUserCircuitID
					OCTET STRING,
				snPortUserRemoteID
					OCTET STRING,
				snPortRateLimit
					INTEGER
			 }

--          1.3.6.1.4.1.37950.1.1.5.10.7.3.4.1.1
-- 1.3.6.1.4.1.37950.1.1.5.10.7.3.4.1.1
-- 1.3.6.1.4.1.37950.1.1.5.10.7.3.4.1.1
-- 1.3.6.1.4.1.37950.1.1.5.10.7.3.4.1.1
-- 1.3.6.1.4.1.37950.1.1.5.10.7.3.4.1.1
-- 1.3.6.1.4.1.37950.1.1.5.10.7.3.4.1.1
-- 1.3.6.1.4.1.37950.1.1.5.10.7.3.4.1.1
-- 1.3.6.1.4.1.37950.1.1.5.10.7.3.4.1.1
-- 1.3.6.1.4.1.37950.1.1.5.10.7.3.4.1.1
		-- 1.3.6.1.4.1.37950.1.1.5.10.7.3.4.1.1
		snPortIndex OBJECT-TYPE
			SYNTAX Integer32
			MAX-ACCESS read-only
			STATUS current
			DESCRIPTION
				"Description."
			::= { dhcpSNPortCfgEntry 1 }

		
--          1.3.6.1.4.1.37950.1.1.5.10.7.3.4.1.2
-- 1.3.6.1.4.1.37950.1.1.5.10.7.3.4.1.2
-- 1.3.6.1.4.1.37950.1.1.5.10.7.3.4.1.2
-- 1.3.6.1.4.1.37950.1.1.5.10.7.3.4.1.2
-- 1.3.6.1.4.1.37950.1.1.5.10.7.3.4.1.2
-- 1.3.6.1.4.1.37950.1.1.5.10.7.3.4.1.2
-- 1.3.6.1.4.1.37950.1.1.5.10.7.3.4.1.2
-- 1.3.6.1.4.1.37950.1.1.5.10.7.3.4.1.2
-- 1.3.6.1.4.1.37950.1.1.5.10.7.3.4.1.2
		-- 1.3.6.1.4.1.37950.1.1.5.10.7.3.4.1.2
		snPortType OBJECT-TYPE
			SYNTAX INTEGER
				{
				trust(1),
				untrust(2)
				}
			MAX-ACCESS read-write
			STATUS current
			DESCRIPTION
				"Description."
			::= { dhcpSNPortCfgEntry 2 }

		
--          1.3.6.1.4.1.37950.1.1.5.10.7.3.4.1.3
-- 1.3.6.1.4.1.37950.1.1.5.10.7.3.4.1.3
-- 1.3.6.1.4.1.37950.1.1.5.10.7.3.4.1.3
-- 1.3.6.1.4.1.37950.1.1.5.10.7.3.4.1.3
-- 1.3.6.1.4.1.37950.1.1.5.10.7.3.4.1.3
-- 1.3.6.1.4.1.37950.1.1.5.10.7.3.4.1.3
-- 1.3.6.1.4.1.37950.1.1.5.10.7.3.4.1.3
-- 1.3.6.1.4.1.37950.1.1.5.10.7.3.4.1.3
-- 1.3.6.1.4.1.37950.1.1.5.10.7.3.4.1.3
		-- 1.3.6.1.4.1.37950.1.1.5.10.7.3.4.1.3
		snPortUserCircuitID OBJECT-TYPE
			SYNTAX OCTET STRING
			MAX-ACCESS read-write
			STATUS current
			DESCRIPTION
				"Description."
			::= { dhcpSNPortCfgEntry 3 }

		
--          1.3.6.1.4.1.37950.1.1.5.10.7.3.4.1.4
-- 1.3.6.1.4.1.37950.1.1.5.10.7.3.4.1.4
-- 1.3.6.1.4.1.37950.1.1.5.10.7.3.4.1.4
-- 1.3.6.1.4.1.37950.1.1.5.10.7.3.4.1.4
-- 1.3.6.1.4.1.37950.1.1.5.10.7.3.4.1.4
-- 1.3.6.1.4.1.37950.1.1.5.10.7.3.4.1.4
-- 1.3.6.1.4.1.37950.1.1.5.10.7.3.4.1.4
-- 1.3.6.1.4.1.37950.1.1.5.10.7.3.4.1.4
-- 1.3.6.1.4.1.37950.1.1.5.10.7.3.4.1.4
		-- 1.3.6.1.4.1.37950.1.1.5.10.7.3.4.1.4
		snPortUserRemoteID OBJECT-TYPE
			SYNTAX OCTET STRING
			MAX-ACCESS read-write
			STATUS current
			DESCRIPTION
				"Description."
			::= { dhcpSNPortCfgEntry 4 }

		
--          1.3.6.1.4.1.37950.1.1.5.10.7.3.4.1.5
-- 1.3.6.1.4.1.37950.1.1.5.10.7.3.4.1.5
-- 1.3.6.1.4.1.37950.1.1.5.10.7.3.4.1.5
-- 1.3.6.1.4.1.37950.1.1.5.10.7.3.4.1.5
-- 1.3.6.1.4.1.37950.1.1.5.10.7.3.4.1.5
-- 1.3.6.1.4.1.37950.1.1.5.10.7.3.4.1.5
-- 1.3.6.1.4.1.37950.1.1.5.10.7.3.4.1.5
-- 1.3.6.1.4.1.37950.1.1.5.10.7.3.4.1.5
-- 1.3.6.1.4.1.37950.1.1.5.10.7.3.4.1.5
		-- 1.3.6.1.4.1.37950.1.1.5.10.7.3.4.1.5
		snPortRateLimit OBJECT-TYPE
			SYNTAX INTEGER (0..4096)
			MAX-ACCESS read-write
			STATUS current
			DESCRIPTION
				"Description."
			::= { dhcpSNPortCfgEntry 5 }

		
--          1.3.6.1.4.1.37950.1.1.5.10.7.3.5
-- 1.3.6.1.4.1.37950.1.1.5.10.7.3.5
-- 1.3.6.1.4.1.37950.1.1.5.10.7.3.5
-- 1.3.6.1.4.1.37950.1.1.5.10.7.3.5
-- 1.3.6.1.4.1.37950.1.1.5.10.7.3.5
-- 1.3.6.1.4.1.37950.1.1.5.10.7.3.5
-- 1.3.6.1.4.1.37950.1.1.5.10.7.3.5
-- 1.3.6.1.4.1.37950.1.1.5.10.7.3.5
-- 1.3.6.1.4.1.37950.1.1.5.10.7.3.5
		-- 1.3.6.1.4.1.37950.1.1.5.10.7.3.5
		dhcpSNErrorRecovery OBJECT-TYPE
			SYNTAX INTEGER
				{
				enable(1),
				disable(2)
				}
			MAX-ACCESS read-write
			STATUS current
			DESCRIPTION
				"Description."
			::= { dhcpSnooping 5 }

		
--          1.3.6.1.4.1.37950.1.1.5.10.7.3.6
-- 1.3.6.1.4.1.37950.1.1.5.10.7.3.6
-- 1.3.6.1.4.1.37950.1.1.5.10.7.3.6
-- 1.3.6.1.4.1.37950.1.1.5.10.7.3.6
-- 1.3.6.1.4.1.37950.1.1.5.10.7.3.6
-- 1.3.6.1.4.1.37950.1.1.5.10.7.3.6
-- 1.3.6.1.4.1.37950.1.1.5.10.7.3.6
-- 1.3.6.1.4.1.37950.1.1.5.10.7.3.6
-- 1.3.6.1.4.1.37950.1.1.5.10.7.3.6
		-- 1.3.6.1.4.1.37950.1.1.5.10.7.3.6
		dhcpSNErrorRecoveryInterval OBJECT-TYPE
			SYNTAX INTEGER (3..3600)
			MAX-ACCESS read-write
			STATUS current
			DESCRIPTION
				"Description."
			::= { dhcpSnooping 6 }

		
--          1.3.6.1.4.1.37950.1.1.5.10.7.3.7
-- 1.3.6.1.4.1.37950.1.1.5.10.7.3.7
-- 1.3.6.1.4.1.37950.1.1.5.10.7.3.7
-- 1.3.6.1.4.1.37950.1.1.5.10.7.3.7
-- 1.3.6.1.4.1.37950.1.1.5.10.7.3.7
-- 1.3.6.1.4.1.37950.1.1.5.10.7.3.7
-- 1.3.6.1.4.1.37950.1.1.5.10.7.3.7
-- 1.3.6.1.4.1.37950.1.1.5.10.7.3.7
-- 1.3.6.1.4.1.37950.1.1.5.10.7.3.7
		-- 1.3.6.1.4.1.37950.1.1.5.10.7.3.7
		dhcpSNBinding OBJECT IDENTIFIER ::= { dhcpSnooping 7 }

		
--          1.3.6.1.4.1.37950.1.1.5.10.7.3.7.1
-- 1.3.6.1.4.1.37950.1.1.5.10.7.3.7.1
-- 1.3.6.1.4.1.37950.1.1.5.10.7.3.7.1
-- 1.3.6.1.4.1.37950.1.1.5.10.7.3.7.1
-- 1.3.6.1.4.1.37950.1.1.5.10.7.3.7.1
-- 1.3.6.1.4.1.37950.1.1.5.10.7.3.7.1
-- 1.3.6.1.4.1.37950.1.1.5.10.7.3.7.1
-- 1.3.6.1.4.1.37950.1.1.5.10.7.3.7.1
-- 1.3.6.1.4.1.37950.1.1.5.10.7.3.7.1
		-- 1.3.6.1.4.1.37950.1.1.5.10.7.3.7.1
		snBindingConfig OBJECT IDENTIFIER ::= { dhcpSNBinding 1 }

		
--          1.3.6.1.4.1.37950.1.1.5.10.7.3.7.1.1
-- 1.3.6.1.4.1.37950.1.1.5.10.7.3.7.1.1
-- 1.3.6.1.4.1.37950.1.1.5.10.7.3.7.1.1
-- 1.3.6.1.4.1.37950.1.1.5.10.7.3.7.1.1
-- 1.3.6.1.4.1.37950.1.1.5.10.7.3.7.1.1
-- 1.3.6.1.4.1.37950.1.1.5.10.7.3.7.1.1
-- 1.3.6.1.4.1.37950.1.1.5.10.7.3.7.1.1
-- 1.3.6.1.4.1.37950.1.1.5.10.7.3.7.1.1
-- 1.3.6.1.4.1.37950.1.1.5.10.7.3.7.1.1
		-- 1.3.6.1.4.1.37950.1.1.5.10.7.3.7.1.1
		snBindMAC OBJECT-TYPE
			SYNTAX OCTET STRING
			MAX-ACCESS read-write
			STATUS current
			DESCRIPTION
				"Description."
			::= { snBindingConfig 1 }

		
--          1.3.6.1.4.1.37950.1.1.5.10.7.3.7.1.2
-- 1.3.6.1.4.1.37950.1.1.5.10.7.3.7.1.2
-- 1.3.6.1.4.1.37950.1.1.5.10.7.3.7.1.2
-- 1.3.6.1.4.1.37950.1.1.5.10.7.3.7.1.2
-- 1.3.6.1.4.1.37950.1.1.5.10.7.3.7.1.2
-- 1.3.6.1.4.1.37950.1.1.5.10.7.3.7.1.2
-- 1.3.6.1.4.1.37950.1.1.5.10.7.3.7.1.2
-- 1.3.6.1.4.1.37950.1.1.5.10.7.3.7.1.2
-- 1.3.6.1.4.1.37950.1.1.5.10.7.3.7.1.2
		-- 1.3.6.1.4.1.37950.1.1.5.10.7.3.7.1.2
		snBindVlan OBJECT-TYPE
			SYNTAX Integer32 (1..4095)
			MAX-ACCESS read-write
			STATUS current
			DESCRIPTION
				"Description."
			::= { snBindingConfig 2 }

		
--          1.3.6.1.4.1.37950.1.1.5.10.7.3.7.1.3
-- 1.3.6.1.4.1.37950.1.1.5.10.7.3.7.1.3
-- 1.3.6.1.4.1.37950.1.1.5.10.7.3.7.1.3
-- 1.3.6.1.4.1.37950.1.1.5.10.7.3.7.1.3
-- 1.3.6.1.4.1.37950.1.1.5.10.7.3.7.1.3
-- 1.3.6.1.4.1.37950.1.1.5.10.7.3.7.1.3
-- 1.3.6.1.4.1.37950.1.1.5.10.7.3.7.1.3
-- 1.3.6.1.4.1.37950.1.1.5.10.7.3.7.1.3
-- 1.3.6.1.4.1.37950.1.1.5.10.7.3.7.1.3
		-- 1.3.6.1.4.1.37950.1.1.5.10.7.3.7.1.3
		snBindIP OBJECT-TYPE
			SYNTAX IpAddress
			MAX-ACCESS read-write
			STATUS current
			DESCRIPTION
				"Description."
			::= { snBindingConfig 3 }

		
--          1.3.6.1.4.1.37950.1.1.5.10.7.3.7.1.4
-- 1.3.6.1.4.1.37950.1.1.5.10.7.3.7.1.4
-- 1.3.6.1.4.1.37950.1.1.5.10.7.3.7.1.4
-- 1.3.6.1.4.1.37950.1.1.5.10.7.3.7.1.4
-- 1.3.6.1.4.1.37950.1.1.5.10.7.3.7.1.4
-- 1.3.6.1.4.1.37950.1.1.5.10.7.3.7.1.4
-- 1.3.6.1.4.1.37950.1.1.5.10.7.3.7.1.4
-- 1.3.6.1.4.1.37950.1.1.5.10.7.3.7.1.4
-- 1.3.6.1.4.1.37950.1.1.5.10.7.3.7.1.4
		-- 1.3.6.1.4.1.37950.1.1.5.10.7.3.7.1.4
		snBindPortIndex OBJECT-TYPE
			SYNTAX Integer32 (1..28)
			MAX-ACCESS read-write
			STATUS current
			DESCRIPTION
				"Description."
			::= { snBindingConfig 4 }

		
--          1.3.6.1.4.1.37950.1.1.5.10.7.3.7.1.5
-- 1.3.6.1.4.1.37950.1.1.5.10.7.3.7.1.5
-- 1.3.6.1.4.1.37950.1.1.5.10.7.3.7.1.5
-- 1.3.6.1.4.1.37950.1.1.5.10.7.3.7.1.5
-- 1.3.6.1.4.1.37950.1.1.5.10.7.3.7.1.5
-- 1.3.6.1.4.1.37950.1.1.5.10.7.3.7.1.5
-- 1.3.6.1.4.1.37950.1.1.5.10.7.3.7.1.5
-- 1.3.6.1.4.1.37950.1.1.5.10.7.3.7.1.5
-- 1.3.6.1.4.1.37950.1.1.5.10.7.3.7.1.5
		-- 1.3.6.1.4.1.37950.1.1.5.10.7.3.7.1.5
		snBindLease OBJECT-TYPE
			SYNTAX Integer32 (60..1000000)
			MAX-ACCESS read-write
			STATUS current
			DESCRIPTION
				"Description."
			::= { snBindingConfig 5 }

		
--          1.3.6.1.4.1.37950.1.1.5.10.7.3.7.1.6
-- 1.3.6.1.4.1.37950.1.1.5.10.7.3.7.1.6
-- 1.3.6.1.4.1.37950.1.1.5.10.7.3.7.1.6
-- 1.3.6.1.4.1.37950.1.1.5.10.7.3.7.1.6
-- 1.3.6.1.4.1.37950.1.1.5.10.7.3.7.1.6
-- 1.3.6.1.4.1.37950.1.1.5.10.7.3.7.1.6
-- 1.3.6.1.4.1.37950.1.1.5.10.7.3.7.1.6
-- 1.3.6.1.4.1.37950.1.1.5.10.7.3.7.1.6
-- 1.3.6.1.4.1.37950.1.1.5.10.7.3.7.1.6
		-- 1.3.6.1.4.1.37950.1.1.5.10.7.3.7.1.6
		snBindAction OBJECT-TYPE
			SYNTAX INTEGER
				{
				addstatic(1),
				deletebymac(2),
				flushall(3),
				flushstatic(4),
				flushdynamic(5)
				}
			MAX-ACCESS read-write
			STATUS current
			DESCRIPTION
				"Description."
			::= { snBindingConfig 6 }

		
--          1.3.6.1.4.1.37950.1.1.5.10.7.3.7.2
-- 1.3.6.1.4.1.37950.1.1.5.10.7.3.7.2
-- 1.3.6.1.4.1.37950.1.1.5.10.7.3.7.2
-- 1.3.6.1.4.1.37950.1.1.5.10.7.3.7.2
-- 1.3.6.1.4.1.37950.1.1.5.10.7.3.7.2
-- 1.3.6.1.4.1.37950.1.1.5.10.7.3.7.2
-- 1.3.6.1.4.1.37950.1.1.5.10.7.3.7.2
-- 1.3.6.1.4.1.37950.1.1.5.10.7.3.7.2
-- 1.3.6.1.4.1.37950.1.1.5.10.7.3.7.2
		-- 1.3.6.1.4.1.37950.1.1.5.10.7.3.7.2
		snBindingTable OBJECT-TYPE
			SYNTAX SEQUENCE OF SnBindingEntry
			MAX-ACCESS not-accessible
			STATUS current
			DESCRIPTION
				"Description."
			::= { dhcpSNBinding 2 }

		
--          1.3.6.1.4.1.37950.1.1.5.10.7.3.7.2.1
-- 1.3.6.1.4.1.37950.1.1.5.10.7.3.7.2.1
-- 1.3.6.1.4.1.37950.1.1.5.10.7.3.7.2.1
-- 1.3.6.1.4.1.37950.1.1.5.10.7.3.7.2.1
-- 1.3.6.1.4.1.37950.1.1.5.10.7.3.7.2.1
-- 1.3.6.1.4.1.37950.1.1.5.10.7.3.7.2.1
-- 1.3.6.1.4.1.37950.1.1.5.10.7.3.7.2.1
-- 1.3.6.1.4.1.37950.1.1.5.10.7.3.7.2.1
-- 1.3.6.1.4.1.37950.1.1.5.10.7.3.7.2.1
		-- 1.3.6.1.4.1.37950.1.1.5.10.7.3.7.2.1
		snBindingEntry OBJECT-TYPE
			SYNTAX SnBindingEntry
			MAX-ACCESS not-accessible
			STATUS current
			DESCRIPTION
				"Description."
			INDEX { snBindingid }
			::= { snBindingTable 1 }

		
		SnBindingEntry ::=
			SEQUENCE { 
				snBindingid
					Integer32,
				snBindingMAC
					OCTET STRING,
				snBindingIP
					IpAddress,
				snBindingLease
					Integer32,
				snBindingType
					INTEGER,
				snBindingVlan
					Integer32,
				snBindingPortIndex
					Integer32
			 }

--          1.3.6.1.4.1.37950.1.1.5.10.7.3.7.2.1.1
-- 1.3.6.1.4.1.37950.1.1.5.10.7.3.7.2.1.1
-- 1.3.6.1.4.1.37950.1.1.5.10.7.3.7.2.1.1
-- 1.3.6.1.4.1.37950.1.1.5.10.7.3.7.2.1.1
-- 1.3.6.1.4.1.37950.1.1.5.10.7.3.7.2.1.1
-- 1.3.6.1.4.1.37950.1.1.5.10.7.3.7.2.1.1
-- 1.3.6.1.4.1.37950.1.1.5.10.7.3.7.2.1.1
-- 1.3.6.1.4.1.37950.1.1.5.10.7.3.7.2.1.1
-- 1.3.6.1.4.1.37950.1.1.5.10.7.3.7.2.1.1
		-- 1.3.6.1.4.1.37950.1.1.5.10.7.3.7.2.1.1
		snBindingid OBJECT-TYPE
			SYNTAX Integer32
			MAX-ACCESS read-only
			STATUS current
			DESCRIPTION
				"Description."
			::= { snBindingEntry 1 }

		
--          1.3.6.1.4.1.37950.1.1.5.10.7.3.7.2.1.2
-- 1.3.6.1.4.1.37950.1.1.5.10.7.3.7.2.1.2
-- 1.3.6.1.4.1.37950.1.1.5.10.7.3.7.2.1.2
-- 1.3.6.1.4.1.37950.1.1.5.10.7.3.7.2.1.2
-- 1.3.6.1.4.1.37950.1.1.5.10.7.3.7.2.1.2
-- 1.3.6.1.4.1.37950.1.1.5.10.7.3.7.2.1.2
-- 1.3.6.1.4.1.37950.1.1.5.10.7.3.7.2.1.2
-- 1.3.6.1.4.1.37950.1.1.5.10.7.3.7.2.1.2
-- 1.3.6.1.4.1.37950.1.1.5.10.7.3.7.2.1.2
		-- 1.3.6.1.4.1.37950.1.1.5.10.7.3.7.2.1.2
		snBindingMAC OBJECT-TYPE
			SYNTAX OCTET STRING
			MAX-ACCESS read-only
			STATUS current
			DESCRIPTION
				"Description."
			::= { snBindingEntry 2 }

		
--          1.3.6.1.4.1.37950.1.1.5.10.7.3.7.2.1.3
-- 1.3.6.1.4.1.37950.1.1.5.10.7.3.7.2.1.3
-- 1.3.6.1.4.1.37950.1.1.5.10.7.3.7.2.1.3
-- 1.3.6.1.4.1.37950.1.1.5.10.7.3.7.2.1.3
-- 1.3.6.1.4.1.37950.1.1.5.10.7.3.7.2.1.3
-- 1.3.6.1.4.1.37950.1.1.5.10.7.3.7.2.1.3
-- 1.3.6.1.4.1.37950.1.1.5.10.7.3.7.2.1.3
-- 1.3.6.1.4.1.37950.1.1.5.10.7.3.7.2.1.3
-- 1.3.6.1.4.1.37950.1.1.5.10.7.3.7.2.1.3
		-- 1.3.6.1.4.1.37950.1.1.5.10.7.3.7.2.1.3
		snBindingIP OBJECT-TYPE
			SYNTAX IpAddress
			MAX-ACCESS read-only
			STATUS current
			DESCRIPTION
				"Description."
			::= { snBindingEntry 3 }

		
--          1.3.6.1.4.1.37950.1.1.5.10.7.3.7.2.1.4
-- 1.3.6.1.4.1.37950.1.1.5.10.7.3.7.2.1.4
-- 1.3.6.1.4.1.37950.1.1.5.10.7.3.7.2.1.4
-- 1.3.6.1.4.1.37950.1.1.5.10.7.3.7.2.1.4
-- 1.3.6.1.4.1.37950.1.1.5.10.7.3.7.2.1.4
-- 1.3.6.1.4.1.37950.1.1.5.10.7.3.7.2.1.4
-- 1.3.6.1.4.1.37950.1.1.5.10.7.3.7.2.1.4
-- 1.3.6.1.4.1.37950.1.1.5.10.7.3.7.2.1.4
-- 1.3.6.1.4.1.37950.1.1.5.10.7.3.7.2.1.4
		-- 1.3.6.1.4.1.37950.1.1.5.10.7.3.7.2.1.4
		snBindingLease OBJECT-TYPE
			SYNTAX Integer32
			MAX-ACCESS read-only
			STATUS current
			DESCRIPTION
				"Description."
			::= { snBindingEntry 4 }

		
--          1.3.6.1.4.1.37950.1.1.5.10.7.3.7.2.1.5
-- 1.3.6.1.4.1.37950.1.1.5.10.7.3.7.2.1.5
-- 1.3.6.1.4.1.37950.1.1.5.10.7.3.7.2.1.5
-- 1.3.6.1.4.1.37950.1.1.5.10.7.3.7.2.1.5
-- 1.3.6.1.4.1.37950.1.1.5.10.7.3.7.2.1.5
-- 1.3.6.1.4.1.37950.1.1.5.10.7.3.7.2.1.5
-- 1.3.6.1.4.1.37950.1.1.5.10.7.3.7.2.1.5
-- 1.3.6.1.4.1.37950.1.1.5.10.7.3.7.2.1.5
-- 1.3.6.1.4.1.37950.1.1.5.10.7.3.7.2.1.5
		-- 1.3.6.1.4.1.37950.1.1.5.10.7.3.7.2.1.5
		snBindingType OBJECT-TYPE
			SYNTAX INTEGER
				{
				static(1),
				dynamic(2)
				}
			MAX-ACCESS read-only
			STATUS current
			DESCRIPTION
				"Description."
			::= { snBindingEntry 5 }

		
--          1.3.6.1.4.1.37950.1.1.5.10.7.3.7.2.1.6
-- 1.3.6.1.4.1.37950.1.1.5.10.7.3.7.2.1.6
-- 1.3.6.1.4.1.37950.1.1.5.10.7.3.7.2.1.6
-- 1.3.6.1.4.1.37950.1.1.5.10.7.3.7.2.1.6
-- 1.3.6.1.4.1.37950.1.1.5.10.7.3.7.2.1.6
-- 1.3.6.1.4.1.37950.1.1.5.10.7.3.7.2.1.6
-- 1.3.6.1.4.1.37950.1.1.5.10.7.3.7.2.1.6
-- 1.3.6.1.4.1.37950.1.1.5.10.7.3.7.2.1.6
-- 1.3.6.1.4.1.37950.1.1.5.10.7.3.7.2.1.6
		-- 1.3.6.1.4.1.37950.1.1.5.10.7.3.7.2.1.6
		snBindingVlan OBJECT-TYPE
			SYNTAX Integer32
			MAX-ACCESS read-only
			STATUS current
			DESCRIPTION
				"Description."
			::= { snBindingEntry 6 }

		
--          1.3.6.1.4.1.37950.1.1.5.10.7.3.7.2.1.7
-- 1.3.6.1.4.1.37950.1.1.5.10.7.3.7.2.1.7
-- 1.3.6.1.4.1.37950.1.1.5.10.7.3.7.2.1.7
-- 1.3.6.1.4.1.37950.1.1.5.10.7.3.7.2.1.7
-- 1.3.6.1.4.1.37950.1.1.5.10.7.3.7.2.1.7
-- 1.3.6.1.4.1.37950.1.1.5.10.7.3.7.2.1.7
-- 1.3.6.1.4.1.37950.1.1.5.10.7.3.7.2.1.7
-- 1.3.6.1.4.1.37950.1.1.5.10.7.3.7.2.1.7
-- 1.3.6.1.4.1.37950.1.1.5.10.7.3.7.2.1.7
		-- 1.3.6.1.4.1.37950.1.1.5.10.7.3.7.2.1.7
		snBindingPortIndex OBJECT-TYPE
			SYNTAX Integer32
			MAX-ACCESS read-only
			STATUS current
			DESCRIPTION
				"Description."
			::= { snBindingEntry 7 }

		
--          1.3.6.1.4.1.37950.1.1.5.10.7.3.7.3
-- 1.3.6.1.4.1.37950.1.1.5.10.7.3.7.3
-- 1.3.6.1.4.1.37950.1.1.5.10.7.3.7.3
-- 1.3.6.1.4.1.37950.1.1.5.10.7.3.7.3
-- 1.3.6.1.4.1.37950.1.1.5.10.7.3.7.3
-- 1.3.6.1.4.1.37950.1.1.5.10.7.3.7.3
-- 1.3.6.1.4.1.37950.1.1.5.10.7.3.7.3
-- 1.3.6.1.4.1.37950.1.1.5.10.7.3.7.3
-- 1.3.6.1.4.1.37950.1.1.5.10.7.3.7.3
		-- 1.3.6.1.4.1.37950.1.1.5.10.7.3.7.3
		snBindingDeleteTime OBJECT-TYPE
			SYNTAX Integer32 (1..3600)
			MAX-ACCESS read-write
			STATUS current
			DESCRIPTION
				"Description."
			::= { dhcpSNBinding 3 }

		
--          1.3.6.1.4.1.37950.1.1.5.10.8
-- 1.3.6.1.4.1.37950.1.1.5.10.8
-- 1.3.6.1.4.1.37950.1.1.5.10.8
-- 1.3.6.1.4.1.37950.1.1.5.10.8
-- 1.3.6.1.4.1.37950.1.1.5.10.8
-- 1.3.6.1.4.1.37950.1.1.5.10.8
-- 1.3.6.1.4.1.37950.1.1.5.10.8
-- 1.3.6.1.4.1.37950.1.1.5.10.8
-- 1.3.6.1.4.1.37950.1.1.5.10.8
		-- 1.3.6.1.4.1.37950.1.1.5.10.8
		v1600dStormControlCfg OBJECT IDENTIFIER ::= { v1600dSwitch 8 }

		
--          1.3.6.1.4.1.37950.1.1.5.10.8.1
-- 1.3.6.1.4.1.37950.1.1.5.10.8.1
-- 1.3.6.1.4.1.37950.1.1.5.10.8.1
-- 1.3.6.1.4.1.37950.1.1.5.10.8.1
-- 1.3.6.1.4.1.37950.1.1.5.10.8.1
-- 1.3.6.1.4.1.37950.1.1.5.10.8.1
-- 1.3.6.1.4.1.37950.1.1.5.10.8.1
-- 1.3.6.1.4.1.37950.1.1.5.10.8.1
-- 1.3.6.1.4.1.37950.1.1.5.10.8.1
		-- 1.3.6.1.4.1.37950.1.1.5.10.8.1
		stormCtrPid OBJECT-TYPE
			SYNTAX Integer32 (1..24)
			MAX-ACCESS read-write
			STATUS current
			DESCRIPTION
				"Description."
			::= { v1600dStormControlCfg 1 }

		
--          1.3.6.1.4.1.37950.1.1.5.10.8.2
-- 1.3.6.1.4.1.37950.1.1.5.10.8.2
-- 1.3.6.1.4.1.37950.1.1.5.10.8.2
-- 1.3.6.1.4.1.37950.1.1.5.10.8.2
-- 1.3.6.1.4.1.37950.1.1.5.10.8.2
-- 1.3.6.1.4.1.37950.1.1.5.10.8.2
-- 1.3.6.1.4.1.37950.1.1.5.10.8.2
-- 1.3.6.1.4.1.37950.1.1.5.10.8.2
-- 1.3.6.1.4.1.37950.1.1.5.10.8.2
		-- 1.3.6.1.4.1.37950.1.1.5.10.8.2
		broadcastStormCtrEn OBJECT-TYPE
			SYNTAX INTEGER
				{
				disable(0),
				enable(1)
				}
			MAX-ACCESS read-write
			STATUS current
			DESCRIPTION
				"Description."
			::= { v1600dStormControlCfg 2 }

		
--          1.3.6.1.4.1.37950.1.1.5.10.8.3
-- 1.3.6.1.4.1.37950.1.1.5.10.8.3
-- 1.3.6.1.4.1.37950.1.1.5.10.8.3
-- 1.3.6.1.4.1.37950.1.1.5.10.8.3
-- 1.3.6.1.4.1.37950.1.1.5.10.8.3
-- 1.3.6.1.4.1.37950.1.1.5.10.8.3
-- 1.3.6.1.4.1.37950.1.1.5.10.8.3
-- 1.3.6.1.4.1.37950.1.1.5.10.8.3
-- 1.3.6.1.4.1.37950.1.1.5.10.8.3
		-- 1.3.6.1.4.1.37950.1.1.5.10.8.3
		multicastStormCtrEn OBJECT-TYPE
			SYNTAX INTEGER
				{
				disable(0),
				enable(1)
				}
			MAX-ACCESS read-write
			STATUS current
			DESCRIPTION
				"Description."
			::= { v1600dStormControlCfg 3 }

		
--          1.3.6.1.4.1.37950.1.1.5.10.8.4
-- 1.3.6.1.4.1.37950.1.1.5.10.8.4
-- 1.3.6.1.4.1.37950.1.1.5.10.8.4
-- 1.3.6.1.4.1.37950.1.1.5.10.8.4
-- 1.3.6.1.4.1.37950.1.1.5.10.8.4
-- 1.3.6.1.4.1.37950.1.1.5.10.8.4
-- 1.3.6.1.4.1.37950.1.1.5.10.8.4
-- 1.3.6.1.4.1.37950.1.1.5.10.8.4
-- 1.3.6.1.4.1.37950.1.1.5.10.8.4
		-- 1.3.6.1.4.1.37950.1.1.5.10.8.4
		unknownStormCtrEn OBJECT-TYPE
			SYNTAX INTEGER
				{
				disable(0),
				enable(1)
				}
			MAX-ACCESS read-write
			STATUS current
			DESCRIPTION
				"Description."
			::= { v1600dStormControlCfg 4 }

		
--          1.3.6.1.4.1.37950.1.1.5.10.8.5
-- 1.3.6.1.4.1.37950.1.1.5.10.8.5
-- 1.3.6.1.4.1.37950.1.1.5.10.8.5
-- 1.3.6.1.4.1.37950.1.1.5.10.8.5
-- 1.3.6.1.4.1.37950.1.1.5.10.8.5
-- 1.3.6.1.4.1.37950.1.1.5.10.8.5
-- 1.3.6.1.4.1.37950.1.1.5.10.8.5
-- 1.3.6.1.4.1.37950.1.1.5.10.8.5
-- 1.3.6.1.4.1.37950.1.1.5.10.8.5
		-- 1.3.6.1.4.1.37950.1.1.5.10.8.5
		broadcastSpeed OBJECT-TYPE
			SYNTAX Integer32
			MAX-ACCESS read-write
			STATUS current
			DESCRIPTION
				"Description."
			::= { v1600dStormControlCfg 5 }

		
--          1.3.6.1.4.1.37950.1.1.5.10.8.6
-- 1.3.6.1.4.1.37950.1.1.5.10.8.6
-- 1.3.6.1.4.1.37950.1.1.5.10.8.6
-- 1.3.6.1.4.1.37950.1.1.5.10.8.6
-- 1.3.6.1.4.1.37950.1.1.5.10.8.6
-- 1.3.6.1.4.1.37950.1.1.5.10.8.6
-- 1.3.6.1.4.1.37950.1.1.5.10.8.6
-- 1.3.6.1.4.1.37950.1.1.5.10.8.6
-- 1.3.6.1.4.1.37950.1.1.5.10.8.6
		-- 1.3.6.1.4.1.37950.1.1.5.10.8.6
		multicastSpeed OBJECT-TYPE
			SYNTAX Integer32
			MAX-ACCESS read-write
			STATUS current
			DESCRIPTION
				"Description."
			::= { v1600dStormControlCfg 6 }

		
--          1.3.6.1.4.1.37950.1.1.5.10.8.7
-- 1.3.6.1.4.1.37950.1.1.5.10.8.7
-- 1.3.6.1.4.1.37950.1.1.5.10.8.7
-- 1.3.6.1.4.1.37950.1.1.5.10.8.7
-- 1.3.6.1.4.1.37950.1.1.5.10.8.7
-- 1.3.6.1.4.1.37950.1.1.5.10.8.7
-- 1.3.6.1.4.1.37950.1.1.5.10.8.7
-- 1.3.6.1.4.1.37950.1.1.5.10.8.7
-- 1.3.6.1.4.1.37950.1.1.5.10.8.7
		-- 1.3.6.1.4.1.37950.1.1.5.10.8.7
		unknownSpeed OBJECT-TYPE
			SYNTAX Integer32
			MAX-ACCESS read-write
			STATUS current
			DESCRIPTION
				"Description."
			::= { v1600dStormControlCfg 7 }

		
--          1.3.6.1.4.1.37950.1.1.5.10.8.8
-- 1.3.6.1.4.1.37950.1.1.5.10.8.8
-- 1.3.6.1.4.1.37950.1.1.5.10.8.8
-- 1.3.6.1.4.1.37950.1.1.5.10.8.8
-- 1.3.6.1.4.1.37950.1.1.5.10.8.8
-- 1.3.6.1.4.1.37950.1.1.5.10.8.8
-- 1.3.6.1.4.1.37950.1.1.5.10.8.8
-- 1.3.6.1.4.1.37950.1.1.5.10.8.8
-- 1.3.6.1.4.1.37950.1.1.5.10.8.8
		-- 1.3.6.1.4.1.37950.1.1.5.10.8.8
		stormCtrAction OBJECT-TYPE
			SYNTAX INTEGER { commit(1) }
			MAX-ACCESS read-write
			STATUS current
			DESCRIPTION
				"Description."
			::= { v1600dStormControlCfg 8 }

		
--          1.3.6.1.4.1.37950.1.1.5.10.9
-- 1.3.6.1.4.1.37950.1.1.5.10.9
-- 1.3.6.1.4.1.37950.1.1.5.10.9
-- 1.3.6.1.4.1.37950.1.1.5.10.9
-- 1.3.6.1.4.1.37950.1.1.5.10.9
-- 1.3.6.1.4.1.37950.1.1.5.10.9
-- 1.3.6.1.4.1.37950.1.1.5.10.9
-- 1.3.6.1.4.1.37950.1.1.5.10.9
-- 1.3.6.1.4.1.37950.1.1.5.10.9
		-- 1.3.6.1.4.1.37950.1.1.5.10.9
		v1600dRstp OBJECT IDENTIFIER ::= { v1600dSwitch 9 }

		
--          1.3.6.1.4.1.37950.1.1.5.10.9.1
-- 1.3.6.1.4.1.37950.1.1.5.10.9.1
-- 1.3.6.1.4.1.37950.1.1.5.10.9.1
-- 1.3.6.1.4.1.37950.1.1.5.10.9.1
-- 1.3.6.1.4.1.37950.1.1.5.10.9.1
-- 1.3.6.1.4.1.37950.1.1.5.10.9.1
-- 1.3.6.1.4.1.37950.1.1.5.10.9.1
-- 1.3.6.1.4.1.37950.1.1.5.10.9.1
-- 1.3.6.1.4.1.37950.1.1.5.10.9.1
		-- 1.3.6.1.4.1.37950.1.1.5.10.9.1
		rstpEn OBJECT-TYPE
			SYNTAX INTEGER
				{
				disable(0),
				enable(1)
				}
			MAX-ACCESS read-write
			STATUS current
			DESCRIPTION
				"Description."
			::= { v1600dRstp 1 }

		
--          1.3.6.1.4.1.37950.1.1.5.10.9.2
-- 1.3.6.1.4.1.37950.1.1.5.10.9.2
-- 1.3.6.1.4.1.37950.1.1.5.10.9.2
-- 1.3.6.1.4.1.37950.1.1.5.10.9.2
-- 1.3.6.1.4.1.37950.1.1.5.10.9.2
-- 1.3.6.1.4.1.37950.1.1.5.10.9.2
-- 1.3.6.1.4.1.37950.1.1.5.10.9.2
-- 1.3.6.1.4.1.37950.1.1.5.10.9.2
-- 1.3.6.1.4.1.37950.1.1.5.10.9.2
		-- 1.3.6.1.4.1.37950.1.1.5.10.9.2
		rstpCfg OBJECT IDENTIFIER ::= { v1600dRstp 2 }

		
--          1.3.6.1.4.1.37950.1.1.5.10.9.2.1
-- 1.3.6.1.4.1.37950.1.1.5.10.9.2.1
-- 1.3.6.1.4.1.37950.1.1.5.10.9.2.1
-- 1.3.6.1.4.1.37950.1.1.5.10.9.2.1
-- 1.3.6.1.4.1.37950.1.1.5.10.9.2.1
-- 1.3.6.1.4.1.37950.1.1.5.10.9.2.1
-- 1.3.6.1.4.1.37950.1.1.5.10.9.2.1
-- 1.3.6.1.4.1.37950.1.1.5.10.9.2.1
-- 1.3.6.1.4.1.37950.1.1.5.10.9.2.1
		-- 1.3.6.1.4.1.37950.1.1.5.10.9.2.1
		maxAge OBJECT-TYPE
			SYNTAX Integer32 (6..40)
			MAX-ACCESS read-write
			STATUS current
			DESCRIPTION
				"Description."
			::= { rstpCfg 1 }

		
--          1.3.6.1.4.1.37950.1.1.5.10.9.2.2
-- 1.3.6.1.4.1.37950.1.1.5.10.9.2.2
-- 1.3.6.1.4.1.37950.1.1.5.10.9.2.2
-- 1.3.6.1.4.1.37950.1.1.5.10.9.2.2
-- 1.3.6.1.4.1.37950.1.1.5.10.9.2.2
-- 1.3.6.1.4.1.37950.1.1.5.10.9.2.2
-- 1.3.6.1.4.1.37950.1.1.5.10.9.2.2
-- 1.3.6.1.4.1.37950.1.1.5.10.9.2.2
-- 1.3.6.1.4.1.37950.1.1.5.10.9.2.2
		-- 1.3.6.1.4.1.37950.1.1.5.10.9.2.2
		bridgePriority OBJECT-TYPE
			SYNTAX Integer32 (0..65535)
			MAX-ACCESS read-write
			STATUS current
			DESCRIPTION
				"Description."
			::= { rstpCfg 2 }

		
--          1.3.6.1.4.1.37950.1.1.5.10.9.2.3
-- 1.3.6.1.4.1.37950.1.1.5.10.9.2.3
-- 1.3.6.1.4.1.37950.1.1.5.10.9.2.3
-- 1.3.6.1.4.1.37950.1.1.5.10.9.2.3
-- 1.3.6.1.4.1.37950.1.1.5.10.9.2.3
-- 1.3.6.1.4.1.37950.1.1.5.10.9.2.3
-- 1.3.6.1.4.1.37950.1.1.5.10.9.2.3
-- 1.3.6.1.4.1.37950.1.1.5.10.9.2.3
-- 1.3.6.1.4.1.37950.1.1.5.10.9.2.3
		-- 1.3.6.1.4.1.37950.1.1.5.10.9.2.3
		bridgeMac OBJECT-TYPE
			SYNTAX OCTET STRING
			MAX-ACCESS read-only
			STATUS current
			DESCRIPTION
				"Description."
			::= { rstpCfg 3 }

		
--          1.3.6.1.4.1.37950.1.1.5.10.9.2.4
-- 1.3.6.1.4.1.37950.1.1.5.10.9.2.4
-- 1.3.6.1.4.1.37950.1.1.5.10.9.2.4
-- 1.3.6.1.4.1.37950.1.1.5.10.9.2.4
-- 1.3.6.1.4.1.37950.1.1.5.10.9.2.4
-- 1.3.6.1.4.1.37950.1.1.5.10.9.2.4
-- 1.3.6.1.4.1.37950.1.1.5.10.9.2.4
-- 1.3.6.1.4.1.37950.1.1.5.10.9.2.4
-- 1.3.6.1.4.1.37950.1.1.5.10.9.2.4
		-- 1.3.6.1.4.1.37950.1.1.5.10.9.2.4
		helloTime OBJECT-TYPE
			SYNTAX Integer32 (1..10)
			MAX-ACCESS read-write
			STATUS current
			DESCRIPTION
				"Description."
			::= { rstpCfg 4 }

		
--          1.3.6.1.4.1.37950.1.1.5.10.9.2.5
-- 1.3.6.1.4.1.37950.1.1.5.10.9.2.5
-- 1.3.6.1.4.1.37950.1.1.5.10.9.2.5
-- 1.3.6.1.4.1.37950.1.1.5.10.9.2.5
-- 1.3.6.1.4.1.37950.1.1.5.10.9.2.5
-- 1.3.6.1.4.1.37950.1.1.5.10.9.2.5
-- 1.3.6.1.4.1.37950.1.1.5.10.9.2.5
-- 1.3.6.1.4.1.37950.1.1.5.10.9.2.5
-- 1.3.6.1.4.1.37950.1.1.5.10.9.2.5
		-- 1.3.6.1.4.1.37950.1.1.5.10.9.2.5
		forwardDelay OBJECT-TYPE
			SYNTAX Integer32 (4..30)
			MAX-ACCESS read-write
			STATUS current
			DESCRIPTION
				"Description."
			::= { rstpCfg 5 }

		
--          1.3.6.1.4.1.37950.1.1.5.10.9.3
-- 1.3.6.1.4.1.37950.1.1.5.10.9.3
-- 1.3.6.1.4.1.37950.1.1.5.10.9.3
-- 1.3.6.1.4.1.37950.1.1.5.10.9.3
-- 1.3.6.1.4.1.37950.1.1.5.10.9.3
-- 1.3.6.1.4.1.37950.1.1.5.10.9.3
-- 1.3.6.1.4.1.37950.1.1.5.10.9.3
-- 1.3.6.1.4.1.37950.1.1.5.10.9.3
-- 1.3.6.1.4.1.37950.1.1.5.10.9.3
		-- 1.3.6.1.4.1.37950.1.1.5.10.9.3
		rstpPortCfgTable OBJECT-TYPE
			SYNTAX SEQUENCE OF RstpPortCfgEntry
			MAX-ACCESS not-accessible
			STATUS current
			DESCRIPTION
				"Description."
			::= { v1600dRstp 3 }

		
--          1.3.6.1.4.1.37950.1.1.5.10.9.3.1
-- 1.3.6.1.4.1.37950.1.1.5.10.9.3.1
-- 1.3.6.1.4.1.37950.1.1.5.10.9.3.1
-- 1.3.6.1.4.1.37950.1.1.5.10.9.3.1
-- 1.3.6.1.4.1.37950.1.1.5.10.9.3.1
-- 1.3.6.1.4.1.37950.1.1.5.10.9.3.1
-- 1.3.6.1.4.1.37950.1.1.5.10.9.3.1
-- 1.3.6.1.4.1.37950.1.1.5.10.9.3.1
-- 1.3.6.1.4.1.37950.1.1.5.10.9.3.1
		-- 1.3.6.1.4.1.37950.1.1.5.10.9.3.1
		rstpPortCfgEntry OBJECT-TYPE
			SYNTAX RstpPortCfgEntry
			MAX-ACCESS not-accessible
			STATUS current
			DESCRIPTION
				"Description."
			INDEX { rstpPortId }
			::= { rstpPortCfgTable 1 }

		
		RstpPortCfgEntry ::=
			SEQUENCE { 
				rstpPortId
					Integer32,
				rstpPortAdminStatus
					INTEGER,
				rstpPortPrioritySet
					Integer32,
				rstpPortCostSet
					Unsigned32,
				rstpPortOperEdgeSet
					INTEGER,
				rstpPortP2PSet
					INTEGER
			 }

--          1.3.6.1.4.1.37950.1.1.5.10.9.3.1.1
-- 1.3.6.1.4.1.37950.1.1.5.10.9.3.1.1
-- 1.3.6.1.4.1.37950.1.1.5.10.9.3.1.1
-- 1.3.6.1.4.1.37950.1.1.5.10.9.3.1.1
-- 1.3.6.1.4.1.37950.1.1.5.10.9.3.1.1
-- 1.3.6.1.4.1.37950.1.1.5.10.9.3.1.1
-- 1.3.6.1.4.1.37950.1.1.5.10.9.3.1.1
-- 1.3.6.1.4.1.37950.1.1.5.10.9.3.1.1
-- 1.3.6.1.4.1.37950.1.1.5.10.9.3.1.1
		-- 1.3.6.1.4.1.37950.1.1.5.10.9.3.1.1
		rstpPortId OBJECT-TYPE
			SYNTAX Integer32 (1..16)
			MAX-ACCESS read-write
			STATUS current
			DESCRIPTION
				"Description."
			::= { rstpPortCfgEntry 1 }

		
--          1.3.6.1.4.1.37950.1.1.5.10.9.3.1.2
-- 1.3.6.1.4.1.37950.1.1.5.10.9.3.1.2
-- 1.3.6.1.4.1.37950.1.1.5.10.9.3.1.2
-- 1.3.6.1.4.1.37950.1.1.5.10.9.3.1.2
-- 1.3.6.1.4.1.37950.1.1.5.10.9.3.1.2
-- 1.3.6.1.4.1.37950.1.1.5.10.9.3.1.2
-- 1.3.6.1.4.1.37950.1.1.5.10.9.3.1.2
-- 1.3.6.1.4.1.37950.1.1.5.10.9.3.1.2
-- 1.3.6.1.4.1.37950.1.1.5.10.9.3.1.2
		-- 1.3.6.1.4.1.37950.1.1.5.10.9.3.1.2
		rstpPortAdminStatus OBJECT-TYPE
			SYNTAX INTEGER
				{
				disable(0),
				enable(1)
				}
			MAX-ACCESS read-write
			STATUS current
			DESCRIPTION
				"Description."
			::= { rstpPortCfgEntry 2 }

		
--          1.3.6.1.4.1.37950.1.1.5.10.9.3.1.3
-- 1.3.6.1.4.1.37950.1.1.5.10.9.3.1.3
-- 1.3.6.1.4.1.37950.1.1.5.10.9.3.1.3
-- 1.3.6.1.4.1.37950.1.1.5.10.9.3.1.3
-- 1.3.6.1.4.1.37950.1.1.5.10.9.3.1.3
-- 1.3.6.1.4.1.37950.1.1.5.10.9.3.1.3
-- 1.3.6.1.4.1.37950.1.1.5.10.9.3.1.3
-- 1.3.6.1.4.1.37950.1.1.5.10.9.3.1.3
-- 1.3.6.1.4.1.37950.1.1.5.10.9.3.1.3
		-- 1.3.6.1.4.1.37950.1.1.5.10.9.3.1.3
		rstpPortPrioritySet OBJECT-TYPE
			SYNTAX Integer32 (0..255)
			MAX-ACCESS read-write
			STATUS current
			DESCRIPTION
				"Description."
			::= { rstpPortCfgEntry 3 }

		
--          1.3.6.1.4.1.37950.1.1.5.10.9.3.1.4
-- 1.3.6.1.4.1.37950.1.1.5.10.9.3.1.4
-- 1.3.6.1.4.1.37950.1.1.5.10.9.3.1.4
-- 1.3.6.1.4.1.37950.1.1.5.10.9.3.1.4
-- 1.3.6.1.4.1.37950.1.1.5.10.9.3.1.4
-- 1.3.6.1.4.1.37950.1.1.5.10.9.3.1.4
-- 1.3.6.1.4.1.37950.1.1.5.10.9.3.1.4
-- 1.3.6.1.4.1.37950.1.1.5.10.9.3.1.4
-- 1.3.6.1.4.1.37950.1.1.5.10.9.3.1.4
		-- 1.3.6.1.4.1.37950.1.1.5.10.9.3.1.4
		rstpPortCostSet OBJECT-TYPE
			SYNTAX Unsigned32 (1..200000000)
			MAX-ACCESS read-write
			STATUS current
			DESCRIPTION
				"Description."
			::= { rstpPortCfgEntry 4 }

		
--          1.3.6.1.4.1.37950.1.1.5.10.9.3.1.5
-- 1.3.6.1.4.1.37950.1.1.5.10.9.3.1.5
-- 1.3.6.1.4.1.37950.1.1.5.10.9.3.1.5
-- 1.3.6.1.4.1.37950.1.1.5.10.9.3.1.5
-- 1.3.6.1.4.1.37950.1.1.5.10.9.3.1.5
-- 1.3.6.1.4.1.37950.1.1.5.10.9.3.1.5
-- 1.3.6.1.4.1.37950.1.1.5.10.9.3.1.5
-- 1.3.6.1.4.1.37950.1.1.5.10.9.3.1.5
-- 1.3.6.1.4.1.37950.1.1.5.10.9.3.1.5
		-- 1.3.6.1.4.1.37950.1.1.5.10.9.3.1.5
		rstpPortOperEdgeSet OBJECT-TYPE
			SYNTAX INTEGER
				{
				disable(0),
				enable(1)
				}
			MAX-ACCESS read-write
			STATUS current
			DESCRIPTION
				"Description."
			::= { rstpPortCfgEntry 5 }

		
--          1.3.6.1.4.1.37950.1.1.5.10.9.3.1.6
-- 1.3.6.1.4.1.37950.1.1.5.10.9.3.1.6
-- 1.3.6.1.4.1.37950.1.1.5.10.9.3.1.6
-- 1.3.6.1.4.1.37950.1.1.5.10.9.3.1.6
-- 1.3.6.1.4.1.37950.1.1.5.10.9.3.1.6
-- 1.3.6.1.4.1.37950.1.1.5.10.9.3.1.6
-- 1.3.6.1.4.1.37950.1.1.5.10.9.3.1.6
-- 1.3.6.1.4.1.37950.1.1.5.10.9.3.1.6
-- 1.3.6.1.4.1.37950.1.1.5.10.9.3.1.6
		-- 1.3.6.1.4.1.37950.1.1.5.10.9.3.1.6
		rstpPortP2PSet OBJECT-TYPE
			SYNTAX INTEGER
				{
				disable(0),
				enable(1)
				}
			MAX-ACCESS read-write
			STATUS current
			DESCRIPTION
				"Description."
			::= { rstpPortCfgEntry 6 }

		
--          1.3.6.1.4.1.37950.1.1.5.10.9.4
-- 1.3.6.1.4.1.37950.1.1.5.10.9.4
-- 1.3.6.1.4.1.37950.1.1.5.10.9.4
-- 1.3.6.1.4.1.37950.1.1.5.10.9.4
-- 1.3.6.1.4.1.37950.1.1.5.10.9.4
-- 1.3.6.1.4.1.37950.1.1.5.10.9.4
-- 1.3.6.1.4.1.37950.1.1.5.10.9.4
-- 1.3.6.1.4.1.37950.1.1.5.10.9.4
-- 1.3.6.1.4.1.37950.1.1.5.10.9.4
		-- 1.3.6.1.4.1.37950.1.1.5.10.9.4
		rstpInfo OBJECT IDENTIFIER ::= { v1600dRstp 4 }

		
--          1.3.6.1.4.1.37950.1.1.5.10.9.4.1
-- 1.3.6.1.4.1.37950.1.1.5.10.9.4.1
-- 1.3.6.1.4.1.37950.1.1.5.10.9.4.1
-- 1.3.6.1.4.1.37950.1.1.5.10.9.4.1
-- 1.3.6.1.4.1.37950.1.1.5.10.9.4.1
-- 1.3.6.1.4.1.37950.1.1.5.10.9.4.1
-- 1.3.6.1.4.1.37950.1.1.5.10.9.4.1
-- 1.3.6.1.4.1.37950.1.1.5.10.9.4.1
-- 1.3.6.1.4.1.37950.1.1.5.10.9.4.1
		-- 1.3.6.1.4.1.37950.1.1.5.10.9.4.1
		rstpRootBridgeInfo OBJECT IDENTIFIER ::= { rstpInfo 1 }

		
--          1.3.6.1.4.1.37950.1.1.5.10.9.4.1.1
-- 1.3.6.1.4.1.37950.1.1.5.10.9.4.1.1
-- 1.3.6.1.4.1.37950.1.1.5.10.9.4.1.1
-- 1.3.6.1.4.1.37950.1.1.5.10.9.4.1.1
-- 1.3.6.1.4.1.37950.1.1.5.10.9.4.1.1
-- 1.3.6.1.4.1.37950.1.1.5.10.9.4.1.1
-- 1.3.6.1.4.1.37950.1.1.5.10.9.4.1.1
-- 1.3.6.1.4.1.37950.1.1.5.10.9.4.1.1
-- 1.3.6.1.4.1.37950.1.1.5.10.9.4.1.1
		-- 1.3.6.1.4.1.37950.1.1.5.10.9.4.1.1
		pathCostToRootBridge OBJECT-TYPE
			SYNTAX Unsigned32
			MAX-ACCESS read-only
			STATUS current
			DESCRIPTION
				"Description."
			::= { rstpRootBridgeInfo 1 }

		
--          1.3.6.1.4.1.37950.1.1.5.10.9.4.1.2
-- 1.3.6.1.4.1.37950.1.1.5.10.9.4.1.2
-- 1.3.6.1.4.1.37950.1.1.5.10.9.4.1.2
-- 1.3.6.1.4.1.37950.1.1.5.10.9.4.1.2
-- 1.3.6.1.4.1.37950.1.1.5.10.9.4.1.2
-- 1.3.6.1.4.1.37950.1.1.5.10.9.4.1.2
-- 1.3.6.1.4.1.37950.1.1.5.10.9.4.1.2
-- 1.3.6.1.4.1.37950.1.1.5.10.9.4.1.2
-- 1.3.6.1.4.1.37950.1.1.5.10.9.4.1.2
		-- 1.3.6.1.4.1.37950.1.1.5.10.9.4.1.2
		rootPort OBJECT-TYPE
			SYNTAX Integer32
			MAX-ACCESS read-only
			STATUS current
			DESCRIPTION
				"Description."
			::= { rstpRootBridgeInfo 2 }

		
--          1.3.6.1.4.1.37950.1.1.5.10.9.4.1.3
-- 1.3.6.1.4.1.37950.1.1.5.10.9.4.1.3
-- 1.3.6.1.4.1.37950.1.1.5.10.9.4.1.3
-- 1.3.6.1.4.1.37950.1.1.5.10.9.4.1.3
-- 1.3.6.1.4.1.37950.1.1.5.10.9.4.1.3
-- 1.3.6.1.4.1.37950.1.1.5.10.9.4.1.3
-- 1.3.6.1.4.1.37950.1.1.5.10.9.4.1.3
-- 1.3.6.1.4.1.37950.1.1.5.10.9.4.1.3
-- 1.3.6.1.4.1.37950.1.1.5.10.9.4.1.3
		-- 1.3.6.1.4.1.37950.1.1.5.10.9.4.1.3
		rootBridgePriority OBJECT-TYPE
			SYNTAX Integer32
			MAX-ACCESS read-only
			STATUS current
			DESCRIPTION
				"Description."
			::= { rstpRootBridgeInfo 3 }

		
--          1.3.6.1.4.1.37950.1.1.5.10.9.4.1.4
-- 1.3.6.1.4.1.37950.1.1.5.10.9.4.1.4
-- 1.3.6.1.4.1.37950.1.1.5.10.9.4.1.4
-- 1.3.6.1.4.1.37950.1.1.5.10.9.4.1.4
-- 1.3.6.1.4.1.37950.1.1.5.10.9.4.1.4
-- 1.3.6.1.4.1.37950.1.1.5.10.9.4.1.4
-- 1.3.6.1.4.1.37950.1.1.5.10.9.4.1.4
-- 1.3.6.1.4.1.37950.1.1.5.10.9.4.1.4
-- 1.3.6.1.4.1.37950.1.1.5.10.9.4.1.4
		-- 1.3.6.1.4.1.37950.1.1.5.10.9.4.1.4
		rootBridgeMac OBJECT-TYPE
			SYNTAX OCTET STRING
			MAX-ACCESS read-only
			STATUS current
			DESCRIPTION
				"Description."
			::= { rstpRootBridgeInfo 4 }

		
--          1.3.6.1.4.1.37950.1.1.5.10.9.4.1.5
-- 1.3.6.1.4.1.37950.1.1.5.10.9.4.1.5
-- 1.3.6.1.4.1.37950.1.1.5.10.9.4.1.5
-- 1.3.6.1.4.1.37950.1.1.5.10.9.4.1.5
-- 1.3.6.1.4.1.37950.1.1.5.10.9.4.1.5
-- 1.3.6.1.4.1.37950.1.1.5.10.9.4.1.5
-- 1.3.6.1.4.1.37950.1.1.5.10.9.4.1.5
-- 1.3.6.1.4.1.37950.1.1.5.10.9.4.1.5
-- 1.3.6.1.4.1.37950.1.1.5.10.9.4.1.5
		-- 1.3.6.1.4.1.37950.1.1.5.10.9.4.1.5
		rootBridgeHelloTime OBJECT-TYPE
			SYNTAX Integer32
			MAX-ACCESS read-only
			STATUS current
			DESCRIPTION
				"Description."
			::= { rstpRootBridgeInfo 5 }

		
--          1.3.6.1.4.1.37950.1.1.5.10.9.4.1.6
-- 1.3.6.1.4.1.37950.1.1.5.10.9.4.1.6
-- 1.3.6.1.4.1.37950.1.1.5.10.9.4.1.6
-- 1.3.6.1.4.1.37950.1.1.5.10.9.4.1.6
-- 1.3.6.1.4.1.37950.1.1.5.10.9.4.1.6
-- 1.3.6.1.4.1.37950.1.1.5.10.9.4.1.6
-- 1.3.6.1.4.1.37950.1.1.5.10.9.4.1.6
-- 1.3.6.1.4.1.37950.1.1.5.10.9.4.1.6
-- 1.3.6.1.4.1.37950.1.1.5.10.9.4.1.6
		-- 1.3.6.1.4.1.37950.1.1.5.10.9.4.1.6
		rootBridgeMaxAge OBJECT-TYPE
			SYNTAX Integer32
			MAX-ACCESS read-only
			STATUS current
			DESCRIPTION
				"Description."
			::= { rstpRootBridgeInfo 6 }

		
--          1.3.6.1.4.1.37950.1.1.5.10.9.4.1.7
-- 1.3.6.1.4.1.37950.1.1.5.10.9.4.1.7
-- 1.3.6.1.4.1.37950.1.1.5.10.9.4.1.7
-- 1.3.6.1.4.1.37950.1.1.5.10.9.4.1.7
-- 1.3.6.1.4.1.37950.1.1.5.10.9.4.1.7
-- 1.3.6.1.4.1.37950.1.1.5.10.9.4.1.7
-- 1.3.6.1.4.1.37950.1.1.5.10.9.4.1.7
-- 1.3.6.1.4.1.37950.1.1.5.10.9.4.1.7
-- 1.3.6.1.4.1.37950.1.1.5.10.9.4.1.7
		-- 1.3.6.1.4.1.37950.1.1.5.10.9.4.1.7
		rootBridgeForwardDelay OBJECT-TYPE
			SYNTAX Integer32
			MAX-ACCESS read-only
			STATUS current
			DESCRIPTION
				"Description."
			::= { rstpRootBridgeInfo 7 }

		
--          1.3.6.1.4.1.37950.1.1.5.10.9.4.2
-- 1.3.6.1.4.1.37950.1.1.5.10.9.4.2
-- 1.3.6.1.4.1.37950.1.1.5.10.9.4.2
-- 1.3.6.1.4.1.37950.1.1.5.10.9.4.2
-- 1.3.6.1.4.1.37950.1.1.5.10.9.4.2
-- 1.3.6.1.4.1.37950.1.1.5.10.9.4.2
-- 1.3.6.1.4.1.37950.1.1.5.10.9.4.2
-- 1.3.6.1.4.1.37950.1.1.5.10.9.4.2
-- 1.3.6.1.4.1.37950.1.1.5.10.9.4.2
		-- 1.3.6.1.4.1.37950.1.1.5.10.9.4.2
		rstpPortStatusTable OBJECT-TYPE
			SYNTAX SEQUENCE OF RstpPortStatusEntry
			MAX-ACCESS not-accessible
			STATUS current
			DESCRIPTION
				"Description."
			::= { rstpInfo 2 }

		
--          1.3.6.1.4.1.37950.1.1.5.10.9.4.2.1
-- 1.3.6.1.4.1.37950.1.1.5.10.9.4.2.1
-- 1.3.6.1.4.1.37950.1.1.5.10.9.4.2.1
-- 1.3.6.1.4.1.37950.1.1.5.10.9.4.2.1
-- 1.3.6.1.4.1.37950.1.1.5.10.9.4.2.1
-- 1.3.6.1.4.1.37950.1.1.5.10.9.4.2.1
-- 1.3.6.1.4.1.37950.1.1.5.10.9.4.2.1
-- 1.3.6.1.4.1.37950.1.1.5.10.9.4.2.1
-- 1.3.6.1.4.1.37950.1.1.5.10.9.4.2.1
		-- 1.3.6.1.4.1.37950.1.1.5.10.9.4.2.1
		rstpPortStatusEntry OBJECT-TYPE
			SYNTAX RstpPortStatusEntry
			MAX-ACCESS not-accessible
			STATUS current
			DESCRIPTION
				"Description."
			INDEX { rstpPortIndex }
			::= { rstpPortStatusTable 1 }

		
		RstpPortStatusEntry ::=
			SEQUENCE { 
				rstpPortIndex
					Integer32,
				rstpPortRole
					INTEGER,
				rstpPortStatus
					INTEGER,
				rstpPortCost
					Integer32,
				rstpPortPriority
					Integer32,
				rstpPortP2P
					INTEGER
			 }

--          1.3.6.1.4.1.37950.1.1.5.10.9.4.2.1.1
-- 1.3.6.1.4.1.37950.1.1.5.10.9.4.2.1.1
-- 1.3.6.1.4.1.37950.1.1.5.10.9.4.2.1.1
-- 1.3.6.1.4.1.37950.1.1.5.10.9.4.2.1.1
-- 1.3.6.1.4.1.37950.1.1.5.10.9.4.2.1.1
-- 1.3.6.1.4.1.37950.1.1.5.10.9.4.2.1.1
-- 1.3.6.1.4.1.37950.1.1.5.10.9.4.2.1.1
-- 1.3.6.1.4.1.37950.1.1.5.10.9.4.2.1.1
-- 1.3.6.1.4.1.37950.1.1.5.10.9.4.2.1.1
		-- 1.3.6.1.4.1.37950.1.1.5.10.9.4.2.1.1
		rstpPortIndex OBJECT-TYPE
			SYNTAX Integer32 (1..24)
			MAX-ACCESS read-only
			STATUS current
			DESCRIPTION
				"Description."
			::= { rstpPortStatusEntry 1 }

		
--          1.3.6.1.4.1.37950.1.1.5.10.9.4.2.1.2
-- 1.3.6.1.4.1.37950.1.1.5.10.9.4.2.1.2
-- 1.3.6.1.4.1.37950.1.1.5.10.9.4.2.1.2
-- 1.3.6.1.4.1.37950.1.1.5.10.9.4.2.1.2
-- 1.3.6.1.4.1.37950.1.1.5.10.9.4.2.1.2
-- 1.3.6.1.4.1.37950.1.1.5.10.9.4.2.1.2
-- 1.3.6.1.4.1.37950.1.1.5.10.9.4.2.1.2
-- 1.3.6.1.4.1.37950.1.1.5.10.9.4.2.1.2
-- 1.3.6.1.4.1.37950.1.1.5.10.9.4.2.1.2
		-- 1.3.6.1.4.1.37950.1.1.5.10.9.4.2.1.2
		rstpPortRole OBJECT-TYPE
			SYNTAX INTEGER
				{
				root(1),
				backup(2),
				design(3),
				alternat(4),
				disable(5),
				unkown(6)
				}
			MAX-ACCESS read-only
			STATUS current
			DESCRIPTION
				"Description."
			::= { rstpPortStatusEntry 2 }

		
--          1.3.6.1.4.1.37950.1.1.5.10.9.4.2.1.3
-- 1.3.6.1.4.1.37950.1.1.5.10.9.4.2.1.3
-- 1.3.6.1.4.1.37950.1.1.5.10.9.4.2.1.3
-- 1.3.6.1.4.1.37950.1.1.5.10.9.4.2.1.3
-- 1.3.6.1.4.1.37950.1.1.5.10.9.4.2.1.3
-- 1.3.6.1.4.1.37950.1.1.5.10.9.4.2.1.3
-- 1.3.6.1.4.1.37950.1.1.5.10.9.4.2.1.3
-- 1.3.6.1.4.1.37950.1.1.5.10.9.4.2.1.3
-- 1.3.6.1.4.1.37950.1.1.5.10.9.4.2.1.3
		-- 1.3.6.1.4.1.37950.1.1.5.10.9.4.2.1.3
		rstpPortStatus OBJECT-TYPE
			SYNTAX INTEGER
				{
				disable(0),
				discarding(1),
				learning(2),
				forwarding(3),
				unkown(4)
				}
			MAX-ACCESS read-only
			STATUS current
			DESCRIPTION
				"Description."
			::= { rstpPortStatusEntry 3 }

		
--          1.3.6.1.4.1.37950.1.1.5.10.9.4.2.1.4
-- 1.3.6.1.4.1.37950.1.1.5.10.9.4.2.1.4
-- 1.3.6.1.4.1.37950.1.1.5.10.9.4.2.1.4
-- 1.3.6.1.4.1.37950.1.1.5.10.9.4.2.1.4
-- 1.3.6.1.4.1.37950.1.1.5.10.9.4.2.1.4
-- 1.3.6.1.4.1.37950.1.1.5.10.9.4.2.1.4
-- 1.3.6.1.4.1.37950.1.1.5.10.9.4.2.1.4
-- 1.3.6.1.4.1.37950.1.1.5.10.9.4.2.1.4
-- 1.3.6.1.4.1.37950.1.1.5.10.9.4.2.1.4
		-- 1.3.6.1.4.1.37950.1.1.5.10.9.4.2.1.4
		rstpPortCost OBJECT-TYPE
			SYNTAX Integer32
			MAX-ACCESS read-only
			STATUS current
			DESCRIPTION
				"Description."
			::= { rstpPortStatusEntry 4 }

		
--          1.3.6.1.4.1.37950.1.1.5.10.9.4.2.1.5
-- 1.3.6.1.4.1.37950.1.1.5.10.9.4.2.1.5
-- 1.3.6.1.4.1.37950.1.1.5.10.9.4.2.1.5
-- 1.3.6.1.4.1.37950.1.1.5.10.9.4.2.1.5
-- 1.3.6.1.4.1.37950.1.1.5.10.9.4.2.1.5
-- 1.3.6.1.4.1.37950.1.1.5.10.9.4.2.1.5
-- 1.3.6.1.4.1.37950.1.1.5.10.9.4.2.1.5
-- 1.3.6.1.4.1.37950.1.1.5.10.9.4.2.1.5
-- 1.3.6.1.4.1.37950.1.1.5.10.9.4.2.1.5
		-- 1.3.6.1.4.1.37950.1.1.5.10.9.4.2.1.5
		rstpPortPriority OBJECT-TYPE
			SYNTAX Integer32
			MAX-ACCESS read-only
			STATUS current
			DESCRIPTION
				"Description."
			::= { rstpPortStatusEntry 5 }

		
--          1.3.6.1.4.1.37950.1.1.5.10.9.4.2.1.6
-- 1.3.6.1.4.1.37950.1.1.5.10.9.4.2.1.6
-- 1.3.6.1.4.1.37950.1.1.5.10.9.4.2.1.6
-- 1.3.6.1.4.1.37950.1.1.5.10.9.4.2.1.6
-- 1.3.6.1.4.1.37950.1.1.5.10.9.4.2.1.6
-- 1.3.6.1.4.1.37950.1.1.5.10.9.4.2.1.6
-- 1.3.6.1.4.1.37950.1.1.5.10.9.4.2.1.6
-- 1.3.6.1.4.1.37950.1.1.5.10.9.4.2.1.6
-- 1.3.6.1.4.1.37950.1.1.5.10.9.4.2.1.6
		-- 1.3.6.1.4.1.37950.1.1.5.10.9.4.2.1.6
		rstpPortP2P OBJECT-TYPE
			SYNTAX INTEGER
				{
				disable(0),
				enable(1)
				}
			MAX-ACCESS read-only
			STATUS current
			DESCRIPTION
				"Description."
			::= { rstpPortStatusEntry 6 }

		
--          1.3.6.1.4.1.37950.1.1.5.10.10
-- 1.3.6.1.4.1.37950.1.1.5.10.10
-- 1.3.6.1.4.1.37950.1.1.5.10.10
-- 1.3.6.1.4.1.37950.1.1.5.10.10
-- 1.3.6.1.4.1.37950.1.1.5.10.10
-- 1.3.6.1.4.1.37950.1.1.5.10.10
-- 1.3.6.1.4.1.37950.1.1.5.10.10
-- 1.3.6.1.4.1.37950.1.1.5.10.10
-- 1.3.6.1.4.1.37950.1.1.5.10.10
		-- 1.3.6.1.4.1.37950.1.1.5.10.10
		v1600dAcl OBJECT IDENTIFIER ::= { v1600dSwitch 10 }

		
--          1.3.6.1.4.1.37950.1.1.5.10.10.1
-- 1.3.6.1.4.1.37950.1.1.5.10.10.1
-- 1.3.6.1.4.1.37950.1.1.5.10.10.1
-- 1.3.6.1.4.1.37950.1.1.5.10.10.1
-- 1.3.6.1.4.1.37950.1.1.5.10.10.1
-- 1.3.6.1.4.1.37950.1.1.5.10.10.1
-- 1.3.6.1.4.1.37950.1.1.5.10.10.1
-- 1.3.6.1.4.1.37950.1.1.5.10.10.1
-- 1.3.6.1.4.1.37950.1.1.5.10.10.1
		-- 1.3.6.1.4.1.37950.1.1.5.10.10.1
		aclCfg OBJECT IDENTIFIER ::= { v1600dAcl 1 }

		
--          1.3.6.1.4.1.37950.1.1.5.10.10.1.1
-- 1.3.6.1.4.1.37950.1.1.5.10.10.1.1
-- 1.3.6.1.4.1.37950.1.1.5.10.10.1.1
-- 1.3.6.1.4.1.37950.1.1.5.10.10.1.1
-- 1.3.6.1.4.1.37950.1.1.5.10.10.1.1
-- 1.3.6.1.4.1.37950.1.1.5.10.10.1.1
-- 1.3.6.1.4.1.37950.1.1.5.10.10.1.1
-- 1.3.6.1.4.1.37950.1.1.5.10.10.1.1
-- 1.3.6.1.4.1.37950.1.1.5.10.10.1.1
		-- 1.3.6.1.4.1.37950.1.1.5.10.10.1.1
		stdIPFilterCfg OBJECT IDENTIFIER ::= { aclCfg 1 }

		
--          1.3.6.1.4.1.37950.1.1.5.10.10.1.1.1
-- 1.3.6.1.4.1.37950.1.1.5.10.10.1.1.1
-- 1.3.6.1.4.1.37950.1.1.5.10.10.1.1.1
-- 1.3.6.1.4.1.37950.1.1.5.10.10.1.1.1
-- 1.3.6.1.4.1.37950.1.1.5.10.10.1.1.1
-- 1.3.6.1.4.1.37950.1.1.5.10.10.1.1.1
-- 1.3.6.1.4.1.37950.1.1.5.10.10.1.1.1
-- 1.3.6.1.4.1.37950.1.1.5.10.10.1.1.1
-- 1.3.6.1.4.1.37950.1.1.5.10.10.1.1.1
		-- 1.3.6.1.4.1.37950.1.1.5.10.10.1.1.1
		stdIpFilterId OBJECT-TYPE
			SYNTAX INTEGER (0..999)
			MAX-ACCESS read-write
			STATUS current
			DESCRIPTION
				"Description."
			::= { stdIPFilterCfg 1 }

		
--          1.3.6.1.4.1.37950.1.1.5.10.10.1.1.2
-- 1.3.6.1.4.1.37950.1.1.5.10.10.1.1.2
-- 1.3.6.1.4.1.37950.1.1.5.10.10.1.1.2
-- 1.3.6.1.4.1.37950.1.1.5.10.10.1.1.2
-- 1.3.6.1.4.1.37950.1.1.5.10.10.1.1.2
-- 1.3.6.1.4.1.37950.1.1.5.10.10.1.1.2
-- 1.3.6.1.4.1.37950.1.1.5.10.10.1.1.2
-- 1.3.6.1.4.1.37950.1.1.5.10.10.1.1.2
-- 1.3.6.1.4.1.37950.1.1.5.10.10.1.1.2
		-- 1.3.6.1.4.1.37950.1.1.5.10.10.1.1.2
		stdIpFilterSrcIp OBJECT-TYPE
			SYNTAX IpAddress
			MAX-ACCESS read-write
			STATUS current
			DESCRIPTION
				"Description."
			::= { stdIPFilterCfg 2 }

		
--          1.3.6.1.4.1.37950.1.1.5.10.10.1.1.3
-- 1.3.6.1.4.1.37950.1.1.5.10.10.1.1.3
-- 1.3.6.1.4.1.37950.1.1.5.10.10.1.1.3
-- 1.3.6.1.4.1.37950.1.1.5.10.10.1.1.3
-- 1.3.6.1.4.1.37950.1.1.5.10.10.1.1.3
-- 1.3.6.1.4.1.37950.1.1.5.10.10.1.1.3
-- 1.3.6.1.4.1.37950.1.1.5.10.10.1.1.3
-- 1.3.6.1.4.1.37950.1.1.5.10.10.1.1.3
-- 1.3.6.1.4.1.37950.1.1.5.10.10.1.1.3
		-- 1.3.6.1.4.1.37950.1.1.5.10.10.1.1.3
		stdIpFilterSrcMask OBJECT-TYPE
			SYNTAX IpAddress
			MAX-ACCESS read-write
			STATUS current
			DESCRIPTION
				"Description."
			::= { stdIPFilterCfg 3 }

		
--          1.3.6.1.4.1.37950.1.1.5.10.10.1.1.4
-- 1.3.6.1.4.1.37950.1.1.5.10.10.1.1.4
-- 1.3.6.1.4.1.37950.1.1.5.10.10.1.1.4
-- 1.3.6.1.4.1.37950.1.1.5.10.10.1.1.4
-- 1.3.6.1.4.1.37950.1.1.5.10.10.1.1.4
-- 1.3.6.1.4.1.37950.1.1.5.10.10.1.1.4
-- 1.3.6.1.4.1.37950.1.1.5.10.10.1.1.4
-- 1.3.6.1.4.1.37950.1.1.5.10.10.1.1.4
-- 1.3.6.1.4.1.37950.1.1.5.10.10.1.1.4
		-- 1.3.6.1.4.1.37950.1.1.5.10.10.1.1.4
		stdIpFilterMode OBJECT-TYPE
			SYNTAX INTEGER
				{
				permit(1),
				deny(2)
				}
			MAX-ACCESS read-write
			STATUS current
			DESCRIPTION
				"Description."
			::= { stdIPFilterCfg 4 }

		
--          1.3.6.1.4.1.37950.1.1.5.10.10.1.1.5
-- 1.3.6.1.4.1.37950.1.1.5.10.10.1.1.5
-- 1.3.6.1.4.1.37950.1.1.5.10.10.1.1.5
-- 1.3.6.1.4.1.37950.1.1.5.10.10.1.1.5
-- 1.3.6.1.4.1.37950.1.1.5.10.10.1.1.5
-- 1.3.6.1.4.1.37950.1.1.5.10.10.1.1.5
-- 1.3.6.1.4.1.37950.1.1.5.10.10.1.1.5
-- 1.3.6.1.4.1.37950.1.1.5.10.10.1.1.5
-- 1.3.6.1.4.1.37950.1.1.5.10.10.1.1.5
		-- 1.3.6.1.4.1.37950.1.1.5.10.10.1.1.5
		stdIpFilterAction OBJECT-TYPE
			SYNTAX INTEGER
				{
				add(1),
				delete(2),
				clear(3)
				}
			MAX-ACCESS read-write
			STATUS current
			DESCRIPTION
				"Description."
			::= { stdIPFilterCfg 5 }

		
--          1.3.6.1.4.1.37950.1.1.5.10.10.1.2
-- 1.3.6.1.4.1.37950.1.1.5.10.10.1.2
-- 1.3.6.1.4.1.37950.1.1.5.10.10.1.2
-- 1.3.6.1.4.1.37950.1.1.5.10.10.1.2
-- 1.3.6.1.4.1.37950.1.1.5.10.10.1.2
-- 1.3.6.1.4.1.37950.1.1.5.10.10.1.2
-- 1.3.6.1.4.1.37950.1.1.5.10.10.1.2
-- 1.3.6.1.4.1.37950.1.1.5.10.10.1.2
-- 1.3.6.1.4.1.37950.1.1.5.10.10.1.2
		-- 1.3.6.1.4.1.37950.1.1.5.10.10.1.2
		extIPFilterCfg OBJECT IDENTIFIER ::= { aclCfg 2 }

		
--          1.3.6.1.4.1.37950.1.1.5.10.10.1.2.1
-- 1.3.6.1.4.1.37950.1.1.5.10.10.1.2.1
-- 1.3.6.1.4.1.37950.1.1.5.10.10.1.2.1
-- 1.3.6.1.4.1.37950.1.1.5.10.10.1.2.1
-- 1.3.6.1.4.1.37950.1.1.5.10.10.1.2.1
-- 1.3.6.1.4.1.37950.1.1.5.10.10.1.2.1
-- 1.3.6.1.4.1.37950.1.1.5.10.10.1.2.1
-- 1.3.6.1.4.1.37950.1.1.5.10.10.1.2.1
-- 1.3.6.1.4.1.37950.1.1.5.10.10.1.2.1
		-- 1.3.6.1.4.1.37950.1.1.5.10.10.1.2.1
		extIpFilterId OBJECT-TYPE
			SYNTAX INTEGER (1000..1999)
			MAX-ACCESS read-write
			STATUS current
			DESCRIPTION
				"Description."
			::= { extIPFilterCfg 1 }

		
--          1.3.6.1.4.1.37950.1.1.5.10.10.1.2.2
-- 1.3.6.1.4.1.37950.1.1.5.10.10.1.2.2
-- 1.3.6.1.4.1.37950.1.1.5.10.10.1.2.2
-- 1.3.6.1.4.1.37950.1.1.5.10.10.1.2.2
-- 1.3.6.1.4.1.37950.1.1.5.10.10.1.2.2
-- 1.3.6.1.4.1.37950.1.1.5.10.10.1.2.2
-- 1.3.6.1.4.1.37950.1.1.5.10.10.1.2.2
-- 1.3.6.1.4.1.37950.1.1.5.10.10.1.2.2
-- 1.3.6.1.4.1.37950.1.1.5.10.10.1.2.2
		-- 1.3.6.1.4.1.37950.1.1.5.10.10.1.2.2
		extIpFilterProtocol OBJECT-TYPE
			SYNTAX INTEGER (-1..255)
			MAX-ACCESS read-write
			STATUS current
			DESCRIPTION
				"Description."
			::= { extIPFilterCfg 2 }

		
--          1.3.6.1.4.1.37950.1.1.5.10.10.1.2.3
-- 1.3.6.1.4.1.37950.1.1.5.10.10.1.2.3
-- 1.3.6.1.4.1.37950.1.1.5.10.10.1.2.3
-- 1.3.6.1.4.1.37950.1.1.5.10.10.1.2.3
-- 1.3.6.1.4.1.37950.1.1.5.10.10.1.2.3
-- 1.3.6.1.4.1.37950.1.1.5.10.10.1.2.3
-- 1.3.6.1.4.1.37950.1.1.5.10.10.1.2.3
-- 1.3.6.1.4.1.37950.1.1.5.10.10.1.2.3
-- 1.3.6.1.4.1.37950.1.1.5.10.10.1.2.3
		-- 1.3.6.1.4.1.37950.1.1.5.10.10.1.2.3
		extIpFilterSrcIp OBJECT-TYPE
			SYNTAX IpAddress
			MAX-ACCESS read-write
			STATUS current
			DESCRIPTION
				"Description."
			::= { extIPFilterCfg 3 }

		
--          1.3.6.1.4.1.37950.1.1.5.10.10.1.2.4
-- 1.3.6.1.4.1.37950.1.1.5.10.10.1.2.4
-- 1.3.6.1.4.1.37950.1.1.5.10.10.1.2.4
-- 1.3.6.1.4.1.37950.1.1.5.10.10.1.2.4
-- 1.3.6.1.4.1.37950.1.1.5.10.10.1.2.4
-- 1.3.6.1.4.1.37950.1.1.5.10.10.1.2.4
-- 1.3.6.1.4.1.37950.1.1.5.10.10.1.2.4
-- 1.3.6.1.4.1.37950.1.1.5.10.10.1.2.4
-- 1.3.6.1.4.1.37950.1.1.5.10.10.1.2.4
		-- 1.3.6.1.4.1.37950.1.1.5.10.10.1.2.4
		extIpFilterSrcMask OBJECT-TYPE
			SYNTAX IpAddress
			MAX-ACCESS read-write
			STATUS current
			DESCRIPTION
				"Description."
			::= { extIPFilterCfg 4 }

		
--          1.3.6.1.4.1.37950.1.1.5.10.10.1.2.5
-- 1.3.6.1.4.1.37950.1.1.5.10.10.1.2.5
-- 1.3.6.1.4.1.37950.1.1.5.10.10.1.2.5
-- 1.3.6.1.4.1.37950.1.1.5.10.10.1.2.5
-- 1.3.6.1.4.1.37950.1.1.5.10.10.1.2.5
-- 1.3.6.1.4.1.37950.1.1.5.10.10.1.2.5
-- 1.3.6.1.4.1.37950.1.1.5.10.10.1.2.5
-- 1.3.6.1.4.1.37950.1.1.5.10.10.1.2.5
-- 1.3.6.1.4.1.37950.1.1.5.10.10.1.2.5
		-- 1.3.6.1.4.1.37950.1.1.5.10.10.1.2.5
		extIpFilterSrcPort OBJECT-TYPE
			SYNTAX INTEGER (-1..65535)
			MAX-ACCESS read-write
			STATUS current
			DESCRIPTION
				"Description."
			::= { extIPFilterCfg 5 }

		
--          1.3.6.1.4.1.37950.1.1.5.10.10.1.2.6
-- 1.3.6.1.4.1.37950.1.1.5.10.10.1.2.6
-- 1.3.6.1.4.1.37950.1.1.5.10.10.1.2.6
-- 1.3.6.1.4.1.37950.1.1.5.10.10.1.2.6
-- 1.3.6.1.4.1.37950.1.1.5.10.10.1.2.6
-- 1.3.6.1.4.1.37950.1.1.5.10.10.1.2.6
-- 1.3.6.1.4.1.37950.1.1.5.10.10.1.2.6
-- 1.3.6.1.4.1.37950.1.1.5.10.10.1.2.6
-- 1.3.6.1.4.1.37950.1.1.5.10.10.1.2.6
		-- 1.3.6.1.4.1.37950.1.1.5.10.10.1.2.6
		extIpFilterDstIp OBJECT-TYPE
			SYNTAX IpAddress
			MAX-ACCESS read-write
			STATUS current
			DESCRIPTION
				"Description."
			::= { extIPFilterCfg 6 }

		
--          1.3.6.1.4.1.37950.1.1.5.10.10.1.2.7
-- 1.3.6.1.4.1.37950.1.1.5.10.10.1.2.7
-- 1.3.6.1.4.1.37950.1.1.5.10.10.1.2.7
-- 1.3.6.1.4.1.37950.1.1.5.10.10.1.2.7
-- 1.3.6.1.4.1.37950.1.1.5.10.10.1.2.7
-- 1.3.6.1.4.1.37950.1.1.5.10.10.1.2.7
-- 1.3.6.1.4.1.37950.1.1.5.10.10.1.2.7
-- 1.3.6.1.4.1.37950.1.1.5.10.10.1.2.7
-- 1.3.6.1.4.1.37950.1.1.5.10.10.1.2.7
		-- 1.3.6.1.4.1.37950.1.1.5.10.10.1.2.7
		extIpFilterDstMask OBJECT-TYPE
			SYNTAX IpAddress
			MAX-ACCESS read-write
			STATUS current
			DESCRIPTION
				"Description."
			::= { extIPFilterCfg 7 }

		
--          1.3.6.1.4.1.37950.1.1.5.10.10.1.2.8
-- 1.3.6.1.4.1.37950.1.1.5.10.10.1.2.8
-- 1.3.6.1.4.1.37950.1.1.5.10.10.1.2.8
-- 1.3.6.1.4.1.37950.1.1.5.10.10.1.2.8
-- 1.3.6.1.4.1.37950.1.1.5.10.10.1.2.8
-- 1.3.6.1.4.1.37950.1.1.5.10.10.1.2.8
-- 1.3.6.1.4.1.37950.1.1.5.10.10.1.2.8
-- 1.3.6.1.4.1.37950.1.1.5.10.10.1.2.8
-- 1.3.6.1.4.1.37950.1.1.5.10.10.1.2.8
		-- 1.3.6.1.4.1.37950.1.1.5.10.10.1.2.8
		extIpFilterDstPort OBJECT-TYPE
			SYNTAX INTEGER (-1..65535)
			MAX-ACCESS read-write
			STATUS current
			DESCRIPTION
				"Description."
			::= { extIPFilterCfg 8 }

		
--          1.3.6.1.4.1.37950.1.1.5.10.10.1.2.9
-- 1.3.6.1.4.1.37950.1.1.5.10.10.1.2.9
-- 1.3.6.1.4.1.37950.1.1.5.10.10.1.2.9
-- 1.3.6.1.4.1.37950.1.1.5.10.10.1.2.9
-- 1.3.6.1.4.1.37950.1.1.5.10.10.1.2.9
-- 1.3.6.1.4.1.37950.1.1.5.10.10.1.2.9
-- 1.3.6.1.4.1.37950.1.1.5.10.10.1.2.9
-- 1.3.6.1.4.1.37950.1.1.5.10.10.1.2.9
-- 1.3.6.1.4.1.37950.1.1.5.10.10.1.2.9
		-- 1.3.6.1.4.1.37950.1.1.5.10.10.1.2.9
		extIpFilterDscp OBJECT-TYPE
			SYNTAX INTEGER (-1..63)
			MAX-ACCESS read-write
			STATUS current
			DESCRIPTION
				"Description."
			::= { extIPFilterCfg 9 }

		
--          1.3.6.1.4.1.37950.1.1.5.10.10.1.2.10
-- 1.3.6.1.4.1.37950.1.1.5.10.10.1.2.10
-- 1.3.6.1.4.1.37950.1.1.5.10.10.1.2.10
-- 1.3.6.1.4.1.37950.1.1.5.10.10.1.2.10
-- 1.3.6.1.4.1.37950.1.1.5.10.10.1.2.10
-- 1.3.6.1.4.1.37950.1.1.5.10.10.1.2.10
-- 1.3.6.1.4.1.37950.1.1.5.10.10.1.2.10
-- 1.3.6.1.4.1.37950.1.1.5.10.10.1.2.10
-- 1.3.6.1.4.1.37950.1.1.5.10.10.1.2.10
		-- 1.3.6.1.4.1.37950.1.1.5.10.10.1.2.10
		extIpFilterMode OBJECT-TYPE
			SYNTAX INTEGER
				{
				permit(1),
				deny(2)
				}
			MAX-ACCESS read-write
			STATUS current
			DESCRIPTION
				"Description."
			::= { extIPFilterCfg 10 }

		
--          1.3.6.1.4.1.37950.1.1.5.10.10.1.2.11
-- 1.3.6.1.4.1.37950.1.1.5.10.10.1.2.11
-- 1.3.6.1.4.1.37950.1.1.5.10.10.1.2.11
-- 1.3.6.1.4.1.37950.1.1.5.10.10.1.2.11
-- 1.3.6.1.4.1.37950.1.1.5.10.10.1.2.11
-- 1.3.6.1.4.1.37950.1.1.5.10.10.1.2.11
-- 1.3.6.1.4.1.37950.1.1.5.10.10.1.2.11
-- 1.3.6.1.4.1.37950.1.1.5.10.10.1.2.11
-- 1.3.6.1.4.1.37950.1.1.5.10.10.1.2.11
		-- 1.3.6.1.4.1.37950.1.1.5.10.10.1.2.11
		extIpFilterAction OBJECT-TYPE
			SYNTAX INTEGER
				{
				add(1),
				delete(2),
				clear(3)
				}
			MAX-ACCESS read-write
			STATUS current
			DESCRIPTION
				"Description."
			::= { extIPFilterCfg 11 }

		
--          1.3.6.1.4.1.37950.1.1.5.10.10.1.3
-- 1.3.6.1.4.1.37950.1.1.5.10.10.1.3
-- 1.3.6.1.4.1.37950.1.1.5.10.10.1.3
-- 1.3.6.1.4.1.37950.1.1.5.10.10.1.3
-- 1.3.6.1.4.1.37950.1.1.5.10.10.1.3
-- 1.3.6.1.4.1.37950.1.1.5.10.10.1.3
-- 1.3.6.1.4.1.37950.1.1.5.10.10.1.3
-- 1.3.6.1.4.1.37950.1.1.5.10.10.1.3
-- 1.3.6.1.4.1.37950.1.1.5.10.10.1.3
		-- 1.3.6.1.4.1.37950.1.1.5.10.10.1.3
		macFilterCfg OBJECT IDENTIFIER ::= { aclCfg 3 }

		
--          1.3.6.1.4.1.37950.1.1.5.10.10.1.3.1
-- 1.3.6.1.4.1.37950.1.1.5.10.10.1.3.1
-- 1.3.6.1.4.1.37950.1.1.5.10.10.1.3.1
-- 1.3.6.1.4.1.37950.1.1.5.10.10.1.3.1
-- 1.3.6.1.4.1.37950.1.1.5.10.10.1.3.1
-- 1.3.6.1.4.1.37950.1.1.5.10.10.1.3.1
-- 1.3.6.1.4.1.37950.1.1.5.10.10.1.3.1
-- 1.3.6.1.4.1.37950.1.1.5.10.10.1.3.1
-- 1.3.6.1.4.1.37950.1.1.5.10.10.1.3.1
		-- 1.3.6.1.4.1.37950.1.1.5.10.10.1.3.1
		macFilterId OBJECT-TYPE
			SYNTAX INTEGER (2000..2999)
			MAX-ACCESS read-write
			STATUS current
			DESCRIPTION
				"Description."
			::= { macFilterCfg 1 }

		
--          1.3.6.1.4.1.37950.1.1.5.10.10.1.3.2
-- 1.3.6.1.4.1.37950.1.1.5.10.10.1.3.2
-- 1.3.6.1.4.1.37950.1.1.5.10.10.1.3.2
-- 1.3.6.1.4.1.37950.1.1.5.10.10.1.3.2
-- 1.3.6.1.4.1.37950.1.1.5.10.10.1.3.2
-- 1.3.6.1.4.1.37950.1.1.5.10.10.1.3.2
-- 1.3.6.1.4.1.37950.1.1.5.10.10.1.3.2
-- 1.3.6.1.4.1.37950.1.1.5.10.10.1.3.2
-- 1.3.6.1.4.1.37950.1.1.5.10.10.1.3.2
		-- 1.3.6.1.4.1.37950.1.1.5.10.10.1.3.2
		macFilterSrcMac OBJECT-TYPE
			SYNTAX OCTET STRING
			MAX-ACCESS read-write
			STATUS current
			DESCRIPTION
				"Description."
			::= { macFilterCfg 2 }

		
--          1.3.6.1.4.1.37950.1.1.5.10.10.1.3.3
-- 1.3.6.1.4.1.37950.1.1.5.10.10.1.3.3
-- 1.3.6.1.4.1.37950.1.1.5.10.10.1.3.3
-- 1.3.6.1.4.1.37950.1.1.5.10.10.1.3.3
-- 1.3.6.1.4.1.37950.1.1.5.10.10.1.3.3
-- 1.3.6.1.4.1.37950.1.1.5.10.10.1.3.3
-- 1.3.6.1.4.1.37950.1.1.5.10.10.1.3.3
-- 1.3.6.1.4.1.37950.1.1.5.10.10.1.3.3
-- 1.3.6.1.4.1.37950.1.1.5.10.10.1.3.3
		-- 1.3.6.1.4.1.37950.1.1.5.10.10.1.3.3
		macFilterSrcMacMask OBJECT-TYPE
			SYNTAX OCTET STRING
			MAX-ACCESS read-write
			STATUS current
			DESCRIPTION
				"Description."
			::= { macFilterCfg 3 }

		
--          1.3.6.1.4.1.37950.1.1.5.10.10.1.3.4
-- 1.3.6.1.4.1.37950.1.1.5.10.10.1.3.4
-- 1.3.6.1.4.1.37950.1.1.5.10.10.1.3.4
-- 1.3.6.1.4.1.37950.1.1.5.10.10.1.3.4
-- 1.3.6.1.4.1.37950.1.1.5.10.10.1.3.4
-- 1.3.6.1.4.1.37950.1.1.5.10.10.1.3.4
-- 1.3.6.1.4.1.37950.1.1.5.10.10.1.3.4
-- 1.3.6.1.4.1.37950.1.1.5.10.10.1.3.4
-- 1.3.6.1.4.1.37950.1.1.5.10.10.1.3.4
		-- 1.3.6.1.4.1.37950.1.1.5.10.10.1.3.4
		macFilterDstMac OBJECT-TYPE
			SYNTAX OCTET STRING
			MAX-ACCESS read-write
			STATUS current
			DESCRIPTION
				"Description."
			::= { macFilterCfg 4 }

		
--          1.3.6.1.4.1.37950.1.1.5.10.10.1.3.5
-- 1.3.6.1.4.1.37950.1.1.5.10.10.1.3.5
-- 1.3.6.1.4.1.37950.1.1.5.10.10.1.3.5
-- 1.3.6.1.4.1.37950.1.1.5.10.10.1.3.5
-- 1.3.6.1.4.1.37950.1.1.5.10.10.1.3.5
-- 1.3.6.1.4.1.37950.1.1.5.10.10.1.3.5
-- 1.3.6.1.4.1.37950.1.1.5.10.10.1.3.5
-- 1.3.6.1.4.1.37950.1.1.5.10.10.1.3.5
-- 1.3.6.1.4.1.37950.1.1.5.10.10.1.3.5
		-- 1.3.6.1.4.1.37950.1.1.5.10.10.1.3.5
		macFilterDstMacMask OBJECT-TYPE
			SYNTAX OCTET STRING
			MAX-ACCESS read-write
			STATUS current
			DESCRIPTION
				"Description."
			::= { macFilterCfg 5 }

		
--          1.3.6.1.4.1.37950.1.1.5.10.10.1.3.6
-- 1.3.6.1.4.1.37950.1.1.5.10.10.1.3.6
-- 1.3.6.1.4.1.37950.1.1.5.10.10.1.3.6
-- 1.3.6.1.4.1.37950.1.1.5.10.10.1.3.6
-- 1.3.6.1.4.1.37950.1.1.5.10.10.1.3.6
-- 1.3.6.1.4.1.37950.1.1.5.10.10.1.3.6
-- 1.3.6.1.4.1.37950.1.1.5.10.10.1.3.6
-- 1.3.6.1.4.1.37950.1.1.5.10.10.1.3.6
-- 1.3.6.1.4.1.37950.1.1.5.10.10.1.3.6
		-- 1.3.6.1.4.1.37950.1.1.5.10.10.1.3.6
		macFilterVlanId OBJECT-TYPE
			SYNTAX INTEGER (0..4094)
			MAX-ACCESS read-write
			STATUS current
			DESCRIPTION
				"Description."
			::= { macFilterCfg 6 }

		
--          1.3.6.1.4.1.37950.1.1.5.10.10.1.3.7
-- 1.3.6.1.4.1.37950.1.1.5.10.10.1.3.7
-- 1.3.6.1.4.1.37950.1.1.5.10.10.1.3.7
-- 1.3.6.1.4.1.37950.1.1.5.10.10.1.3.7
-- 1.3.6.1.4.1.37950.1.1.5.10.10.1.3.7
-- 1.3.6.1.4.1.37950.1.1.5.10.10.1.3.7
-- 1.3.6.1.4.1.37950.1.1.5.10.10.1.3.7
-- 1.3.6.1.4.1.37950.1.1.5.10.10.1.3.7
-- 1.3.6.1.4.1.37950.1.1.5.10.10.1.3.7
		-- 1.3.6.1.4.1.37950.1.1.5.10.10.1.3.7
		macFilterCos OBJECT-TYPE
			SYNTAX INTEGER (-1..7)
			MAX-ACCESS read-write
			STATUS current
			DESCRIPTION
				"Description."
			::= { macFilterCfg 7 }

		
--          1.3.6.1.4.1.37950.1.1.5.10.10.1.3.8
-- 1.3.6.1.4.1.37950.1.1.5.10.10.1.3.8
-- 1.3.6.1.4.1.37950.1.1.5.10.10.1.3.8
-- 1.3.6.1.4.1.37950.1.1.5.10.10.1.3.8
-- 1.3.6.1.4.1.37950.1.1.5.10.10.1.3.8
-- 1.3.6.1.4.1.37950.1.1.5.10.10.1.3.8
-- 1.3.6.1.4.1.37950.1.1.5.10.10.1.3.8
-- 1.3.6.1.4.1.37950.1.1.5.10.10.1.3.8
-- 1.3.6.1.4.1.37950.1.1.5.10.10.1.3.8
		-- 1.3.6.1.4.1.37950.1.1.5.10.10.1.3.8
		macFilterEthType OBJECT-TYPE
			SYNTAX OCTET STRING
			MAX-ACCESS read-write
			STATUS current
			DESCRIPTION
				"Description."
			::= { macFilterCfg 8 }

		
--          1.3.6.1.4.1.37950.1.1.5.10.10.1.3.9
-- 1.3.6.1.4.1.37950.1.1.5.10.10.1.3.9
-- 1.3.6.1.4.1.37950.1.1.5.10.10.1.3.9
-- 1.3.6.1.4.1.37950.1.1.5.10.10.1.3.9
-- 1.3.6.1.4.1.37950.1.1.5.10.10.1.3.9
-- 1.3.6.1.4.1.37950.1.1.5.10.10.1.3.9
-- 1.3.6.1.4.1.37950.1.1.5.10.10.1.3.9
-- 1.3.6.1.4.1.37950.1.1.5.10.10.1.3.9
-- 1.3.6.1.4.1.37950.1.1.5.10.10.1.3.9
		-- 1.3.6.1.4.1.37950.1.1.5.10.10.1.3.9
		macFilterEthTypeMask OBJECT-TYPE
			SYNTAX OCTET STRING
			MAX-ACCESS read-write
			STATUS current
			DESCRIPTION
				"Description."
			::= { macFilterCfg 9 }

		
--          1.3.6.1.4.1.37950.1.1.5.10.10.1.3.10
-- 1.3.6.1.4.1.37950.1.1.5.10.10.1.3.10
-- 1.3.6.1.4.1.37950.1.1.5.10.10.1.3.10
-- 1.3.6.1.4.1.37950.1.1.5.10.10.1.3.10
-- 1.3.6.1.4.1.37950.1.1.5.10.10.1.3.10
-- 1.3.6.1.4.1.37950.1.1.5.10.10.1.3.10
-- 1.3.6.1.4.1.37950.1.1.5.10.10.1.3.10
-- 1.3.6.1.4.1.37950.1.1.5.10.10.1.3.10
-- 1.3.6.1.4.1.37950.1.1.5.10.10.1.3.10
		-- 1.3.6.1.4.1.37950.1.1.5.10.10.1.3.10
		macFilterMode OBJECT-TYPE
			SYNTAX INTEGER
				{
				permit(1),
				deny(2)
				}
			MAX-ACCESS read-write
			STATUS current
			DESCRIPTION
				"Description."
			::= { macFilterCfg 10 }

		
--          1.3.6.1.4.1.37950.1.1.5.10.10.1.3.11
-- 1.3.6.1.4.1.37950.1.1.5.10.10.1.3.11
-- 1.3.6.1.4.1.37950.1.1.5.10.10.1.3.11
-- 1.3.6.1.4.1.37950.1.1.5.10.10.1.3.11
-- 1.3.6.1.4.1.37950.1.1.5.10.10.1.3.11
-- 1.3.6.1.4.1.37950.1.1.5.10.10.1.3.11
-- 1.3.6.1.4.1.37950.1.1.5.10.10.1.3.11
-- 1.3.6.1.4.1.37950.1.1.5.10.10.1.3.11
-- 1.3.6.1.4.1.37950.1.1.5.10.10.1.3.11
		-- 1.3.6.1.4.1.37950.1.1.5.10.10.1.3.11
		macFilterAction OBJECT-TYPE
			SYNTAX INTEGER
				{
				add(1),
				delete(2),
				clear(3)
				}
			MAX-ACCESS read-write
			STATUS current
			DESCRIPTION
				"Description."
			::= { macFilterCfg 11 }

		
--          1.3.6.1.4.1.37950.1.1.5.10.10.1.4
-- 1.3.6.1.4.1.37950.1.1.5.10.10.1.4
-- 1.3.6.1.4.1.37950.1.1.5.10.10.1.4
-- 1.3.6.1.4.1.37950.1.1.5.10.10.1.4
-- 1.3.6.1.4.1.37950.1.1.5.10.10.1.4
-- 1.3.6.1.4.1.37950.1.1.5.10.10.1.4
-- 1.3.6.1.4.1.37950.1.1.5.10.10.1.4
-- 1.3.6.1.4.1.37950.1.1.5.10.10.1.4
-- 1.3.6.1.4.1.37950.1.1.5.10.10.1.4
		-- 1.3.6.1.4.1.37950.1.1.5.10.10.1.4
		portBaseAclCfg OBJECT IDENTIFIER ::= { aclCfg 4 }

		
--          1.3.6.1.4.1.37950.1.1.5.10.10.1.4.1
-- 1.3.6.1.4.1.37950.1.1.5.10.10.1.4.1
-- 1.3.6.1.4.1.37950.1.1.5.10.10.1.4.1
-- 1.3.6.1.4.1.37950.1.1.5.10.10.1.4.1
-- 1.3.6.1.4.1.37950.1.1.5.10.10.1.4.1
-- 1.3.6.1.4.1.37950.1.1.5.10.10.1.4.1
-- 1.3.6.1.4.1.37950.1.1.5.10.10.1.4.1
-- 1.3.6.1.4.1.37950.1.1.5.10.10.1.4.1
-- 1.3.6.1.4.1.37950.1.1.5.10.10.1.4.1
		-- 1.3.6.1.4.1.37950.1.1.5.10.10.1.4.1
		portBaseAclId OBJECT-TYPE
			SYNTAX Integer32 (5000..5999)
			MAX-ACCESS read-write
			STATUS current
			DESCRIPTION
				"Description."
			::= { portBaseAclCfg 1 }

		
--          1.3.6.1.4.1.37950.1.1.5.10.10.1.4.2
-- 1.3.6.1.4.1.37950.1.1.5.10.10.1.4.2
-- 1.3.6.1.4.1.37950.1.1.5.10.10.1.4.2
-- 1.3.6.1.4.1.37950.1.1.5.10.10.1.4.2
-- 1.3.6.1.4.1.37950.1.1.5.10.10.1.4.2
-- 1.3.6.1.4.1.37950.1.1.5.10.10.1.4.2
-- 1.3.6.1.4.1.37950.1.1.5.10.10.1.4.2
-- 1.3.6.1.4.1.37950.1.1.5.10.10.1.4.2
-- 1.3.6.1.4.1.37950.1.1.5.10.10.1.4.2
		-- 1.3.6.1.4.1.37950.1.1.5.10.10.1.4.2
		portBaseFltMode OBJECT-TYPE
			SYNTAX INTEGER
				{
				permit(1),
				deny(2)
				}
			MAX-ACCESS read-write
			STATUS current
			DESCRIPTION
				"Description."
			::= { portBaseAclCfg 2 }

		
--          1.3.6.1.4.1.37950.1.1.5.10.10.1.4.3
-- 1.3.6.1.4.1.37950.1.1.5.10.10.1.4.3
-- 1.3.6.1.4.1.37950.1.1.5.10.10.1.4.3
-- 1.3.6.1.4.1.37950.1.1.5.10.10.1.4.3
-- 1.3.6.1.4.1.37950.1.1.5.10.10.1.4.3
-- 1.3.6.1.4.1.37950.1.1.5.10.10.1.4.3
-- 1.3.6.1.4.1.37950.1.1.5.10.10.1.4.3
-- 1.3.6.1.4.1.37950.1.1.5.10.10.1.4.3
-- 1.3.6.1.4.1.37950.1.1.5.10.10.1.4.3
		-- 1.3.6.1.4.1.37950.1.1.5.10.10.1.4.3
		portBaseSrcMac OBJECT-TYPE
			SYNTAX OCTET STRING
			MAX-ACCESS read-write
			STATUS current
			DESCRIPTION
				"Description."
			::= { portBaseAclCfg 3 }

		
--          1.3.6.1.4.1.37950.1.1.5.10.10.1.4.4
-- 1.3.6.1.4.1.37950.1.1.5.10.10.1.4.4
-- 1.3.6.1.4.1.37950.1.1.5.10.10.1.4.4
-- 1.3.6.1.4.1.37950.1.1.5.10.10.1.4.4
-- 1.3.6.1.4.1.37950.1.1.5.10.10.1.4.4
-- 1.3.6.1.4.1.37950.1.1.5.10.10.1.4.4
-- 1.3.6.1.4.1.37950.1.1.5.10.10.1.4.4
-- 1.3.6.1.4.1.37950.1.1.5.10.10.1.4.4
-- 1.3.6.1.4.1.37950.1.1.5.10.10.1.4.4
		-- 1.3.6.1.4.1.37950.1.1.5.10.10.1.4.4
		portBaseSrcMacMask OBJECT-TYPE
			SYNTAX OCTET STRING
			MAX-ACCESS read-write
			STATUS current
			DESCRIPTION
				"Description."
			::= { portBaseAclCfg 4 }

		
--          1.3.6.1.4.1.37950.1.1.5.10.10.1.4.5
-- 1.3.6.1.4.1.37950.1.1.5.10.10.1.4.5
-- 1.3.6.1.4.1.37950.1.1.5.10.10.1.4.5
-- 1.3.6.1.4.1.37950.1.1.5.10.10.1.4.5
-- 1.3.6.1.4.1.37950.1.1.5.10.10.1.4.5
-- 1.3.6.1.4.1.37950.1.1.5.10.10.1.4.5
-- 1.3.6.1.4.1.37950.1.1.5.10.10.1.4.5
-- 1.3.6.1.4.1.37950.1.1.5.10.10.1.4.5
-- 1.3.6.1.4.1.37950.1.1.5.10.10.1.4.5
		-- 1.3.6.1.4.1.37950.1.1.5.10.10.1.4.5
		portBaseDstMac OBJECT-TYPE
			SYNTAX OCTET STRING
			MAX-ACCESS read-write
			STATUS current
			DESCRIPTION
				"Description."
			::= { portBaseAclCfg 5 }

		
--          1.3.6.1.4.1.37950.1.1.5.10.10.1.4.6
-- 1.3.6.1.4.1.37950.1.1.5.10.10.1.4.6
-- 1.3.6.1.4.1.37950.1.1.5.10.10.1.4.6
-- 1.3.6.1.4.1.37950.1.1.5.10.10.1.4.6
-- 1.3.6.1.4.1.37950.1.1.5.10.10.1.4.6
-- 1.3.6.1.4.1.37950.1.1.5.10.10.1.4.6
-- 1.3.6.1.4.1.37950.1.1.5.10.10.1.4.6
-- 1.3.6.1.4.1.37950.1.1.5.10.10.1.4.6
-- 1.3.6.1.4.1.37950.1.1.5.10.10.1.4.6
		-- 1.3.6.1.4.1.37950.1.1.5.10.10.1.4.6
		portBaseDstMacMask OBJECT-TYPE
			SYNTAX OCTET STRING
			MAX-ACCESS read-write
			STATUS current
			DESCRIPTION
				"Description."
			::= { portBaseAclCfg 6 }

		
--          1.3.6.1.4.1.37950.1.1.5.10.10.1.4.7
-- 1.3.6.1.4.1.37950.1.1.5.10.10.1.4.7
-- 1.3.6.1.4.1.37950.1.1.5.10.10.1.4.7
-- 1.3.6.1.4.1.37950.1.1.5.10.10.1.4.7
-- 1.3.6.1.4.1.37950.1.1.5.10.10.1.4.7
-- 1.3.6.1.4.1.37950.1.1.5.10.10.1.4.7
-- 1.3.6.1.4.1.37950.1.1.5.10.10.1.4.7
-- 1.3.6.1.4.1.37950.1.1.5.10.10.1.4.7
-- 1.3.6.1.4.1.37950.1.1.5.10.10.1.4.7
		-- 1.3.6.1.4.1.37950.1.1.5.10.10.1.4.7
		portBaseVlan OBJECT-TYPE
			SYNTAX INTEGER (0..4094)
			MAX-ACCESS read-write
			STATUS current
			DESCRIPTION
				"Description."
			::= { portBaseAclCfg 7 }

		
--          1.3.6.1.4.1.37950.1.1.5.10.10.1.4.8
-- 1.3.6.1.4.1.37950.1.1.5.10.10.1.4.8
-- 1.3.6.1.4.1.37950.1.1.5.10.10.1.4.8
-- 1.3.6.1.4.1.37950.1.1.5.10.10.1.4.8
-- 1.3.6.1.4.1.37950.1.1.5.10.10.1.4.8
-- 1.3.6.1.4.1.37950.1.1.5.10.10.1.4.8
-- 1.3.6.1.4.1.37950.1.1.5.10.10.1.4.8
-- 1.3.6.1.4.1.37950.1.1.5.10.10.1.4.8
-- 1.3.6.1.4.1.37950.1.1.5.10.10.1.4.8
		-- 1.3.6.1.4.1.37950.1.1.5.10.10.1.4.8
		portBaseVlanMask OBJECT-TYPE
			SYNTAX INTEGER (0..4095)
			MAX-ACCESS read-write
			STATUS current
			DESCRIPTION
				"Description."
			::= { portBaseAclCfg 8 }

		
--          1.3.6.1.4.1.37950.1.1.5.10.10.1.4.9
-- 1.3.6.1.4.1.37950.1.1.5.10.10.1.4.9
-- 1.3.6.1.4.1.37950.1.1.5.10.10.1.4.9
-- 1.3.6.1.4.1.37950.1.1.5.10.10.1.4.9
-- 1.3.6.1.4.1.37950.1.1.5.10.10.1.4.9
-- 1.3.6.1.4.1.37950.1.1.5.10.10.1.4.9
-- 1.3.6.1.4.1.37950.1.1.5.10.10.1.4.9
-- 1.3.6.1.4.1.37950.1.1.5.10.10.1.4.9
-- 1.3.6.1.4.1.37950.1.1.5.10.10.1.4.9
		-- 1.3.6.1.4.1.37950.1.1.5.10.10.1.4.9
		portBaseCos OBJECT-TYPE
			SYNTAX INTEGER (-1..7)
			MAX-ACCESS read-write
			STATUS current
			DESCRIPTION
				"Description."
			::= { portBaseAclCfg 9 }

		
--          1.3.6.1.4.1.37950.1.1.5.10.10.1.4.10
-- 1.3.6.1.4.1.37950.1.1.5.10.10.1.4.10
-- 1.3.6.1.4.1.37950.1.1.5.10.10.1.4.10
-- 1.3.6.1.4.1.37950.1.1.5.10.10.1.4.10
-- 1.3.6.1.4.1.37950.1.1.5.10.10.1.4.10
-- 1.3.6.1.4.1.37950.1.1.5.10.10.1.4.10
-- 1.3.6.1.4.1.37950.1.1.5.10.10.1.4.10
-- 1.3.6.1.4.1.37950.1.1.5.10.10.1.4.10
-- 1.3.6.1.4.1.37950.1.1.5.10.10.1.4.10
		-- 1.3.6.1.4.1.37950.1.1.5.10.10.1.4.10
		portBaseEthernetType OBJECT-TYPE
			SYNTAX OCTET STRING
			MAX-ACCESS read-write
			STATUS current
			DESCRIPTION
				"Description."
			::= { portBaseAclCfg 10 }

		
--          1.3.6.1.4.1.37950.1.1.5.10.10.1.4.11
-- 1.3.6.1.4.1.37950.1.1.5.10.10.1.4.11
-- 1.3.6.1.4.1.37950.1.1.5.10.10.1.4.11
-- 1.3.6.1.4.1.37950.1.1.5.10.10.1.4.11
-- 1.3.6.1.4.1.37950.1.1.5.10.10.1.4.11
-- 1.3.6.1.4.1.37950.1.1.5.10.10.1.4.11
-- 1.3.6.1.4.1.37950.1.1.5.10.10.1.4.11
-- 1.3.6.1.4.1.37950.1.1.5.10.10.1.4.11
-- 1.3.6.1.4.1.37950.1.1.5.10.10.1.4.11
		-- 1.3.6.1.4.1.37950.1.1.5.10.10.1.4.11
		portBaseSrcIp OBJECT-TYPE
			SYNTAX IpAddress
			MAX-ACCESS read-write
			STATUS current
			DESCRIPTION
				"Description."
			::= { portBaseAclCfg 11 }

		
--          1.3.6.1.4.1.37950.1.1.5.10.10.1.4.12
-- 1.3.6.1.4.1.37950.1.1.5.10.10.1.4.12
-- 1.3.6.1.4.1.37950.1.1.5.10.10.1.4.12
-- 1.3.6.1.4.1.37950.1.1.5.10.10.1.4.12
-- 1.3.6.1.4.1.37950.1.1.5.10.10.1.4.12
-- 1.3.6.1.4.1.37950.1.1.5.10.10.1.4.12
-- 1.3.6.1.4.1.37950.1.1.5.10.10.1.4.12
-- 1.3.6.1.4.1.37950.1.1.5.10.10.1.4.12
-- 1.3.6.1.4.1.37950.1.1.5.10.10.1.4.12
		-- 1.3.6.1.4.1.37950.1.1.5.10.10.1.4.12
		portBaseSrcIpMask OBJECT-TYPE
			SYNTAX IpAddress
			MAX-ACCESS read-write
			STATUS current
			DESCRIPTION
				"Description."
			::= { portBaseAclCfg 12 }

		
--          1.3.6.1.4.1.37950.1.1.5.10.10.1.4.13
-- 1.3.6.1.4.1.37950.1.1.5.10.10.1.4.13
-- 1.3.6.1.4.1.37950.1.1.5.10.10.1.4.13
-- 1.3.6.1.4.1.37950.1.1.5.10.10.1.4.13
-- 1.3.6.1.4.1.37950.1.1.5.10.10.1.4.13
-- 1.3.6.1.4.1.37950.1.1.5.10.10.1.4.13
-- 1.3.6.1.4.1.37950.1.1.5.10.10.1.4.13
-- 1.3.6.1.4.1.37950.1.1.5.10.10.1.4.13
-- 1.3.6.1.4.1.37950.1.1.5.10.10.1.4.13
		-- 1.3.6.1.4.1.37950.1.1.5.10.10.1.4.13
		portBaseDstIp OBJECT-TYPE
			SYNTAX IpAddress
			MAX-ACCESS read-write
			STATUS current
			DESCRIPTION
				"Description."
			::= { portBaseAclCfg 13 }

		
--          1.3.6.1.4.1.37950.1.1.5.10.10.1.4.14
-- 1.3.6.1.4.1.37950.1.1.5.10.10.1.4.14
-- 1.3.6.1.4.1.37950.1.1.5.10.10.1.4.14
-- 1.3.6.1.4.1.37950.1.1.5.10.10.1.4.14
-- 1.3.6.1.4.1.37950.1.1.5.10.10.1.4.14
-- 1.3.6.1.4.1.37950.1.1.5.10.10.1.4.14
-- 1.3.6.1.4.1.37950.1.1.5.10.10.1.4.14
-- 1.3.6.1.4.1.37950.1.1.5.10.10.1.4.14
-- 1.3.6.1.4.1.37950.1.1.5.10.10.1.4.14
		-- 1.3.6.1.4.1.37950.1.1.5.10.10.1.4.14
		portBaseDstIpMask OBJECT-TYPE
			SYNTAX IpAddress
			MAX-ACCESS read-write
			STATUS current
			DESCRIPTION
				"Description."
			::= { portBaseAclCfg 14 }

		
--          1.3.6.1.4.1.37950.1.1.5.10.10.1.4.15
-- 1.3.6.1.4.1.37950.1.1.5.10.10.1.4.15
-- 1.3.6.1.4.1.37950.1.1.5.10.10.1.4.15
-- 1.3.6.1.4.1.37950.1.1.5.10.10.1.4.15
-- 1.3.6.1.4.1.37950.1.1.5.10.10.1.4.15
-- 1.3.6.1.4.1.37950.1.1.5.10.10.1.4.15
-- 1.3.6.1.4.1.37950.1.1.5.10.10.1.4.15
-- 1.3.6.1.4.1.37950.1.1.5.10.10.1.4.15
-- 1.3.6.1.4.1.37950.1.1.5.10.10.1.4.15
		-- 1.3.6.1.4.1.37950.1.1.5.10.10.1.4.15
		portBaseProtocol OBJECT-TYPE
			SYNTAX INTEGER (-1..255)
			MAX-ACCESS read-write
			STATUS current
			DESCRIPTION
				"Description."
			::= { portBaseAclCfg 15 }

		
--          1.3.6.1.4.1.37950.1.1.5.10.10.1.4.16
-- 1.3.6.1.4.1.37950.1.1.5.10.10.1.4.16
-- 1.3.6.1.4.1.37950.1.1.5.10.10.1.4.16
-- 1.3.6.1.4.1.37950.1.1.5.10.10.1.4.16
-- 1.3.6.1.4.1.37950.1.1.5.10.10.1.4.16
-- 1.3.6.1.4.1.37950.1.1.5.10.10.1.4.16
-- 1.3.6.1.4.1.37950.1.1.5.10.10.1.4.16
-- 1.3.6.1.4.1.37950.1.1.5.10.10.1.4.16
-- 1.3.6.1.4.1.37950.1.1.5.10.10.1.4.16
		-- 1.3.6.1.4.1.37950.1.1.5.10.10.1.4.16
		portBaseProtocolMask OBJECT-TYPE
			SYNTAX INTEGER (0..255)
			MAX-ACCESS read-write
			STATUS current
			DESCRIPTION
				"Description."
			::= { portBaseAclCfg 16 }

		
--          1.3.6.1.4.1.37950.1.1.5.10.10.1.4.17
-- 1.3.6.1.4.1.37950.1.1.5.10.10.1.4.17
-- 1.3.6.1.4.1.37950.1.1.5.10.10.1.4.17
-- 1.3.6.1.4.1.37950.1.1.5.10.10.1.4.17
-- 1.3.6.1.4.1.37950.1.1.5.10.10.1.4.17
-- 1.3.6.1.4.1.37950.1.1.5.10.10.1.4.17
-- 1.3.6.1.4.1.37950.1.1.5.10.10.1.4.17
-- 1.3.6.1.4.1.37950.1.1.5.10.10.1.4.17
-- 1.3.6.1.4.1.37950.1.1.5.10.10.1.4.17
		-- 1.3.6.1.4.1.37950.1.1.5.10.10.1.4.17
		portBaseTosDscp OBJECT-TYPE
			SYNTAX INTEGER (-1..255)
			MAX-ACCESS read-write
			STATUS current
			DESCRIPTION
				"Description."
			::= { portBaseAclCfg 17 }

		
--          1.3.6.1.4.1.37950.1.1.5.10.10.1.4.18
-- 1.3.6.1.4.1.37950.1.1.5.10.10.1.4.18
-- 1.3.6.1.4.1.37950.1.1.5.10.10.1.4.18
-- 1.3.6.1.4.1.37950.1.1.5.10.10.1.4.18
-- 1.3.6.1.4.1.37950.1.1.5.10.10.1.4.18
-- 1.3.6.1.4.1.37950.1.1.5.10.10.1.4.18
-- 1.3.6.1.4.1.37950.1.1.5.10.10.1.4.18
-- 1.3.6.1.4.1.37950.1.1.5.10.10.1.4.18
-- 1.3.6.1.4.1.37950.1.1.5.10.10.1.4.18
		-- 1.3.6.1.4.1.37950.1.1.5.10.10.1.4.18
		portBaseTosDscpMask OBJECT-TYPE
			SYNTAX INTEGER (0..255)
			MAX-ACCESS read-write
			STATUS current
			DESCRIPTION
				"Description."
			::= { portBaseAclCfg 18 }

		
--          1.3.6.1.4.1.37950.1.1.5.10.10.1.4.19
-- 1.3.6.1.4.1.37950.1.1.5.10.10.1.4.19
-- 1.3.6.1.4.1.37950.1.1.5.10.10.1.4.19
-- 1.3.6.1.4.1.37950.1.1.5.10.10.1.4.19
-- 1.3.6.1.4.1.37950.1.1.5.10.10.1.4.19
-- 1.3.6.1.4.1.37950.1.1.5.10.10.1.4.19
-- 1.3.6.1.4.1.37950.1.1.5.10.10.1.4.19
-- 1.3.6.1.4.1.37950.1.1.5.10.10.1.4.19
-- 1.3.6.1.4.1.37950.1.1.5.10.10.1.4.19
		-- 1.3.6.1.4.1.37950.1.1.5.10.10.1.4.19
		portBaseSrcPort OBJECT-TYPE
			SYNTAX INTEGER (-1..65535)
			MAX-ACCESS read-write
			STATUS current
			DESCRIPTION
				"Description."
			::= { portBaseAclCfg 19 }

		
--          1.3.6.1.4.1.37950.1.1.5.10.10.1.4.20
-- 1.3.6.1.4.1.37950.1.1.5.10.10.1.4.20
-- 1.3.6.1.4.1.37950.1.1.5.10.10.1.4.20
-- 1.3.6.1.4.1.37950.1.1.5.10.10.1.4.20
-- 1.3.6.1.4.1.37950.1.1.5.10.10.1.4.20
-- 1.3.6.1.4.1.37950.1.1.5.10.10.1.4.20
-- 1.3.6.1.4.1.37950.1.1.5.10.10.1.4.20
-- 1.3.6.1.4.1.37950.1.1.5.10.10.1.4.20
-- 1.3.6.1.4.1.37950.1.1.5.10.10.1.4.20
		-- 1.3.6.1.4.1.37950.1.1.5.10.10.1.4.20
		portBaseSrcPortMask OBJECT-TYPE
			SYNTAX OCTET STRING
			MAX-ACCESS read-write
			STATUS current
			DESCRIPTION
				"Description."
			::= { portBaseAclCfg 20 }

		
--          1.3.6.1.4.1.37950.1.1.5.10.10.1.4.21
-- 1.3.6.1.4.1.37950.1.1.5.10.10.1.4.21
-- 1.3.6.1.4.1.37950.1.1.5.10.10.1.4.21
-- 1.3.6.1.4.1.37950.1.1.5.10.10.1.4.21
-- 1.3.6.1.4.1.37950.1.1.5.10.10.1.4.21
-- 1.3.6.1.4.1.37950.1.1.5.10.10.1.4.21
-- 1.3.6.1.4.1.37950.1.1.5.10.10.1.4.21
-- 1.3.6.1.4.1.37950.1.1.5.10.10.1.4.21
-- 1.3.6.1.4.1.37950.1.1.5.10.10.1.4.21
		-- 1.3.6.1.4.1.37950.1.1.5.10.10.1.4.21
		portBaseDstPort OBJECT-TYPE
			SYNTAX INTEGER (-1..65535)
			MAX-ACCESS read-write
			STATUS current
			DESCRIPTION
				"Description."
			::= { portBaseAclCfg 21 }

		
--          1.3.6.1.4.1.37950.1.1.5.10.10.1.4.22
-- 1.3.6.1.4.1.37950.1.1.5.10.10.1.4.22
-- 1.3.6.1.4.1.37950.1.1.5.10.10.1.4.22
-- 1.3.6.1.4.1.37950.1.1.5.10.10.1.4.22
-- 1.3.6.1.4.1.37950.1.1.5.10.10.1.4.22
-- 1.3.6.1.4.1.37950.1.1.5.10.10.1.4.22
-- 1.3.6.1.4.1.37950.1.1.5.10.10.1.4.22
-- 1.3.6.1.4.1.37950.1.1.5.10.10.1.4.22
-- 1.3.6.1.4.1.37950.1.1.5.10.10.1.4.22
		-- 1.3.6.1.4.1.37950.1.1.5.10.10.1.4.22
		portBaseDstPortMask OBJECT-TYPE
			SYNTAX OCTET STRING
			MAX-ACCESS read-write
			STATUS current
			DESCRIPTION
				"Description."
			::= { portBaseAclCfg 22 }

		
--          1.3.6.1.4.1.37950.1.1.5.10.10.1.4.23
-- 1.3.6.1.4.1.37950.1.1.5.10.10.1.4.23
-- 1.3.6.1.4.1.37950.1.1.5.10.10.1.4.23
-- 1.3.6.1.4.1.37950.1.1.5.10.10.1.4.23
-- 1.3.6.1.4.1.37950.1.1.5.10.10.1.4.23
-- 1.3.6.1.4.1.37950.1.1.5.10.10.1.4.23
-- 1.3.6.1.4.1.37950.1.1.5.10.10.1.4.23
-- 1.3.6.1.4.1.37950.1.1.5.10.10.1.4.23
-- 1.3.6.1.4.1.37950.1.1.5.10.10.1.4.23
		-- 1.3.6.1.4.1.37950.1.1.5.10.10.1.4.23
		portBaseAction OBJECT-TYPE
			SYNTAX INTEGER
				{
				add(1),
				delete(2),
				clear(3)
				}
			MAX-ACCESS read-write
			STATUS current
			DESCRIPTION
				"Description."
			::= { portBaseAclCfg 23 }

		
--          1.3.6.1.4.1.37950.1.1.5.10.10.1.5
-- 1.3.6.1.4.1.37950.1.1.5.10.10.1.5
-- 1.3.6.1.4.1.37950.1.1.5.10.10.1.5
-- 1.3.6.1.4.1.37950.1.1.5.10.10.1.5
-- 1.3.6.1.4.1.37950.1.1.5.10.10.1.5
-- 1.3.6.1.4.1.37950.1.1.5.10.10.1.5
-- 1.3.6.1.4.1.37950.1.1.5.10.10.1.5
-- 1.3.6.1.4.1.37950.1.1.5.10.10.1.5
-- 1.3.6.1.4.1.37950.1.1.5.10.10.1.5
		-- 1.3.6.1.4.1.37950.1.1.5.10.10.1.5
		qosBaseAclCfg OBJECT IDENTIFIER ::= { aclCfg 5 }

		
--          1.3.6.1.4.1.37950.1.1.5.10.10.1.5.1
-- 1.3.6.1.4.1.37950.1.1.5.10.10.1.5.1
-- 1.3.6.1.4.1.37950.1.1.5.10.10.1.5.1
-- 1.3.6.1.4.1.37950.1.1.5.10.10.1.5.1
-- 1.3.6.1.4.1.37950.1.1.5.10.10.1.5.1
-- 1.3.6.1.4.1.37950.1.1.5.10.10.1.5.1
-- 1.3.6.1.4.1.37950.1.1.5.10.10.1.5.1
-- 1.3.6.1.4.1.37950.1.1.5.10.10.1.5.1
-- 1.3.6.1.4.1.37950.1.1.5.10.10.1.5.1
		-- 1.3.6.1.4.1.37950.1.1.5.10.10.1.5.1
		qosBaseAclId OBJECT-TYPE
			SYNTAX INTEGER (6000..6999)
			MAX-ACCESS read-write
			STATUS current
			DESCRIPTION
				"Description."
			::= { qosBaseAclCfg 1 }

		
--          1.3.6.1.4.1.37950.1.1.5.10.10.1.5.2
-- 1.3.6.1.4.1.37950.1.1.5.10.10.1.5.2
-- 1.3.6.1.4.1.37950.1.1.5.10.10.1.5.2
-- 1.3.6.1.4.1.37950.1.1.5.10.10.1.5.2
-- 1.3.6.1.4.1.37950.1.1.5.10.10.1.5.2
-- 1.3.6.1.4.1.37950.1.1.5.10.10.1.5.2
-- 1.3.6.1.4.1.37950.1.1.5.10.10.1.5.2
-- 1.3.6.1.4.1.37950.1.1.5.10.10.1.5.2
-- 1.3.6.1.4.1.37950.1.1.5.10.10.1.5.2
		-- 1.3.6.1.4.1.37950.1.1.5.10.10.1.5.2
		qosBaseOutPacketPri OBJECT-TYPE
			SYNTAX INTEGER (0..8)
			MAX-ACCESS read-write
			STATUS current
			DESCRIPTION
				"Description."
			::= { qosBaseAclCfg 2 }

		
--          1.3.6.1.4.1.37950.1.1.5.10.10.1.5.3
-- 1.3.6.1.4.1.37950.1.1.5.10.10.1.5.3
-- 1.3.6.1.4.1.37950.1.1.5.10.10.1.5.3
-- 1.3.6.1.4.1.37950.1.1.5.10.10.1.5.3
-- 1.3.6.1.4.1.37950.1.1.5.10.10.1.5.3
-- 1.3.6.1.4.1.37950.1.1.5.10.10.1.5.3
-- 1.3.6.1.4.1.37950.1.1.5.10.10.1.5.3
-- 1.3.6.1.4.1.37950.1.1.5.10.10.1.5.3
-- 1.3.6.1.4.1.37950.1.1.5.10.10.1.5.3
		-- 1.3.6.1.4.1.37950.1.1.5.10.10.1.5.3
		qosBaseHwTransQueue OBJECT-TYPE
			SYNTAX INTEGER (0..7)
			MAX-ACCESS read-write
			STATUS current
			DESCRIPTION
				"Description."
			::= { qosBaseAclCfg 3 }

		
--          1.3.6.1.4.1.37950.1.1.5.10.10.1.5.4
-- 1.3.6.1.4.1.37950.1.1.5.10.10.1.5.4
-- 1.3.6.1.4.1.37950.1.1.5.10.10.1.5.4
-- 1.3.6.1.4.1.37950.1.1.5.10.10.1.5.4
-- 1.3.6.1.4.1.37950.1.1.5.10.10.1.5.4
-- 1.3.6.1.4.1.37950.1.1.5.10.10.1.5.4
-- 1.3.6.1.4.1.37950.1.1.5.10.10.1.5.4
-- 1.3.6.1.4.1.37950.1.1.5.10.10.1.5.4
-- 1.3.6.1.4.1.37950.1.1.5.10.10.1.5.4
		-- 1.3.6.1.4.1.37950.1.1.5.10.10.1.5.4
		qosBaseRulePri OBJECT-TYPE
			SYNTAX INTEGER (1..12)
			MAX-ACCESS read-write
			STATUS current
			DESCRIPTION
				"Description."
			::= { qosBaseAclCfg 4 }

		
--          1.3.6.1.4.1.37950.1.1.5.10.10.1.5.5
-- 1.3.6.1.4.1.37950.1.1.5.10.10.1.5.5
-- 1.3.6.1.4.1.37950.1.1.5.10.10.1.5.5
-- 1.3.6.1.4.1.37950.1.1.5.10.10.1.5.5
-- 1.3.6.1.4.1.37950.1.1.5.10.10.1.5.5
-- 1.3.6.1.4.1.37950.1.1.5.10.10.1.5.5
-- 1.3.6.1.4.1.37950.1.1.5.10.10.1.5.5
-- 1.3.6.1.4.1.37950.1.1.5.10.10.1.5.5
-- 1.3.6.1.4.1.37950.1.1.5.10.10.1.5.5
		-- 1.3.6.1.4.1.37950.1.1.5.10.10.1.5.5
		qosBaseSrcMac OBJECT-TYPE
			SYNTAX OCTET STRING
			MAX-ACCESS read-write
			STATUS current
			DESCRIPTION
				"Description."
			::= { qosBaseAclCfg 5 }

		
--          1.3.6.1.4.1.37950.1.1.5.10.10.1.5.6
-- 1.3.6.1.4.1.37950.1.1.5.10.10.1.5.6
-- 1.3.6.1.4.1.37950.1.1.5.10.10.1.5.6
-- 1.3.6.1.4.1.37950.1.1.5.10.10.1.5.6
-- 1.3.6.1.4.1.37950.1.1.5.10.10.1.5.6
-- 1.3.6.1.4.1.37950.1.1.5.10.10.1.5.6
-- 1.3.6.1.4.1.37950.1.1.5.10.10.1.5.6
-- 1.3.6.1.4.1.37950.1.1.5.10.10.1.5.6
-- 1.3.6.1.4.1.37950.1.1.5.10.10.1.5.6
		-- 1.3.6.1.4.1.37950.1.1.5.10.10.1.5.6
		qosBaseSrcMacMask OBJECT-TYPE
			SYNTAX OCTET STRING
			MAX-ACCESS read-write
			STATUS current
			DESCRIPTION
				"Description."
			::= { qosBaseAclCfg 6 }

		
--          1.3.6.1.4.1.37950.1.1.5.10.10.1.5.7
-- 1.3.6.1.4.1.37950.1.1.5.10.10.1.5.7
-- 1.3.6.1.4.1.37950.1.1.5.10.10.1.5.7
-- 1.3.6.1.4.1.37950.1.1.5.10.10.1.5.7
-- 1.3.6.1.4.1.37950.1.1.5.10.10.1.5.7
-- 1.3.6.1.4.1.37950.1.1.5.10.10.1.5.7
-- 1.3.6.1.4.1.37950.1.1.5.10.10.1.5.7
-- 1.3.6.1.4.1.37950.1.1.5.10.10.1.5.7
-- 1.3.6.1.4.1.37950.1.1.5.10.10.1.5.7
		-- 1.3.6.1.4.1.37950.1.1.5.10.10.1.5.7
		qosBaseDstMac OBJECT-TYPE
			SYNTAX OCTET STRING
			MAX-ACCESS read-write
			STATUS current
			DESCRIPTION
				"Description."
			::= { qosBaseAclCfg 7 }

		
--          1.3.6.1.4.1.37950.1.1.5.10.10.1.5.8
-- 1.3.6.1.4.1.37950.1.1.5.10.10.1.5.8
-- 1.3.6.1.4.1.37950.1.1.5.10.10.1.5.8
-- 1.3.6.1.4.1.37950.1.1.5.10.10.1.5.8
-- 1.3.6.1.4.1.37950.1.1.5.10.10.1.5.8
-- 1.3.6.1.4.1.37950.1.1.5.10.10.1.5.8
-- 1.3.6.1.4.1.37950.1.1.5.10.10.1.5.8
-- 1.3.6.1.4.1.37950.1.1.5.10.10.1.5.8
-- 1.3.6.1.4.1.37950.1.1.5.10.10.1.5.8
		-- 1.3.6.1.4.1.37950.1.1.5.10.10.1.5.8
		qosBaseDstMacMask OBJECT-TYPE
			SYNTAX OCTET STRING
			MAX-ACCESS read-write
			STATUS current
			DESCRIPTION
				"Description."
			::= { qosBaseAclCfg 8 }

		
--          1.3.6.1.4.1.37950.1.1.5.10.10.1.5.9
-- 1.3.6.1.4.1.37950.1.1.5.10.10.1.5.9
-- 1.3.6.1.4.1.37950.1.1.5.10.10.1.5.9
-- 1.3.6.1.4.1.37950.1.1.5.10.10.1.5.9
-- 1.3.6.1.4.1.37950.1.1.5.10.10.1.5.9
-- 1.3.6.1.4.1.37950.1.1.5.10.10.1.5.9
-- 1.3.6.1.4.1.37950.1.1.5.10.10.1.5.9
-- 1.3.6.1.4.1.37950.1.1.5.10.10.1.5.9
-- 1.3.6.1.4.1.37950.1.1.5.10.10.1.5.9
		-- 1.3.6.1.4.1.37950.1.1.5.10.10.1.5.9
		qosBaseVlan OBJECT-TYPE
			SYNTAX INTEGER (0..4094)
			MAX-ACCESS read-write
			STATUS current
			DESCRIPTION
				"Description."
			::= { qosBaseAclCfg 9 }

		
--          1.3.6.1.4.1.37950.1.1.5.10.10.1.5.10
-- 1.3.6.1.4.1.37950.1.1.5.10.10.1.5.10
-- 1.3.6.1.4.1.37950.1.1.5.10.10.1.5.10
-- 1.3.6.1.4.1.37950.1.1.5.10.10.1.5.10
-- 1.3.6.1.4.1.37950.1.1.5.10.10.1.5.10
-- 1.3.6.1.4.1.37950.1.1.5.10.10.1.5.10
-- 1.3.6.1.4.1.37950.1.1.5.10.10.1.5.10
-- 1.3.6.1.4.1.37950.1.1.5.10.10.1.5.10
-- 1.3.6.1.4.1.37950.1.1.5.10.10.1.5.10
		-- 1.3.6.1.4.1.37950.1.1.5.10.10.1.5.10
		qosBaseVlanMask OBJECT-TYPE
			SYNTAX INTEGER (0..4095)
			MAX-ACCESS read-write
			STATUS current
			DESCRIPTION
				"Description."
			::= { qosBaseAclCfg 10 }

		
--          1.3.6.1.4.1.37950.1.1.5.10.10.1.5.11
-- 1.3.6.1.4.1.37950.1.1.5.10.10.1.5.11
-- 1.3.6.1.4.1.37950.1.1.5.10.10.1.5.11
-- 1.3.6.1.4.1.37950.1.1.5.10.10.1.5.11
-- 1.3.6.1.4.1.37950.1.1.5.10.10.1.5.11
-- 1.3.6.1.4.1.37950.1.1.5.10.10.1.5.11
-- 1.3.6.1.4.1.37950.1.1.5.10.10.1.5.11
-- 1.3.6.1.4.1.37950.1.1.5.10.10.1.5.11
-- 1.3.6.1.4.1.37950.1.1.5.10.10.1.5.11
		-- 1.3.6.1.4.1.37950.1.1.5.10.10.1.5.11
		qosBaseCos OBJECT-TYPE
			SYNTAX INTEGER (-1..7)
			MAX-ACCESS read-write
			STATUS current
			DESCRIPTION
				"Description."
			::= { qosBaseAclCfg 11 }

		
--          1.3.6.1.4.1.37950.1.1.5.10.10.1.5.12
-- 1.3.6.1.4.1.37950.1.1.5.10.10.1.5.12
-- 1.3.6.1.4.1.37950.1.1.5.10.10.1.5.12
-- 1.3.6.1.4.1.37950.1.1.5.10.10.1.5.12
-- 1.3.6.1.4.1.37950.1.1.5.10.10.1.5.12
-- 1.3.6.1.4.1.37950.1.1.5.10.10.1.5.12
-- 1.3.6.1.4.1.37950.1.1.5.10.10.1.5.12
-- 1.3.6.1.4.1.37950.1.1.5.10.10.1.5.12
-- 1.3.6.1.4.1.37950.1.1.5.10.10.1.5.12
		-- 1.3.6.1.4.1.37950.1.1.5.10.10.1.5.12
		qosEthernetType OBJECT-TYPE
			SYNTAX OCTET STRING
			MAX-ACCESS read-write
			STATUS current
			DESCRIPTION
				"Description."
			::= { qosBaseAclCfg 12 }

		
--          1.3.6.1.4.1.37950.1.1.5.10.10.1.5.13
-- 1.3.6.1.4.1.37950.1.1.5.10.10.1.5.13
-- 1.3.6.1.4.1.37950.1.1.5.10.10.1.5.13
-- 1.3.6.1.4.1.37950.1.1.5.10.10.1.5.13
-- 1.3.6.1.4.1.37950.1.1.5.10.10.1.5.13
-- 1.3.6.1.4.1.37950.1.1.5.10.10.1.5.13
-- 1.3.6.1.4.1.37950.1.1.5.10.10.1.5.13
-- 1.3.6.1.4.1.37950.1.1.5.10.10.1.5.13
-- 1.3.6.1.4.1.37950.1.1.5.10.10.1.5.13
		-- 1.3.6.1.4.1.37950.1.1.5.10.10.1.5.13
		qosBaseSrcIp OBJECT-TYPE
			SYNTAX IpAddress
			MAX-ACCESS read-write
			STATUS current
			DESCRIPTION
				"Description."
			::= { qosBaseAclCfg 13 }

		
--          1.3.6.1.4.1.37950.1.1.5.10.10.1.5.14
-- 1.3.6.1.4.1.37950.1.1.5.10.10.1.5.14
-- 1.3.6.1.4.1.37950.1.1.5.10.10.1.5.14
-- 1.3.6.1.4.1.37950.1.1.5.10.10.1.5.14
-- 1.3.6.1.4.1.37950.1.1.5.10.10.1.5.14
-- 1.3.6.1.4.1.37950.1.1.5.10.10.1.5.14
-- 1.3.6.1.4.1.37950.1.1.5.10.10.1.5.14
-- 1.3.6.1.4.1.37950.1.1.5.10.10.1.5.14
-- 1.3.6.1.4.1.37950.1.1.5.10.10.1.5.14
		-- 1.3.6.1.4.1.37950.1.1.5.10.10.1.5.14
		qosBaseSrcIpMask OBJECT-TYPE
			SYNTAX IpAddress
			MAX-ACCESS read-write
			STATUS current
			DESCRIPTION
				"Description."
			::= { qosBaseAclCfg 14 }

		
--          1.3.6.1.4.1.37950.1.1.5.10.10.1.5.15
-- 1.3.6.1.4.1.37950.1.1.5.10.10.1.5.15
-- 1.3.6.1.4.1.37950.1.1.5.10.10.1.5.15
-- 1.3.6.1.4.1.37950.1.1.5.10.10.1.5.15
-- 1.3.6.1.4.1.37950.1.1.5.10.10.1.5.15
-- 1.3.6.1.4.1.37950.1.1.5.10.10.1.5.15
-- 1.3.6.1.4.1.37950.1.1.5.10.10.1.5.15
-- 1.3.6.1.4.1.37950.1.1.5.10.10.1.5.15
-- 1.3.6.1.4.1.37950.1.1.5.10.10.1.5.15
		-- 1.3.6.1.4.1.37950.1.1.5.10.10.1.5.15
		qosBaseDstIp OBJECT-TYPE
			SYNTAX IpAddress
			MAX-ACCESS read-write
			STATUS current
			DESCRIPTION
				"Description."
			::= { qosBaseAclCfg 15 }

		
--          1.3.6.1.4.1.37950.1.1.5.10.10.1.5.16
-- 1.3.6.1.4.1.37950.1.1.5.10.10.1.5.16
-- 1.3.6.1.4.1.37950.1.1.5.10.10.1.5.16
-- 1.3.6.1.4.1.37950.1.1.5.10.10.1.5.16
-- 1.3.6.1.4.1.37950.1.1.5.10.10.1.5.16
-- 1.3.6.1.4.1.37950.1.1.5.10.10.1.5.16
-- 1.3.6.1.4.1.37950.1.1.5.10.10.1.5.16
-- 1.3.6.1.4.1.37950.1.1.5.10.10.1.5.16
-- 1.3.6.1.4.1.37950.1.1.5.10.10.1.5.16
		-- 1.3.6.1.4.1.37950.1.1.5.10.10.1.5.16
		qosBaseDstIpMask OBJECT-TYPE
			SYNTAX IpAddress
			MAX-ACCESS read-write
			STATUS current
			DESCRIPTION
				"Description."
			::= { qosBaseAclCfg 16 }

		
--          1.3.6.1.4.1.37950.1.1.5.10.10.1.5.17
-- 1.3.6.1.4.1.37950.1.1.5.10.10.1.5.17
-- 1.3.6.1.4.1.37950.1.1.5.10.10.1.5.17
-- 1.3.6.1.4.1.37950.1.1.5.10.10.1.5.17
-- 1.3.6.1.4.1.37950.1.1.5.10.10.1.5.17
-- 1.3.6.1.4.1.37950.1.1.5.10.10.1.5.17
-- 1.3.6.1.4.1.37950.1.1.5.10.10.1.5.17
-- 1.3.6.1.4.1.37950.1.1.5.10.10.1.5.17
-- 1.3.6.1.4.1.37950.1.1.5.10.10.1.5.17
		-- 1.3.6.1.4.1.37950.1.1.5.10.10.1.5.17
		qosBaseProtocol OBJECT-TYPE
			SYNTAX INTEGER (-1..255)
			MAX-ACCESS read-write
			STATUS current
			DESCRIPTION
				"Description."
			::= { qosBaseAclCfg 17 }

		
--          1.3.6.1.4.1.37950.1.1.5.10.10.1.5.18
-- 1.3.6.1.4.1.37950.1.1.5.10.10.1.5.18
-- 1.3.6.1.4.1.37950.1.1.5.10.10.1.5.18
-- 1.3.6.1.4.1.37950.1.1.5.10.10.1.5.18
-- 1.3.6.1.4.1.37950.1.1.5.10.10.1.5.18
-- 1.3.6.1.4.1.37950.1.1.5.10.10.1.5.18
-- 1.3.6.1.4.1.37950.1.1.5.10.10.1.5.18
-- 1.3.6.1.4.1.37950.1.1.5.10.10.1.5.18
-- 1.3.6.1.4.1.37950.1.1.5.10.10.1.5.18
		-- 1.3.6.1.4.1.37950.1.1.5.10.10.1.5.18
		qosBaseProtocolMask OBJECT-TYPE
			SYNTAX INTEGER (0..255)
			MAX-ACCESS read-write
			STATUS current
			DESCRIPTION
				"Description."
			::= { qosBaseAclCfg 18 }

		
--          1.3.6.1.4.1.37950.1.1.5.10.10.1.5.19
-- 1.3.6.1.4.1.37950.1.1.5.10.10.1.5.19
-- 1.3.6.1.4.1.37950.1.1.5.10.10.1.5.19
-- 1.3.6.1.4.1.37950.1.1.5.10.10.1.5.19
-- 1.3.6.1.4.1.37950.1.1.5.10.10.1.5.19
-- 1.3.6.1.4.1.37950.1.1.5.10.10.1.5.19
-- 1.3.6.1.4.1.37950.1.1.5.10.10.1.5.19
-- 1.3.6.1.4.1.37950.1.1.5.10.10.1.5.19
-- 1.3.6.1.4.1.37950.1.1.5.10.10.1.5.19
		-- 1.3.6.1.4.1.37950.1.1.5.10.10.1.5.19
		qosBaseTosDscp OBJECT-TYPE
			SYNTAX INTEGER (-1..255)
			MAX-ACCESS read-write
			STATUS current
			DESCRIPTION
				"Description."
			::= { qosBaseAclCfg 19 }

		
--          1.3.6.1.4.1.37950.1.1.5.10.10.1.5.20
-- 1.3.6.1.4.1.37950.1.1.5.10.10.1.5.20
-- 1.3.6.1.4.1.37950.1.1.5.10.10.1.5.20
-- 1.3.6.1.4.1.37950.1.1.5.10.10.1.5.20
-- 1.3.6.1.4.1.37950.1.1.5.10.10.1.5.20
-- 1.3.6.1.4.1.37950.1.1.5.10.10.1.5.20
-- 1.3.6.1.4.1.37950.1.1.5.10.10.1.5.20
-- 1.3.6.1.4.1.37950.1.1.5.10.10.1.5.20
-- 1.3.6.1.4.1.37950.1.1.5.10.10.1.5.20
		-- 1.3.6.1.4.1.37950.1.1.5.10.10.1.5.20
		qosBaseTosDscpMask OBJECT-TYPE
			SYNTAX INTEGER (0..255)
			MAX-ACCESS read-write
			STATUS current
			DESCRIPTION
				"Description."
			::= { qosBaseAclCfg 20 }

		
--          1.3.6.1.4.1.37950.1.1.5.10.10.1.5.21
-- 1.3.6.1.4.1.37950.1.1.5.10.10.1.5.21
-- 1.3.6.1.4.1.37950.1.1.5.10.10.1.5.21
-- 1.3.6.1.4.1.37950.1.1.5.10.10.1.5.21
-- 1.3.6.1.4.1.37950.1.1.5.10.10.1.5.21
-- 1.3.6.1.4.1.37950.1.1.5.10.10.1.5.21
-- 1.3.6.1.4.1.37950.1.1.5.10.10.1.5.21
-- 1.3.6.1.4.1.37950.1.1.5.10.10.1.5.21
-- 1.3.6.1.4.1.37950.1.1.5.10.10.1.5.21
		-- 1.3.6.1.4.1.37950.1.1.5.10.10.1.5.21
		qosBaseSrcPort OBJECT-TYPE
			SYNTAX INTEGER (-1..65535)
			MAX-ACCESS read-write
			STATUS current
			DESCRIPTION
				"Description."
			::= { qosBaseAclCfg 21 }

		
--          1.3.6.1.4.1.37950.1.1.5.10.10.1.5.22
-- 1.3.6.1.4.1.37950.1.1.5.10.10.1.5.22
-- 1.3.6.1.4.1.37950.1.1.5.10.10.1.5.22
-- 1.3.6.1.4.1.37950.1.1.5.10.10.1.5.22
-- 1.3.6.1.4.1.37950.1.1.5.10.10.1.5.22
-- 1.3.6.1.4.1.37950.1.1.5.10.10.1.5.22
-- 1.3.6.1.4.1.37950.1.1.5.10.10.1.5.22
-- 1.3.6.1.4.1.37950.1.1.5.10.10.1.5.22
-- 1.3.6.1.4.1.37950.1.1.5.10.10.1.5.22
		-- 1.3.6.1.4.1.37950.1.1.5.10.10.1.5.22
		qosBaseSrcPortMask OBJECT-TYPE
			SYNTAX OCTET STRING
			MAX-ACCESS read-write
			STATUS current
			DESCRIPTION
				"Description."
			::= { qosBaseAclCfg 22 }

		
--          1.3.6.1.4.1.37950.1.1.5.10.10.1.5.23
-- 1.3.6.1.4.1.37950.1.1.5.10.10.1.5.23
-- 1.3.6.1.4.1.37950.1.1.5.10.10.1.5.23
-- 1.3.6.1.4.1.37950.1.1.5.10.10.1.5.23
-- 1.3.6.1.4.1.37950.1.1.5.10.10.1.5.23
-- 1.3.6.1.4.1.37950.1.1.5.10.10.1.5.23
-- 1.3.6.1.4.1.37950.1.1.5.10.10.1.5.23
-- 1.3.6.1.4.1.37950.1.1.5.10.10.1.5.23
-- 1.3.6.1.4.1.37950.1.1.5.10.10.1.5.23
		-- 1.3.6.1.4.1.37950.1.1.5.10.10.1.5.23
		qosBaseDstPort OBJECT-TYPE
			SYNTAX INTEGER (-1..65535)
			MAX-ACCESS read-write
			STATUS current
			DESCRIPTION
				"Description."
			::= { qosBaseAclCfg 23 }

		
--          1.3.6.1.4.1.37950.1.1.5.10.10.1.5.24
-- 1.3.6.1.4.1.37950.1.1.5.10.10.1.5.24
-- 1.3.6.1.4.1.37950.1.1.5.10.10.1.5.24
-- 1.3.6.1.4.1.37950.1.1.5.10.10.1.5.24
-- 1.3.6.1.4.1.37950.1.1.5.10.10.1.5.24
-- 1.3.6.1.4.1.37950.1.1.5.10.10.1.5.24
-- 1.3.6.1.4.1.37950.1.1.5.10.10.1.5.24
-- 1.3.6.1.4.1.37950.1.1.5.10.10.1.5.24
-- 1.3.6.1.4.1.37950.1.1.5.10.10.1.5.24
		-- 1.3.6.1.4.1.37950.1.1.5.10.10.1.5.24
		qosBaseDstPortMask OBJECT-TYPE
			SYNTAX OCTET STRING
			MAX-ACCESS read-write
			STATUS current
			DESCRIPTION
				"Description."
			::= { qosBaseAclCfg 24 }

		
--          1.3.6.1.4.1.37950.1.1.5.10.10.1.5.25
-- 1.3.6.1.4.1.37950.1.1.5.10.10.1.5.25
-- 1.3.6.1.4.1.37950.1.1.5.10.10.1.5.25
-- 1.3.6.1.4.1.37950.1.1.5.10.10.1.5.25
-- 1.3.6.1.4.1.37950.1.1.5.10.10.1.5.25
-- 1.3.6.1.4.1.37950.1.1.5.10.10.1.5.25
-- 1.3.6.1.4.1.37950.1.1.5.10.10.1.5.25
-- 1.3.6.1.4.1.37950.1.1.5.10.10.1.5.25
-- 1.3.6.1.4.1.37950.1.1.5.10.10.1.5.25
		-- 1.3.6.1.4.1.37950.1.1.5.10.10.1.5.25
		qosBaseAction OBJECT-TYPE
			SYNTAX INTEGER
				{
				add(1),
				delete(2),
				clear(3)
				}
			MAX-ACCESS read-write
			STATUS current
			DESCRIPTION
				"Description."
			::= { qosBaseAclCfg 25 }

		
--          1.3.6.1.4.1.37950.1.1.5.10.10.2
-- 1.3.6.1.4.1.37950.1.1.5.10.10.2
-- 1.3.6.1.4.1.37950.1.1.5.10.10.2
-- 1.3.6.1.4.1.37950.1.1.5.10.10.2
-- 1.3.6.1.4.1.37950.1.1.5.10.10.2
-- 1.3.6.1.4.1.37950.1.1.5.10.10.2
-- 1.3.6.1.4.1.37950.1.1.5.10.10.2
-- 1.3.6.1.4.1.37950.1.1.5.10.10.2
-- 1.3.6.1.4.1.37950.1.1.5.10.10.2
		-- 1.3.6.1.4.1.37950.1.1.5.10.10.2
		aclTable OBJECT IDENTIFIER ::= { v1600dAcl 2 }

		
--          1.3.6.1.4.1.37950.1.1.5.10.10.2.1
-- 1.3.6.1.4.1.37950.1.1.5.10.10.2.1
-- 1.3.6.1.4.1.37950.1.1.5.10.10.2.1
-- 1.3.6.1.4.1.37950.1.1.5.10.10.2.1
-- 1.3.6.1.4.1.37950.1.1.5.10.10.2.1
-- 1.3.6.1.4.1.37950.1.1.5.10.10.2.1
-- 1.3.6.1.4.1.37950.1.1.5.10.10.2.1
-- 1.3.6.1.4.1.37950.1.1.5.10.10.2.1
-- 1.3.6.1.4.1.37950.1.1.5.10.10.2.1
		-- 1.3.6.1.4.1.37950.1.1.5.10.10.2.1
		stdIpFilterTable OBJECT-TYPE
			SYNTAX SEQUENCE OF StdIpFilterEntry
			MAX-ACCESS not-accessible
			STATUS current
			DESCRIPTION
				"Description."
			::= { aclTable 1 }

		
--          1.3.6.1.4.1.37950.1.1.5.10.10.2.1.1
-- 1.3.6.1.4.1.37950.1.1.5.10.10.2.1.1
-- 1.3.6.1.4.1.37950.1.1.5.10.10.2.1.1
-- 1.3.6.1.4.1.37950.1.1.5.10.10.2.1.1
-- 1.3.6.1.4.1.37950.1.1.5.10.10.2.1.1
-- 1.3.6.1.4.1.37950.1.1.5.10.10.2.1.1
-- 1.3.6.1.4.1.37950.1.1.5.10.10.2.1.1
-- 1.3.6.1.4.1.37950.1.1.5.10.10.2.1.1
-- 1.3.6.1.4.1.37950.1.1.5.10.10.2.1.1
		-- 1.3.6.1.4.1.37950.1.1.5.10.10.2.1.1
		stdIpFilterEntry OBJECT-TYPE
			SYNTAX StdIpFilterEntry
			MAX-ACCESS not-accessible
			STATUS current
			DESCRIPTION
				"Description."
			INDEX { stdIpFltId }
			::= { stdIpFilterTable 1 }

		
		StdIpFilterEntry ::=
			SEQUENCE { 
				stdIpFltId
					INTEGER,
				stdIpFltSrcIp
					IpAddress,
				stdIpFltSrcMask
					IpAddress,
				stdIpFltMode
					INTEGER
			 }

--          1.3.6.1.4.1.37950.1.1.5.10.10.2.1.1.1
-- 1.3.6.1.4.1.37950.1.1.5.10.10.2.1.1.1
-- 1.3.6.1.4.1.37950.1.1.5.10.10.2.1.1.1
-- 1.3.6.1.4.1.37950.1.1.5.10.10.2.1.1.1
-- 1.3.6.1.4.1.37950.1.1.5.10.10.2.1.1.1
-- 1.3.6.1.4.1.37950.1.1.5.10.10.2.1.1.1
-- 1.3.6.1.4.1.37950.1.1.5.10.10.2.1.1.1
-- 1.3.6.1.4.1.37950.1.1.5.10.10.2.1.1.1
-- 1.3.6.1.4.1.37950.1.1.5.10.10.2.1.1.1
		-- 1.3.6.1.4.1.37950.1.1.5.10.10.2.1.1.1
		stdIpFltId OBJECT-TYPE
			SYNTAX INTEGER (0..999)
			MAX-ACCESS read-only
			STATUS current
			DESCRIPTION
				"Description."
			::= { stdIpFilterEntry 1 }

		
--          1.3.6.1.4.1.37950.1.1.5.10.10.2.1.1.2
-- 1.3.6.1.4.1.37950.1.1.5.10.10.2.1.1.2
-- 1.3.6.1.4.1.37950.1.1.5.10.10.2.1.1.2
-- 1.3.6.1.4.1.37950.1.1.5.10.10.2.1.1.2
-- 1.3.6.1.4.1.37950.1.1.5.10.10.2.1.1.2
-- 1.3.6.1.4.1.37950.1.1.5.10.10.2.1.1.2
-- 1.3.6.1.4.1.37950.1.1.5.10.10.2.1.1.2
-- 1.3.6.1.4.1.37950.1.1.5.10.10.2.1.1.2
-- 1.3.6.1.4.1.37950.1.1.5.10.10.2.1.1.2
		-- 1.3.6.1.4.1.37950.1.1.5.10.10.2.1.1.2
		stdIpFltSrcIp OBJECT-TYPE
			SYNTAX IpAddress
			MAX-ACCESS read-only
			STATUS current
			DESCRIPTION
				"Description."
			::= { stdIpFilterEntry 2 }

		
--          1.3.6.1.4.1.37950.1.1.5.10.10.2.1.1.3
-- 1.3.6.1.4.1.37950.1.1.5.10.10.2.1.1.3
-- 1.3.6.1.4.1.37950.1.1.5.10.10.2.1.1.3
-- 1.3.6.1.4.1.37950.1.1.5.10.10.2.1.1.3
-- 1.3.6.1.4.1.37950.1.1.5.10.10.2.1.1.3
-- 1.3.6.1.4.1.37950.1.1.5.10.10.2.1.1.3
-- 1.3.6.1.4.1.37950.1.1.5.10.10.2.1.1.3
-- 1.3.6.1.4.1.37950.1.1.5.10.10.2.1.1.3
-- 1.3.6.1.4.1.37950.1.1.5.10.10.2.1.1.3
		-- 1.3.6.1.4.1.37950.1.1.5.10.10.2.1.1.3
		stdIpFltSrcMask OBJECT-TYPE
			SYNTAX IpAddress
			MAX-ACCESS read-only
			STATUS current
			DESCRIPTION
				"Description."
			::= { stdIpFilterEntry 3 }

		
--          1.3.6.1.4.1.37950.1.1.5.10.10.2.1.1.4
-- 1.3.6.1.4.1.37950.1.1.5.10.10.2.1.1.4
-- 1.3.6.1.4.1.37950.1.1.5.10.10.2.1.1.4
-- 1.3.6.1.4.1.37950.1.1.5.10.10.2.1.1.4
-- 1.3.6.1.4.1.37950.1.1.5.10.10.2.1.1.4
-- 1.3.6.1.4.1.37950.1.1.5.10.10.2.1.1.4
-- 1.3.6.1.4.1.37950.1.1.5.10.10.2.1.1.4
-- 1.3.6.1.4.1.37950.1.1.5.10.10.2.1.1.4
-- 1.3.6.1.4.1.37950.1.1.5.10.10.2.1.1.4
		-- 1.3.6.1.4.1.37950.1.1.5.10.10.2.1.1.4
		stdIpFltMode OBJECT-TYPE
			SYNTAX INTEGER
				{
				permit(1),
				deny(2)
				}
			MAX-ACCESS read-only
			STATUS current
			DESCRIPTION
				"Description."
			::= { stdIpFilterEntry 4 }

		
--          1.3.6.1.4.1.37950.1.1.5.10.10.2.2
-- 1.3.6.1.4.1.37950.1.1.5.10.10.2.2
-- 1.3.6.1.4.1.37950.1.1.5.10.10.2.2
-- 1.3.6.1.4.1.37950.1.1.5.10.10.2.2
-- 1.3.6.1.4.1.37950.1.1.5.10.10.2.2
-- 1.3.6.1.4.1.37950.1.1.5.10.10.2.2
-- 1.3.6.1.4.1.37950.1.1.5.10.10.2.2
-- 1.3.6.1.4.1.37950.1.1.5.10.10.2.2
-- 1.3.6.1.4.1.37950.1.1.5.10.10.2.2
		-- 1.3.6.1.4.1.37950.1.1.5.10.10.2.2
		extIpFilterTable OBJECT-TYPE
			SYNTAX SEQUENCE OF ExtIpFilterEntry
			MAX-ACCESS not-accessible
			STATUS current
			DESCRIPTION
				"Description."
			::= { aclTable 2 }

		
--          1.3.6.1.4.1.37950.1.1.5.10.10.2.2.1
-- 1.3.6.1.4.1.37950.1.1.5.10.10.2.2.1
-- 1.3.6.1.4.1.37950.1.1.5.10.10.2.2.1
-- 1.3.6.1.4.1.37950.1.1.5.10.10.2.2.1
-- 1.3.6.1.4.1.37950.1.1.5.10.10.2.2.1
-- 1.3.6.1.4.1.37950.1.1.5.10.10.2.2.1
-- 1.3.6.1.4.1.37950.1.1.5.10.10.2.2.1
-- 1.3.6.1.4.1.37950.1.1.5.10.10.2.2.1
-- 1.3.6.1.4.1.37950.1.1.5.10.10.2.2.1
		-- 1.3.6.1.4.1.37950.1.1.5.10.10.2.2.1
		extIpFilterEntry OBJECT-TYPE
			SYNTAX ExtIpFilterEntry
			MAX-ACCESS not-accessible
			STATUS current
			DESCRIPTION
				"Description."
			INDEX { extIpFltId }
			::= { extIpFilterTable 1 }

		
		ExtIpFilterEntry ::=
			SEQUENCE { 
				extIpFltId
					INTEGER,
				extIpFltProtocol
					INTEGER,
				extIpFltSrcIp
					IpAddress,
				extIpFltSrcMask
					IpAddress,
				extIpFltSrcPort
					INTEGER,
				extIpFltDstIp
					IpAddress,
				extIpFltDstMask
					IpAddress,
				extIpFltDstPort
					INTEGER,
				extIpFltDscp
					INTEGER,
				extIpFltMode
					INTEGER
			 }

--          1.3.6.1.4.1.37950.1.1.5.10.10.2.2.1.1
-- 1.3.6.1.4.1.37950.1.1.5.10.10.2.2.1.1
-- 1.3.6.1.4.1.37950.1.1.5.10.10.2.2.1.1
-- 1.3.6.1.4.1.37950.1.1.5.10.10.2.2.1.1
-- 1.3.6.1.4.1.37950.1.1.5.10.10.2.2.1.1
-- 1.3.6.1.4.1.37950.1.1.5.10.10.2.2.1.1
-- 1.3.6.1.4.1.37950.1.1.5.10.10.2.2.1.1
-- 1.3.6.1.4.1.37950.1.1.5.10.10.2.2.1.1
-- 1.3.6.1.4.1.37950.1.1.5.10.10.2.2.1.1
		-- 1.3.6.1.4.1.37950.1.1.5.10.10.2.2.1.1
		extIpFltId OBJECT-TYPE
			SYNTAX INTEGER (1000..1999)
			MAX-ACCESS read-only
			STATUS current
			DESCRIPTION
				"Description."
			::= { extIpFilterEntry 1 }

		
--          1.3.6.1.4.1.37950.1.1.5.10.10.2.2.1.2
-- 1.3.6.1.4.1.37950.1.1.5.10.10.2.2.1.2
-- 1.3.6.1.4.1.37950.1.1.5.10.10.2.2.1.2
-- 1.3.6.1.4.1.37950.1.1.5.10.10.2.2.1.2
-- 1.3.6.1.4.1.37950.1.1.5.10.10.2.2.1.2
-- 1.3.6.1.4.1.37950.1.1.5.10.10.2.2.1.2
-- 1.3.6.1.4.1.37950.1.1.5.10.10.2.2.1.2
-- 1.3.6.1.4.1.37950.1.1.5.10.10.2.2.1.2
-- 1.3.6.1.4.1.37950.1.1.5.10.10.2.2.1.2
		-- 1.3.6.1.4.1.37950.1.1.5.10.10.2.2.1.2
		extIpFltProtocol OBJECT-TYPE
			SYNTAX INTEGER (-1..255)
			MAX-ACCESS read-only
			STATUS current
			DESCRIPTION
				"Description."
			::= { extIpFilterEntry 2 }

		
--          1.3.6.1.4.1.37950.1.1.5.10.10.2.2.1.3
-- 1.3.6.1.4.1.37950.1.1.5.10.10.2.2.1.3
-- 1.3.6.1.4.1.37950.1.1.5.10.10.2.2.1.3
-- 1.3.6.1.4.1.37950.1.1.5.10.10.2.2.1.3
-- 1.3.6.1.4.1.37950.1.1.5.10.10.2.2.1.3
-- 1.3.6.1.4.1.37950.1.1.5.10.10.2.2.1.3
-- 1.3.6.1.4.1.37950.1.1.5.10.10.2.2.1.3
-- 1.3.6.1.4.1.37950.1.1.5.10.10.2.2.1.3
-- 1.3.6.1.4.1.37950.1.1.5.10.10.2.2.1.3
		-- 1.3.6.1.4.1.37950.1.1.5.10.10.2.2.1.3
		extIpFltSrcIp OBJECT-TYPE
			SYNTAX IpAddress
			MAX-ACCESS read-only
			STATUS current
			DESCRIPTION
				"Description."
			::= { extIpFilterEntry 3 }

		
--          1.3.6.1.4.1.37950.1.1.5.10.10.2.2.1.4
-- 1.3.6.1.4.1.37950.1.1.5.10.10.2.2.1.4
-- 1.3.6.1.4.1.37950.1.1.5.10.10.2.2.1.4
-- 1.3.6.1.4.1.37950.1.1.5.10.10.2.2.1.4
-- 1.3.6.1.4.1.37950.1.1.5.10.10.2.2.1.4
-- 1.3.6.1.4.1.37950.1.1.5.10.10.2.2.1.4
-- 1.3.6.1.4.1.37950.1.1.5.10.10.2.2.1.4
-- 1.3.6.1.4.1.37950.1.1.5.10.10.2.2.1.4
-- 1.3.6.1.4.1.37950.1.1.5.10.10.2.2.1.4
		-- 1.3.6.1.4.1.37950.1.1.5.10.10.2.2.1.4
		extIpFltSrcMask OBJECT-TYPE
			SYNTAX IpAddress
			MAX-ACCESS read-only
			STATUS current
			DESCRIPTION
				"Description."
			::= { extIpFilterEntry 4 }

		
--          1.3.6.1.4.1.37950.1.1.5.10.10.2.2.1.5
-- 1.3.6.1.4.1.37950.1.1.5.10.10.2.2.1.5
-- 1.3.6.1.4.1.37950.1.1.5.10.10.2.2.1.5
-- 1.3.6.1.4.1.37950.1.1.5.10.10.2.2.1.5
-- 1.3.6.1.4.1.37950.1.1.5.10.10.2.2.1.5
-- 1.3.6.1.4.1.37950.1.1.5.10.10.2.2.1.5
-- 1.3.6.1.4.1.37950.1.1.5.10.10.2.2.1.5
-- 1.3.6.1.4.1.37950.1.1.5.10.10.2.2.1.5
-- 1.3.6.1.4.1.37950.1.1.5.10.10.2.2.1.5
		-- 1.3.6.1.4.1.37950.1.1.5.10.10.2.2.1.5
		extIpFltSrcPort OBJECT-TYPE
			SYNTAX INTEGER (-1..65535)
			MAX-ACCESS read-write
			STATUS current
			DESCRIPTION
				"Description."
			::= { extIpFilterEntry 5 }

		
--          1.3.6.1.4.1.37950.1.1.5.10.10.2.2.1.6
-- 1.3.6.1.4.1.37950.1.1.5.10.10.2.2.1.6
-- 1.3.6.1.4.1.37950.1.1.5.10.10.2.2.1.6
-- 1.3.6.1.4.1.37950.1.1.5.10.10.2.2.1.6
-- 1.3.6.1.4.1.37950.1.1.5.10.10.2.2.1.6
-- 1.3.6.1.4.1.37950.1.1.5.10.10.2.2.1.6
-- 1.3.6.1.4.1.37950.1.1.5.10.10.2.2.1.6
-- 1.3.6.1.4.1.37950.1.1.5.10.10.2.2.1.6
-- 1.3.6.1.4.1.37950.1.1.5.10.10.2.2.1.6
		-- 1.3.6.1.4.1.37950.1.1.5.10.10.2.2.1.6
		extIpFltDstIp OBJECT-TYPE
			SYNTAX IpAddress
			MAX-ACCESS read-only
			STATUS current
			DESCRIPTION
				"Description."
			::= { extIpFilterEntry 6 }

		
--          1.3.6.1.4.1.37950.1.1.5.10.10.2.2.1.7
-- 1.3.6.1.4.1.37950.1.1.5.10.10.2.2.1.7
-- 1.3.6.1.4.1.37950.1.1.5.10.10.2.2.1.7
-- 1.3.6.1.4.1.37950.1.1.5.10.10.2.2.1.7
-- 1.3.6.1.4.1.37950.1.1.5.10.10.2.2.1.7
-- 1.3.6.1.4.1.37950.1.1.5.10.10.2.2.1.7
-- 1.3.6.1.4.1.37950.1.1.5.10.10.2.2.1.7
-- 1.3.6.1.4.1.37950.1.1.5.10.10.2.2.1.7
-- 1.3.6.1.4.1.37950.1.1.5.10.10.2.2.1.7
		-- 1.3.6.1.4.1.37950.1.1.5.10.10.2.2.1.7
		extIpFltDstMask OBJECT-TYPE
			SYNTAX IpAddress
			MAX-ACCESS read-only
			STATUS current
			DESCRIPTION
				"Description."
			::= { extIpFilterEntry 7 }

		
--          1.3.6.1.4.1.37950.1.1.5.10.10.2.2.1.8
-- 1.3.6.1.4.1.37950.1.1.5.10.10.2.2.1.8
-- 1.3.6.1.4.1.37950.1.1.5.10.10.2.2.1.8
-- 1.3.6.1.4.1.37950.1.1.5.10.10.2.2.1.8
-- 1.3.6.1.4.1.37950.1.1.5.10.10.2.2.1.8
-- 1.3.6.1.4.1.37950.1.1.5.10.10.2.2.1.8
-- 1.3.6.1.4.1.37950.1.1.5.10.10.2.2.1.8
-- 1.3.6.1.4.1.37950.1.1.5.10.10.2.2.1.8
-- 1.3.6.1.4.1.37950.1.1.5.10.10.2.2.1.8
		-- 1.3.6.1.4.1.37950.1.1.5.10.10.2.2.1.8
		extIpFltDstPort OBJECT-TYPE
			SYNTAX INTEGER (-1..65535)
			MAX-ACCESS read-only
			STATUS current
			DESCRIPTION
				"Description."
			::= { extIpFilterEntry 8 }

		
--          1.3.6.1.4.1.37950.1.1.5.10.10.2.2.1.9
-- 1.3.6.1.4.1.37950.1.1.5.10.10.2.2.1.9
-- 1.3.6.1.4.1.37950.1.1.5.10.10.2.2.1.9
-- 1.3.6.1.4.1.37950.1.1.5.10.10.2.2.1.9
-- 1.3.6.1.4.1.37950.1.1.5.10.10.2.2.1.9
-- 1.3.6.1.4.1.37950.1.1.5.10.10.2.2.1.9
-- 1.3.6.1.4.1.37950.1.1.5.10.10.2.2.1.9
-- 1.3.6.1.4.1.37950.1.1.5.10.10.2.2.1.9
-- 1.3.6.1.4.1.37950.1.1.5.10.10.2.2.1.9
		-- 1.3.6.1.4.1.37950.1.1.5.10.10.2.2.1.9
		extIpFltDscp OBJECT-TYPE
			SYNTAX INTEGER (-1..63)
			MAX-ACCESS read-only
			STATUS current
			DESCRIPTION
				"Description."
			::= { extIpFilterEntry 9 }

		
--          1.3.6.1.4.1.37950.1.1.5.10.10.2.2.1.10
-- 1.3.6.1.4.1.37950.1.1.5.10.10.2.2.1.10
-- 1.3.6.1.4.1.37950.1.1.5.10.10.2.2.1.10
-- 1.3.6.1.4.1.37950.1.1.5.10.10.2.2.1.10
-- 1.3.6.1.4.1.37950.1.1.5.10.10.2.2.1.10
-- 1.3.6.1.4.1.37950.1.1.5.10.10.2.2.1.10
-- 1.3.6.1.4.1.37950.1.1.5.10.10.2.2.1.10
-- 1.3.6.1.4.1.37950.1.1.5.10.10.2.2.1.10
-- 1.3.6.1.4.1.37950.1.1.5.10.10.2.2.1.10
		-- 1.3.6.1.4.1.37950.1.1.5.10.10.2.2.1.10
		extIpFltMode OBJECT-TYPE
			SYNTAX INTEGER
				{
				permit(1),
				deny(2)
				}
			MAX-ACCESS read-only
			STATUS current
			DESCRIPTION
				"Description."
			::= { extIpFilterEntry 10 }

		
--          1.3.6.1.4.1.37950.1.1.5.10.10.2.3
-- 1.3.6.1.4.1.37950.1.1.5.10.10.2.3
-- 1.3.6.1.4.1.37950.1.1.5.10.10.2.3
-- 1.3.6.1.4.1.37950.1.1.5.10.10.2.3
-- 1.3.6.1.4.1.37950.1.1.5.10.10.2.3
-- 1.3.6.1.4.1.37950.1.1.5.10.10.2.3
-- 1.3.6.1.4.1.37950.1.1.5.10.10.2.3
-- 1.3.6.1.4.1.37950.1.1.5.10.10.2.3
-- 1.3.6.1.4.1.37950.1.1.5.10.10.2.3
		-- 1.3.6.1.4.1.37950.1.1.5.10.10.2.3
		macFilterTable OBJECT-TYPE
			SYNTAX SEQUENCE OF MacFilterEntry
			MAX-ACCESS not-accessible
			STATUS current
			DESCRIPTION
				"Description."
			::= { aclTable 3 }

		
--          1.3.6.1.4.1.37950.1.1.5.10.10.2.3.1
-- 1.3.6.1.4.1.37950.1.1.5.10.10.2.3.1
-- 1.3.6.1.4.1.37950.1.1.5.10.10.2.3.1
-- 1.3.6.1.4.1.37950.1.1.5.10.10.2.3.1
-- 1.3.6.1.4.1.37950.1.1.5.10.10.2.3.1
-- 1.3.6.1.4.1.37950.1.1.5.10.10.2.3.1
-- 1.3.6.1.4.1.37950.1.1.5.10.10.2.3.1
-- 1.3.6.1.4.1.37950.1.1.5.10.10.2.3.1
-- 1.3.6.1.4.1.37950.1.1.5.10.10.2.3.1
		-- 1.3.6.1.4.1.37950.1.1.5.10.10.2.3.1
		macFilterEntry OBJECT-TYPE
			SYNTAX MacFilterEntry
			MAX-ACCESS not-accessible
			STATUS current
			DESCRIPTION
				"Description."
			INDEX { macFltId }
			::= { macFilterTable 1 }

		
		MacFilterEntry ::=
			SEQUENCE { 
				macFltId
					INTEGER,
				macFltSrcMac
					OCTET STRING,
				macFltSrcMacMask
					OCTET STRING,
				macFltDstMac
					OCTET STRING,
				macFltDstMacMask
					OCTET STRING,
				macFltVlanId
					INTEGER,
				macFltCos
					INTEGER,
				macFltEthType
					OCTET STRING,
				macFltEthTypeMask
					OCTET STRING,
				macFltMode
					INTEGER
			 }

--          1.3.6.1.4.1.37950.1.1.5.10.10.2.3.1.1
-- 1.3.6.1.4.1.37950.1.1.5.10.10.2.3.1.1
-- 1.3.6.1.4.1.37950.1.1.5.10.10.2.3.1.1
-- 1.3.6.1.4.1.37950.1.1.5.10.10.2.3.1.1
-- 1.3.6.1.4.1.37950.1.1.5.10.10.2.3.1.1
-- 1.3.6.1.4.1.37950.1.1.5.10.10.2.3.1.1
-- 1.3.6.1.4.1.37950.1.1.5.10.10.2.3.1.1
-- 1.3.6.1.4.1.37950.1.1.5.10.10.2.3.1.1
-- 1.3.6.1.4.1.37950.1.1.5.10.10.2.3.1.1
		-- 1.3.6.1.4.1.37950.1.1.5.10.10.2.3.1.1
		macFltId OBJECT-TYPE
			SYNTAX INTEGER (2000..2999)
			MAX-ACCESS read-only
			STATUS current
			DESCRIPTION
				"Description."
			::= { macFilterEntry 1 }

		
--          1.3.6.1.4.1.37950.1.1.5.10.10.2.3.1.2
-- 1.3.6.1.4.1.37950.1.1.5.10.10.2.3.1.2
-- 1.3.6.1.4.1.37950.1.1.5.10.10.2.3.1.2
-- 1.3.6.1.4.1.37950.1.1.5.10.10.2.3.1.2
-- 1.3.6.1.4.1.37950.1.1.5.10.10.2.3.1.2
-- 1.3.6.1.4.1.37950.1.1.5.10.10.2.3.1.2
-- 1.3.6.1.4.1.37950.1.1.5.10.10.2.3.1.2
-- 1.3.6.1.4.1.37950.1.1.5.10.10.2.3.1.2
-- 1.3.6.1.4.1.37950.1.1.5.10.10.2.3.1.2
		-- 1.3.6.1.4.1.37950.1.1.5.10.10.2.3.1.2
		macFltSrcMac OBJECT-TYPE
			SYNTAX OCTET STRING
			MAX-ACCESS read-only
			STATUS current
			DESCRIPTION
				"Description."
			::= { macFilterEntry 2 }

		
--          1.3.6.1.4.1.37950.1.1.5.10.10.2.3.1.3
-- 1.3.6.1.4.1.37950.1.1.5.10.10.2.3.1.3
-- 1.3.6.1.4.1.37950.1.1.5.10.10.2.3.1.3
-- 1.3.6.1.4.1.37950.1.1.5.10.10.2.3.1.3
-- 1.3.6.1.4.1.37950.1.1.5.10.10.2.3.1.3
-- 1.3.6.1.4.1.37950.1.1.5.10.10.2.3.1.3
-- 1.3.6.1.4.1.37950.1.1.5.10.10.2.3.1.3
-- 1.3.6.1.4.1.37950.1.1.5.10.10.2.3.1.3
-- 1.3.6.1.4.1.37950.1.1.5.10.10.2.3.1.3
		-- 1.3.6.1.4.1.37950.1.1.5.10.10.2.3.1.3
		macFltSrcMacMask OBJECT-TYPE
			SYNTAX OCTET STRING
			MAX-ACCESS read-only
			STATUS current
			DESCRIPTION
				"Description."
			::= { macFilterEntry 3 }

		
--          1.3.6.1.4.1.37950.1.1.5.10.10.2.3.1.4
-- 1.3.6.1.4.1.37950.1.1.5.10.10.2.3.1.4
-- 1.3.6.1.4.1.37950.1.1.5.10.10.2.3.1.4
-- 1.3.6.1.4.1.37950.1.1.5.10.10.2.3.1.4
-- 1.3.6.1.4.1.37950.1.1.5.10.10.2.3.1.4
-- 1.3.6.1.4.1.37950.1.1.5.10.10.2.3.1.4
-- 1.3.6.1.4.1.37950.1.1.5.10.10.2.3.1.4
-- 1.3.6.1.4.1.37950.1.1.5.10.10.2.3.1.4
-- 1.3.6.1.4.1.37950.1.1.5.10.10.2.3.1.4
		-- 1.3.6.1.4.1.37950.1.1.5.10.10.2.3.1.4
		macFltDstMac OBJECT-TYPE
			SYNTAX OCTET STRING
			MAX-ACCESS read-only
			STATUS current
			DESCRIPTION
				"Description."
			::= { macFilterEntry 4 }

		
--          1.3.6.1.4.1.37950.1.1.5.10.10.2.3.1.5
-- 1.3.6.1.4.1.37950.1.1.5.10.10.2.3.1.5
-- 1.3.6.1.4.1.37950.1.1.5.10.10.2.3.1.5
-- 1.3.6.1.4.1.37950.1.1.5.10.10.2.3.1.5
-- 1.3.6.1.4.1.37950.1.1.5.10.10.2.3.1.5
-- 1.3.6.1.4.1.37950.1.1.5.10.10.2.3.1.5
-- 1.3.6.1.4.1.37950.1.1.5.10.10.2.3.1.5
-- 1.3.6.1.4.1.37950.1.1.5.10.10.2.3.1.5
-- 1.3.6.1.4.1.37950.1.1.5.10.10.2.3.1.5
		-- 1.3.6.1.4.1.37950.1.1.5.10.10.2.3.1.5
		macFltDstMacMask OBJECT-TYPE
			SYNTAX OCTET STRING
			MAX-ACCESS read-only
			STATUS current
			DESCRIPTION
				"Description."
			::= { macFilterEntry 5 }

		
--          1.3.6.1.4.1.37950.1.1.5.10.10.2.3.1.6
-- 1.3.6.1.4.1.37950.1.1.5.10.10.2.3.1.6
-- 1.3.6.1.4.1.37950.1.1.5.10.10.2.3.1.6
-- 1.3.6.1.4.1.37950.1.1.5.10.10.2.3.1.6
-- 1.3.6.1.4.1.37950.1.1.5.10.10.2.3.1.6
-- 1.3.6.1.4.1.37950.1.1.5.10.10.2.3.1.6
-- 1.3.6.1.4.1.37950.1.1.5.10.10.2.3.1.6
-- 1.3.6.1.4.1.37950.1.1.5.10.10.2.3.1.6
-- 1.3.6.1.4.1.37950.1.1.5.10.10.2.3.1.6
		-- 1.3.6.1.4.1.37950.1.1.5.10.10.2.3.1.6
		macFltVlanId OBJECT-TYPE
			SYNTAX INTEGER (0..4094)
			MAX-ACCESS read-only
			STATUS current
			DESCRIPTION
				"Description."
			::= { macFilterEntry 6 }

		
--          1.3.6.1.4.1.37950.1.1.5.10.10.2.3.1.7
-- 1.3.6.1.4.1.37950.1.1.5.10.10.2.3.1.7
-- 1.3.6.1.4.1.37950.1.1.5.10.10.2.3.1.7
-- 1.3.6.1.4.1.37950.1.1.5.10.10.2.3.1.7
-- 1.3.6.1.4.1.37950.1.1.5.10.10.2.3.1.7
-- 1.3.6.1.4.1.37950.1.1.5.10.10.2.3.1.7
-- 1.3.6.1.4.1.37950.1.1.5.10.10.2.3.1.7
-- 1.3.6.1.4.1.37950.1.1.5.10.10.2.3.1.7
-- 1.3.6.1.4.1.37950.1.1.5.10.10.2.3.1.7
		-- 1.3.6.1.4.1.37950.1.1.5.10.10.2.3.1.7
		macFltCos OBJECT-TYPE
			SYNTAX INTEGER (-1..7)
			MAX-ACCESS read-only
			STATUS current
			DESCRIPTION
				"Description."
			::= { macFilterEntry 7 }

		
--          1.3.6.1.4.1.37950.1.1.5.10.10.2.3.1.8
-- 1.3.6.1.4.1.37950.1.1.5.10.10.2.3.1.8
-- 1.3.6.1.4.1.37950.1.1.5.10.10.2.3.1.8
-- 1.3.6.1.4.1.37950.1.1.5.10.10.2.3.1.8
-- 1.3.6.1.4.1.37950.1.1.5.10.10.2.3.1.8
-- 1.3.6.1.4.1.37950.1.1.5.10.10.2.3.1.8
-- 1.3.6.1.4.1.37950.1.1.5.10.10.2.3.1.8
-- 1.3.6.1.4.1.37950.1.1.5.10.10.2.3.1.8
-- 1.3.6.1.4.1.37950.1.1.5.10.10.2.3.1.8
		-- 1.3.6.1.4.1.37950.1.1.5.10.10.2.3.1.8
		macFltEthType OBJECT-TYPE
			SYNTAX OCTET STRING
			MAX-ACCESS read-write
			STATUS current
			DESCRIPTION
				"Description."
			::= { macFilterEntry 8 }

		
--          1.3.6.1.4.1.37950.1.1.5.10.10.2.3.1.9
-- 1.3.6.1.4.1.37950.1.1.5.10.10.2.3.1.9
-- 1.3.6.1.4.1.37950.1.1.5.10.10.2.3.1.9
-- 1.3.6.1.4.1.37950.1.1.5.10.10.2.3.1.9
-- 1.3.6.1.4.1.37950.1.1.5.10.10.2.3.1.9
-- 1.3.6.1.4.1.37950.1.1.5.10.10.2.3.1.9
-- 1.3.6.1.4.1.37950.1.1.5.10.10.2.3.1.9
-- 1.3.6.1.4.1.37950.1.1.5.10.10.2.3.1.9
-- 1.3.6.1.4.1.37950.1.1.5.10.10.2.3.1.9
		-- 1.3.6.1.4.1.37950.1.1.5.10.10.2.3.1.9
		macFltEthTypeMask OBJECT-TYPE
			SYNTAX OCTET STRING
			MAX-ACCESS read-write
			STATUS current
			DESCRIPTION
				"Description."
			::= { macFilterEntry 9 }

		
--          1.3.6.1.4.1.37950.1.1.5.10.10.2.3.1.10
-- 1.3.6.1.4.1.37950.1.1.5.10.10.2.3.1.10
-- 1.3.6.1.4.1.37950.1.1.5.10.10.2.3.1.10
-- 1.3.6.1.4.1.37950.1.1.5.10.10.2.3.1.10
-- 1.3.6.1.4.1.37950.1.1.5.10.10.2.3.1.10
-- 1.3.6.1.4.1.37950.1.1.5.10.10.2.3.1.10
-- 1.3.6.1.4.1.37950.1.1.5.10.10.2.3.1.10
-- 1.3.6.1.4.1.37950.1.1.5.10.10.2.3.1.10
-- 1.3.6.1.4.1.37950.1.1.5.10.10.2.3.1.10
		-- 1.3.6.1.4.1.37950.1.1.5.10.10.2.3.1.10
		macFltMode OBJECT-TYPE
			SYNTAX INTEGER
				{
				permit(1),
				deny(2)
				}
			MAX-ACCESS read-only
			STATUS current
			DESCRIPTION
				"Description."
			::= { macFilterEntry 10 }

		
--          1.3.6.1.4.1.37950.1.1.5.10.10.2.4
-- 1.3.6.1.4.1.37950.1.1.5.10.10.2.4
-- 1.3.6.1.4.1.37950.1.1.5.10.10.2.4
-- 1.3.6.1.4.1.37950.1.1.5.10.10.2.4
-- 1.3.6.1.4.1.37950.1.1.5.10.10.2.4
-- 1.3.6.1.4.1.37950.1.1.5.10.10.2.4
-- 1.3.6.1.4.1.37950.1.1.5.10.10.2.4
-- 1.3.6.1.4.1.37950.1.1.5.10.10.2.4
-- 1.3.6.1.4.1.37950.1.1.5.10.10.2.4
		-- 1.3.6.1.4.1.37950.1.1.5.10.10.2.4
		portBaseAclTable OBJECT-TYPE
			SYNTAX SEQUENCE OF PortBaseAclEntry
			MAX-ACCESS not-accessible
			STATUS current
			DESCRIPTION
				"Description."
			::= { aclTable 4 }

		
--          1.3.6.1.4.1.37950.1.1.5.10.10.2.4.1
-- 1.3.6.1.4.1.37950.1.1.5.10.10.2.4.1
-- 1.3.6.1.4.1.37950.1.1.5.10.10.2.4.1
-- 1.3.6.1.4.1.37950.1.1.5.10.10.2.4.1
-- 1.3.6.1.4.1.37950.1.1.5.10.10.2.4.1
-- 1.3.6.1.4.1.37950.1.1.5.10.10.2.4.1
-- 1.3.6.1.4.1.37950.1.1.5.10.10.2.4.1
-- 1.3.6.1.4.1.37950.1.1.5.10.10.2.4.1
-- 1.3.6.1.4.1.37950.1.1.5.10.10.2.4.1
		-- 1.3.6.1.4.1.37950.1.1.5.10.10.2.4.1
		portBaseAclEntry OBJECT-TYPE
			SYNTAX PortBaseAclEntry
			MAX-ACCESS not-accessible
			STATUS current
			DESCRIPTION
				"Description."
			INDEX { portBaseAclIndex }
			::= { portBaseAclTable 1 }

		
		PortBaseAclEntry ::=
			SEQUENCE { 
				portBaseAclIndex
					Integer32,
				portBaseAclFltMode
					INTEGER,
				portBaseAclSrcMac
					OCTET STRING,
				portBaseAclSrcMacMask
					OCTET STRING,
				portBaseAclDstMac
					OCTET STRING,
				portBaseAclDstMacMask
					OCTET STRING,
				portBaseAclVlan
					INTEGER,
				portBaseAclVlanMask
					INTEGER,
				portBaseAclCos
					INTEGER,
				portBaseAclEthernetType
					OCTET STRING,
				portBaseAclSrcIp
					IpAddress,
				portBaseAclSrcIpMask
					IpAddress,
				portBaseAclDstIp
					IpAddress,
				portBaseAclDstIpMask
					IpAddress,
				portBaseAclProtocol
					INTEGER,
				portBaseAclProtocolMask
					INTEGER,
				portBaseAclTosDscp
					INTEGER,
				portBaseAclTosDscpMask
					INTEGER,
				portBaseAclSrcPort
					INTEGER,
				portBaseAclSrcPortMask
					OCTET STRING,
				portBaseAclDstPort
					INTEGER,
				portBaseAclDstPortMask
					OCTET STRING
			 }

--          1.3.6.1.4.1.37950.1.1.5.10.10.2.4.1.1
-- 1.3.6.1.4.1.37950.1.1.5.10.10.2.4.1.1
-- 1.3.6.1.4.1.37950.1.1.5.10.10.2.4.1.1
-- 1.3.6.1.4.1.37950.1.1.5.10.10.2.4.1.1
-- 1.3.6.1.4.1.37950.1.1.5.10.10.2.4.1.1
-- 1.3.6.1.4.1.37950.1.1.5.10.10.2.4.1.1
-- 1.3.6.1.4.1.37950.1.1.5.10.10.2.4.1.1
-- 1.3.6.1.4.1.37950.1.1.5.10.10.2.4.1.1
-- 1.3.6.1.4.1.37950.1.1.5.10.10.2.4.1.1
		-- 1.3.6.1.4.1.37950.1.1.5.10.10.2.4.1.1
		portBaseAclIndex OBJECT-TYPE
			SYNTAX Integer32 (5000..5999)
			MAX-ACCESS read-only
			STATUS current
			DESCRIPTION
				"Description."
			::= { portBaseAclEntry 1 }

		
--          1.3.6.1.4.1.37950.1.1.5.10.10.2.4.1.2
-- 1.3.6.1.4.1.37950.1.1.5.10.10.2.4.1.2
-- 1.3.6.1.4.1.37950.1.1.5.10.10.2.4.1.2
-- 1.3.6.1.4.1.37950.1.1.5.10.10.2.4.1.2
-- 1.3.6.1.4.1.37950.1.1.5.10.10.2.4.1.2
-- 1.3.6.1.4.1.37950.1.1.5.10.10.2.4.1.2
-- 1.3.6.1.4.1.37950.1.1.5.10.10.2.4.1.2
-- 1.3.6.1.4.1.37950.1.1.5.10.10.2.4.1.2
-- 1.3.6.1.4.1.37950.1.1.5.10.10.2.4.1.2
		-- 1.3.6.1.4.1.37950.1.1.5.10.10.2.4.1.2
		portBaseAclFltMode OBJECT-TYPE
			SYNTAX INTEGER
				{
				permit(1),
				deny(2)
				}
			MAX-ACCESS read-only
			STATUS current
			DESCRIPTION
				"Description."
			::= { portBaseAclEntry 2 }

		
--          1.3.6.1.4.1.37950.1.1.5.10.10.2.4.1.3
-- 1.3.6.1.4.1.37950.1.1.5.10.10.2.4.1.3
-- 1.3.6.1.4.1.37950.1.1.5.10.10.2.4.1.3
-- 1.3.6.1.4.1.37950.1.1.5.10.10.2.4.1.3
-- 1.3.6.1.4.1.37950.1.1.5.10.10.2.4.1.3
-- 1.3.6.1.4.1.37950.1.1.5.10.10.2.4.1.3
-- 1.3.6.1.4.1.37950.1.1.5.10.10.2.4.1.3
-- 1.3.6.1.4.1.37950.1.1.5.10.10.2.4.1.3
-- 1.3.6.1.4.1.37950.1.1.5.10.10.2.4.1.3
		-- 1.3.6.1.4.1.37950.1.1.5.10.10.2.4.1.3
		portBaseAclSrcMac OBJECT-TYPE
			SYNTAX OCTET STRING
			MAX-ACCESS read-only
			STATUS current
			DESCRIPTION
				"Description."
			::= { portBaseAclEntry 3 }

		
--          1.3.6.1.4.1.37950.1.1.5.10.10.2.4.1.4
-- 1.3.6.1.4.1.37950.1.1.5.10.10.2.4.1.4
-- 1.3.6.1.4.1.37950.1.1.5.10.10.2.4.1.4
-- 1.3.6.1.4.1.37950.1.1.5.10.10.2.4.1.4
-- 1.3.6.1.4.1.37950.1.1.5.10.10.2.4.1.4
-- 1.3.6.1.4.1.37950.1.1.5.10.10.2.4.1.4
-- 1.3.6.1.4.1.37950.1.1.5.10.10.2.4.1.4
-- 1.3.6.1.4.1.37950.1.1.5.10.10.2.4.1.4
-- 1.3.6.1.4.1.37950.1.1.5.10.10.2.4.1.4
		-- 1.3.6.1.4.1.37950.1.1.5.10.10.2.4.1.4
		portBaseAclSrcMacMask OBJECT-TYPE
			SYNTAX OCTET STRING
			MAX-ACCESS read-only
			STATUS current
			DESCRIPTION
				"Description."
			::= { portBaseAclEntry 4 }

		
--          1.3.6.1.4.1.37950.1.1.5.10.10.2.4.1.5
-- 1.3.6.1.4.1.37950.1.1.5.10.10.2.4.1.5
-- 1.3.6.1.4.1.37950.1.1.5.10.10.2.4.1.5
-- 1.3.6.1.4.1.37950.1.1.5.10.10.2.4.1.5
-- 1.3.6.1.4.1.37950.1.1.5.10.10.2.4.1.5
-- 1.3.6.1.4.1.37950.1.1.5.10.10.2.4.1.5
-- 1.3.6.1.4.1.37950.1.1.5.10.10.2.4.1.5
-- 1.3.6.1.4.1.37950.1.1.5.10.10.2.4.1.5
-- 1.3.6.1.4.1.37950.1.1.5.10.10.2.4.1.5
		-- 1.3.6.1.4.1.37950.1.1.5.10.10.2.4.1.5
		portBaseAclDstMac OBJECT-TYPE
			SYNTAX OCTET STRING
			MAX-ACCESS read-only
			STATUS current
			DESCRIPTION
				"Description."
			::= { portBaseAclEntry 5 }

		
--          1.3.6.1.4.1.37950.1.1.5.10.10.2.4.1.6
-- 1.3.6.1.4.1.37950.1.1.5.10.10.2.4.1.6
-- 1.3.6.1.4.1.37950.1.1.5.10.10.2.4.1.6
-- 1.3.6.1.4.1.37950.1.1.5.10.10.2.4.1.6
-- 1.3.6.1.4.1.37950.1.1.5.10.10.2.4.1.6
-- 1.3.6.1.4.1.37950.1.1.5.10.10.2.4.1.6
-- 1.3.6.1.4.1.37950.1.1.5.10.10.2.4.1.6
-- 1.3.6.1.4.1.37950.1.1.5.10.10.2.4.1.6
-- 1.3.6.1.4.1.37950.1.1.5.10.10.2.4.1.6
		-- 1.3.6.1.4.1.37950.1.1.5.10.10.2.4.1.6
		portBaseAclDstMacMask OBJECT-TYPE
			SYNTAX OCTET STRING
			MAX-ACCESS read-only
			STATUS current
			DESCRIPTION
				"Description."
			::= { portBaseAclEntry 6 }

		
--          1.3.6.1.4.1.37950.1.1.5.10.10.2.4.1.7
-- 1.3.6.1.4.1.37950.1.1.5.10.10.2.4.1.7
-- 1.3.6.1.4.1.37950.1.1.5.10.10.2.4.1.7
-- 1.3.6.1.4.1.37950.1.1.5.10.10.2.4.1.7
-- 1.3.6.1.4.1.37950.1.1.5.10.10.2.4.1.7
-- 1.3.6.1.4.1.37950.1.1.5.10.10.2.4.1.7
-- 1.3.6.1.4.1.37950.1.1.5.10.10.2.4.1.7
-- 1.3.6.1.4.1.37950.1.1.5.10.10.2.4.1.7
-- 1.3.6.1.4.1.37950.1.1.5.10.10.2.4.1.7
		-- 1.3.6.1.4.1.37950.1.1.5.10.10.2.4.1.7
		portBaseAclVlan OBJECT-TYPE
			SYNTAX INTEGER (0..4094)
			MAX-ACCESS read-only
			STATUS current
			DESCRIPTION
				"Description."
			::= { portBaseAclEntry 7 }

		
--          1.3.6.1.4.1.37950.1.1.5.10.10.2.4.1.8
-- 1.3.6.1.4.1.37950.1.1.5.10.10.2.4.1.8
-- 1.3.6.1.4.1.37950.1.1.5.10.10.2.4.1.8
-- 1.3.6.1.4.1.37950.1.1.5.10.10.2.4.1.8
-- 1.3.6.1.4.1.37950.1.1.5.10.10.2.4.1.8
-- 1.3.6.1.4.1.37950.1.1.5.10.10.2.4.1.8
-- 1.3.6.1.4.1.37950.1.1.5.10.10.2.4.1.8
-- 1.3.6.1.4.1.37950.1.1.5.10.10.2.4.1.8
-- 1.3.6.1.4.1.37950.1.1.5.10.10.2.4.1.8
		-- 1.3.6.1.4.1.37950.1.1.5.10.10.2.4.1.8
		portBaseAclVlanMask OBJECT-TYPE
			SYNTAX INTEGER (0..4095)
			MAX-ACCESS read-only
			STATUS current
			DESCRIPTION
				"Description."
			::= { portBaseAclEntry 8 }

		
--          1.3.6.1.4.1.37950.1.1.5.10.10.2.4.1.9
-- 1.3.6.1.4.1.37950.1.1.5.10.10.2.4.1.9
-- 1.3.6.1.4.1.37950.1.1.5.10.10.2.4.1.9
-- 1.3.6.1.4.1.37950.1.1.5.10.10.2.4.1.9
-- 1.3.6.1.4.1.37950.1.1.5.10.10.2.4.1.9
-- 1.3.6.1.4.1.37950.1.1.5.10.10.2.4.1.9
-- 1.3.6.1.4.1.37950.1.1.5.10.10.2.4.1.9
-- 1.3.6.1.4.1.37950.1.1.5.10.10.2.4.1.9
-- 1.3.6.1.4.1.37950.1.1.5.10.10.2.4.1.9
		-- 1.3.6.1.4.1.37950.1.1.5.10.10.2.4.1.9
		portBaseAclCos OBJECT-TYPE
			SYNTAX INTEGER (-1..7)
			MAX-ACCESS read-only
			STATUS current
			DESCRIPTION
				"Description."
			::= { portBaseAclEntry 9 }

		
--          1.3.6.1.4.1.37950.1.1.5.10.10.2.4.1.10
-- 1.3.6.1.4.1.37950.1.1.5.10.10.2.4.1.10
-- 1.3.6.1.4.1.37950.1.1.5.10.10.2.4.1.10
-- 1.3.6.1.4.1.37950.1.1.5.10.10.2.4.1.10
-- 1.3.6.1.4.1.37950.1.1.5.10.10.2.4.1.10
-- 1.3.6.1.4.1.37950.1.1.5.10.10.2.4.1.10
-- 1.3.6.1.4.1.37950.1.1.5.10.10.2.4.1.10
-- 1.3.6.1.4.1.37950.1.1.5.10.10.2.4.1.10
-- 1.3.6.1.4.1.37950.1.1.5.10.10.2.4.1.10
		-- 1.3.6.1.4.1.37950.1.1.5.10.10.2.4.1.10
		portBaseAclEthernetType OBJECT-TYPE
			SYNTAX OCTET STRING
			MAX-ACCESS read-only
			STATUS current
			DESCRIPTION
				"Description."
			::= { portBaseAclEntry 10 }

		
--          1.3.6.1.4.1.37950.1.1.5.10.10.2.4.1.11
-- 1.3.6.1.4.1.37950.1.1.5.10.10.2.4.1.11
-- 1.3.6.1.4.1.37950.1.1.5.10.10.2.4.1.11
-- 1.3.6.1.4.1.37950.1.1.5.10.10.2.4.1.11
-- 1.3.6.1.4.1.37950.1.1.5.10.10.2.4.1.11
-- 1.3.6.1.4.1.37950.1.1.5.10.10.2.4.1.11
-- 1.3.6.1.4.1.37950.1.1.5.10.10.2.4.1.11
-- 1.3.6.1.4.1.37950.1.1.5.10.10.2.4.1.11
-- 1.3.6.1.4.1.37950.1.1.5.10.10.2.4.1.11
		-- 1.3.6.1.4.1.37950.1.1.5.10.10.2.4.1.11
		portBaseAclSrcIp OBJECT-TYPE
			SYNTAX IpAddress
			MAX-ACCESS read-only
			STATUS current
			DESCRIPTION
				"Description."
			::= { portBaseAclEntry 11 }

		
--          1.3.6.1.4.1.37950.1.1.5.10.10.2.4.1.12
-- 1.3.6.1.4.1.37950.1.1.5.10.10.2.4.1.12
-- 1.3.6.1.4.1.37950.1.1.5.10.10.2.4.1.12
-- 1.3.6.1.4.1.37950.1.1.5.10.10.2.4.1.12
-- 1.3.6.1.4.1.37950.1.1.5.10.10.2.4.1.12
-- 1.3.6.1.4.1.37950.1.1.5.10.10.2.4.1.12
-- 1.3.6.1.4.1.37950.1.1.5.10.10.2.4.1.12
-- 1.3.6.1.4.1.37950.1.1.5.10.10.2.4.1.12
-- 1.3.6.1.4.1.37950.1.1.5.10.10.2.4.1.12
		-- 1.3.6.1.4.1.37950.1.1.5.10.10.2.4.1.12
		portBaseAclSrcIpMask OBJECT-TYPE
			SYNTAX IpAddress
			MAX-ACCESS read-only
			STATUS current
			DESCRIPTION
				"Description."
			::= { portBaseAclEntry 12 }

		
--          1.3.6.1.4.1.37950.1.1.5.10.10.2.4.1.13
-- 1.3.6.1.4.1.37950.1.1.5.10.10.2.4.1.13
-- 1.3.6.1.4.1.37950.1.1.5.10.10.2.4.1.13
-- 1.3.6.1.4.1.37950.1.1.5.10.10.2.4.1.13
-- 1.3.6.1.4.1.37950.1.1.5.10.10.2.4.1.13
-- 1.3.6.1.4.1.37950.1.1.5.10.10.2.4.1.13
-- 1.3.6.1.4.1.37950.1.1.5.10.10.2.4.1.13
-- 1.3.6.1.4.1.37950.1.1.5.10.10.2.4.1.13
-- 1.3.6.1.4.1.37950.1.1.5.10.10.2.4.1.13
		-- 1.3.6.1.4.1.37950.1.1.5.10.10.2.4.1.13
		portBaseAclDstIp OBJECT-TYPE
			SYNTAX IpAddress
			MAX-ACCESS read-only
			STATUS current
			DESCRIPTION
				"Description."
			::= { portBaseAclEntry 13 }

		
--          1.3.6.1.4.1.37950.1.1.5.10.10.2.4.1.14
-- 1.3.6.1.4.1.37950.1.1.5.10.10.2.4.1.14
-- 1.3.6.1.4.1.37950.1.1.5.10.10.2.4.1.14
-- 1.3.6.1.4.1.37950.1.1.5.10.10.2.4.1.14
-- 1.3.6.1.4.1.37950.1.1.5.10.10.2.4.1.14
-- 1.3.6.1.4.1.37950.1.1.5.10.10.2.4.1.14
-- 1.3.6.1.4.1.37950.1.1.5.10.10.2.4.1.14
-- 1.3.6.1.4.1.37950.1.1.5.10.10.2.4.1.14
-- 1.3.6.1.4.1.37950.1.1.5.10.10.2.4.1.14
		-- 1.3.6.1.4.1.37950.1.1.5.10.10.2.4.1.14
		portBaseAclDstIpMask OBJECT-TYPE
			SYNTAX IpAddress
			MAX-ACCESS read-only
			STATUS current
			DESCRIPTION
				"Description."
			::= { portBaseAclEntry 14 }

		
--          1.3.6.1.4.1.37950.1.1.5.10.10.2.4.1.15
-- 1.3.6.1.4.1.37950.1.1.5.10.10.2.4.1.15
-- 1.3.6.1.4.1.37950.1.1.5.10.10.2.4.1.15
-- 1.3.6.1.4.1.37950.1.1.5.10.10.2.4.1.15
-- 1.3.6.1.4.1.37950.1.1.5.10.10.2.4.1.15
-- 1.3.6.1.4.1.37950.1.1.5.10.10.2.4.1.15
-- 1.3.6.1.4.1.37950.1.1.5.10.10.2.4.1.15
-- 1.3.6.1.4.1.37950.1.1.5.10.10.2.4.1.15
-- 1.3.6.1.4.1.37950.1.1.5.10.10.2.4.1.15
		-- 1.3.6.1.4.1.37950.1.1.5.10.10.2.4.1.15
		portBaseAclProtocol OBJECT-TYPE
			SYNTAX INTEGER (-1..255)
			MAX-ACCESS read-only
			STATUS current
			DESCRIPTION
				"Description."
			::= { portBaseAclEntry 15 }

		
--          1.3.6.1.4.1.37950.1.1.5.10.10.2.4.1.16
-- 1.3.6.1.4.1.37950.1.1.5.10.10.2.4.1.16
-- 1.3.6.1.4.1.37950.1.1.5.10.10.2.4.1.16
-- 1.3.6.1.4.1.37950.1.1.5.10.10.2.4.1.16
-- 1.3.6.1.4.1.37950.1.1.5.10.10.2.4.1.16
-- 1.3.6.1.4.1.37950.1.1.5.10.10.2.4.1.16
-- 1.3.6.1.4.1.37950.1.1.5.10.10.2.4.1.16
-- 1.3.6.1.4.1.37950.1.1.5.10.10.2.4.1.16
-- 1.3.6.1.4.1.37950.1.1.5.10.10.2.4.1.16
		-- 1.3.6.1.4.1.37950.1.1.5.10.10.2.4.1.16
		portBaseAclProtocolMask OBJECT-TYPE
			SYNTAX INTEGER (0..255)
			MAX-ACCESS read-only
			STATUS current
			DESCRIPTION
				"Description."
			::= { portBaseAclEntry 16 }

		
--          1.3.6.1.4.1.37950.1.1.5.10.10.2.4.1.17
-- 1.3.6.1.4.1.37950.1.1.5.10.10.2.4.1.17
-- 1.3.6.1.4.1.37950.1.1.5.10.10.2.4.1.17
-- 1.3.6.1.4.1.37950.1.1.5.10.10.2.4.1.17
-- 1.3.6.1.4.1.37950.1.1.5.10.10.2.4.1.17
-- 1.3.6.1.4.1.37950.1.1.5.10.10.2.4.1.17
-- 1.3.6.1.4.1.37950.1.1.5.10.10.2.4.1.17
-- 1.3.6.1.4.1.37950.1.1.5.10.10.2.4.1.17
-- 1.3.6.1.4.1.37950.1.1.5.10.10.2.4.1.17
		-- 1.3.6.1.4.1.37950.1.1.5.10.10.2.4.1.17
		portBaseAclTosDscp OBJECT-TYPE
			SYNTAX INTEGER (-1..255)
			MAX-ACCESS read-only
			STATUS current
			DESCRIPTION
				"Description."
			::= { portBaseAclEntry 17 }

		
--          1.3.6.1.4.1.37950.1.1.5.10.10.2.4.1.18
-- 1.3.6.1.4.1.37950.1.1.5.10.10.2.4.1.18
-- 1.3.6.1.4.1.37950.1.1.5.10.10.2.4.1.18
-- 1.3.6.1.4.1.37950.1.1.5.10.10.2.4.1.18
-- 1.3.6.1.4.1.37950.1.1.5.10.10.2.4.1.18
-- 1.3.6.1.4.1.37950.1.1.5.10.10.2.4.1.18
-- 1.3.6.1.4.1.37950.1.1.5.10.10.2.4.1.18
-- 1.3.6.1.4.1.37950.1.1.5.10.10.2.4.1.18
-- 1.3.6.1.4.1.37950.1.1.5.10.10.2.4.1.18
		-- 1.3.6.1.4.1.37950.1.1.5.10.10.2.4.1.18
		portBaseAclTosDscpMask OBJECT-TYPE
			SYNTAX INTEGER (0..255)
			MAX-ACCESS read-only
			STATUS current
			DESCRIPTION
				"Description."
			::= { portBaseAclEntry 18 }

		
--          1.3.6.1.4.1.37950.1.1.5.10.10.2.4.1.19
-- 1.3.6.1.4.1.37950.1.1.5.10.10.2.4.1.19
-- 1.3.6.1.4.1.37950.1.1.5.10.10.2.4.1.19
-- 1.3.6.1.4.1.37950.1.1.5.10.10.2.4.1.19
-- 1.3.6.1.4.1.37950.1.1.5.10.10.2.4.1.19
-- 1.3.6.1.4.1.37950.1.1.5.10.10.2.4.1.19
-- 1.3.6.1.4.1.37950.1.1.5.10.10.2.4.1.19
-- 1.3.6.1.4.1.37950.1.1.5.10.10.2.4.1.19
-- 1.3.6.1.4.1.37950.1.1.5.10.10.2.4.1.19
		-- 1.3.6.1.4.1.37950.1.1.5.10.10.2.4.1.19
		portBaseAclSrcPort OBJECT-TYPE
			SYNTAX INTEGER (-1..65535)
			MAX-ACCESS read-only
			STATUS current
			DESCRIPTION
				"Description."
			::= { portBaseAclEntry 19 }

		
--          1.3.6.1.4.1.37950.1.1.5.10.10.2.4.1.20
-- 1.3.6.1.4.1.37950.1.1.5.10.10.2.4.1.20
-- 1.3.6.1.4.1.37950.1.1.5.10.10.2.4.1.20
-- 1.3.6.1.4.1.37950.1.1.5.10.10.2.4.1.20
-- 1.3.6.1.4.1.37950.1.1.5.10.10.2.4.1.20
-- 1.3.6.1.4.1.37950.1.1.5.10.10.2.4.1.20
-- 1.3.6.1.4.1.37950.1.1.5.10.10.2.4.1.20
-- 1.3.6.1.4.1.37950.1.1.5.10.10.2.4.1.20
-- 1.3.6.1.4.1.37950.1.1.5.10.10.2.4.1.20
		-- 1.3.6.1.4.1.37950.1.1.5.10.10.2.4.1.20
		portBaseAclSrcPortMask OBJECT-TYPE
			SYNTAX OCTET STRING
			MAX-ACCESS read-only
			STATUS current
			DESCRIPTION
				"Description."
			::= { portBaseAclEntry 20 }

		
--          1.3.6.1.4.1.37950.1.1.5.10.10.2.4.1.21
-- 1.3.6.1.4.1.37950.1.1.5.10.10.2.4.1.21
-- 1.3.6.1.4.1.37950.1.1.5.10.10.2.4.1.21
-- 1.3.6.1.4.1.37950.1.1.5.10.10.2.4.1.21
-- 1.3.6.1.4.1.37950.1.1.5.10.10.2.4.1.21
-- 1.3.6.1.4.1.37950.1.1.5.10.10.2.4.1.21
-- 1.3.6.1.4.1.37950.1.1.5.10.10.2.4.1.21
-- 1.3.6.1.4.1.37950.1.1.5.10.10.2.4.1.21
-- 1.3.6.1.4.1.37950.1.1.5.10.10.2.4.1.21
		-- 1.3.6.1.4.1.37950.1.1.5.10.10.2.4.1.21
		portBaseAclDstPort OBJECT-TYPE
			SYNTAX INTEGER (-1..65535)
			MAX-ACCESS read-only
			STATUS current
			DESCRIPTION
				"Description."
			::= { portBaseAclEntry 21 }

		
--          1.3.6.1.4.1.37950.1.1.5.10.10.2.4.1.22
-- 1.3.6.1.4.1.37950.1.1.5.10.10.2.4.1.22
-- 1.3.6.1.4.1.37950.1.1.5.10.10.2.4.1.22
-- 1.3.6.1.4.1.37950.1.1.5.10.10.2.4.1.22
-- 1.3.6.1.4.1.37950.1.1.5.10.10.2.4.1.22
-- 1.3.6.1.4.1.37950.1.1.5.10.10.2.4.1.22
-- 1.3.6.1.4.1.37950.1.1.5.10.10.2.4.1.22
-- 1.3.6.1.4.1.37950.1.1.5.10.10.2.4.1.22
-- 1.3.6.1.4.1.37950.1.1.5.10.10.2.4.1.22
		-- 1.3.6.1.4.1.37950.1.1.5.10.10.2.4.1.22
		portBaseAclDstPortMask OBJECT-TYPE
			SYNTAX OCTET STRING
			MAX-ACCESS read-only
			STATUS current
			DESCRIPTION
				"Description."
			::= { portBaseAclEntry 22 }

		
--          1.3.6.1.4.1.37950.1.1.5.10.10.2.5
-- 1.3.6.1.4.1.37950.1.1.5.10.10.2.5
-- 1.3.6.1.4.1.37950.1.1.5.10.10.2.5
-- 1.3.6.1.4.1.37950.1.1.5.10.10.2.5
-- 1.3.6.1.4.1.37950.1.1.5.10.10.2.5
-- 1.3.6.1.4.1.37950.1.1.5.10.10.2.5
-- 1.3.6.1.4.1.37950.1.1.5.10.10.2.5
-- 1.3.6.1.4.1.37950.1.1.5.10.10.2.5
-- 1.3.6.1.4.1.37950.1.1.5.10.10.2.5
		-- 1.3.6.1.4.1.37950.1.1.5.10.10.2.5
		qosBaseAclTable OBJECT-TYPE
			SYNTAX SEQUENCE OF QosBaseAclEntry
			MAX-ACCESS not-accessible
			STATUS current
			DESCRIPTION
				"Description."
			::= { aclTable 5 }

		
--          1.3.6.1.4.1.37950.1.1.5.10.10.2.5.1
-- 1.3.6.1.4.1.37950.1.1.5.10.10.2.5.1
-- 1.3.6.1.4.1.37950.1.1.5.10.10.2.5.1
-- 1.3.6.1.4.1.37950.1.1.5.10.10.2.5.1
-- 1.3.6.1.4.1.37950.1.1.5.10.10.2.5.1
-- 1.3.6.1.4.1.37950.1.1.5.10.10.2.5.1
-- 1.3.6.1.4.1.37950.1.1.5.10.10.2.5.1
-- 1.3.6.1.4.1.37950.1.1.5.10.10.2.5.1
-- 1.3.6.1.4.1.37950.1.1.5.10.10.2.5.1
		-- 1.3.6.1.4.1.37950.1.1.5.10.10.2.5.1
		qosBaseAclEntry OBJECT-TYPE
			SYNTAX QosBaseAclEntry
			MAX-ACCESS not-accessible
			STATUS current
			DESCRIPTION
				"Description."
			INDEX { qosBaseAclIndex }
			::= { qosBaseAclTable 1 }

		
		QosBaseAclEntry ::=
			SEQUENCE { 
				qosBaseAclIndex
					Integer32,
				qosBaseAclOutPacketPri
					INTEGER,
				qosBaseAclHwTransQueue
					INTEGER,
				qosBaseAclRulePri
					INTEGER,
				qosBaseAclSrcMac
					OCTET STRING,
				qosBaseAclSrcMacMask
					OCTET STRING,
				qosBaseAclDstMac
					OCTET STRING,
				qosBaseAclDstMacMask
					OCTET STRING,
				qosBaseAclVlan
					INTEGER,
				qosBaseAclVlanMask
					INTEGER,
				qosBaseAclCos
					INTEGER,
				qosBaseAclEthernetType
					OCTET STRING,
				qosBaseAclSrcIp
					IpAddress,
				qosBaseAclSrcIpMask
					IpAddress,
				qosBaseAclDstIp
					IpAddress,
				qosBaseAclDstIpMask
					IpAddress,
				qosBaseAclProtocol
					INTEGER,
				qosBaseAclProtocolMask
					INTEGER,
				qosBaseAclTosDscp
					INTEGER,
				qosBaseAclTosDscpMask
					INTEGER,
				qosBaseAclSrcPort
					INTEGER,
				qosBaseAclSrcPortMask
					OCTET STRING,
				qosBaseAclDstPort
					INTEGER,
				qosBaseAclDstPortMask
					OCTET STRING
			 }

--          1.3.6.1.4.1.37950.1.1.5.10.10.2.5.1.1
-- 1.3.6.1.4.1.37950.1.1.5.10.10.2.5.1.1
-- 1.3.6.1.4.1.37950.1.1.5.10.10.2.5.1.1
-- 1.3.6.1.4.1.37950.1.1.5.10.10.2.5.1.1
-- 1.3.6.1.4.1.37950.1.1.5.10.10.2.5.1.1
-- 1.3.6.1.4.1.37950.1.1.5.10.10.2.5.1.1
-- 1.3.6.1.4.1.37950.1.1.5.10.10.2.5.1.1
-- 1.3.6.1.4.1.37950.1.1.5.10.10.2.5.1.1
-- 1.3.6.1.4.1.37950.1.1.5.10.10.2.5.1.1
		-- 1.3.6.1.4.1.37950.1.1.5.10.10.2.5.1.1
		qosBaseAclIndex OBJECT-TYPE
			SYNTAX Integer32 (6000..6999)
			MAX-ACCESS read-only
			STATUS current
			DESCRIPTION
				"Description."
			::= { qosBaseAclEntry 1 }

		
--          1.3.6.1.4.1.37950.1.1.5.10.10.2.5.1.2
-- 1.3.6.1.4.1.37950.1.1.5.10.10.2.5.1.2
-- 1.3.6.1.4.1.37950.1.1.5.10.10.2.5.1.2
-- 1.3.6.1.4.1.37950.1.1.5.10.10.2.5.1.2
-- 1.3.6.1.4.1.37950.1.1.5.10.10.2.5.1.2
-- 1.3.6.1.4.1.37950.1.1.5.10.10.2.5.1.2
-- 1.3.6.1.4.1.37950.1.1.5.10.10.2.5.1.2
-- 1.3.6.1.4.1.37950.1.1.5.10.10.2.5.1.2
-- 1.3.6.1.4.1.37950.1.1.5.10.10.2.5.1.2
		-- 1.3.6.1.4.1.37950.1.1.5.10.10.2.5.1.2
		qosBaseAclOutPacketPri OBJECT-TYPE
			SYNTAX INTEGER (0..8)
			MAX-ACCESS read-only
			STATUS current
			DESCRIPTION
				"Description."
			::= { qosBaseAclEntry 2 }

		
--          1.3.6.1.4.1.37950.1.1.5.10.10.2.5.1.3
-- 1.3.6.1.4.1.37950.1.1.5.10.10.2.5.1.3
-- 1.3.6.1.4.1.37950.1.1.5.10.10.2.5.1.3
-- 1.3.6.1.4.1.37950.1.1.5.10.10.2.5.1.3
-- 1.3.6.1.4.1.37950.1.1.5.10.10.2.5.1.3
-- 1.3.6.1.4.1.37950.1.1.5.10.10.2.5.1.3
-- 1.3.6.1.4.1.37950.1.1.5.10.10.2.5.1.3
-- 1.3.6.1.4.1.37950.1.1.5.10.10.2.5.1.3
-- 1.3.6.1.4.1.37950.1.1.5.10.10.2.5.1.3
		-- 1.3.6.1.4.1.37950.1.1.5.10.10.2.5.1.3
		qosBaseAclHwTransQueue OBJECT-TYPE
			SYNTAX INTEGER (0..7)
			MAX-ACCESS read-only
			STATUS current
			DESCRIPTION
				"Description."
			::= { qosBaseAclEntry 3 }

		
--          1.3.6.1.4.1.37950.1.1.5.10.10.2.5.1.4
-- 1.3.6.1.4.1.37950.1.1.5.10.10.2.5.1.4
-- 1.3.6.1.4.1.37950.1.1.5.10.10.2.5.1.4
-- 1.3.6.1.4.1.37950.1.1.5.10.10.2.5.1.4
-- 1.3.6.1.4.1.37950.1.1.5.10.10.2.5.1.4
-- 1.3.6.1.4.1.37950.1.1.5.10.10.2.5.1.4
-- 1.3.6.1.4.1.37950.1.1.5.10.10.2.5.1.4
-- 1.3.6.1.4.1.37950.1.1.5.10.10.2.5.1.4
-- 1.3.6.1.4.1.37950.1.1.5.10.10.2.5.1.4
		-- 1.3.6.1.4.1.37950.1.1.5.10.10.2.5.1.4
		qosBaseAclRulePri OBJECT-TYPE
			SYNTAX INTEGER (1..12)
			MAX-ACCESS read-only
			STATUS current
			DESCRIPTION
				"Description."
			::= { qosBaseAclEntry 4 }

		
--          1.3.6.1.4.1.37950.1.1.5.10.10.2.5.1.5
-- 1.3.6.1.4.1.37950.1.1.5.10.10.2.5.1.5
-- 1.3.6.1.4.1.37950.1.1.5.10.10.2.5.1.5
-- 1.3.6.1.4.1.37950.1.1.5.10.10.2.5.1.5
-- 1.3.6.1.4.1.37950.1.1.5.10.10.2.5.1.5
-- 1.3.6.1.4.1.37950.1.1.5.10.10.2.5.1.5
-- 1.3.6.1.4.1.37950.1.1.5.10.10.2.5.1.5
-- 1.3.6.1.4.1.37950.1.1.5.10.10.2.5.1.5
-- 1.3.6.1.4.1.37950.1.1.5.10.10.2.5.1.5
		-- 1.3.6.1.4.1.37950.1.1.5.10.10.2.5.1.5
		qosBaseAclSrcMac OBJECT-TYPE
			SYNTAX OCTET STRING
			MAX-ACCESS read-only
			STATUS current
			DESCRIPTION
				"Description."
			::= { qosBaseAclEntry 5 }

		
--          1.3.6.1.4.1.37950.1.1.5.10.10.2.5.1.6
-- 1.3.6.1.4.1.37950.1.1.5.10.10.2.5.1.6
-- 1.3.6.1.4.1.37950.1.1.5.10.10.2.5.1.6
-- 1.3.6.1.4.1.37950.1.1.5.10.10.2.5.1.6
-- 1.3.6.1.4.1.37950.1.1.5.10.10.2.5.1.6
-- 1.3.6.1.4.1.37950.1.1.5.10.10.2.5.1.6
-- 1.3.6.1.4.1.37950.1.1.5.10.10.2.5.1.6
-- 1.3.6.1.4.1.37950.1.1.5.10.10.2.5.1.6
-- 1.3.6.1.4.1.37950.1.1.5.10.10.2.5.1.6
		-- 1.3.6.1.4.1.37950.1.1.5.10.10.2.5.1.6
		qosBaseAclSrcMacMask OBJECT-TYPE
			SYNTAX OCTET STRING
			MAX-ACCESS read-only
			STATUS current
			DESCRIPTION
				"Description."
			::= { qosBaseAclEntry 6 }

		
--          1.3.6.1.4.1.37950.1.1.5.10.10.2.5.1.7
-- 1.3.6.1.4.1.37950.1.1.5.10.10.2.5.1.7
-- 1.3.6.1.4.1.37950.1.1.5.10.10.2.5.1.7
-- 1.3.6.1.4.1.37950.1.1.5.10.10.2.5.1.7
-- 1.3.6.1.4.1.37950.1.1.5.10.10.2.5.1.7
-- 1.3.6.1.4.1.37950.1.1.5.10.10.2.5.1.7
-- 1.3.6.1.4.1.37950.1.1.5.10.10.2.5.1.7
-- 1.3.6.1.4.1.37950.1.1.5.10.10.2.5.1.7
-- 1.3.6.1.4.1.37950.1.1.5.10.10.2.5.1.7
		-- 1.3.6.1.4.1.37950.1.1.5.10.10.2.5.1.7
		qosBaseAclDstMac OBJECT-TYPE
			SYNTAX OCTET STRING
			MAX-ACCESS read-only
			STATUS current
			DESCRIPTION
				"Description."
			::= { qosBaseAclEntry 7 }

		
--          1.3.6.1.4.1.37950.1.1.5.10.10.2.5.1.8
-- 1.3.6.1.4.1.37950.1.1.5.10.10.2.5.1.8
-- 1.3.6.1.4.1.37950.1.1.5.10.10.2.5.1.8
-- 1.3.6.1.4.1.37950.1.1.5.10.10.2.5.1.8
-- 1.3.6.1.4.1.37950.1.1.5.10.10.2.5.1.8
-- 1.3.6.1.4.1.37950.1.1.5.10.10.2.5.1.8
-- 1.3.6.1.4.1.37950.1.1.5.10.10.2.5.1.8
-- 1.3.6.1.4.1.37950.1.1.5.10.10.2.5.1.8
-- 1.3.6.1.4.1.37950.1.1.5.10.10.2.5.1.8
		-- 1.3.6.1.4.1.37950.1.1.5.10.10.2.5.1.8
		qosBaseAclDstMacMask OBJECT-TYPE
			SYNTAX OCTET STRING
			MAX-ACCESS read-only
			STATUS current
			DESCRIPTION
				"Description."
			::= { qosBaseAclEntry 8 }

		
--          1.3.6.1.4.1.37950.1.1.5.10.10.2.5.1.9
-- 1.3.6.1.4.1.37950.1.1.5.10.10.2.5.1.9
-- 1.3.6.1.4.1.37950.1.1.5.10.10.2.5.1.9
-- 1.3.6.1.4.1.37950.1.1.5.10.10.2.5.1.9
-- 1.3.6.1.4.1.37950.1.1.5.10.10.2.5.1.9
-- 1.3.6.1.4.1.37950.1.1.5.10.10.2.5.1.9
-- 1.3.6.1.4.1.37950.1.1.5.10.10.2.5.1.9
-- 1.3.6.1.4.1.37950.1.1.5.10.10.2.5.1.9
-- 1.3.6.1.4.1.37950.1.1.5.10.10.2.5.1.9
		-- 1.3.6.1.4.1.37950.1.1.5.10.10.2.5.1.9
		qosBaseAclVlan OBJECT-TYPE
			SYNTAX INTEGER (0..4094)
			MAX-ACCESS read-only
			STATUS current
			DESCRIPTION
				"Description."
			::= { qosBaseAclEntry 9 }

		
--          1.3.6.1.4.1.37950.1.1.5.10.10.2.5.1.10
-- 1.3.6.1.4.1.37950.1.1.5.10.10.2.5.1.10
-- 1.3.6.1.4.1.37950.1.1.5.10.10.2.5.1.10
-- 1.3.6.1.4.1.37950.1.1.5.10.10.2.5.1.10
-- 1.3.6.1.4.1.37950.1.1.5.10.10.2.5.1.10
-- 1.3.6.1.4.1.37950.1.1.5.10.10.2.5.1.10
-- 1.3.6.1.4.1.37950.1.1.5.10.10.2.5.1.10
-- 1.3.6.1.4.1.37950.1.1.5.10.10.2.5.1.10
-- 1.3.6.1.4.1.37950.1.1.5.10.10.2.5.1.10
		-- 1.3.6.1.4.1.37950.1.1.5.10.10.2.5.1.10
		qosBaseAclVlanMask OBJECT-TYPE
			SYNTAX INTEGER (0..4095)
			MAX-ACCESS read-only
			STATUS current
			DESCRIPTION
				"Description."
			::= { qosBaseAclEntry 10 }

		
--          1.3.6.1.4.1.37950.1.1.5.10.10.2.5.1.11
-- 1.3.6.1.4.1.37950.1.1.5.10.10.2.5.1.11
-- 1.3.6.1.4.1.37950.1.1.5.10.10.2.5.1.11
-- 1.3.6.1.4.1.37950.1.1.5.10.10.2.5.1.11
-- 1.3.6.1.4.1.37950.1.1.5.10.10.2.5.1.11
-- 1.3.6.1.4.1.37950.1.1.5.10.10.2.5.1.11
-- 1.3.6.1.4.1.37950.1.1.5.10.10.2.5.1.11
-- 1.3.6.1.4.1.37950.1.1.5.10.10.2.5.1.11
-- 1.3.6.1.4.1.37950.1.1.5.10.10.2.5.1.11
		-- 1.3.6.1.4.1.37950.1.1.5.10.10.2.5.1.11
		qosBaseAclCos OBJECT-TYPE
			SYNTAX INTEGER (-1..7)
			MAX-ACCESS read-only
			STATUS current
			DESCRIPTION
				"Description."
			::= { qosBaseAclEntry 11 }

		
--          1.3.6.1.4.1.37950.1.1.5.10.10.2.5.1.12
-- 1.3.6.1.4.1.37950.1.1.5.10.10.2.5.1.12
-- 1.3.6.1.4.1.37950.1.1.5.10.10.2.5.1.12
-- 1.3.6.1.4.1.37950.1.1.5.10.10.2.5.1.12
-- 1.3.6.1.4.1.37950.1.1.5.10.10.2.5.1.12
-- 1.3.6.1.4.1.37950.1.1.5.10.10.2.5.1.12
-- 1.3.6.1.4.1.37950.1.1.5.10.10.2.5.1.12
-- 1.3.6.1.4.1.37950.1.1.5.10.10.2.5.1.12
-- 1.3.6.1.4.1.37950.1.1.5.10.10.2.5.1.12
		-- 1.3.6.1.4.1.37950.1.1.5.10.10.2.5.1.12
		qosBaseAclEthernetType OBJECT-TYPE
			SYNTAX OCTET STRING
			MAX-ACCESS read-only
			STATUS current
			DESCRIPTION
				"Description."
			::= { qosBaseAclEntry 12 }

		
--          1.3.6.1.4.1.37950.1.1.5.10.10.2.5.1.13
-- 1.3.6.1.4.1.37950.1.1.5.10.10.2.5.1.13
-- 1.3.6.1.4.1.37950.1.1.5.10.10.2.5.1.13
-- 1.3.6.1.4.1.37950.1.1.5.10.10.2.5.1.13
-- 1.3.6.1.4.1.37950.1.1.5.10.10.2.5.1.13
-- 1.3.6.1.4.1.37950.1.1.5.10.10.2.5.1.13
-- 1.3.6.1.4.1.37950.1.1.5.10.10.2.5.1.13
-- 1.3.6.1.4.1.37950.1.1.5.10.10.2.5.1.13
-- 1.3.6.1.4.1.37950.1.1.5.10.10.2.5.1.13
		-- 1.3.6.1.4.1.37950.1.1.5.10.10.2.5.1.13
		qosBaseAclSrcIp OBJECT-TYPE
			SYNTAX IpAddress
			MAX-ACCESS read-only
			STATUS current
			DESCRIPTION
				"Description."
			::= { qosBaseAclEntry 13 }

		
--          1.3.6.1.4.1.37950.1.1.5.10.10.2.5.1.14
-- 1.3.6.1.4.1.37950.1.1.5.10.10.2.5.1.14
-- 1.3.6.1.4.1.37950.1.1.5.10.10.2.5.1.14
-- 1.3.6.1.4.1.37950.1.1.5.10.10.2.5.1.14
-- 1.3.6.1.4.1.37950.1.1.5.10.10.2.5.1.14
-- 1.3.6.1.4.1.37950.1.1.5.10.10.2.5.1.14
-- 1.3.6.1.4.1.37950.1.1.5.10.10.2.5.1.14
-- 1.3.6.1.4.1.37950.1.1.5.10.10.2.5.1.14
-- 1.3.6.1.4.1.37950.1.1.5.10.10.2.5.1.14
		-- 1.3.6.1.4.1.37950.1.1.5.10.10.2.5.1.14
		qosBaseAclSrcIpMask OBJECT-TYPE
			SYNTAX IpAddress
			MAX-ACCESS read-only
			STATUS current
			DESCRIPTION
				"Description."
			::= { qosBaseAclEntry 14 }

		
--          1.3.6.1.4.1.37950.1.1.5.10.10.2.5.1.15
-- 1.3.6.1.4.1.37950.1.1.5.10.10.2.5.1.15
-- 1.3.6.1.4.1.37950.1.1.5.10.10.2.5.1.15
-- 1.3.6.1.4.1.37950.1.1.5.10.10.2.5.1.15
-- 1.3.6.1.4.1.37950.1.1.5.10.10.2.5.1.15
-- 1.3.6.1.4.1.37950.1.1.5.10.10.2.5.1.15
-- 1.3.6.1.4.1.37950.1.1.5.10.10.2.5.1.15
-- 1.3.6.1.4.1.37950.1.1.5.10.10.2.5.1.15
-- 1.3.6.1.4.1.37950.1.1.5.10.10.2.5.1.15
		-- 1.3.6.1.4.1.37950.1.1.5.10.10.2.5.1.15
		qosBaseAclDstIp OBJECT-TYPE
			SYNTAX IpAddress
			MAX-ACCESS read-only
			STATUS current
			DESCRIPTION
				"Description."
			::= { qosBaseAclEntry 15 }

		
--          1.3.6.1.4.1.37950.1.1.5.10.10.2.5.1.16
-- 1.3.6.1.4.1.37950.1.1.5.10.10.2.5.1.16
-- 1.3.6.1.4.1.37950.1.1.5.10.10.2.5.1.16
-- 1.3.6.1.4.1.37950.1.1.5.10.10.2.5.1.16
-- 1.3.6.1.4.1.37950.1.1.5.10.10.2.5.1.16
-- 1.3.6.1.4.1.37950.1.1.5.10.10.2.5.1.16
-- 1.3.6.1.4.1.37950.1.1.5.10.10.2.5.1.16
-- 1.3.6.1.4.1.37950.1.1.5.10.10.2.5.1.16
-- 1.3.6.1.4.1.37950.1.1.5.10.10.2.5.1.16
		-- 1.3.6.1.4.1.37950.1.1.5.10.10.2.5.1.16
		qosBaseAclDstIpMask OBJECT-TYPE
			SYNTAX IpAddress
			MAX-ACCESS read-only
			STATUS current
			DESCRIPTION
				"Description."
			::= { qosBaseAclEntry 16 }

		
--          1.3.6.1.4.1.37950.1.1.5.10.10.2.5.1.17
-- 1.3.6.1.4.1.37950.1.1.5.10.10.2.5.1.17
-- 1.3.6.1.4.1.37950.1.1.5.10.10.2.5.1.17
-- 1.3.6.1.4.1.37950.1.1.5.10.10.2.5.1.17
-- 1.3.6.1.4.1.37950.1.1.5.10.10.2.5.1.17
-- 1.3.6.1.4.1.37950.1.1.5.10.10.2.5.1.17
-- 1.3.6.1.4.1.37950.1.1.5.10.10.2.5.1.17
-- 1.3.6.1.4.1.37950.1.1.5.10.10.2.5.1.17
-- 1.3.6.1.4.1.37950.1.1.5.10.10.2.5.1.17
		-- 1.3.6.1.4.1.37950.1.1.5.10.10.2.5.1.17
		qosBaseAclProtocol OBJECT-TYPE
			SYNTAX INTEGER (-1..255)
			MAX-ACCESS read-only
			STATUS current
			DESCRIPTION
				"Description."
			::= { qosBaseAclEntry 17 }

		
--          1.3.6.1.4.1.37950.1.1.5.10.10.2.5.1.18
-- 1.3.6.1.4.1.37950.1.1.5.10.10.2.5.1.18
-- 1.3.6.1.4.1.37950.1.1.5.10.10.2.5.1.18
-- 1.3.6.1.4.1.37950.1.1.5.10.10.2.5.1.18
-- 1.3.6.1.4.1.37950.1.1.5.10.10.2.5.1.18
-- 1.3.6.1.4.1.37950.1.1.5.10.10.2.5.1.18
-- 1.3.6.1.4.1.37950.1.1.5.10.10.2.5.1.18
-- 1.3.6.1.4.1.37950.1.1.5.10.10.2.5.1.18
-- 1.3.6.1.4.1.37950.1.1.5.10.10.2.5.1.18
		-- 1.3.6.1.4.1.37950.1.1.5.10.10.2.5.1.18
		qosBaseAclProtocolMask OBJECT-TYPE
			SYNTAX INTEGER (0..255)
			MAX-ACCESS read-only
			STATUS current
			DESCRIPTION
				"Description."
			::= { qosBaseAclEntry 18 }

		
--          1.3.6.1.4.1.37950.1.1.5.10.10.2.5.1.19
-- 1.3.6.1.4.1.37950.1.1.5.10.10.2.5.1.19
-- 1.3.6.1.4.1.37950.1.1.5.10.10.2.5.1.19
-- 1.3.6.1.4.1.37950.1.1.5.10.10.2.5.1.19
-- 1.3.6.1.4.1.37950.1.1.5.10.10.2.5.1.19
-- 1.3.6.1.4.1.37950.1.1.5.10.10.2.5.1.19
-- 1.3.6.1.4.1.37950.1.1.5.10.10.2.5.1.19
-- 1.3.6.1.4.1.37950.1.1.5.10.10.2.5.1.19
-- 1.3.6.1.4.1.37950.1.1.5.10.10.2.5.1.19
		-- 1.3.6.1.4.1.37950.1.1.5.10.10.2.5.1.19
		qosBaseAclTosDscp OBJECT-TYPE
			SYNTAX INTEGER (-1..255)
			MAX-ACCESS read-only
			STATUS current
			DESCRIPTION
				"Description."
			::= { qosBaseAclEntry 19 }

		
--          1.3.6.1.4.1.37950.1.1.5.10.10.2.5.1.20
-- 1.3.6.1.4.1.37950.1.1.5.10.10.2.5.1.20
-- 1.3.6.1.4.1.37950.1.1.5.10.10.2.5.1.20
-- 1.3.6.1.4.1.37950.1.1.5.10.10.2.5.1.20
-- 1.3.6.1.4.1.37950.1.1.5.10.10.2.5.1.20
-- 1.3.6.1.4.1.37950.1.1.5.10.10.2.5.1.20
-- 1.3.6.1.4.1.37950.1.1.5.10.10.2.5.1.20
-- 1.3.6.1.4.1.37950.1.1.5.10.10.2.5.1.20
-- 1.3.6.1.4.1.37950.1.1.5.10.10.2.5.1.20
		-- 1.3.6.1.4.1.37950.1.1.5.10.10.2.5.1.20
		qosBaseAclTosDscpMask OBJECT-TYPE
			SYNTAX INTEGER (0..255)
			MAX-ACCESS read-only
			STATUS current
			DESCRIPTION
				"Description."
			::= { qosBaseAclEntry 20 }

		
--          1.3.6.1.4.1.37950.1.1.5.10.10.2.5.1.21
-- 1.3.6.1.4.1.37950.1.1.5.10.10.2.5.1.21
-- 1.3.6.1.4.1.37950.1.1.5.10.10.2.5.1.21
-- 1.3.6.1.4.1.37950.1.1.5.10.10.2.5.1.21
-- 1.3.6.1.4.1.37950.1.1.5.10.10.2.5.1.21
-- 1.3.6.1.4.1.37950.1.1.5.10.10.2.5.1.21
-- 1.3.6.1.4.1.37950.1.1.5.10.10.2.5.1.21
-- 1.3.6.1.4.1.37950.1.1.5.10.10.2.5.1.21
-- 1.3.6.1.4.1.37950.1.1.5.10.10.2.5.1.21
		-- 1.3.6.1.4.1.37950.1.1.5.10.10.2.5.1.21
		qosBaseAclSrcPort OBJECT-TYPE
			SYNTAX INTEGER (-1..65535)
			MAX-ACCESS read-only
			STATUS current
			DESCRIPTION
				"Description."
			::= { qosBaseAclEntry 21 }

		
--          1.3.6.1.4.1.37950.1.1.5.10.10.2.5.1.22
-- 1.3.6.1.4.1.37950.1.1.5.10.10.2.5.1.22
-- 1.3.6.1.4.1.37950.1.1.5.10.10.2.5.1.22
-- 1.3.6.1.4.1.37950.1.1.5.10.10.2.5.1.22
-- 1.3.6.1.4.1.37950.1.1.5.10.10.2.5.1.22
-- 1.3.6.1.4.1.37950.1.1.5.10.10.2.5.1.22
-- 1.3.6.1.4.1.37950.1.1.5.10.10.2.5.1.22
-- 1.3.6.1.4.1.37950.1.1.5.10.10.2.5.1.22
-- 1.3.6.1.4.1.37950.1.1.5.10.10.2.5.1.22
		-- 1.3.6.1.4.1.37950.1.1.5.10.10.2.5.1.22
		qosBaseAclSrcPortMask OBJECT-TYPE
			SYNTAX OCTET STRING
			MAX-ACCESS read-only
			STATUS current
			DESCRIPTION
				"Description."
			::= { qosBaseAclEntry 22 }

		
--          1.3.6.1.4.1.37950.1.1.5.10.10.2.5.1.23
-- 1.3.6.1.4.1.37950.1.1.5.10.10.2.5.1.23
-- 1.3.6.1.4.1.37950.1.1.5.10.10.2.5.1.23
-- 1.3.6.1.4.1.37950.1.1.5.10.10.2.5.1.23
-- 1.3.6.1.4.1.37950.1.1.5.10.10.2.5.1.23
-- 1.3.6.1.4.1.37950.1.1.5.10.10.2.5.1.23
-- 1.3.6.1.4.1.37950.1.1.5.10.10.2.5.1.23
-- 1.3.6.1.4.1.37950.1.1.5.10.10.2.5.1.23
-- 1.3.6.1.4.1.37950.1.1.5.10.10.2.5.1.23
		-- 1.3.6.1.4.1.37950.1.1.5.10.10.2.5.1.23
		qosBaseAclDstPort OBJECT-TYPE
			SYNTAX INTEGER (-1..65535)
			MAX-ACCESS read-only
			STATUS current
			DESCRIPTION
				"Description."
			::= { qosBaseAclEntry 23 }

		
--          1.3.6.1.4.1.37950.1.1.5.10.10.2.5.1.24
-- 1.3.6.1.4.1.37950.1.1.5.10.10.2.5.1.24
-- 1.3.6.1.4.1.37950.1.1.5.10.10.2.5.1.24
-- 1.3.6.1.4.1.37950.1.1.5.10.10.2.5.1.24
-- 1.3.6.1.4.1.37950.1.1.5.10.10.2.5.1.24
-- 1.3.6.1.4.1.37950.1.1.5.10.10.2.5.1.24
-- 1.3.6.1.4.1.37950.1.1.5.10.10.2.5.1.24
-- 1.3.6.1.4.1.37950.1.1.5.10.10.2.5.1.24
-- 1.3.6.1.4.1.37950.1.1.5.10.10.2.5.1.24
		-- 1.3.6.1.4.1.37950.1.1.5.10.10.2.5.1.24
		qosBaseAclDstPortMask OBJECT-TYPE
			SYNTAX OCTET STRING
			MAX-ACCESS read-only
			STATUS current
			DESCRIPTION
				"Description."
			::= { qosBaseAclEntry 24 }

		
--          1.3.6.1.4.1.37950.1.1.5.10.10.3
-- 1.3.6.1.4.1.37950.1.1.5.10.10.3
-- 1.3.6.1.4.1.37950.1.1.5.10.10.3
-- 1.3.6.1.4.1.37950.1.1.5.10.10.3
-- 1.3.6.1.4.1.37950.1.1.5.10.10.3
-- 1.3.6.1.4.1.37950.1.1.5.10.10.3
-- 1.3.6.1.4.1.37950.1.1.5.10.10.3
-- 1.3.6.1.4.1.37950.1.1.5.10.10.3
-- 1.3.6.1.4.1.37950.1.1.5.10.10.3
		-- 1.3.6.1.4.1.37950.1.1.5.10.10.3
		aclEffectTable OBJECT-TYPE
			SYNTAX SEQUENCE OF AclEffectEntry
			MAX-ACCESS not-accessible
			STATUS current
			DESCRIPTION
				"Description."
			::= { v1600dAcl 3 }

		
--          1.3.6.1.4.1.37950.1.1.5.10.10.3.1
-- 1.3.6.1.4.1.37950.1.1.5.10.10.3.1
-- 1.3.6.1.4.1.37950.1.1.5.10.10.3.1
-- 1.3.6.1.4.1.37950.1.1.5.10.10.3.1
-- 1.3.6.1.4.1.37950.1.1.5.10.10.3.1
-- 1.3.6.1.4.1.37950.1.1.5.10.10.3.1
-- 1.3.6.1.4.1.37950.1.1.5.10.10.3.1
-- 1.3.6.1.4.1.37950.1.1.5.10.10.3.1
-- 1.3.6.1.4.1.37950.1.1.5.10.10.3.1
		-- 1.3.6.1.4.1.37950.1.1.5.10.10.3.1
		aclEffectEntry OBJECT-TYPE
			SYNTAX AclEffectEntry
			MAX-ACCESS not-accessible
			STATUS current
			DESCRIPTION
				"Description."
			INDEX { aclIndex }
			::= { aclEffectTable 1 }

		
		AclEffectEntry ::=
			SEQUENCE { 
				aclIndex
					Integer32,
				aclPortList
					OCTET STRING,
				aclPortListEgress
					OCTET STRING
			 }

--          1.3.6.1.4.1.37950.1.1.5.10.10.3.1.1
-- 1.3.6.1.4.1.37950.1.1.5.10.10.3.1.1
-- 1.3.6.1.4.1.37950.1.1.5.10.10.3.1.1
-- 1.3.6.1.4.1.37950.1.1.5.10.10.3.1.1
-- 1.3.6.1.4.1.37950.1.1.5.10.10.3.1.1
-- 1.3.6.1.4.1.37950.1.1.5.10.10.3.1.1
-- 1.3.6.1.4.1.37950.1.1.5.10.10.3.1.1
-- 1.3.6.1.4.1.37950.1.1.5.10.10.3.1.1
-- 1.3.6.1.4.1.37950.1.1.5.10.10.3.1.1
		-- 1.3.6.1.4.1.37950.1.1.5.10.10.3.1.1
		aclIndex OBJECT-TYPE
			SYNTAX Integer32
			MAX-ACCESS read-only
			STATUS current
			DESCRIPTION
				"Description."
			::= { aclEffectEntry 1 }

		
--          1.3.6.1.4.1.37950.1.1.5.10.10.3.1.2
-- 1.3.6.1.4.1.37950.1.1.5.10.10.3.1.2
-- 1.3.6.1.4.1.37950.1.1.5.10.10.3.1.2
-- 1.3.6.1.4.1.37950.1.1.5.10.10.3.1.2
-- 1.3.6.1.4.1.37950.1.1.5.10.10.3.1.2
-- 1.3.6.1.4.1.37950.1.1.5.10.10.3.1.2
-- 1.3.6.1.4.1.37950.1.1.5.10.10.3.1.2
-- 1.3.6.1.4.1.37950.1.1.5.10.10.3.1.2
-- 1.3.6.1.4.1.37950.1.1.5.10.10.3.1.2
		-- 1.3.6.1.4.1.37950.1.1.5.10.10.3.1.2
		aclPortList OBJECT-TYPE
			SYNTAX OCTET STRING
			MAX-ACCESS read-write
			STATUS current
			DESCRIPTION
				"Description."
			::= { aclEffectEntry 2 }

		
--         1.3.6.1.4.1.37950.1.1.5.10.10.3.1.3
-- 1.3.6.1.4.1.37950.1.1.5.10.10.3.1.3
-- 1.3.6.1.4.1.37950.1.1.5.10.10.3.1.3
-- 1.3.6.1.4.1.37950.1.1.5.10.10.3.1.3
-- 1.3.6.1.4.1.37950.1.1.5.10.10.3.1.3
-- 1.3.6.1.4.1.37950.1.1.5.10.10.3.1.3
-- 1.3.6.1.4.1.37950.1.1.5.10.10.3.1.3
-- 1.3.6.1.4.1.37950.1.1.5.10.10.3.1.3
		-- 1.3.6.1.4.1.37950.1.1.5.10.10.3.1.3
		aclPortListEgress OBJECT-TYPE
			SYNTAX OCTET STRING
			MAX-ACCESS read-write
			STATUS current
			DESCRIPTION
				"Description."
			::= { aclEffectEntry 3 }

		
--          1.3.6.1.4.1.37950.1.1.5.10.10.1
-- 1.3.6.1.4.1.37950.1.1.5.10.10.4
-- 1.3.6.1.4.1.37950.1.1.5.10.10.4
-- 1.3.6.1.4.1.37950.1.1.5.10.10.4
-- 1.3.6.1.4.1.37950.1.1.5.10.10.4
-- 1.3.6.1.4.1.37950.1.1.5.10.10.4
-- 1.3.6.1.4.1.37950.1.1.5.10.10.4
-- 1.3.6.1.4.1.37950.1.1.5.10.10.4
-- 1.3.6.1.4.1.37950.1.1.5.10.10.4
		-- 1.3.6.1.4.1.37950.1.1.5.10.10.4
		ipv6aclCfg OBJECT IDENTIFIER ::= { v1600dAcl 4 }

		
--          1.3.6.1.4.1.37950.1.1.5.10.10.1.1
-- 1.3.6.1.4.1.37950.1.1.5.10.10.4.1
-- 1.3.6.1.4.1.37950.1.1.5.10.10.4.1
-- 1.3.6.1.4.1.37950.1.1.5.10.10.4.1
-- 1.3.6.1.4.1.37950.1.1.5.10.10.4.1
-- 1.3.6.1.4.1.37950.1.1.5.10.10.4.1
-- 1.3.6.1.4.1.37950.1.1.5.10.10.4.1
-- 1.3.6.1.4.1.37950.1.1.5.10.10.4.1
-- 1.3.6.1.4.1.37950.1.1.5.10.10.4.1
		-- 1.3.6.1.4.1.37950.1.1.5.10.10.4.1
		stdIPv6FilterCfg OBJECT IDENTIFIER ::= { ipv6aclCfg 1 }

		
--          1.3.6.1.4.1.37950.1.1.5.10.10.1.1.1
-- 1.3.6.1.4.1.37950.1.1.5.10.10.4.1.1
-- 1.3.6.1.4.1.37950.1.1.5.10.10.4.1.1
-- 1.3.6.1.4.1.37950.1.1.5.10.10.4.1.1
-- 1.3.6.1.4.1.37950.1.1.5.10.10.4.1.1
-- 1.3.6.1.4.1.37950.1.1.5.10.10.4.1.1
-- 1.3.6.1.4.1.37950.1.1.5.10.10.4.1.1
-- 1.3.6.1.4.1.37950.1.1.5.10.10.4.1.1
-- 1.3.6.1.4.1.37950.1.1.5.10.10.4.1.1
		-- 1.3.6.1.4.1.37950.1.1.5.10.10.4.1.1
		stdIpv6FilterId OBJECT-TYPE
			SYNTAX INTEGER (0..999)
			MAX-ACCESS read-write
			STATUS current
			DESCRIPTION
				"Description."
			::= { stdIPv6FilterCfg 1 }

		
--          1.3.6.1.4.1.37950.1.1.5.10.10.1.1.2
-- 1.3.6.1.4.1.37950.1.1.5.10.10.4.1.2
-- 1.3.6.1.4.1.37950.1.1.5.10.10.4.1.2
-- 1.3.6.1.4.1.37950.1.1.5.10.10.4.1.2
-- 1.3.6.1.4.1.37950.1.1.5.10.10.4.1.2
-- 1.3.6.1.4.1.37950.1.1.5.10.10.4.1.2
-- 1.3.6.1.4.1.37950.1.1.5.10.10.4.1.2
-- 1.3.6.1.4.1.37950.1.1.5.10.10.4.1.2
-- 1.3.6.1.4.1.37950.1.1.5.10.10.4.1.2
		-- 1.3.6.1.4.1.37950.1.1.5.10.10.4.1.2
		stdIpv6FilterSrcIpv6 OBJECT-TYPE
			SYNTAX OCTET STRING
			MAX-ACCESS read-write
			STATUS current
			DESCRIPTION
				"Description."
			::= { stdIPv6FilterCfg 2 }

		
--          1.3.6.1.4.1.37950.1.1.5.10.10.1.1.3
-- 1.3.6.1.4.1.37950.1.1.5.10.10.4.1.3
-- 1.3.6.1.4.1.37950.1.1.5.10.10.4.1.3
-- 1.3.6.1.4.1.37950.1.1.5.10.10.4.1.3
-- 1.3.6.1.4.1.37950.1.1.5.10.10.4.1.3
-- 1.3.6.1.4.1.37950.1.1.5.10.10.4.1.3
-- 1.3.6.1.4.1.37950.1.1.5.10.10.4.1.3
-- 1.3.6.1.4.1.37950.1.1.5.10.10.4.1.3
-- 1.3.6.1.4.1.37950.1.1.5.10.10.4.1.3
		-- 1.3.6.1.4.1.37950.1.1.5.10.10.4.1.3
		stdIpv6FilterSrcPrefixlen OBJECT-TYPE
			SYNTAX Integer32 (-1..128)
			MAX-ACCESS read-write
			STATUS current
			DESCRIPTION
				"Description."
			::= { stdIPv6FilterCfg 3 }

		
--          1.3.6.1.4.1.37950.1.1.5.10.10.1.1.4
-- 1.3.6.1.4.1.37950.1.1.5.10.10.4.1.4
-- 1.3.6.1.4.1.37950.1.1.5.10.10.4.1.4
-- 1.3.6.1.4.1.37950.1.1.5.10.10.4.1.4
-- 1.3.6.1.4.1.37950.1.1.5.10.10.4.1.4
-- 1.3.6.1.4.1.37950.1.1.5.10.10.4.1.4
-- 1.3.6.1.4.1.37950.1.1.5.10.10.4.1.4
-- 1.3.6.1.4.1.37950.1.1.5.10.10.4.1.4
-- 1.3.6.1.4.1.37950.1.1.5.10.10.4.1.4
		-- 1.3.6.1.4.1.37950.1.1.5.10.10.4.1.4
		stdIpv6FilterMode OBJECT-TYPE
			SYNTAX INTEGER
				{
				permit(1),
				deny(2)
				}
			MAX-ACCESS read-write
			STATUS current
			DESCRIPTION
				"Description."
			::= { stdIPv6FilterCfg 4 }

		
--          1.3.6.1.4.1.37950.1.1.5.10.10.1.1.5
-- 1.3.6.1.4.1.37950.1.1.5.10.10.4.1.5
-- 1.3.6.1.4.1.37950.1.1.5.10.10.4.1.5
-- 1.3.6.1.4.1.37950.1.1.5.10.10.4.1.5
-- 1.3.6.1.4.1.37950.1.1.5.10.10.4.1.5
-- 1.3.6.1.4.1.37950.1.1.5.10.10.4.1.5
-- 1.3.6.1.4.1.37950.1.1.5.10.10.4.1.5
-- 1.3.6.1.4.1.37950.1.1.5.10.10.4.1.5
-- 1.3.6.1.4.1.37950.1.1.5.10.10.4.1.5
		-- 1.3.6.1.4.1.37950.1.1.5.10.10.4.1.5
		stdIpv6FilterAction OBJECT-TYPE
			SYNTAX INTEGER
				{
				add(1),
				delete(2),
				clear(3)
				}
			MAX-ACCESS read-write
			STATUS current
			DESCRIPTION
				"Description."
			::= { stdIPv6FilterCfg 5 }

		
--          1.3.6.1.4.1.37950.1.1.5.10.10.1.2
-- 1.3.6.1.4.1.37950.1.1.5.10.10.4.2
-- 1.3.6.1.4.1.37950.1.1.5.10.10.4.2
-- 1.3.6.1.4.1.37950.1.1.5.10.10.4.2
-- 1.3.6.1.4.1.37950.1.1.5.10.10.4.2
-- 1.3.6.1.4.1.37950.1.1.5.10.10.4.2
-- 1.3.6.1.4.1.37950.1.1.5.10.10.4.2
-- 1.3.6.1.4.1.37950.1.1.5.10.10.4.2
-- 1.3.6.1.4.1.37950.1.1.5.10.10.4.2
		-- 1.3.6.1.4.1.37950.1.1.5.10.10.4.2
		extIPv6FilterCfg OBJECT IDENTIFIER ::= { ipv6aclCfg 2 }

		
--          1.3.6.1.4.1.37950.1.1.5.10.10.1.2.1
-- 1.3.6.1.4.1.37950.1.1.5.10.10.4.2.1
-- 1.3.6.1.4.1.37950.1.1.5.10.10.4.2.1
-- 1.3.6.1.4.1.37950.1.1.5.10.10.4.2.1
-- 1.3.6.1.4.1.37950.1.1.5.10.10.4.2.1
-- 1.3.6.1.4.1.37950.1.1.5.10.10.4.2.1
-- 1.3.6.1.4.1.37950.1.1.5.10.10.4.2.1
-- 1.3.6.1.4.1.37950.1.1.5.10.10.4.2.1
-- 1.3.6.1.4.1.37950.1.1.5.10.10.4.2.1
		-- 1.3.6.1.4.1.37950.1.1.5.10.10.4.2.1
		extIpv6FilterId OBJECT-TYPE
			SYNTAX INTEGER (1000..1999)
			MAX-ACCESS read-write
			STATUS current
			DESCRIPTION
				"Description."
			::= { extIPv6FilterCfg 1 }

		
--          1.3.6.1.4.1.37950.1.1.5.10.10.1.2.2
-- 1.3.6.1.4.1.37950.1.1.5.10.10.4.2.2
-- 1.3.6.1.4.1.37950.1.1.5.10.10.4.2.2
-- 1.3.6.1.4.1.37950.1.1.5.10.10.4.2.2
-- 1.3.6.1.4.1.37950.1.1.5.10.10.4.2.2
-- 1.3.6.1.4.1.37950.1.1.5.10.10.4.2.2
-- 1.3.6.1.4.1.37950.1.1.5.10.10.4.2.2
-- 1.3.6.1.4.1.37950.1.1.5.10.10.4.2.2
-- 1.3.6.1.4.1.37950.1.1.5.10.10.4.2.2
		-- 1.3.6.1.4.1.37950.1.1.5.10.10.4.2.2
		extIpv6FilterProtocol OBJECT-TYPE
			SYNTAX INTEGER (-1..255)
			MAX-ACCESS read-write
			STATUS current
			DESCRIPTION
				"Description."
			::= { extIPv6FilterCfg 2 }

		
--          1.3.6.1.4.1.37950.1.1.5.10.10.1.2.3
-- 1.3.6.1.4.1.37950.1.1.5.10.10.4.2.3
-- 1.3.6.1.4.1.37950.1.1.5.10.10.4.2.3
-- 1.3.6.1.4.1.37950.1.1.5.10.10.4.2.3
-- 1.3.6.1.4.1.37950.1.1.5.10.10.4.2.3
-- 1.3.6.1.4.1.37950.1.1.5.10.10.4.2.3
-- 1.3.6.1.4.1.37950.1.1.5.10.10.4.2.3
-- 1.3.6.1.4.1.37950.1.1.5.10.10.4.2.3
-- 1.3.6.1.4.1.37950.1.1.5.10.10.4.2.3
		-- 1.3.6.1.4.1.37950.1.1.5.10.10.4.2.3
		extIpv6FilterSrcIpv6 OBJECT-TYPE
			SYNTAX OCTET STRING
			MAX-ACCESS read-write
			STATUS current
			DESCRIPTION
				"Description."
			::= { extIPv6FilterCfg 3 }

		
--          1.3.6.1.4.1.37950.1.1.5.10.10.1.2.4
-- 1.3.6.1.4.1.37950.1.1.5.10.10.4.2.4
-- 1.3.6.1.4.1.37950.1.1.5.10.10.4.2.4
-- 1.3.6.1.4.1.37950.1.1.5.10.10.4.2.4
-- 1.3.6.1.4.1.37950.1.1.5.10.10.4.2.4
-- 1.3.6.1.4.1.37950.1.1.5.10.10.4.2.4
-- 1.3.6.1.4.1.37950.1.1.5.10.10.4.2.4
-- 1.3.6.1.4.1.37950.1.1.5.10.10.4.2.4
-- 1.3.6.1.4.1.37950.1.1.5.10.10.4.2.4
		-- 1.3.6.1.4.1.37950.1.1.5.10.10.4.2.4
		extIpv6FilterSrcPrefixlen OBJECT-TYPE
			SYNTAX Integer32 (-1..128)
			MAX-ACCESS read-write
			STATUS current
			DESCRIPTION
				"Description."
			::= { extIPv6FilterCfg 4 }

		
--          1.3.6.1.4.1.37950.1.1.5.10.10.1.2.5
-- 1.3.6.1.4.1.37950.1.1.5.10.10.4.2.5
-- 1.3.6.1.4.1.37950.1.1.5.10.10.4.2.5
-- 1.3.6.1.4.1.37950.1.1.5.10.10.4.2.5
-- 1.3.6.1.4.1.37950.1.1.5.10.10.4.2.5
-- 1.3.6.1.4.1.37950.1.1.5.10.10.4.2.5
-- 1.3.6.1.4.1.37950.1.1.5.10.10.4.2.5
-- 1.3.6.1.4.1.37950.1.1.5.10.10.4.2.5
-- 1.3.6.1.4.1.37950.1.1.5.10.10.4.2.5
		-- 1.3.6.1.4.1.37950.1.1.5.10.10.4.2.5
		extIpv6FilterSrcPort OBJECT-TYPE
			SYNTAX INTEGER (-1..65535)
			MAX-ACCESS read-write
			STATUS current
			DESCRIPTION
				"Description."
			::= { extIPv6FilterCfg 5 }

		
--          1.3.6.1.4.1.37950.1.1.5.10.10.1.2.6
-- 1.3.6.1.4.1.37950.1.1.5.10.10.4.2.6
-- 1.3.6.1.4.1.37950.1.1.5.10.10.4.2.6
-- 1.3.6.1.4.1.37950.1.1.5.10.10.4.2.6
-- 1.3.6.1.4.1.37950.1.1.5.10.10.4.2.6
-- 1.3.6.1.4.1.37950.1.1.5.10.10.4.2.6
-- 1.3.6.1.4.1.37950.1.1.5.10.10.4.2.6
-- 1.3.6.1.4.1.37950.1.1.5.10.10.4.2.6
-- 1.3.6.1.4.1.37950.1.1.5.10.10.4.2.6
		-- 1.3.6.1.4.1.37950.1.1.5.10.10.4.2.6
		extIpv6FilterDstIpv6 OBJECT-TYPE
			SYNTAX OCTET STRING
			MAX-ACCESS read-write
			STATUS current
			DESCRIPTION
				"Description."
			::= { extIPv6FilterCfg 6 }

		
--          1.3.6.1.4.1.37950.1.1.5.10.10.1.2.7
-- 1.3.6.1.4.1.37950.1.1.5.10.10.4.2.7
-- 1.3.6.1.4.1.37950.1.1.5.10.10.4.2.7
-- 1.3.6.1.4.1.37950.1.1.5.10.10.4.2.7
-- 1.3.6.1.4.1.37950.1.1.5.10.10.4.2.7
-- 1.3.6.1.4.1.37950.1.1.5.10.10.4.2.7
-- 1.3.6.1.4.1.37950.1.1.5.10.10.4.2.7
-- 1.3.6.1.4.1.37950.1.1.5.10.10.4.2.7
-- 1.3.6.1.4.1.37950.1.1.5.10.10.4.2.7
		-- 1.3.6.1.4.1.37950.1.1.5.10.10.4.2.7
		extIpv6FilterDstPrefixlen OBJECT-TYPE
			SYNTAX Integer32 (-1..128)
			MAX-ACCESS read-write
			STATUS current
			DESCRIPTION
				"Description."
			::= { extIPv6FilterCfg 7 }

		
--          1.3.6.1.4.1.37950.1.1.5.10.10.1.2.8
-- 1.3.6.1.4.1.37950.1.1.5.10.10.4.2.8
-- 1.3.6.1.4.1.37950.1.1.5.10.10.4.2.8
-- 1.3.6.1.4.1.37950.1.1.5.10.10.4.2.8
-- 1.3.6.1.4.1.37950.1.1.5.10.10.4.2.8
-- 1.3.6.1.4.1.37950.1.1.5.10.10.4.2.8
-- 1.3.6.1.4.1.37950.1.1.5.10.10.4.2.8
-- 1.3.6.1.4.1.37950.1.1.5.10.10.4.2.8
-- 1.3.6.1.4.1.37950.1.1.5.10.10.4.2.8
		-- 1.3.6.1.4.1.37950.1.1.5.10.10.4.2.8
		extIpv6FilterDstPort OBJECT-TYPE
			SYNTAX INTEGER (-1..65535)
			MAX-ACCESS read-write
			STATUS current
			DESCRIPTION
				"Description."
			::= { extIPv6FilterCfg 8 }

		
--          1.3.6.1.4.1.37950.1.1.5.10.10.1.2.9
-- 1.3.6.1.4.1.37950.1.1.5.10.10.4.2.9
-- 1.3.6.1.4.1.37950.1.1.5.10.10.4.2.9
-- 1.3.6.1.4.1.37950.1.1.5.10.10.4.2.9
-- 1.3.6.1.4.1.37950.1.1.5.10.10.4.2.9
-- 1.3.6.1.4.1.37950.1.1.5.10.10.4.2.9
-- 1.3.6.1.4.1.37950.1.1.5.10.10.4.2.9
-- 1.3.6.1.4.1.37950.1.1.5.10.10.4.2.9
-- 1.3.6.1.4.1.37950.1.1.5.10.10.4.2.9
		-- 1.3.6.1.4.1.37950.1.1.5.10.10.4.2.9
		extIpv6FilterDscp OBJECT-TYPE
			SYNTAX INTEGER (-1..63)
			MAX-ACCESS read-write
			STATUS current
			DESCRIPTION
				"Description."
			::= { extIPv6FilterCfg 9 }

		
--          1.3.6.1.4.1.37950.1.1.5.10.10.1.2.10
-- 1.3.6.1.4.1.37950.1.1.5.10.10.4.2.10
-- 1.3.6.1.4.1.37950.1.1.5.10.10.4.2.10
-- 1.3.6.1.4.1.37950.1.1.5.10.10.4.2.10
-- 1.3.6.1.4.1.37950.1.1.5.10.10.4.2.10
-- 1.3.6.1.4.1.37950.1.1.5.10.10.4.2.10
-- 1.3.6.1.4.1.37950.1.1.5.10.10.4.2.10
-- 1.3.6.1.4.1.37950.1.1.5.10.10.4.2.10
-- 1.3.6.1.4.1.37950.1.1.5.10.10.4.2.10
		-- 1.3.6.1.4.1.37950.1.1.5.10.10.4.2.10
		extIpv6FilterMode OBJECT-TYPE
			SYNTAX INTEGER
				{
				permit(1),
				deny(2)
				}
			MAX-ACCESS read-write
			STATUS current
			DESCRIPTION
				"Description."
			::= { extIPv6FilterCfg 10 }

		
--          1.3.6.1.4.1.37950.1.1.5.10.10.1.2.11
-- 1.3.6.1.4.1.37950.1.1.5.10.10.4.2.11
-- 1.3.6.1.4.1.37950.1.1.5.10.10.4.2.11
-- 1.3.6.1.4.1.37950.1.1.5.10.10.4.2.11
-- 1.3.6.1.4.1.37950.1.1.5.10.10.4.2.11
-- 1.3.6.1.4.1.37950.1.1.5.10.10.4.2.11
-- 1.3.6.1.4.1.37950.1.1.5.10.10.4.2.11
-- 1.3.6.1.4.1.37950.1.1.5.10.10.4.2.11
-- 1.3.6.1.4.1.37950.1.1.5.10.10.4.2.11
		-- 1.3.6.1.4.1.37950.1.1.5.10.10.4.2.11
		extIpv6FilterAction OBJECT-TYPE
			SYNTAX INTEGER
				{
				add(1),
				delete(2),
				clear(3)
				}
			MAX-ACCESS read-write
			STATUS current
			DESCRIPTION
				"Description."
			::= { extIPv6FilterCfg 11 }

		
--          1.3.6.1.4.1.37950.1.1.5.10.10.1.4
-- 1.3.6.1.4.1.37950.1.1.5.10.10.4.4
-- 1.3.6.1.4.1.37950.1.1.5.10.10.4.3
-- 1.3.6.1.4.1.37950.1.1.5.10.10.4.3
-- 1.3.6.1.4.1.37950.1.1.5.10.10.4.3
-- 1.3.6.1.4.1.37950.1.1.5.10.10.4.3
-- 1.3.6.1.4.1.37950.1.1.5.10.10.4.3
-- 1.3.6.1.4.1.37950.1.1.5.10.10.4.3
-- 1.3.6.1.4.1.37950.1.1.5.10.10.4.3
		-- 1.3.6.1.4.1.37950.1.1.5.10.10.4.3
		portBasev6AclCfg OBJECT IDENTIFIER ::= { ipv6aclCfg 3 }

		
--          1.3.6.1.4.1.37950.1.1.5.10.10.1.4.1
-- 1.3.6.1.4.1.37950.1.1.5.10.10.4.4.1
-- 1.3.6.1.4.1.37950.1.1.5.10.10.4.3.1
-- 1.3.6.1.4.1.37950.1.1.5.10.10.4.3.1
-- 1.3.6.1.4.1.37950.1.1.5.10.10.4.3.1
-- 1.3.6.1.4.1.37950.1.1.5.10.10.4.3.1
-- 1.3.6.1.4.1.37950.1.1.5.10.10.4.3.1
-- 1.3.6.1.4.1.37950.1.1.5.10.10.4.3.1
-- 1.3.6.1.4.1.37950.1.1.5.10.10.4.3.1
		-- 1.3.6.1.4.1.37950.1.1.5.10.10.4.3.1
		portBasev6AclId OBJECT-TYPE
			SYNTAX Integer32 (5000..5999)
			MAX-ACCESS read-write
			STATUS current
			DESCRIPTION
				"Description."
			::= { portBasev6AclCfg 1 }

		
--          1.3.6.1.4.1.37950.1.1.5.10.10.1.4.2
-- 1.3.6.1.4.1.37950.1.1.5.10.10.4.4.2
-- 1.3.6.1.4.1.37950.1.1.5.10.10.4.3.2
-- 1.3.6.1.4.1.37950.1.1.5.10.10.4.3.2
-- 1.3.6.1.4.1.37950.1.1.5.10.10.4.3.2
-- 1.3.6.1.4.1.37950.1.1.5.10.10.4.3.2
-- 1.3.6.1.4.1.37950.1.1.5.10.10.4.3.2
-- 1.3.6.1.4.1.37950.1.1.5.10.10.4.3.2
-- 1.3.6.1.4.1.37950.1.1.5.10.10.4.3.2
		-- 1.3.6.1.4.1.37950.1.1.5.10.10.4.3.2
		portBasev6FltMode OBJECT-TYPE
			SYNTAX INTEGER
				{
				permit(1),
				deny(2)
				}
			MAX-ACCESS read-write
			STATUS current
			DESCRIPTION
				"Description."
			::= { portBasev6AclCfg 2 }

		
--          1.3.6.1.4.1.37950.1.1.5.10.10.1.4.3
-- 1.3.6.1.4.1.37950.1.1.5.10.10.4.4.3
-- 1.3.6.1.4.1.37950.1.1.5.10.10.4.3.3
-- 1.3.6.1.4.1.37950.1.1.5.10.10.4.3.3
-- 1.3.6.1.4.1.37950.1.1.5.10.10.4.3.3
-- 1.3.6.1.4.1.37950.1.1.5.10.10.4.3.3
-- 1.3.6.1.4.1.37950.1.1.5.10.10.4.3.3
-- 1.3.6.1.4.1.37950.1.1.5.10.10.4.3.3
-- 1.3.6.1.4.1.37950.1.1.5.10.10.4.3.3
		-- 1.3.6.1.4.1.37950.1.1.5.10.10.4.3.3
		portBasev6SrcMac OBJECT-TYPE
			SYNTAX OCTET STRING
			MAX-ACCESS read-write
			STATUS current
			DESCRIPTION
				"Description."
			::= { portBasev6AclCfg 3 }

		
--          1.3.6.1.4.1.37950.1.1.5.10.10.1.4.4
-- 1.3.6.1.4.1.37950.1.1.5.10.10.4.4.4
-- 1.3.6.1.4.1.37950.1.1.5.10.10.4.3.4
-- 1.3.6.1.4.1.37950.1.1.5.10.10.4.3.4
-- 1.3.6.1.4.1.37950.1.1.5.10.10.4.3.4
-- 1.3.6.1.4.1.37950.1.1.5.10.10.4.3.4
-- 1.3.6.1.4.1.37950.1.1.5.10.10.4.3.4
-- 1.3.6.1.4.1.37950.1.1.5.10.10.4.3.4
-- 1.3.6.1.4.1.37950.1.1.5.10.10.4.3.4
		-- 1.3.6.1.4.1.37950.1.1.5.10.10.4.3.4
		portBasev6SrcMacMask OBJECT-TYPE
			SYNTAX OCTET STRING
			MAX-ACCESS read-write
			STATUS current
			DESCRIPTION
				"Description."
			::= { portBasev6AclCfg 4 }

		
--          1.3.6.1.4.1.37950.1.1.5.10.10.1.4.5
-- 1.3.6.1.4.1.37950.1.1.5.10.10.4.4.5
-- 1.3.6.1.4.1.37950.1.1.5.10.10.4.3.5
-- 1.3.6.1.4.1.37950.1.1.5.10.10.4.3.5
-- 1.3.6.1.4.1.37950.1.1.5.10.10.4.3.5
-- 1.3.6.1.4.1.37950.1.1.5.10.10.4.3.5
-- 1.3.6.1.4.1.37950.1.1.5.10.10.4.3.5
-- 1.3.6.1.4.1.37950.1.1.5.10.10.4.3.5
-- 1.3.6.1.4.1.37950.1.1.5.10.10.4.3.5
		-- 1.3.6.1.4.1.37950.1.1.5.10.10.4.3.5
		portBasev6DstMac OBJECT-TYPE
			SYNTAX OCTET STRING
			MAX-ACCESS read-write
			STATUS current
			DESCRIPTION
				"Description."
			::= { portBasev6AclCfg 5 }

		
--          1.3.6.1.4.1.37950.1.1.5.10.10.1.4.6
-- 1.3.6.1.4.1.37950.1.1.5.10.10.4.4.6
-- 1.3.6.1.4.1.37950.1.1.5.10.10.4.3.6
-- 1.3.6.1.4.1.37950.1.1.5.10.10.4.3.6
-- 1.3.6.1.4.1.37950.1.1.5.10.10.4.3.6
-- 1.3.6.1.4.1.37950.1.1.5.10.10.4.3.6
-- 1.3.6.1.4.1.37950.1.1.5.10.10.4.3.6
-- 1.3.6.1.4.1.37950.1.1.5.10.10.4.3.6
-- 1.3.6.1.4.1.37950.1.1.5.10.10.4.3.6
		-- 1.3.6.1.4.1.37950.1.1.5.10.10.4.3.6
		portBasev6DstMacMask OBJECT-TYPE
			SYNTAX OCTET STRING
			MAX-ACCESS read-write
			STATUS current
			DESCRIPTION
				"Description."
			::= { portBasev6AclCfg 6 }

		
--          1.3.6.1.4.1.37950.1.1.5.10.10.1.4.7
-- 1.3.6.1.4.1.37950.1.1.5.10.10.4.4.7
-- 1.3.6.1.4.1.37950.1.1.5.10.10.4.3.7
-- 1.3.6.1.4.1.37950.1.1.5.10.10.4.3.7
-- 1.3.6.1.4.1.37950.1.1.5.10.10.4.3.7
-- 1.3.6.1.4.1.37950.1.1.5.10.10.4.3.7
-- 1.3.6.1.4.1.37950.1.1.5.10.10.4.3.7
-- 1.3.6.1.4.1.37950.1.1.5.10.10.4.3.7
-- 1.3.6.1.4.1.37950.1.1.5.10.10.4.3.7
		-- 1.3.6.1.4.1.37950.1.1.5.10.10.4.3.7
		portBasev6Vlan OBJECT-TYPE
			SYNTAX INTEGER (0..4094)
			MAX-ACCESS read-write
			STATUS current
			DESCRIPTION
				"Description."
			::= { portBasev6AclCfg 7 }

		
--          1.3.6.1.4.1.37950.1.1.5.10.10.1.4.8
-- 1.3.6.1.4.1.37950.1.1.5.10.10.4.4.8
-- 1.3.6.1.4.1.37950.1.1.5.10.10.4.3.8
-- 1.3.6.1.4.1.37950.1.1.5.10.10.4.3.8
-- 1.3.6.1.4.1.37950.1.1.5.10.10.4.3.8
-- 1.3.6.1.4.1.37950.1.1.5.10.10.4.3.8
-- 1.3.6.1.4.1.37950.1.1.5.10.10.4.3.8
-- 1.3.6.1.4.1.37950.1.1.5.10.10.4.3.8
-- 1.3.6.1.4.1.37950.1.1.5.10.10.4.3.8
		-- 1.3.6.1.4.1.37950.1.1.5.10.10.4.3.8
		portBasev6VlanMask OBJECT-TYPE
			SYNTAX INTEGER (0..4095)
			MAX-ACCESS read-write
			STATUS current
			DESCRIPTION
				"Description."
			::= { portBasev6AclCfg 8 }

		
--          1.3.6.1.4.1.37950.1.1.5.10.10.1.4.9
-- 1.3.6.1.4.1.37950.1.1.5.10.10.4.4.9
-- 1.3.6.1.4.1.37950.1.1.5.10.10.4.3.9
-- 1.3.6.1.4.1.37950.1.1.5.10.10.4.3.9
-- 1.3.6.1.4.1.37950.1.1.5.10.10.4.3.9
-- 1.3.6.1.4.1.37950.1.1.5.10.10.4.3.9
-- 1.3.6.1.4.1.37950.1.1.5.10.10.4.3.9
-- 1.3.6.1.4.1.37950.1.1.5.10.10.4.3.9
-- 1.3.6.1.4.1.37950.1.1.5.10.10.4.3.9
		-- 1.3.6.1.4.1.37950.1.1.5.10.10.4.3.9
		portBasev6Cos OBJECT-TYPE
			SYNTAX INTEGER (-1..7)
			MAX-ACCESS read-write
			STATUS current
			DESCRIPTION
				"Description."
			::= { portBasev6AclCfg 9 }

		
--          1.3.6.1.4.1.37950.1.1.5.10.10.1.4.10
-- 1.3.6.1.4.1.37950.1.1.5.10.10.4.4.10
-- 1.3.6.1.4.1.37950.1.1.5.10.10.4.3.10
-- 1.3.6.1.4.1.37950.1.1.5.10.10.4.3.10
-- 1.3.6.1.4.1.37950.1.1.5.10.10.4.3.10
-- 1.3.6.1.4.1.37950.1.1.5.10.10.4.3.10
-- 1.3.6.1.4.1.37950.1.1.5.10.10.4.3.10
-- 1.3.6.1.4.1.37950.1.1.5.10.10.4.3.10
-- 1.3.6.1.4.1.37950.1.1.5.10.10.4.3.10
		-- 1.3.6.1.4.1.37950.1.1.5.10.10.4.3.10
		portBasev6EthernetType OBJECT-TYPE
			SYNTAX OCTET STRING
			MAX-ACCESS read-write
			STATUS current
			DESCRIPTION
				"Description."
			::= { portBasev6AclCfg 10 }

		
--          1.3.6.1.4.1.37950.1.1.5.10.10.1.4.11
-- 1.3.6.1.4.1.37950.1.1.5.10.10.4.4.11
-- 1.3.6.1.4.1.37950.1.1.5.10.10.4.3.11
-- 1.3.6.1.4.1.37950.1.1.5.10.10.4.3.11
-- 1.3.6.1.4.1.37950.1.1.5.10.10.4.3.11
-- 1.3.6.1.4.1.37950.1.1.5.10.10.4.3.11
-- 1.3.6.1.4.1.37950.1.1.5.10.10.4.3.11
-- 1.3.6.1.4.1.37950.1.1.5.10.10.4.3.11
-- 1.3.6.1.4.1.37950.1.1.5.10.10.4.3.11
		-- 1.3.6.1.4.1.37950.1.1.5.10.10.4.3.11
		portBasev6SrcIpv6 OBJECT-TYPE
			SYNTAX OCTET STRING
			MAX-ACCESS read-write
			STATUS current
			DESCRIPTION
				"Description."
			::= { portBasev6AclCfg 11 }

		
--          1.3.6.1.4.1.37950.1.1.5.10.10.1.4.12
-- 1.3.6.1.4.1.37950.1.1.5.10.10.4.4.12
-- 1.3.6.1.4.1.37950.1.1.5.10.10.4.3.12
-- 1.3.6.1.4.1.37950.1.1.5.10.10.4.3.12
-- 1.3.6.1.4.1.37950.1.1.5.10.10.4.3.12
-- 1.3.6.1.4.1.37950.1.1.5.10.10.4.3.12
-- 1.3.6.1.4.1.37950.1.1.5.10.10.4.3.12
-- 1.3.6.1.4.1.37950.1.1.5.10.10.4.3.12
-- 1.3.6.1.4.1.37950.1.1.5.10.10.4.3.12
		-- 1.3.6.1.4.1.37950.1.1.5.10.10.4.3.12
		portBasev6SrcPrefixlen OBJECT-TYPE
			SYNTAX Integer32 (-1..128)
			MAX-ACCESS read-write
			STATUS current
			DESCRIPTION
				"Description."
			::= { portBasev6AclCfg 12 }

		
--          1.3.6.1.4.1.37950.1.1.5.10.10.1.4.13
-- 1.3.6.1.4.1.37950.1.1.5.10.10.4.4.13
-- 1.3.6.1.4.1.37950.1.1.5.10.10.4.3.13
-- 1.3.6.1.4.1.37950.1.1.5.10.10.4.3.13
-- 1.3.6.1.4.1.37950.1.1.5.10.10.4.3.13
-- 1.3.6.1.4.1.37950.1.1.5.10.10.4.3.13
-- 1.3.6.1.4.1.37950.1.1.5.10.10.4.3.13
-- 1.3.6.1.4.1.37950.1.1.5.10.10.4.3.13
-- 1.3.6.1.4.1.37950.1.1.5.10.10.4.3.13
		-- 1.3.6.1.4.1.37950.1.1.5.10.10.4.3.13
		portBasev6DstIpv6 OBJECT-TYPE
			SYNTAX OCTET STRING
			MAX-ACCESS read-write
			STATUS current
			DESCRIPTION
				"Description."
			::= { portBasev6AclCfg 13 }

		
--          1.3.6.1.4.1.37950.1.1.5.10.10.1.4.14
-- 1.3.6.1.4.1.37950.1.1.5.10.10.4.4.14
-- 1.3.6.1.4.1.37950.1.1.5.10.10.4.3.14
-- 1.3.6.1.4.1.37950.1.1.5.10.10.4.3.14
-- 1.3.6.1.4.1.37950.1.1.5.10.10.4.3.14
-- 1.3.6.1.4.1.37950.1.1.5.10.10.4.3.14
-- 1.3.6.1.4.1.37950.1.1.5.10.10.4.3.14
-- 1.3.6.1.4.1.37950.1.1.5.10.10.4.3.14
-- 1.3.6.1.4.1.37950.1.1.5.10.10.4.3.14
		-- 1.3.6.1.4.1.37950.1.1.5.10.10.4.3.14
		portBasev6DstPrefixlen OBJECT-TYPE
			SYNTAX Integer32 (-1..128)
			MAX-ACCESS read-write
			STATUS current
			DESCRIPTION
				"Description."
			::= { portBasev6AclCfg 14 }

		
--          1.3.6.1.4.1.37950.1.1.5.10.10.1.4.15
-- 1.3.6.1.4.1.37950.1.1.5.10.10.4.4.15
-- 1.3.6.1.4.1.37950.1.1.5.10.10.4.3.15
-- 1.3.6.1.4.1.37950.1.1.5.10.10.4.3.15
-- 1.3.6.1.4.1.37950.1.1.5.10.10.4.3.15
-- 1.3.6.1.4.1.37950.1.1.5.10.10.4.3.15
-- 1.3.6.1.4.1.37950.1.1.5.10.10.4.3.15
-- 1.3.6.1.4.1.37950.1.1.5.10.10.4.3.15
-- 1.3.6.1.4.1.37950.1.1.5.10.10.4.3.15
		-- 1.3.6.1.4.1.37950.1.1.5.10.10.4.3.15
		portBasev6Protocol OBJECT-TYPE
			SYNTAX INTEGER (-1..255)
			MAX-ACCESS read-write
			STATUS current
			DESCRIPTION
				"Description."
			::= { portBasev6AclCfg 15 }

		
--          1.3.6.1.4.1.37950.1.1.5.10.10.1.4.16
-- 1.3.6.1.4.1.37950.1.1.5.10.10.4.4.16
-- 1.3.6.1.4.1.37950.1.1.5.10.10.4.3.16
-- 1.3.6.1.4.1.37950.1.1.5.10.10.4.3.16
-- 1.3.6.1.4.1.37950.1.1.5.10.10.4.3.16
-- 1.3.6.1.4.1.37950.1.1.5.10.10.4.3.16
-- 1.3.6.1.4.1.37950.1.1.5.10.10.4.3.16
-- 1.3.6.1.4.1.37950.1.1.5.10.10.4.3.16
-- 1.3.6.1.4.1.37950.1.1.5.10.10.4.3.16
		-- 1.3.6.1.4.1.37950.1.1.5.10.10.4.3.16
		portBasev6ProtocolMask OBJECT-TYPE
			SYNTAX INTEGER (0..255)
			MAX-ACCESS read-write
			STATUS current
			DESCRIPTION
				"Description."
			::= { portBasev6AclCfg 16 }

		
--          1.3.6.1.4.1.37950.1.1.5.10.10.1.4.17
-- 1.3.6.1.4.1.37950.1.1.5.10.10.4.4.17
-- 1.3.6.1.4.1.37950.1.1.5.10.10.4.3.17
-- 1.3.6.1.4.1.37950.1.1.5.10.10.4.3.17
-- 1.3.6.1.4.1.37950.1.1.5.10.10.4.3.17
-- 1.3.6.1.4.1.37950.1.1.5.10.10.4.3.17
-- 1.3.6.1.4.1.37950.1.1.5.10.10.4.3.17
-- 1.3.6.1.4.1.37950.1.1.5.10.10.4.3.17
-- 1.3.6.1.4.1.37950.1.1.5.10.10.4.3.17
		-- 1.3.6.1.4.1.37950.1.1.5.10.10.4.3.17
		portBasev6TosDscp OBJECT-TYPE
			SYNTAX INTEGER (-1..255)
			MAX-ACCESS read-write
			STATUS current
			DESCRIPTION
				"Description."
			::= { portBasev6AclCfg 17 }

		
--          1.3.6.1.4.1.37950.1.1.5.10.10.1.4.18
-- 1.3.6.1.4.1.37950.1.1.5.10.10.4.4.18
-- 1.3.6.1.4.1.37950.1.1.5.10.10.4.3.18
-- 1.3.6.1.4.1.37950.1.1.5.10.10.4.3.18
-- 1.3.6.1.4.1.37950.1.1.5.10.10.4.3.18
-- 1.3.6.1.4.1.37950.1.1.5.10.10.4.3.18
-- 1.3.6.1.4.1.37950.1.1.5.10.10.4.3.18
-- 1.3.6.1.4.1.37950.1.1.5.10.10.4.3.18
-- 1.3.6.1.4.1.37950.1.1.5.10.10.4.3.18
		-- 1.3.6.1.4.1.37950.1.1.5.10.10.4.3.18
		portBasev6TosDscpMask OBJECT-TYPE
			SYNTAX INTEGER (0..255)
			MAX-ACCESS read-write
			STATUS current
			DESCRIPTION
				"Description."
			::= { portBasev6AclCfg 18 }

		
--          1.3.6.1.4.1.37950.1.1.5.10.10.1.4.19
-- 1.3.6.1.4.1.37950.1.1.5.10.10.4.4.19
-- 1.3.6.1.4.1.37950.1.1.5.10.10.4.3.19
-- 1.3.6.1.4.1.37950.1.1.5.10.10.4.3.19
-- 1.3.6.1.4.1.37950.1.1.5.10.10.4.3.19
-- 1.3.6.1.4.1.37950.1.1.5.10.10.4.3.19
-- 1.3.6.1.4.1.37950.1.1.5.10.10.4.3.19
-- 1.3.6.1.4.1.37950.1.1.5.10.10.4.3.19
-- 1.3.6.1.4.1.37950.1.1.5.10.10.4.3.19
		-- 1.3.6.1.4.1.37950.1.1.5.10.10.4.3.19
		portBasev6SrcPort OBJECT-TYPE
			SYNTAX INTEGER (-1..65535)
			MAX-ACCESS read-write
			STATUS current
			DESCRIPTION
				"Description."
			::= { portBasev6AclCfg 19 }

		
--          1.3.6.1.4.1.37950.1.1.5.10.10.1.4.20
-- 1.3.6.1.4.1.37950.1.1.5.10.10.4.4.20
-- 1.3.6.1.4.1.37950.1.1.5.10.10.4.3.20
-- 1.3.6.1.4.1.37950.1.1.5.10.10.4.3.20
-- 1.3.6.1.4.1.37950.1.1.5.10.10.4.3.20
-- 1.3.6.1.4.1.37950.1.1.5.10.10.4.3.20
-- 1.3.6.1.4.1.37950.1.1.5.10.10.4.3.20
-- 1.3.6.1.4.1.37950.1.1.5.10.10.4.3.20
-- 1.3.6.1.4.1.37950.1.1.5.10.10.4.3.20
		-- 1.3.6.1.4.1.37950.1.1.5.10.10.4.3.20
		portBasev6SrcPortMask OBJECT-TYPE
			SYNTAX OCTET STRING
			MAX-ACCESS read-write
			STATUS current
			DESCRIPTION
				"Description."
			::= { portBasev6AclCfg 20 }

		
--          1.3.6.1.4.1.37950.1.1.5.10.10.1.4.21
-- 1.3.6.1.4.1.37950.1.1.5.10.10.4.4.21
-- 1.3.6.1.4.1.37950.1.1.5.10.10.4.3.21
-- 1.3.6.1.4.1.37950.1.1.5.10.10.4.3.21
-- 1.3.6.1.4.1.37950.1.1.5.10.10.4.3.21
-- 1.3.6.1.4.1.37950.1.1.5.10.10.4.3.21
-- 1.3.6.1.4.1.37950.1.1.5.10.10.4.3.21
-- 1.3.6.1.4.1.37950.1.1.5.10.10.4.3.21
-- 1.3.6.1.4.1.37950.1.1.5.10.10.4.3.21
		-- 1.3.6.1.4.1.37950.1.1.5.10.10.4.3.21
		portBasev6DstPort OBJECT-TYPE
			SYNTAX INTEGER (-1..65535)
			MAX-ACCESS read-write
			STATUS current
			DESCRIPTION
				"Description."
			::= { portBasev6AclCfg 21 }

		
--          1.3.6.1.4.1.37950.1.1.5.10.10.1.4.22
-- 1.3.6.1.4.1.37950.1.1.5.10.10.4.4.22
-- 1.3.6.1.4.1.37950.1.1.5.10.10.4.3.22
-- 1.3.6.1.4.1.37950.1.1.5.10.10.4.3.22
-- 1.3.6.1.4.1.37950.1.1.5.10.10.4.3.22
-- 1.3.6.1.4.1.37950.1.1.5.10.10.4.3.22
-- 1.3.6.1.4.1.37950.1.1.5.10.10.4.3.22
-- 1.3.6.1.4.1.37950.1.1.5.10.10.4.3.22
-- 1.3.6.1.4.1.37950.1.1.5.10.10.4.3.22
		-- 1.3.6.1.4.1.37950.1.1.5.10.10.4.3.22
		portBasev6DstPortMask OBJECT-TYPE
			SYNTAX OCTET STRING
			MAX-ACCESS read-write
			STATUS current
			DESCRIPTION
				"Description."
			::= { portBasev6AclCfg 22 }

		
--          1.3.6.1.4.1.37950.1.1.5.10.10.1.4.23
-- 1.3.6.1.4.1.37950.1.1.5.10.10.4.4.23
-- 1.3.6.1.4.1.37950.1.1.5.10.10.4.3.23
-- 1.3.6.1.4.1.37950.1.1.5.10.10.4.3.23
-- 1.3.6.1.4.1.37950.1.1.5.10.10.4.3.23
-- 1.3.6.1.4.1.37950.1.1.5.10.10.4.3.23
-- 1.3.6.1.4.1.37950.1.1.5.10.10.4.3.23
-- 1.3.6.1.4.1.37950.1.1.5.10.10.4.3.23
-- 1.3.6.1.4.1.37950.1.1.5.10.10.4.3.23
		-- 1.3.6.1.4.1.37950.1.1.5.10.10.4.3.23
		portBasev6Action OBJECT-TYPE
			SYNTAX INTEGER
				{
				add(1),
				delete(2),
				clear(3)
				}
			MAX-ACCESS read-write
			STATUS current
			DESCRIPTION
				"Description."
			::= { portBasev6AclCfg 23 }

		
--          1.3.6.1.4.1.37950.1.1.5.10.10.2
-- 1.3.6.1.4.1.37950.1.1.5.10.10.5
-- 1.3.6.1.4.1.37950.1.1.5.10.10.5
-- 1.3.6.1.4.1.37950.1.1.5.10.10.5
-- 1.3.6.1.4.1.37950.1.1.5.10.10.5
-- 1.3.6.1.4.1.37950.1.1.5.10.10.5
-- 1.3.6.1.4.1.37950.1.1.5.10.10.5
-- 1.3.6.1.4.1.37950.1.1.5.10.10.5
-- 1.3.6.1.4.1.37950.1.1.5.10.10.5
		-- 1.3.6.1.4.1.37950.1.1.5.10.10.5
		ipv6aclTable OBJECT IDENTIFIER ::= { v1600dAcl 5 }

		
--          1.3.6.1.4.1.37950.1.1.5.10.10.2.1
-- 1.3.6.1.4.1.37950.1.1.5.10.10.5.1
-- 1.3.6.1.4.1.37950.1.1.5.10.10.5.1
-- 1.3.6.1.4.1.37950.1.1.5.10.10.5.1
-- 1.3.6.1.4.1.37950.1.1.5.10.10.5.1
-- 1.3.6.1.4.1.37950.1.1.5.10.10.5.1
-- 1.3.6.1.4.1.37950.1.1.5.10.10.5.1
-- 1.3.6.1.4.1.37950.1.1.5.10.10.5.1
-- 1.3.6.1.4.1.37950.1.1.5.10.10.5.1
		-- 1.3.6.1.4.1.37950.1.1.5.10.10.5.1
		stdIpv6FilterTable OBJECT-TYPE
			SYNTAX SEQUENCE OF StdIpv6FilterEntry
			MAX-ACCESS not-accessible
			STATUS current
			DESCRIPTION
				"Description."
			::= { ipv6aclTable 1 }

		
--          1.3.6.1.4.1.37950.1.1.5.10.10.2.1.1
-- 1.3.6.1.4.1.37950.1.1.5.10.10.5.1.1
-- 1.3.6.1.4.1.37950.1.1.5.10.10.5.1.1
-- 1.3.6.1.4.1.37950.1.1.5.10.10.5.1.1
-- 1.3.6.1.4.1.37950.1.1.5.10.10.5.1.1
-- 1.3.6.1.4.1.37950.1.1.5.10.10.5.1.1
-- 1.3.6.1.4.1.37950.1.1.5.10.10.5.1.1
-- 1.3.6.1.4.1.37950.1.1.5.10.10.5.1.1
-- 1.3.6.1.4.1.37950.1.1.5.10.10.5.1.1
		-- 1.3.6.1.4.1.37950.1.1.5.10.10.5.1.1
		stdIpv6FilterEntry OBJECT-TYPE
			SYNTAX StdIpv6FilterEntry
			MAX-ACCESS not-accessible
			STATUS current
			DESCRIPTION
				"Description."
			INDEX { stdIpv6FltId }
			::= { stdIpv6FilterTable 1 }

		
		StdIpv6FilterEntry ::=
			SEQUENCE { 
				stdIpv6FltId
					INTEGER,
				stdIpv6FltSrcIpv6
					OCTET STRING,
				stdIpv6FltSrcPrefixlen
					Integer32,
				stdIpv6FltMode
					INTEGER
			 }

--          1.3.6.1.4.1.37950.1.1.5.10.10.2.1.1.1
-- 1.3.6.1.4.1.37950.1.1.5.10.10.5.1.1.1
-- 1.3.6.1.4.1.37950.1.1.5.10.10.5.1.1.1
-- 1.3.6.1.4.1.37950.1.1.5.10.10.5.1.1.1
-- 1.3.6.1.4.1.37950.1.1.5.10.10.5.1.1.1
-- 1.3.6.1.4.1.37950.1.1.5.10.10.5.1.1.1
-- 1.3.6.1.4.1.37950.1.1.5.10.10.5.1.1.1
-- 1.3.6.1.4.1.37950.1.1.5.10.10.5.1.1.1
-- 1.3.6.1.4.1.37950.1.1.5.10.10.5.1.1.1
		-- 1.3.6.1.4.1.37950.1.1.5.10.10.5.1.1.1
		stdIpv6FltId OBJECT-TYPE
			SYNTAX INTEGER (0..999)
			MAX-ACCESS read-only
			STATUS current
			DESCRIPTION
				"Description."
			::= { stdIpv6FilterEntry 1 }

		
--          1.3.6.1.4.1.37950.1.1.5.10.10.2.1.1.2
-- 1.3.6.1.4.1.37950.1.1.5.10.10.5.1.1.2
-- 1.3.6.1.4.1.37950.1.1.5.10.10.5.1.1.2
-- 1.3.6.1.4.1.37950.1.1.5.10.10.5.1.1.2
-- 1.3.6.1.4.1.37950.1.1.5.10.10.5.1.1.2
-- 1.3.6.1.4.1.37950.1.1.5.10.10.5.1.1.2
-- 1.3.6.1.4.1.37950.1.1.5.10.10.5.1.1.2
-- 1.3.6.1.4.1.37950.1.1.5.10.10.5.1.1.2
-- 1.3.6.1.4.1.37950.1.1.5.10.10.5.1.1.2
		-- 1.3.6.1.4.1.37950.1.1.5.10.10.5.1.1.2
		stdIpv6FltSrcIpv6 OBJECT-TYPE
			SYNTAX OCTET STRING
			MAX-ACCESS read-only
			STATUS current
			DESCRIPTION
				"Description."
			::= { stdIpv6FilterEntry 2 }

		
--          1.3.6.1.4.1.37950.1.1.5.10.10.2.1.1.3
-- 1.3.6.1.4.1.37950.1.1.5.10.10.5.1.1.3
-- 1.3.6.1.4.1.37950.1.1.5.10.10.5.1.1.3
-- 1.3.6.1.4.1.37950.1.1.5.10.10.5.1.1.3
-- 1.3.6.1.4.1.37950.1.1.5.10.10.5.1.1.3
-- 1.3.6.1.4.1.37950.1.1.5.10.10.5.1.1.3
-- 1.3.6.1.4.1.37950.1.1.5.10.10.5.1.1.3
-- 1.3.6.1.4.1.37950.1.1.5.10.10.5.1.1.3
-- 1.3.6.1.4.1.37950.1.1.5.10.10.5.1.1.3
		-- 1.3.6.1.4.1.37950.1.1.5.10.10.5.1.1.3
		stdIpv6FltSrcPrefixlen OBJECT-TYPE
			SYNTAX Integer32 (-1..128)
			MAX-ACCESS read-only
			STATUS current
			DESCRIPTION
				"Description."
			::= { stdIpv6FilterEntry 3 }

		
--          1.3.6.1.4.1.37950.1.1.5.10.10.2.1.1.4
-- 1.3.6.1.4.1.37950.1.1.5.10.10.5.1.1.4
-- 1.3.6.1.4.1.37950.1.1.5.10.10.5.1.1.4
-- 1.3.6.1.4.1.37950.1.1.5.10.10.5.1.1.4
-- 1.3.6.1.4.1.37950.1.1.5.10.10.5.1.1.4
-- 1.3.6.1.4.1.37950.1.1.5.10.10.5.1.1.4
-- 1.3.6.1.4.1.37950.1.1.5.10.10.5.1.1.4
-- 1.3.6.1.4.1.37950.1.1.5.10.10.5.1.1.4
-- 1.3.6.1.4.1.37950.1.1.5.10.10.5.1.1.4
		-- 1.3.6.1.4.1.37950.1.1.5.10.10.5.1.1.4
		stdIpv6FltMode OBJECT-TYPE
			SYNTAX INTEGER
				{
				permit(1),
				deny(2)
				}
			MAX-ACCESS read-only
			STATUS current
			DESCRIPTION
				"Description."
			::= { stdIpv6FilterEntry 4 }

		
--          1.3.6.1.4.1.37950.1.1.5.10.10.2.2
-- 1.3.6.1.4.1.37950.1.1.5.10.10.5.2
-- 1.3.6.1.4.1.37950.1.1.5.10.10.5.2
-- 1.3.6.1.4.1.37950.1.1.5.10.10.5.2
-- 1.3.6.1.4.1.37950.1.1.5.10.10.5.2
-- 1.3.6.1.4.1.37950.1.1.5.10.10.5.2
-- 1.3.6.1.4.1.37950.1.1.5.10.10.5.2
-- 1.3.6.1.4.1.37950.1.1.5.10.10.5.2
-- 1.3.6.1.4.1.37950.1.1.5.10.10.5.2
		-- 1.3.6.1.4.1.37950.1.1.5.10.10.5.2
		extIpv6FilterTable OBJECT-TYPE
			SYNTAX SEQUENCE OF ExtIpv6FilterEntry
			MAX-ACCESS not-accessible
			STATUS current
			DESCRIPTION
				"Description."
			::= { ipv6aclTable 2 }

		
--          1.3.6.1.4.1.37950.1.1.5.10.10.2.2.1
-- 1.3.6.1.4.1.37950.1.1.5.10.10.5.2.1
-- 1.3.6.1.4.1.37950.1.1.5.10.10.5.2.1
-- 1.3.6.1.4.1.37950.1.1.5.10.10.5.2.1
-- 1.3.6.1.4.1.37950.1.1.5.10.10.5.2.1
-- 1.3.6.1.4.1.37950.1.1.5.10.10.5.2.1
-- 1.3.6.1.4.1.37950.1.1.5.10.10.5.2.1
-- 1.3.6.1.4.1.37950.1.1.5.10.10.5.2.1
-- 1.3.6.1.4.1.37950.1.1.5.10.10.5.2.1
		-- 1.3.6.1.4.1.37950.1.1.5.10.10.5.2.1
		extIpv6FilterEntry OBJECT-TYPE
			SYNTAX ExtIpv6FilterEntry
			MAX-ACCESS not-accessible
			STATUS current
			DESCRIPTION
				"Description."
			INDEX { extIpv6FltId }
			::= { extIpv6FilterTable 1 }

		
		ExtIpv6FilterEntry ::=
			SEQUENCE { 
				extIpv6FltId
					INTEGER,
				extIpv6FltProtocol
					INTEGER,
				extIpv6FltSrcIpv6
					OCTET STRING,
				extIpv6FltSrcPrefixlen
					Integer32,
				extIpv6FltSrcPort
					INTEGER,
				extIpv6FltDstIpv6
					OCTET STRING,
				extIpv6FltDstPrefixlen
					Integer32,
				extIpv6FltDstPort
					INTEGER,
				extIpv6FltDscp
					INTEGER,
				extIpv6FltMode
					INTEGER
			 }

--          1.3.6.1.4.1.37950.1.1.5.10.10.2.2.1.1
-- 1.3.6.1.4.1.37950.1.1.5.10.10.5.2.1.1
-- 1.3.6.1.4.1.37950.1.1.5.10.10.5.2.1.1
-- 1.3.6.1.4.1.37950.1.1.5.10.10.5.2.1.1
-- 1.3.6.1.4.1.37950.1.1.5.10.10.5.2.1.1
-- 1.3.6.1.4.1.37950.1.1.5.10.10.5.2.1.1
-- 1.3.6.1.4.1.37950.1.1.5.10.10.5.2.1.1
-- 1.3.6.1.4.1.37950.1.1.5.10.10.5.2.1.1
-- 1.3.6.1.4.1.37950.1.1.5.10.10.5.2.1.1
		-- 1.3.6.1.4.1.37950.1.1.5.10.10.5.2.1.1
		extIpv6FltId OBJECT-TYPE
			SYNTAX INTEGER (1000..1999)
			MAX-ACCESS read-only
			STATUS current
			DESCRIPTION
				"Description."
			::= { extIpv6FilterEntry 1 }

		
--          1.3.6.1.4.1.37950.1.1.5.10.10.2.2.1.2
-- 1.3.6.1.4.1.37950.1.1.5.10.10.5.2.1.2
-- 1.3.6.1.4.1.37950.1.1.5.10.10.5.2.1.2
-- 1.3.6.1.4.1.37950.1.1.5.10.10.5.2.1.2
-- 1.3.6.1.4.1.37950.1.1.5.10.10.5.2.1.2
-- 1.3.6.1.4.1.37950.1.1.5.10.10.5.2.1.2
-- 1.3.6.1.4.1.37950.1.1.5.10.10.5.2.1.2
-- 1.3.6.1.4.1.37950.1.1.5.10.10.5.2.1.2
-- 1.3.6.1.4.1.37950.1.1.5.10.10.5.2.1.2
		-- 1.3.6.1.4.1.37950.1.1.5.10.10.5.2.1.2
		extIpv6FltProtocol OBJECT-TYPE
			SYNTAX INTEGER (-1..255)
			MAX-ACCESS read-only
			STATUS current
			DESCRIPTION
				"Description."
			::= { extIpv6FilterEntry 2 }

		
--          1.3.6.1.4.1.37950.1.1.5.10.10.2.2.1.3
-- 1.3.6.1.4.1.37950.1.1.5.10.10.5.2.1.3
-- 1.3.6.1.4.1.37950.1.1.5.10.10.5.2.1.3
-- 1.3.6.1.4.1.37950.1.1.5.10.10.5.2.1.3
-- 1.3.6.1.4.1.37950.1.1.5.10.10.5.2.1.3
-- 1.3.6.1.4.1.37950.1.1.5.10.10.5.2.1.3
-- 1.3.6.1.4.1.37950.1.1.5.10.10.5.2.1.3
-- 1.3.6.1.4.1.37950.1.1.5.10.10.5.2.1.3
-- 1.3.6.1.4.1.37950.1.1.5.10.10.5.2.1.3
		-- 1.3.6.1.4.1.37950.1.1.5.10.10.5.2.1.3
		extIpv6FltSrcIpv6 OBJECT-TYPE
			SYNTAX OCTET STRING
			MAX-ACCESS read-only
			STATUS current
			DESCRIPTION
				"Description."
			::= { extIpv6FilterEntry 3 }

		
--          1.3.6.1.4.1.37950.1.1.5.10.10.2.2.1.4
-- 1.3.6.1.4.1.37950.1.1.5.10.10.5.2.1.4
-- 1.3.6.1.4.1.37950.1.1.5.10.10.5.2.1.4
-- 1.3.6.1.4.1.37950.1.1.5.10.10.5.2.1.4
-- 1.3.6.1.4.1.37950.1.1.5.10.10.5.2.1.4
-- 1.3.6.1.4.1.37950.1.1.5.10.10.5.2.1.4
-- 1.3.6.1.4.1.37950.1.1.5.10.10.5.2.1.4
-- 1.3.6.1.4.1.37950.1.1.5.10.10.5.2.1.4
-- 1.3.6.1.4.1.37950.1.1.5.10.10.5.2.1.4
		-- 1.3.6.1.4.1.37950.1.1.5.10.10.5.2.1.4
		extIpv6FltSrcPrefixlen OBJECT-TYPE
			SYNTAX Integer32 (-1..128)
			MAX-ACCESS read-only
			STATUS current
			DESCRIPTION
				"Description."
			::= { extIpv6FilterEntry 4 }

		
--          1.3.6.1.4.1.37950.1.1.5.10.10.2.2.1.5
-- 1.3.6.1.4.1.37950.1.1.5.10.10.5.2.1.5
-- 1.3.6.1.4.1.37950.1.1.5.10.10.5.2.1.5
-- 1.3.6.1.4.1.37950.1.1.5.10.10.5.2.1.5
-- 1.3.6.1.4.1.37950.1.1.5.10.10.5.2.1.5
-- 1.3.6.1.4.1.37950.1.1.5.10.10.5.2.1.5
-- 1.3.6.1.4.1.37950.1.1.5.10.10.5.2.1.5
-- 1.3.6.1.4.1.37950.1.1.5.10.10.5.2.1.5
-- 1.3.6.1.4.1.37950.1.1.5.10.10.5.2.1.5
		-- 1.3.6.1.4.1.37950.1.1.5.10.10.5.2.1.5
		extIpv6FltSrcPort OBJECT-TYPE
			SYNTAX INTEGER (-1..65535)
			MAX-ACCESS read-write
			STATUS current
			DESCRIPTION
				"Description."
			::= { extIpv6FilterEntry 5 }

		
--          1.3.6.1.4.1.37950.1.1.5.10.10.2.2.1.6
-- 1.3.6.1.4.1.37950.1.1.5.10.10.5.2.1.6
-- 1.3.6.1.4.1.37950.1.1.5.10.10.5.2.1.6
-- 1.3.6.1.4.1.37950.1.1.5.10.10.5.2.1.6
-- 1.3.6.1.4.1.37950.1.1.5.10.10.5.2.1.6
-- 1.3.6.1.4.1.37950.1.1.5.10.10.5.2.1.6
-- 1.3.6.1.4.1.37950.1.1.5.10.10.5.2.1.6
-- 1.3.6.1.4.1.37950.1.1.5.10.10.5.2.1.6
-- 1.3.6.1.4.1.37950.1.1.5.10.10.5.2.1.6
		-- 1.3.6.1.4.1.37950.1.1.5.10.10.5.2.1.6
		extIpv6FltDstIpv6 OBJECT-TYPE
			SYNTAX OCTET STRING
			MAX-ACCESS read-only
			STATUS current
			DESCRIPTION
				"Description."
			::= { extIpv6FilterEntry 6 }

		
--          1.3.6.1.4.1.37950.1.1.5.10.10.2.2.1.7
-- 1.3.6.1.4.1.37950.1.1.5.10.10.5.2.1.7
-- 1.3.6.1.4.1.37950.1.1.5.10.10.5.2.1.7
-- 1.3.6.1.4.1.37950.1.1.5.10.10.5.2.1.7
-- 1.3.6.1.4.1.37950.1.1.5.10.10.5.2.1.7
-- 1.3.6.1.4.1.37950.1.1.5.10.10.5.2.1.7
-- 1.3.6.1.4.1.37950.1.1.5.10.10.5.2.1.7
-- 1.3.6.1.4.1.37950.1.1.5.10.10.5.2.1.7
-- 1.3.6.1.4.1.37950.1.1.5.10.10.5.2.1.7
		-- 1.3.6.1.4.1.37950.1.1.5.10.10.5.2.1.7
		extIpv6FltDstPrefixlen OBJECT-TYPE
			SYNTAX Integer32 (-1..128)
			MAX-ACCESS read-only
			STATUS current
			DESCRIPTION
				"Description."
			::= { extIpv6FilterEntry 7 }

		
--          1.3.6.1.4.1.37950.1.1.5.10.10.2.2.1.8
-- 1.3.6.1.4.1.37950.1.1.5.10.10.5.2.1.8
-- 1.3.6.1.4.1.37950.1.1.5.10.10.5.2.1.8
-- 1.3.6.1.4.1.37950.1.1.5.10.10.5.2.1.8
-- 1.3.6.1.4.1.37950.1.1.5.10.10.5.2.1.8
-- 1.3.6.1.4.1.37950.1.1.5.10.10.5.2.1.8
-- 1.3.6.1.4.1.37950.1.1.5.10.10.5.2.1.8
-- 1.3.6.1.4.1.37950.1.1.5.10.10.5.2.1.8
-- 1.3.6.1.4.1.37950.1.1.5.10.10.5.2.1.8
		-- 1.3.6.1.4.1.37950.1.1.5.10.10.5.2.1.8
		extIpv6FltDstPort OBJECT-TYPE
			SYNTAX INTEGER (-1..65535)
			MAX-ACCESS read-only
			STATUS current
			DESCRIPTION
				"Description."
			::= { extIpv6FilterEntry 8 }

		
--          1.3.6.1.4.1.37950.1.1.5.10.10.2.2.1.9
-- 1.3.6.1.4.1.37950.1.1.5.10.10.5.2.1.9
-- 1.3.6.1.4.1.37950.1.1.5.10.10.5.2.1.9
-- 1.3.6.1.4.1.37950.1.1.5.10.10.5.2.1.9
-- 1.3.6.1.4.1.37950.1.1.5.10.10.5.2.1.9
-- 1.3.6.1.4.1.37950.1.1.5.10.10.5.2.1.9
-- 1.3.6.1.4.1.37950.1.1.5.10.10.5.2.1.9
-- 1.3.6.1.4.1.37950.1.1.5.10.10.5.2.1.9
-- 1.3.6.1.4.1.37950.1.1.5.10.10.5.2.1.9
		-- 1.3.6.1.4.1.37950.1.1.5.10.10.5.2.1.9
		extIpv6FltDscp OBJECT-TYPE
			SYNTAX INTEGER (-1..63)
			MAX-ACCESS read-only
			STATUS current
			DESCRIPTION
				"Description."
			::= { extIpv6FilterEntry 9 }

		
--          1.3.6.1.4.1.37950.1.1.5.10.10.2.2.1.10
-- 1.3.6.1.4.1.37950.1.1.5.10.10.5.2.1.10
-- 1.3.6.1.4.1.37950.1.1.5.10.10.5.2.1.10
-- 1.3.6.1.4.1.37950.1.1.5.10.10.5.2.1.10
-- 1.3.6.1.4.1.37950.1.1.5.10.10.5.2.1.10
-- 1.3.6.1.4.1.37950.1.1.5.10.10.5.2.1.10
-- 1.3.6.1.4.1.37950.1.1.5.10.10.5.2.1.10
-- 1.3.6.1.4.1.37950.1.1.5.10.10.5.2.1.10
-- 1.3.6.1.4.1.37950.1.1.5.10.10.5.2.1.10
		-- 1.3.6.1.4.1.37950.1.1.5.10.10.5.2.1.10
		extIpv6FltMode OBJECT-TYPE
			SYNTAX INTEGER
				{
				permit(1),
				deny(2)
				}
			MAX-ACCESS read-only
			STATUS current
			DESCRIPTION
				"Description."
			::= { extIpv6FilterEntry 10 }

		
--          1.3.6.1.4.1.37950.1.1.5.10.10.2.4
-- 1.3.6.1.4.1.37950.1.1.5.10.10.5.4
-- 1.3.6.1.4.1.37950.1.1.5.10.10.5.3
-- 1.3.6.1.4.1.37950.1.1.5.10.10.5.3
-- 1.3.6.1.4.1.37950.1.1.5.10.10.5.3
-- 1.3.6.1.4.1.37950.1.1.5.10.10.5.3
-- 1.3.6.1.4.1.37950.1.1.5.10.10.5.3
-- 1.3.6.1.4.1.37950.1.1.5.10.10.5.3
-- 1.3.6.1.4.1.37950.1.1.5.10.10.5.3
		-- 1.3.6.1.4.1.37950.1.1.5.10.10.5.3
		portBasev6AclTable OBJECT-TYPE
			SYNTAX SEQUENCE OF PortBasev6AclEntry
			MAX-ACCESS not-accessible
			STATUS current
			DESCRIPTION
				"Description."
			::= { ipv6aclTable 3 }

		
--          1.3.6.1.4.1.37950.1.1.5.10.10.2.4.1
-- 1.3.6.1.4.1.37950.1.1.5.10.10.5.4.1
-- 1.3.6.1.4.1.37950.1.1.5.10.10.5.3.1
-- 1.3.6.1.4.1.37950.1.1.5.10.10.5.3.1
-- 1.3.6.1.4.1.37950.1.1.5.10.10.5.3.1
-- 1.3.6.1.4.1.37950.1.1.5.10.10.5.3.1
-- 1.3.6.1.4.1.37950.1.1.5.10.10.5.3.1
-- 1.3.6.1.4.1.37950.1.1.5.10.10.5.3.1
-- 1.3.6.1.4.1.37950.1.1.5.10.10.5.3.1
		-- 1.3.6.1.4.1.37950.1.1.5.10.10.5.3.1
		portBasev6AclEntry OBJECT-TYPE
			SYNTAX PortBasev6AclEntry
			MAX-ACCESS not-accessible
			STATUS current
			DESCRIPTION
				"Description."
			INDEX { portBasev6AclIndex }
			::= { portBasev6AclTable 1 }

		
		PortBasev6AclEntry ::=
			SEQUENCE { 
				portBasev6AclIndex
					Integer32,
				portBasev6AclFltMode
					INTEGER,
				portBasev6AclSrcMac
					OCTET STRING,
				portBasev6AclSrcMacMask
					OCTET STRING,
				portBasev6AclDstMac
					OCTET STRING,
				portBasev6AclDstMacMask
					OCTET STRING,
				portBasev6AclVlan
					INTEGER,
				portBasev6AclVlanMask
					INTEGER,
				portBasev6AclCos
					INTEGER,
				portBasev6AclEthernetType
					OCTET STRING,
				portBasev6AclSrcIpv6
					OCTET STRING,
				portBasev6AclSrcPrefixlen
					Integer32,
				portBasev6AclDstIpv6
					OCTET STRING,
				portBasev6AclDstPrefixlen
					Integer32,
				portBasev6AclProtocol
					INTEGER,
				portBasev6AclProtocolMask
					INTEGER,
				portBasev6AclTosDscp
					INTEGER,
				portBasev6AclTosDscpMask
					INTEGER,
				portBasev6AclSrcPort
					INTEGER,
				portBasev6AclSrcPortMask
					OCTET STRING,
				portBasev6AclDstPort
					INTEGER,
				portBasev6AclDstPortMask
					OCTET STRING
			 }

--          1.3.6.1.4.1.37950.1.1.5.10.10.2.4.1.1
-- 1.3.6.1.4.1.37950.1.1.5.10.10.5.4.1.1
-- 1.3.6.1.4.1.37950.1.1.5.10.10.5.3.1.1
-- 1.3.6.1.4.1.37950.1.1.5.10.10.5.3.1.1
-- 1.3.6.1.4.1.37950.1.1.5.10.10.5.3.1.1
-- 1.3.6.1.4.1.37950.1.1.5.10.10.5.3.1.1
-- 1.3.6.1.4.1.37950.1.1.5.10.10.5.3.1.1
-- 1.3.6.1.4.1.37950.1.1.5.10.10.5.3.1.1
-- 1.3.6.1.4.1.37950.1.1.5.10.10.5.3.1.1
		-- 1.3.6.1.4.1.37950.1.1.5.10.10.5.3.1.1
		portBasev6AclIndex OBJECT-TYPE
			SYNTAX Integer32 (5000..5999)
			MAX-ACCESS read-only
			STATUS current
			DESCRIPTION
				"Description."
			::= { portBasev6AclEntry 1 }

		
--          1.3.6.1.4.1.37950.1.1.5.10.10.2.4.1.2
-- 1.3.6.1.4.1.37950.1.1.5.10.10.5.4.1.2
-- 1.3.6.1.4.1.37950.1.1.5.10.10.5.3.1.2
-- 1.3.6.1.4.1.37950.1.1.5.10.10.5.3.1.2
-- 1.3.6.1.4.1.37950.1.1.5.10.10.5.3.1.2
-- 1.3.6.1.4.1.37950.1.1.5.10.10.5.3.1.2
-- 1.3.6.1.4.1.37950.1.1.5.10.10.5.3.1.2
-- 1.3.6.1.4.1.37950.1.1.5.10.10.5.3.1.2
-- 1.3.6.1.4.1.37950.1.1.5.10.10.5.3.1.2
		-- 1.3.6.1.4.1.37950.1.1.5.10.10.5.3.1.2
		portBasev6AclFltMode OBJECT-TYPE
			SYNTAX INTEGER
				{
				permit(1),
				deny(2)
				}
			MAX-ACCESS read-only
			STATUS current
			DESCRIPTION
				"Description."
			::= { portBasev6AclEntry 2 }

		
--          1.3.6.1.4.1.37950.1.1.5.10.10.2.4.1.3
-- 1.3.6.1.4.1.37950.1.1.5.10.10.5.4.1.3
-- 1.3.6.1.4.1.37950.1.1.5.10.10.5.3.1.3
-- 1.3.6.1.4.1.37950.1.1.5.10.10.5.3.1.3
-- 1.3.6.1.4.1.37950.1.1.5.10.10.5.3.1.3
-- 1.3.6.1.4.1.37950.1.1.5.10.10.5.3.1.3
-- 1.3.6.1.4.1.37950.1.1.5.10.10.5.3.1.3
-- 1.3.6.1.4.1.37950.1.1.5.10.10.5.3.1.3
-- 1.3.6.1.4.1.37950.1.1.5.10.10.5.3.1.3
		-- 1.3.6.1.4.1.37950.1.1.5.10.10.5.3.1.3
		portBasev6AclSrcMac OBJECT-TYPE
			SYNTAX OCTET STRING
			MAX-ACCESS read-only
			STATUS current
			DESCRIPTION
				"Description."
			::= { portBasev6AclEntry 3 }

		
--          1.3.6.1.4.1.37950.1.1.5.10.10.2.4.1.4
-- 1.3.6.1.4.1.37950.1.1.5.10.10.5.4.1.4
-- 1.3.6.1.4.1.37950.1.1.5.10.10.5.3.1.4
-- 1.3.6.1.4.1.37950.1.1.5.10.10.5.3.1.4
-- 1.3.6.1.4.1.37950.1.1.5.10.10.5.3.1.4
-- 1.3.6.1.4.1.37950.1.1.5.10.10.5.3.1.4
-- 1.3.6.1.4.1.37950.1.1.5.10.10.5.3.1.4
-- 1.3.6.1.4.1.37950.1.1.5.10.10.5.3.1.4
-- 1.3.6.1.4.1.37950.1.1.5.10.10.5.3.1.4
		-- 1.3.6.1.4.1.37950.1.1.5.10.10.5.3.1.4
		portBasev6AclSrcMacMask OBJECT-TYPE
			SYNTAX OCTET STRING
			MAX-ACCESS read-only
			STATUS current
			DESCRIPTION
				"Description."
			::= { portBasev6AclEntry 4 }

		
--          1.3.6.1.4.1.37950.1.1.5.10.10.2.4.1.5
-- 1.3.6.1.4.1.37950.1.1.5.10.10.5.4.1.5
-- 1.3.6.1.4.1.37950.1.1.5.10.10.5.3.1.5
-- 1.3.6.1.4.1.37950.1.1.5.10.10.5.3.1.5
-- 1.3.6.1.4.1.37950.1.1.5.10.10.5.3.1.5
-- 1.3.6.1.4.1.37950.1.1.5.10.10.5.3.1.5
-- 1.3.6.1.4.1.37950.1.1.5.10.10.5.3.1.5
-- 1.3.6.1.4.1.37950.1.1.5.10.10.5.3.1.5
-- 1.3.6.1.4.1.37950.1.1.5.10.10.5.3.1.5
		-- 1.3.6.1.4.1.37950.1.1.5.10.10.5.3.1.5
		portBasev6AclDstMac OBJECT-TYPE
			SYNTAX OCTET STRING
			MAX-ACCESS read-only
			STATUS current
			DESCRIPTION
				"Description."
			::= { portBasev6AclEntry 5 }

		
--          1.3.6.1.4.1.37950.1.1.5.10.10.2.4.1.6
-- 1.3.6.1.4.1.37950.1.1.5.10.10.5.4.1.6
-- 1.3.6.1.4.1.37950.1.1.5.10.10.5.3.1.6
-- 1.3.6.1.4.1.37950.1.1.5.10.10.5.3.1.6
-- 1.3.6.1.4.1.37950.1.1.5.10.10.5.3.1.6
-- 1.3.6.1.4.1.37950.1.1.5.10.10.5.3.1.6
-- 1.3.6.1.4.1.37950.1.1.5.10.10.5.3.1.6
-- 1.3.6.1.4.1.37950.1.1.5.10.10.5.3.1.6
-- 1.3.6.1.4.1.37950.1.1.5.10.10.5.3.1.6
		-- 1.3.6.1.4.1.37950.1.1.5.10.10.5.3.1.6
		portBasev6AclDstMacMask OBJECT-TYPE
			SYNTAX OCTET STRING
			MAX-ACCESS read-only
			STATUS current
			DESCRIPTION
				"Description."
			::= { portBasev6AclEntry 6 }

		
--          1.3.6.1.4.1.37950.1.1.5.10.10.2.4.1.7
-- 1.3.6.1.4.1.37950.1.1.5.10.10.5.4.1.7
-- 1.3.6.1.4.1.37950.1.1.5.10.10.5.3.1.7
-- 1.3.6.1.4.1.37950.1.1.5.10.10.5.3.1.7
-- 1.3.6.1.4.1.37950.1.1.5.10.10.5.3.1.7
-- 1.3.6.1.4.1.37950.1.1.5.10.10.5.3.1.7
-- 1.3.6.1.4.1.37950.1.1.5.10.10.5.3.1.7
-- 1.3.6.1.4.1.37950.1.1.5.10.10.5.3.1.7
-- 1.3.6.1.4.1.37950.1.1.5.10.10.5.3.1.7
		-- 1.3.6.1.4.1.37950.1.1.5.10.10.5.3.1.7
		portBasev6AclVlan OBJECT-TYPE
			SYNTAX INTEGER (0..4094)
			MAX-ACCESS read-only
			STATUS current
			DESCRIPTION
				"Description."
			::= { portBasev6AclEntry 7 }

		
--          1.3.6.1.4.1.37950.1.1.5.10.10.2.4.1.8
-- 1.3.6.1.4.1.37950.1.1.5.10.10.5.4.1.8
-- 1.3.6.1.4.1.37950.1.1.5.10.10.5.3.1.8
-- 1.3.6.1.4.1.37950.1.1.5.10.10.5.3.1.8
-- 1.3.6.1.4.1.37950.1.1.5.10.10.5.3.1.8
-- 1.3.6.1.4.1.37950.1.1.5.10.10.5.3.1.8
-- 1.3.6.1.4.1.37950.1.1.5.10.10.5.3.1.8
-- 1.3.6.1.4.1.37950.1.1.5.10.10.5.3.1.8
-- 1.3.6.1.4.1.37950.1.1.5.10.10.5.3.1.8
		-- 1.3.6.1.4.1.37950.1.1.5.10.10.5.3.1.8
		portBasev6AclVlanMask OBJECT-TYPE
			SYNTAX INTEGER (0..4095)
			MAX-ACCESS read-only
			STATUS current
			DESCRIPTION
				"Description."
			::= { portBasev6AclEntry 8 }

		
--          1.3.6.1.4.1.37950.1.1.5.10.10.2.4.1.9
-- 1.3.6.1.4.1.37950.1.1.5.10.10.5.4.1.9
-- 1.3.6.1.4.1.37950.1.1.5.10.10.5.3.1.9
-- 1.3.6.1.4.1.37950.1.1.5.10.10.5.3.1.9
-- 1.3.6.1.4.1.37950.1.1.5.10.10.5.3.1.9
-- 1.3.6.1.4.1.37950.1.1.5.10.10.5.3.1.9
-- 1.3.6.1.4.1.37950.1.1.5.10.10.5.3.1.9
-- 1.3.6.1.4.1.37950.1.1.5.10.10.5.3.1.9
-- 1.3.6.1.4.1.37950.1.1.5.10.10.5.3.1.9
		-- 1.3.6.1.4.1.37950.1.1.5.10.10.5.3.1.9
		portBasev6AclCos OBJECT-TYPE
			SYNTAX INTEGER (-1..7)
			MAX-ACCESS read-only
			STATUS current
			DESCRIPTION
				"Description."
			::= { portBasev6AclEntry 9 }

		
--          1.3.6.1.4.1.37950.1.1.5.10.10.2.4.1.10
-- 1.3.6.1.4.1.37950.1.1.5.10.10.5.4.1.10
-- 1.3.6.1.4.1.37950.1.1.5.10.10.5.3.1.10
-- 1.3.6.1.4.1.37950.1.1.5.10.10.5.3.1.10
-- 1.3.6.1.4.1.37950.1.1.5.10.10.5.3.1.10
-- 1.3.6.1.4.1.37950.1.1.5.10.10.5.3.1.10
-- 1.3.6.1.4.1.37950.1.1.5.10.10.5.3.1.10
-- 1.3.6.1.4.1.37950.1.1.5.10.10.5.3.1.10
-- 1.3.6.1.4.1.37950.1.1.5.10.10.5.3.1.10
		-- 1.3.6.1.4.1.37950.1.1.5.10.10.5.3.1.10
		portBasev6AclEthernetType OBJECT-TYPE
			SYNTAX OCTET STRING
			MAX-ACCESS read-only
			STATUS current
			DESCRIPTION
				"Description."
			::= { portBasev6AclEntry 10 }

		
--          1.3.6.1.4.1.37950.1.1.5.10.10.2.4.1.11
-- 1.3.6.1.4.1.37950.1.1.5.10.10.5.4.1.11
-- 1.3.6.1.4.1.37950.1.1.5.10.10.5.3.1.11
-- 1.3.6.1.4.1.37950.1.1.5.10.10.5.3.1.11
-- 1.3.6.1.4.1.37950.1.1.5.10.10.5.3.1.11
-- 1.3.6.1.4.1.37950.1.1.5.10.10.5.3.1.11
-- 1.3.6.1.4.1.37950.1.1.5.10.10.5.3.1.11
-- 1.3.6.1.4.1.37950.1.1.5.10.10.5.3.1.11
-- 1.3.6.1.4.1.37950.1.1.5.10.10.5.3.1.11
		-- 1.3.6.1.4.1.37950.1.1.5.10.10.5.3.1.11
		portBasev6AclSrcIpv6 OBJECT-TYPE
			SYNTAX OCTET STRING
			MAX-ACCESS read-only
			STATUS current
			DESCRIPTION
				"Description."
			::= { portBasev6AclEntry 11 }

		
--          1.3.6.1.4.1.37950.1.1.5.10.10.2.4.1.12
-- 1.3.6.1.4.1.37950.1.1.5.10.10.5.4.1.12
-- 1.3.6.1.4.1.37950.1.1.5.10.10.5.3.1.12
-- 1.3.6.1.4.1.37950.1.1.5.10.10.5.3.1.12
-- 1.3.6.1.4.1.37950.1.1.5.10.10.5.3.1.12
-- 1.3.6.1.4.1.37950.1.1.5.10.10.5.3.1.12
-- 1.3.6.1.4.1.37950.1.1.5.10.10.5.3.1.12
-- 1.3.6.1.4.1.37950.1.1.5.10.10.5.3.1.12
-- 1.3.6.1.4.1.37950.1.1.5.10.10.5.3.1.12
		-- 1.3.6.1.4.1.37950.1.1.5.10.10.5.3.1.12
		portBasev6AclSrcPrefixlen OBJECT-TYPE
			SYNTAX Integer32 (-1..128)
			MAX-ACCESS read-only
			STATUS current
			DESCRIPTION
				"Description."
			::= { portBasev6AclEntry 12 }

		
--          1.3.6.1.4.1.37950.1.1.5.10.10.2.4.1.13
-- 1.3.6.1.4.1.37950.1.1.5.10.10.5.4.1.13
-- 1.3.6.1.4.1.37950.1.1.5.10.10.5.3.1.13
-- 1.3.6.1.4.1.37950.1.1.5.10.10.5.3.1.13
-- 1.3.6.1.4.1.37950.1.1.5.10.10.5.3.1.13
-- 1.3.6.1.4.1.37950.1.1.5.10.10.5.3.1.13
-- 1.3.6.1.4.1.37950.1.1.5.10.10.5.3.1.13
-- 1.3.6.1.4.1.37950.1.1.5.10.10.5.3.1.13
-- 1.3.6.1.4.1.37950.1.1.5.10.10.5.3.1.13
		-- 1.3.6.1.4.1.37950.1.1.5.10.10.5.3.1.13
		portBasev6AclDstIpv6 OBJECT-TYPE
			SYNTAX OCTET STRING
			MAX-ACCESS read-only
			STATUS current
			DESCRIPTION
				"Description."
			::= { portBasev6AclEntry 13 }

		
--          1.3.6.1.4.1.37950.1.1.5.10.10.2.4.1.14
-- 1.3.6.1.4.1.37950.1.1.5.10.10.5.4.1.14
-- 1.3.6.1.4.1.37950.1.1.5.10.10.5.3.1.14
-- 1.3.6.1.4.1.37950.1.1.5.10.10.5.3.1.14
-- 1.3.6.1.4.1.37950.1.1.5.10.10.5.3.1.14
-- 1.3.6.1.4.1.37950.1.1.5.10.10.5.3.1.14
-- 1.3.6.1.4.1.37950.1.1.5.10.10.5.3.1.14
-- 1.3.6.1.4.1.37950.1.1.5.10.10.5.3.1.14
-- 1.3.6.1.4.1.37950.1.1.5.10.10.5.3.1.14
		-- 1.3.6.1.4.1.37950.1.1.5.10.10.5.3.1.14
		portBasev6AclDstPrefixlen OBJECT-TYPE
			SYNTAX Integer32 (-1..128)
			MAX-ACCESS read-only
			STATUS current
			DESCRIPTION
				"Description."
			::= { portBasev6AclEntry 14 }

		
--          1.3.6.1.4.1.37950.1.1.5.10.10.2.4.1.15
-- 1.3.6.1.4.1.37950.1.1.5.10.10.5.4.1.15
-- 1.3.6.1.4.1.37950.1.1.5.10.10.5.3.1.15
-- 1.3.6.1.4.1.37950.1.1.5.10.10.5.3.1.15
-- 1.3.6.1.4.1.37950.1.1.5.10.10.5.3.1.15
-- 1.3.6.1.4.1.37950.1.1.5.10.10.5.3.1.15
-- 1.3.6.1.4.1.37950.1.1.5.10.10.5.3.1.15
-- 1.3.6.1.4.1.37950.1.1.5.10.10.5.3.1.15
-- 1.3.6.1.4.1.37950.1.1.5.10.10.5.3.1.15
		-- 1.3.6.1.4.1.37950.1.1.5.10.10.5.3.1.15
		portBasev6AclProtocol OBJECT-TYPE
			SYNTAX INTEGER (-1..255)
			MAX-ACCESS read-only
			STATUS current
			DESCRIPTION
				"Description."
			::= { portBasev6AclEntry 15 }

		
--          1.3.6.1.4.1.37950.1.1.5.10.10.2.4.1.16
-- 1.3.6.1.4.1.37950.1.1.5.10.10.5.4.1.16
-- 1.3.6.1.4.1.37950.1.1.5.10.10.5.3.1.16
-- 1.3.6.1.4.1.37950.1.1.5.10.10.5.3.1.16
-- 1.3.6.1.4.1.37950.1.1.5.10.10.5.3.1.16
-- 1.3.6.1.4.1.37950.1.1.5.10.10.5.3.1.16
-- 1.3.6.1.4.1.37950.1.1.5.10.10.5.3.1.16
-- 1.3.6.1.4.1.37950.1.1.5.10.10.5.3.1.16
-- 1.3.6.1.4.1.37950.1.1.5.10.10.5.3.1.16
		-- 1.3.6.1.4.1.37950.1.1.5.10.10.5.3.1.16
		portBasev6AclProtocolMask OBJECT-TYPE
			SYNTAX INTEGER (0..255)
			MAX-ACCESS read-only
			STATUS current
			DESCRIPTION
				"Description."
			::= { portBasev6AclEntry 16 }

		
--          1.3.6.1.4.1.37950.1.1.5.10.10.2.4.1.17
-- 1.3.6.1.4.1.37950.1.1.5.10.10.5.4.1.17
-- 1.3.6.1.4.1.37950.1.1.5.10.10.5.3.1.17
-- 1.3.6.1.4.1.37950.1.1.5.10.10.5.3.1.17
-- 1.3.6.1.4.1.37950.1.1.5.10.10.5.3.1.17
-- 1.3.6.1.4.1.37950.1.1.5.10.10.5.3.1.17
-- 1.3.6.1.4.1.37950.1.1.5.10.10.5.3.1.17
-- 1.3.6.1.4.1.37950.1.1.5.10.10.5.3.1.17
-- 1.3.6.1.4.1.37950.1.1.5.10.10.5.3.1.17
		-- 1.3.6.1.4.1.37950.1.1.5.10.10.5.3.1.17
		portBasev6AclTosDscp OBJECT-TYPE
			SYNTAX INTEGER (-1..255)
			MAX-ACCESS read-only
			STATUS current
			DESCRIPTION
				"Description."
			::= { portBasev6AclEntry 17 }

		
--          1.3.6.1.4.1.37950.1.1.5.10.10.2.4.1.18
-- 1.3.6.1.4.1.37950.1.1.5.10.10.5.4.1.18
-- 1.3.6.1.4.1.37950.1.1.5.10.10.5.3.1.18
-- 1.3.6.1.4.1.37950.1.1.5.10.10.5.3.1.18
-- 1.3.6.1.4.1.37950.1.1.5.10.10.5.3.1.18
-- 1.3.6.1.4.1.37950.1.1.5.10.10.5.3.1.18
-- 1.3.6.1.4.1.37950.1.1.5.10.10.5.3.1.18
-- 1.3.6.1.4.1.37950.1.1.5.10.10.5.3.1.18
-- 1.3.6.1.4.1.37950.1.1.5.10.10.5.3.1.18
		-- 1.3.6.1.4.1.37950.1.1.5.10.10.5.3.1.18
		portBasev6AclTosDscpMask OBJECT-TYPE
			SYNTAX INTEGER (0..255)
			MAX-ACCESS read-only
			STATUS current
			DESCRIPTION
				"Description."
			::= { portBasev6AclEntry 18 }

		
--          1.3.6.1.4.1.37950.1.1.5.10.10.2.4.1.19
-- 1.3.6.1.4.1.37950.1.1.5.10.10.5.4.1.19
-- 1.3.6.1.4.1.37950.1.1.5.10.10.5.3.1.19
-- 1.3.6.1.4.1.37950.1.1.5.10.10.5.3.1.19
-- 1.3.6.1.4.1.37950.1.1.5.10.10.5.3.1.19
-- 1.3.6.1.4.1.37950.1.1.5.10.10.5.3.1.19
-- 1.3.6.1.4.1.37950.1.1.5.10.10.5.3.1.19
-- 1.3.6.1.4.1.37950.1.1.5.10.10.5.3.1.19
-- 1.3.6.1.4.1.37950.1.1.5.10.10.5.3.1.19
		-- 1.3.6.1.4.1.37950.1.1.5.10.10.5.3.1.19
		portBasev6AclSrcPort OBJECT-TYPE
			SYNTAX INTEGER (-1..65535)
			MAX-ACCESS read-only
			STATUS current
			DESCRIPTION
				"Description."
			::= { portBasev6AclEntry 19 }

		
--          1.3.6.1.4.1.37950.1.1.5.10.10.2.4.1.20
-- 1.3.6.1.4.1.37950.1.1.5.10.10.5.4.1.20
-- 1.3.6.1.4.1.37950.1.1.5.10.10.5.3.1.20
-- 1.3.6.1.4.1.37950.1.1.5.10.10.5.3.1.20
-- 1.3.6.1.4.1.37950.1.1.5.10.10.5.3.1.20
-- 1.3.6.1.4.1.37950.1.1.5.10.10.5.3.1.20
-- 1.3.6.1.4.1.37950.1.1.5.10.10.5.3.1.20
-- 1.3.6.1.4.1.37950.1.1.5.10.10.5.3.1.20
-- 1.3.6.1.4.1.37950.1.1.5.10.10.5.3.1.20
		-- 1.3.6.1.4.1.37950.1.1.5.10.10.5.3.1.20
		portBasev6AclSrcPortMask OBJECT-TYPE
			SYNTAX OCTET STRING
			MAX-ACCESS read-only
			STATUS current
			DESCRIPTION
				"Description."
			::= { portBasev6AclEntry 20 }

		
--          1.3.6.1.4.1.37950.1.1.5.10.10.2.4.1.21
-- 1.3.6.1.4.1.37950.1.1.5.10.10.5.4.1.21
-- 1.3.6.1.4.1.37950.1.1.5.10.10.5.3.1.21
-- 1.3.6.1.4.1.37950.1.1.5.10.10.5.3.1.21
-- 1.3.6.1.4.1.37950.1.1.5.10.10.5.3.1.21
-- 1.3.6.1.4.1.37950.1.1.5.10.10.5.3.1.21
-- 1.3.6.1.4.1.37950.1.1.5.10.10.5.3.1.21
-- 1.3.6.1.4.1.37950.1.1.5.10.10.5.3.1.21
-- 1.3.6.1.4.1.37950.1.1.5.10.10.5.3.1.21
		-- 1.3.6.1.4.1.37950.1.1.5.10.10.5.3.1.21
		portBasev6AclDstPort OBJECT-TYPE
			SYNTAX INTEGER (-1..65535)
			MAX-ACCESS read-only
			STATUS current
			DESCRIPTION
				"Description."
			::= { portBasev6AclEntry 21 }

		
--          1.3.6.1.4.1.37950.1.1.5.10.10.2.4.1.22
-- 1.3.6.1.4.1.37950.1.1.5.10.10.5.4.1.22
-- 1.3.6.1.4.1.37950.1.1.5.10.10.5.3.1.22
-- 1.3.6.1.4.1.37950.1.1.5.10.10.5.3.1.22
-- 1.3.6.1.4.1.37950.1.1.5.10.10.5.3.1.22
-- 1.3.6.1.4.1.37950.1.1.5.10.10.5.3.1.22
-- 1.3.6.1.4.1.37950.1.1.5.10.10.5.3.1.22
-- 1.3.6.1.4.1.37950.1.1.5.10.10.5.3.1.22
-- 1.3.6.1.4.1.37950.1.1.5.10.10.5.3.1.22
		-- 1.3.6.1.4.1.37950.1.1.5.10.10.5.3.1.22
		portBasev6AclDstPortMask OBJECT-TYPE
			SYNTAX OCTET STRING
			MAX-ACCESS read-only
			STATUS current
			DESCRIPTION
				"Description."
			::= { portBasev6AclEntry 22 }

		
--          1.3.6.1.4.1.37950.1.1.5.10.10.3
-- 1.3.6.1.4.1.37950.1.1.5.10.10.6
-- 1.3.6.1.4.1.37950.1.1.5.10.10.6
-- 1.3.6.1.4.1.37950.1.1.5.10.10.6
-- 1.3.6.1.4.1.37950.1.1.5.10.10.6
-- 1.3.6.1.4.1.37950.1.1.5.10.10.6
-- 1.3.6.1.4.1.37950.1.1.5.10.10.6
-- 1.3.6.1.4.1.37950.1.1.5.10.10.6
-- 1.3.6.1.4.1.37950.1.1.5.10.10.6
		-- 1.3.6.1.4.1.37950.1.1.5.10.10.6
		ipv6aclEffectTable OBJECT-TYPE
			SYNTAX SEQUENCE OF Ipv6aclEffectEntry
			MAX-ACCESS not-accessible
			STATUS current
			DESCRIPTION
				"Description."
			::= { v1600dAcl 6 }

		
--          1.3.6.1.4.1.37950.1.1.5.10.10.3.1
-- 1.3.6.1.4.1.37950.1.1.5.10.10.6.1
-- 1.3.6.1.4.1.37950.1.1.5.10.10.6.1
-- 1.3.6.1.4.1.37950.1.1.5.10.10.6.1
-- 1.3.6.1.4.1.37950.1.1.5.10.10.6.1
-- 1.3.6.1.4.1.37950.1.1.5.10.10.6.1
-- 1.3.6.1.4.1.37950.1.1.5.10.10.6.1
-- 1.3.6.1.4.1.37950.1.1.5.10.10.6.1
-- 1.3.6.1.4.1.37950.1.1.5.10.10.6.1
		-- 1.3.6.1.4.1.37950.1.1.5.10.10.6.1
		ipv6aclEffectEntry OBJECT-TYPE
			SYNTAX Ipv6aclEffectEntry
			MAX-ACCESS not-accessible
			STATUS current
			DESCRIPTION
				"Description."
			INDEX { ipv6aclIndex }
			::= { ipv6aclEffectTable 1 }

		
		Ipv6aclEffectEntry ::=
			SEQUENCE { 
				ipv6aclIndex
					Integer32,
				ipv6aclPortList
					OCTET STRING,
				ipv6aclPortListEgress
					OCTET STRING
			 }

--          1.3.6.1.4.1.37950.1.1.5.10.10.3.1.1
-- 1.3.6.1.4.1.37950.1.1.5.10.10.6.1.1
-- 1.3.6.1.4.1.37950.1.1.5.10.10.6.1.1
-- 1.3.6.1.4.1.37950.1.1.5.10.10.6.1.1
-- 1.3.6.1.4.1.37950.1.1.5.10.10.6.1.1
-- 1.3.6.1.4.1.37950.1.1.5.10.10.6.1.1
-- 1.3.6.1.4.1.37950.1.1.5.10.10.6.1.1
-- 1.3.6.1.4.1.37950.1.1.5.10.10.6.1.1
-- 1.3.6.1.4.1.37950.1.1.5.10.10.6.1.1
		-- 1.3.6.1.4.1.37950.1.1.5.10.10.6.1.1
		ipv6aclIndex OBJECT-TYPE
			SYNTAX Integer32
			MAX-ACCESS read-only
			STATUS current
			DESCRIPTION
				"Description."
			::= { ipv6aclEffectEntry 1 }

		
--          1.3.6.1.4.1.37950.1.1.5.10.10.3.1.2
-- 1.3.6.1.4.1.37950.1.1.5.10.10.6.1.2
-- 1.3.6.1.4.1.37950.1.1.5.10.10.6.1.2
-- 1.3.6.1.4.1.37950.1.1.5.10.10.6.1.2
-- 1.3.6.1.4.1.37950.1.1.5.10.10.6.1.2
-- 1.3.6.1.4.1.37950.1.1.5.10.10.6.1.2
-- 1.3.6.1.4.1.37950.1.1.5.10.10.6.1.2
-- 1.3.6.1.4.1.37950.1.1.5.10.10.6.1.2
-- 1.3.6.1.4.1.37950.1.1.5.10.10.6.1.2
		-- 1.3.6.1.4.1.37950.1.1.5.10.10.6.1.2
		ipv6aclPortList OBJECT-TYPE
			SYNTAX OCTET STRING
			MAX-ACCESS read-write
			STATUS current
			DESCRIPTION
				"Description."
			::= { ipv6aclEffectEntry 2 }

		
--         1.3.6.1.4.1.37950.1.1.5.10.10.6.1.3
-- 1.3.6.1.4.1.37950.1.1.5.10.10.6.1.3
-- 1.3.6.1.4.1.37950.1.1.5.10.10.6.1.3
-- 1.3.6.1.4.1.37950.1.1.5.10.10.6.1.3
-- 1.3.6.1.4.1.37950.1.1.5.10.10.6.1.3
-- 1.3.6.1.4.1.37950.1.1.5.10.10.6.1.3
-- 1.3.6.1.4.1.37950.1.1.5.10.10.6.1.3
-- 1.3.6.1.4.1.37950.1.1.5.10.10.6.1.3
		-- 1.3.6.1.4.1.37950.1.1.5.10.10.6.1.3
		ipv6aclPortListEgress OBJECT-TYPE
			SYNTAX OCTET STRING
			MAX-ACCESS read-write
			STATUS current
			DESCRIPTION
				"Description."
			::= { ipv6aclEffectEntry 3 }

		
--         1.3.6.1.4.1.37950.1.1.5.10.10.7
-- 1.3.6.1.4.1.37950.1.1.5.10.10.7
-- 1.3.6.1.4.1.37950.1.1.5.10.10.7
-- 1.3.6.1.4.1.37950.1.1.5.10.10.7
-- 1.3.6.1.4.1.37950.1.1.5.10.10.7
-- 1.3.6.1.4.1.37950.1.1.5.10.10.7
-- 1.3.6.1.4.1.37950.1.1.5.10.10.7
-- 1.3.6.1.4.1.37950.1.1.5.10.10.7
		-- 1.3.6.1.4.1.37950.1.1.5.10.10.7
		ipSourceGuard OBJECT IDENTIFIER ::= { v1600dAcl 7 }

		
--         1.3.6.1.4.1.37950.1.1.5.10.10.7.1
-- 1.3.6.1.4.1.37950.1.1.5.10.10.7.1
-- 1.3.6.1.4.1.37950.1.1.5.10.10.7.1
-- 1.3.6.1.4.1.37950.1.1.5.10.10.7.1
-- 1.3.6.1.4.1.37950.1.1.5.10.10.7.1
-- 1.3.6.1.4.1.37950.1.1.5.10.10.7.1
-- 1.3.6.1.4.1.37950.1.1.5.10.10.7.1
-- 1.3.6.1.4.1.37950.1.1.5.10.10.7.1
		-- 1.3.6.1.4.1.37950.1.1.5.10.10.7.1
		sourceGuardPortindex OBJECT-TYPE
			SYNTAX Integer32
			MAX-ACCESS read-write
			STATUS current
			DESCRIPTION
				"Description."
			::= { ipSourceGuard 1 }

		
--         1.3.6.1.4.1.37950.1.1.5.10.10.7.2
-- 1.3.6.1.4.1.37950.1.1.5.10.10.7.2
-- 1.3.6.1.4.1.37950.1.1.5.10.10.7.2
-- 1.3.6.1.4.1.37950.1.1.5.10.10.7.2
-- 1.3.6.1.4.1.37950.1.1.5.10.10.7.2
-- 1.3.6.1.4.1.37950.1.1.5.10.10.7.2
-- 1.3.6.1.4.1.37950.1.1.5.10.10.7.2
-- 1.3.6.1.4.1.37950.1.1.5.10.10.7.2
		-- 1.3.6.1.4.1.37950.1.1.5.10.10.7.2
		ipSourceGuardAction OBJECT-TYPE
			SYNTAX INTEGER
				{
				ip-addr(1),
				ip-mac-addr(2),
				mac-addr(3),
				disable(4)
				}
			MAX-ACCESS read-write
			STATUS current
			DESCRIPTION
				"Description."
			::= { ipSourceGuard 2 }

		
--         1.3.6.1.4.1.37950.1.1.5.10.10.7.3
-- 1.3.6.1.4.1.37950.1.1.5.10.10.7.3
-- 1.3.6.1.4.1.37950.1.1.5.10.10.7.3
-- 1.3.6.1.4.1.37950.1.1.5.10.10.7.3
-- 1.3.6.1.4.1.37950.1.1.5.10.10.7.3
-- 1.3.6.1.4.1.37950.1.1.5.10.10.7.3
-- 1.3.6.1.4.1.37950.1.1.5.10.10.7.3
-- 1.3.6.1.4.1.37950.1.1.5.10.10.7.3
		-- 1.3.6.1.4.1.37950.1.1.5.10.10.7.3
		ipSourceGuardVlan OBJECT-TYPE
			SYNTAX Integer32 (1..4094)
			MAX-ACCESS read-write
			STATUS deprecated
			DESCRIPTION
				"Description."
			::= { ipSourceGuard 3 }

		
--         1.3.6.1.4.1.37950.1.1.5.10.10.8
-- 1.3.6.1.4.1.37950.1.1.5.10.10.8
-- 1.3.6.1.4.1.37950.1.1.5.10.10.8
-- 1.3.6.1.4.1.37950.1.1.5.10.10.8
-- 1.3.6.1.4.1.37950.1.1.5.10.10.8
-- 1.3.6.1.4.1.37950.1.1.5.10.10.8
-- 1.3.6.1.4.1.37950.1.1.5.10.10.8
-- 1.3.6.1.4.1.37950.1.1.5.10.10.8
		-- 1.3.6.1.4.1.37950.1.1.5.10.10.8
		ipSourceGuardTable OBJECT-TYPE
			SYNTAX SEQUENCE OF IpSourceGuardEntry
			MAX-ACCESS not-accessible
			STATUS current
			DESCRIPTION
				"Description."
			::= { v1600dAcl 8 }

		
--         1.3.6.1.4.1.37950.1.1.5.10.10.8.1
-- 1.3.6.1.4.1.37950.1.1.5.10.10.8.1
-- 1.3.6.1.4.1.37950.1.1.5.10.10.8.1
-- 1.3.6.1.4.1.37950.1.1.5.10.10.8.1
-- 1.3.6.1.4.1.37950.1.1.5.10.10.8.1
-- 1.3.6.1.4.1.37950.1.1.5.10.10.8.1
-- 1.3.6.1.4.1.37950.1.1.5.10.10.8.1
-- 1.3.6.1.4.1.37950.1.1.5.10.10.8.1
		-- 1.3.6.1.4.1.37950.1.1.5.10.10.8.1
		ipSourceGuardEntry OBJECT-TYPE
			SYNTAX IpSourceGuardEntry
			MAX-ACCESS not-accessible
			STATUS current
			DESCRIPTION
				"Description."
			INDEX { ipSourceGuardindex }
			::= { ipSourceGuardTable 1 }

		
		IpSourceGuardEntry ::=
			SEQUENCE { 
				ipSourceGuardindex
					Integer32,
				ipSourceGuardInterface
					OCTET STRING,
				ipSourceGuardFilterType
					INTEGER,
				ipSourceGuardFilterMode
					INTEGER,
				ipSourceGuardIPAddr
					OCTET STRING,
				ipSourceGuardMacAddr
					OCTET STRING,
				ipSourceGuardVlanId
					OCTET STRING
			 }

--         1.3.6.1.4.1.37950.1.1.5.10.10.8.1.1
-- 1.3.6.1.4.1.37950.1.1.5.10.10.8.1.1
-- 1.3.6.1.4.1.37950.1.1.5.10.10.8.1.1
-- 1.3.6.1.4.1.37950.1.1.5.10.10.8.1.1
-- 1.3.6.1.4.1.37950.1.1.5.10.10.8.1.1
-- 1.3.6.1.4.1.37950.1.1.5.10.10.8.1.1
-- 1.3.6.1.4.1.37950.1.1.5.10.10.8.1.1
-- 1.3.6.1.4.1.37950.1.1.5.10.10.8.1.1
		-- 1.3.6.1.4.1.37950.1.1.5.10.10.8.1.1
		ipSourceGuardindex OBJECT-TYPE
			SYNTAX Integer32
			MAX-ACCESS not-accessible
			STATUS current
			DESCRIPTION
				"Description."
			::= { ipSourceGuardEntry 1 }

		
--         1.3.6.1.4.1.37950.1.1.5.10.10.8.1.2
-- 1.3.6.1.4.1.37950.1.1.5.10.10.8.1.2
-- 1.3.6.1.4.1.37950.1.1.5.10.10.8.1.2
-- 1.3.6.1.4.1.37950.1.1.5.10.10.8.1.2
-- 1.3.6.1.4.1.37950.1.1.5.10.10.8.1.2
-- 1.3.6.1.4.1.37950.1.1.5.10.10.8.1.2
-- 1.3.6.1.4.1.37950.1.1.5.10.10.8.1.2
-- 1.3.6.1.4.1.37950.1.1.5.10.10.8.1.2
		-- 1.3.6.1.4.1.37950.1.1.5.10.10.8.1.2
		ipSourceGuardInterface OBJECT-TYPE
			SYNTAX OCTET STRING
			MAX-ACCESS read-only
			STATUS current
			DESCRIPTION
				"Description."
			::= { ipSourceGuardEntry 2 }

		
--         1.3.6.1.4.1.37950.1.1.5.10.10.8.1.3
-- 1.3.6.1.4.1.37950.1.1.5.10.10.8.1.3
-- 1.3.6.1.4.1.37950.1.1.5.10.10.8.1.3
-- 1.3.6.1.4.1.37950.1.1.5.10.10.8.1.3
-- 1.3.6.1.4.1.37950.1.1.5.10.10.8.1.3
-- 1.3.6.1.4.1.37950.1.1.5.10.10.8.1.3
-- 1.3.6.1.4.1.37950.1.1.5.10.10.8.1.3
-- 1.3.6.1.4.1.37950.1.1.5.10.10.8.1.3
		-- 1.3.6.1.4.1.37950.1.1.5.10.10.8.1.3
		ipSourceGuardFilterType OBJECT-TYPE
			SYNTAX INTEGER
				{
				ip(1),
				ip-mac(2),
				mac(3)
				}
			MAX-ACCESS read-only
			STATUS current
			DESCRIPTION
				"Description."
			::= { ipSourceGuardEntry 3 }

		
--         1.3.6.1.4.1.37950.1.1.5.10.10.8.1.4
-- 1.3.6.1.4.1.37950.1.1.5.10.10.8.1.4
-- 1.3.6.1.4.1.37950.1.1.5.10.10.8.1.4
-- 1.3.6.1.4.1.37950.1.1.5.10.10.8.1.4
-- 1.3.6.1.4.1.37950.1.1.5.10.10.8.1.4
-- 1.3.6.1.4.1.37950.1.1.5.10.10.8.1.4
-- 1.3.6.1.4.1.37950.1.1.5.10.10.8.1.4
-- 1.3.6.1.4.1.37950.1.1.5.10.10.8.1.4
		-- 1.3.6.1.4.1.37950.1.1.5.10.10.8.1.4
		ipSourceGuardFilterMode OBJECT-TYPE
			SYNTAX INTEGER { active(1) }
			MAX-ACCESS read-only
			STATUS current
			DESCRIPTION
				"Description."
			::= { ipSourceGuardEntry 4 }

		
--         1.3.6.1.4.1.37950.1.1.5.10.10.8.1.5
-- 1.3.6.1.4.1.37950.1.1.5.10.10.8.1.5
-- 1.3.6.1.4.1.37950.1.1.5.10.10.8.1.5
-- 1.3.6.1.4.1.37950.1.1.5.10.10.8.1.5
-- 1.3.6.1.4.1.37950.1.1.5.10.10.8.1.5
-- 1.3.6.1.4.1.37950.1.1.5.10.10.8.1.5
-- 1.3.6.1.4.1.37950.1.1.5.10.10.8.1.5
-- 1.3.6.1.4.1.37950.1.1.5.10.10.8.1.5
		-- 1.3.6.1.4.1.37950.1.1.5.10.10.8.1.5
		ipSourceGuardIPAddr OBJECT-TYPE
			SYNTAX OCTET STRING
			MAX-ACCESS read-only
			STATUS current
			DESCRIPTION
				"Description."
			::= { ipSourceGuardEntry 5 }

		
--         1.3.6.1.4.1.37950.1.1.5.10.10.8.1.6
-- 1.3.6.1.4.1.37950.1.1.5.10.10.8.1.6
-- 1.3.6.1.4.1.37950.1.1.5.10.10.8.1.6
-- 1.3.6.1.4.1.37950.1.1.5.10.10.8.1.6
-- 1.3.6.1.4.1.37950.1.1.5.10.10.8.1.6
-- 1.3.6.1.4.1.37950.1.1.5.10.10.8.1.6
-- 1.3.6.1.4.1.37950.1.1.5.10.10.8.1.6
-- 1.3.6.1.4.1.37950.1.1.5.10.10.8.1.6
		-- 1.3.6.1.4.1.37950.1.1.5.10.10.8.1.6
		ipSourceGuardMacAddr OBJECT-TYPE
			SYNTAX OCTET STRING
			MAX-ACCESS read-only
			STATUS current
			DESCRIPTION
				"Description."
			::= { ipSourceGuardEntry 6 }

		
--         1.3.6.1.4.1.37950.1.1.5.10.10.8.1.7
-- 1.3.6.1.4.1.37950.1.1.5.10.10.8.1.7
-- 1.3.6.1.4.1.37950.1.1.5.10.10.8.1.7
-- 1.3.6.1.4.1.37950.1.1.5.10.10.8.1.7
-- 1.3.6.1.4.1.37950.1.1.5.10.10.8.1.7
-- 1.3.6.1.4.1.37950.1.1.5.10.10.8.1.7
-- 1.3.6.1.4.1.37950.1.1.5.10.10.8.1.7
-- 1.3.6.1.4.1.37950.1.1.5.10.10.8.1.7
		-- 1.3.6.1.4.1.37950.1.1.5.10.10.8.1.7
		ipSourceGuardVlanId OBJECT-TYPE
			SYNTAX OCTET STRING
			MAX-ACCESS read-only
			STATUS current
			DESCRIPTION
				"Description."
			::= { ipSourceGuardEntry 7 }

		
--         1.3.6.1.4.1.37950.1.1.5.10.10.9
-- 1.3.6.1.4.1.37950.1.1.5.10.10.9
-- 1.3.6.1.4.1.37950.1.1.5.10.10.9
-- 1.3.6.1.4.1.37950.1.1.5.10.10.9
-- 1.3.6.1.4.1.37950.1.1.5.10.10.9
-- 1.3.6.1.4.1.37950.1.1.5.10.10.9
-- 1.3.6.1.4.1.37950.1.1.5.10.10.9
-- 1.3.6.1.4.1.37950.1.1.5.10.10.9
		-- 1.3.6.1.4.1.37950.1.1.5.10.10.9
		ipSourceBind OBJECT IDENTIFIER ::= { v1600dAcl 9 }

		
--         1.3.6.1.4.1.37950.1.1.5.10.10.9.1
-- 1.3.6.1.4.1.37950.1.1.5.10.10.9.1
-- 1.3.6.1.4.1.37950.1.1.5.10.10.9.1
-- 1.3.6.1.4.1.37950.1.1.5.10.10.9.1
-- 1.3.6.1.4.1.37950.1.1.5.10.10.9.1
-- 1.3.6.1.4.1.37950.1.1.5.10.10.9.1
-- 1.3.6.1.4.1.37950.1.1.5.10.10.9.1
-- 1.3.6.1.4.1.37950.1.1.5.10.10.9.1
		-- 1.3.6.1.4.1.37950.1.1.5.10.10.9.1
		bindIPAddr OBJECT-TYPE
			SYNTAX OCTET STRING
			MAX-ACCESS read-write
			STATUS current
			DESCRIPTION
				"Description."
			::= { ipSourceBind 1 }

		
--         1.3.6.1.4.1.37950.1.1.5.10.10.9.2
-- 1.3.6.1.4.1.37950.1.1.5.10.10.9.2
-- 1.3.6.1.4.1.37950.1.1.5.10.10.9.2
-- 1.3.6.1.4.1.37950.1.1.5.10.10.9.2
-- 1.3.6.1.4.1.37950.1.1.5.10.10.9.2
-- 1.3.6.1.4.1.37950.1.1.5.10.10.9.2
-- 1.3.6.1.4.1.37950.1.1.5.10.10.9.2
-- 1.3.6.1.4.1.37950.1.1.5.10.10.9.2
		-- 1.3.6.1.4.1.37950.1.1.5.10.10.9.2
		bindIPMask OBJECT-TYPE
			SYNTAX OCTET STRING
			MAX-ACCESS read-write
			STATUS current
			DESCRIPTION
				"Description."
			::= { ipSourceBind 2 }

		
--         1.3.6.1.4.1.37950.1.1.5.10.10.9.3
-- 1.3.6.1.4.1.37950.1.1.5.10.10.9.3
-- 1.3.6.1.4.1.37950.1.1.5.10.10.9.3
-- 1.3.6.1.4.1.37950.1.1.5.10.10.9.3
-- 1.3.6.1.4.1.37950.1.1.5.10.10.9.3
-- 1.3.6.1.4.1.37950.1.1.5.10.10.9.3
-- 1.3.6.1.4.1.37950.1.1.5.10.10.9.3
-- 1.3.6.1.4.1.37950.1.1.5.10.10.9.3
		-- 1.3.6.1.4.1.37950.1.1.5.10.10.9.3
		bindMacAddr OBJECT-TYPE
			SYNTAX OCTET STRING
			MAX-ACCESS read-write
			STATUS current
			DESCRIPTION
				"Description."
			DEFVAL { "" }
			::= { ipSourceBind 3 }

		
--         1.3.6.1.4.1.37950.1.1.5.10.10.9.4
-- 1.3.6.1.4.1.37950.1.1.5.10.10.9.4
-- 1.3.6.1.4.1.37950.1.1.5.10.10.9.4
-- 1.3.6.1.4.1.37950.1.1.5.10.10.9.4
-- 1.3.6.1.4.1.37950.1.1.5.10.10.9.4
-- 1.3.6.1.4.1.37950.1.1.5.10.10.9.4
-- 1.3.6.1.4.1.37950.1.1.5.10.10.9.4
-- 1.3.6.1.4.1.37950.1.1.5.10.10.9.4
		-- 1.3.6.1.4.1.37950.1.1.5.10.10.9.4
		bindVlanid OBJECT-TYPE
			SYNTAX INTEGER (1..4094)
			MAX-ACCESS read-write
			STATUS current
			DESCRIPTION
				"Description."
			DEFVAL { 0 }
			::= { ipSourceBind 4 }

		
--         1.3.6.1.4.1.37950.1.1.5.10.10.9.5
-- 1.3.6.1.4.1.37950.1.1.5.10.10.9.5
-- 1.3.6.1.4.1.37950.1.1.5.10.10.9.5
-- 1.3.6.1.4.1.37950.1.1.5.10.10.9.5
-- 1.3.6.1.4.1.37950.1.1.5.10.10.9.5
-- 1.3.6.1.4.1.37950.1.1.5.10.10.9.5
-- 1.3.6.1.4.1.37950.1.1.5.10.10.9.5
-- 1.3.6.1.4.1.37950.1.1.5.10.10.9.5
		-- 1.3.6.1.4.1.37950.1.1.5.10.10.9.5
		bindInterfacePortindex OBJECT-TYPE
			SYNTAX Integer32
			MAX-ACCESS read-write
			STATUS current
			DESCRIPTION
				"Description."
			::= { ipSourceBind 5 }

		
--         1.3.6.1.4.1.37950.1.1.5.10.10.9.6
-- 1.3.6.1.4.1.37950.1.1.5.10.10.9.6
-- 1.3.6.1.4.1.37950.1.1.5.10.10.9.6
-- 1.3.6.1.4.1.37950.1.1.5.10.10.9.6
-- 1.3.6.1.4.1.37950.1.1.5.10.10.9.6
-- 1.3.6.1.4.1.37950.1.1.5.10.10.9.6
-- 1.3.6.1.4.1.37950.1.1.5.10.10.9.6
-- 1.3.6.1.4.1.37950.1.1.5.10.10.9.6
		-- 1.3.6.1.4.1.37950.1.1.5.10.10.9.6
		bindAction OBJECT-TYPE
			SYNTAX INTEGER
				{
				add(1),
				del(2)
				}
			MAX-ACCESS read-write
			STATUS current
			DESCRIPTION
				"Description."
			::= { ipSourceBind 6 }

		
--         1.3.6.1.4.1.37950.1.1.5.10.10.10
-- 1.3.6.1.4.1.37950.1.1.5.10.10.10
-- 1.3.6.1.4.1.37950.1.1.5.10.10.10
-- 1.3.6.1.4.1.37950.1.1.5.10.10.10
-- 1.3.6.1.4.1.37950.1.1.5.10.10.10
-- 1.3.6.1.4.1.37950.1.1.5.10.10.10
-- 1.3.6.1.4.1.37950.1.1.5.10.10.10
-- 1.3.6.1.4.1.37950.1.1.5.10.10.10
		-- 1.3.6.1.4.1.37950.1.1.5.10.10.10
		ipSourceBindTable OBJECT-TYPE
			SYNTAX SEQUENCE OF IpSourceBindEntry
			MAX-ACCESS not-accessible
			STATUS current
			DESCRIPTION
				"Description."
			::= { v1600dAcl 10 }

		
--         1.3.6.1.4.1.37950.1.1.5.10.10.10.1
-- 1.3.6.1.4.1.37950.1.1.5.10.10.10.1
-- 1.3.6.1.4.1.37950.1.1.5.10.10.10.1
-- 1.3.6.1.4.1.37950.1.1.5.10.10.10.1
-- 1.3.6.1.4.1.37950.1.1.5.10.10.10.1
-- 1.3.6.1.4.1.37950.1.1.5.10.10.10.1
-- 1.3.6.1.4.1.37950.1.1.5.10.10.10.1
-- 1.3.6.1.4.1.37950.1.1.5.10.10.10.1
		-- 1.3.6.1.4.1.37950.1.1.5.10.10.10.1
		ipSourceBindEntry OBJECT-TYPE
			SYNTAX IpSourceBindEntry
			MAX-ACCESS not-accessible
			STATUS current
			DESCRIPTION
				"Description."
			INDEX { ipSourceBindindex }
			::= { ipSourceBindTable 1 }

		
		IpSourceBindEntry ::=
			SEQUENCE { 
				ipSourceBindindex
					Integer32,
				ipSourceBindMacAddress
					OCTET STRING,
				ipSourceBindIPAddress
					OCTET STRING,
				ipSourceBindtype
					INTEGER,
				ipSourceBindVlanId
					OCTET STRING,
				ipSourceBindInterface
					OCTET STRING
			 }

--         1.3.6.1.4.1.37950.1.1.5.10.10.10.1.1
-- 1.3.6.1.4.1.37950.1.1.5.10.10.10.1.1
-- 1.3.6.1.4.1.37950.1.1.5.10.10.10.1.1
-- 1.3.6.1.4.1.37950.1.1.5.10.10.10.1.1
-- 1.3.6.1.4.1.37950.1.1.5.10.10.10.1.1
-- 1.3.6.1.4.1.37950.1.1.5.10.10.10.1.1
-- 1.3.6.1.4.1.37950.1.1.5.10.10.10.1.1
-- 1.3.6.1.4.1.37950.1.1.5.10.10.10.1.1
		-- 1.3.6.1.4.1.37950.1.1.5.10.10.10.1.1
		ipSourceBindindex OBJECT-TYPE
			SYNTAX Integer32
			MAX-ACCESS not-accessible
			STATUS current
			DESCRIPTION
				"Description."
			::= { ipSourceBindEntry 1 }

		
--         1.3.6.1.4.1.37950.1.1.5.10.10.10.1.2
-- 1.3.6.1.4.1.37950.1.1.5.10.10.10.1.2
-- 1.3.6.1.4.1.37950.1.1.5.10.10.10.1.2
-- 1.3.6.1.4.1.37950.1.1.5.10.10.10.1.2
-- 1.3.6.1.4.1.37950.1.1.5.10.10.10.1.2
-- 1.3.6.1.4.1.37950.1.1.5.10.10.10.1.2
-- 1.3.6.1.4.1.37950.1.1.5.10.10.10.1.2
-- 1.3.6.1.4.1.37950.1.1.5.10.10.10.1.2
		-- 1.3.6.1.4.1.37950.1.1.5.10.10.10.1.2
		ipSourceBindMacAddress OBJECT-TYPE
			SYNTAX OCTET STRING
			MAX-ACCESS read-only
			STATUS current
			DESCRIPTION
				"Description."
			::= { ipSourceBindEntry 2 }

		
--         1.3.6.1.4.1.37950.1.1.5.10.10.10.1.3
-- 1.3.6.1.4.1.37950.1.1.5.10.10.10.1.3
-- 1.3.6.1.4.1.37950.1.1.5.10.10.10.1.3
-- 1.3.6.1.4.1.37950.1.1.5.10.10.10.1.3
-- 1.3.6.1.4.1.37950.1.1.5.10.10.10.1.3
-- 1.3.6.1.4.1.37950.1.1.5.10.10.10.1.3
-- 1.3.6.1.4.1.37950.1.1.5.10.10.10.1.3
-- 1.3.6.1.4.1.37950.1.1.5.10.10.10.1.3
		-- 1.3.6.1.4.1.37950.1.1.5.10.10.10.1.3
		ipSourceBindIPAddress OBJECT-TYPE
			SYNTAX OCTET STRING
			MAX-ACCESS read-only
			STATUS current
			DESCRIPTION
				"Description."
			::= { ipSourceBindEntry 3 }

		
--         1.3.6.1.4.1.37950.1.1.5.10.10.10.1.4
-- 1.3.6.1.4.1.37950.1.1.5.10.10.10.1.4
-- 1.3.6.1.4.1.37950.1.1.5.10.10.10.1.4
-- 1.3.6.1.4.1.37950.1.1.5.10.10.10.1.4
-- 1.3.6.1.4.1.37950.1.1.5.10.10.10.1.4
-- 1.3.6.1.4.1.37950.1.1.5.10.10.10.1.4
-- 1.3.6.1.4.1.37950.1.1.5.10.10.10.1.4
-- 1.3.6.1.4.1.37950.1.1.5.10.10.10.1.4
		-- 1.3.6.1.4.1.37950.1.1.5.10.10.10.1.4
		ipSourceBindtype OBJECT-TYPE
			SYNTAX INTEGER
				{
				static(1),
				dynamic(2)
				}
			MAX-ACCESS read-only
			STATUS current
			DESCRIPTION
				"Description."
			::= { ipSourceBindEntry 4 }

		
--         1.3.6.1.4.1.37950.1.1.5.10.10.10.1.5
-- 1.3.6.1.4.1.37950.1.1.5.10.10.10.1.5
-- 1.3.6.1.4.1.37950.1.1.5.10.10.10.1.5
-- 1.3.6.1.4.1.37950.1.1.5.10.10.10.1.5
-- 1.3.6.1.4.1.37950.1.1.5.10.10.10.1.5
-- 1.3.6.1.4.1.37950.1.1.5.10.10.10.1.5
-- 1.3.6.1.4.1.37950.1.1.5.10.10.10.1.5
-- 1.3.6.1.4.1.37950.1.1.5.10.10.10.1.5
		-- 1.3.6.1.4.1.37950.1.1.5.10.10.10.1.5
		ipSourceBindVlanId OBJECT-TYPE
			SYNTAX OCTET STRING
			MAX-ACCESS read-only
			STATUS current
			DESCRIPTION
				"Description."
			::= { ipSourceBindEntry 5 }

		
--         1.3.6.1.4.1.37950.1.1.5.10.10.10.1.6
-- 1.3.6.1.4.1.37950.1.1.5.10.10.10.1.6
-- 1.3.6.1.4.1.37950.1.1.5.10.10.10.1.6
-- 1.3.6.1.4.1.37950.1.1.5.10.10.10.1.6
-- 1.3.6.1.4.1.37950.1.1.5.10.10.10.1.6
-- 1.3.6.1.4.1.37950.1.1.5.10.10.10.1.6
-- 1.3.6.1.4.1.37950.1.1.5.10.10.10.1.6
-- 1.3.6.1.4.1.37950.1.1.5.10.10.10.1.6
		-- 1.3.6.1.4.1.37950.1.1.5.10.10.10.1.6
		ipSourceBindInterface OBJECT-TYPE
			SYNTAX OCTET STRING
			MAX-ACCESS read-only
			STATUS current
			DESCRIPTION
				"Description."
			::= { ipSourceBindEntry 6 }

		
--          1.3.6.1.4.1.37950.1.1.5.10.11
-- 1.3.6.1.4.1.37950.1.1.5.10.11
-- 1.3.6.1.4.1.37950.1.1.5.10.11
-- 1.3.6.1.4.1.37950.1.1.5.10.11
-- 1.3.6.1.4.1.37950.1.1.5.10.11
-- 1.3.6.1.4.1.37950.1.1.5.10.11
-- 1.3.6.1.4.1.37950.1.1.5.10.11
-- 1.3.6.1.4.1.37950.1.1.5.10.11
-- 1.3.6.1.4.1.37950.1.1.5.10.11
		-- 1.3.6.1.4.1.37950.1.1.5.10.11
		v1600dStaticRoute OBJECT IDENTIFIER ::= { v1600dSwitch 11 }

		
--          1.3.6.1.4.1.37950.1.1.5.10.11.1
-- 1.3.6.1.4.1.37950.1.1.5.10.11.1
-- 1.3.6.1.4.1.37950.1.1.5.10.11.1
-- 1.3.6.1.4.1.37950.1.1.5.10.11.1
-- 1.3.6.1.4.1.37950.1.1.5.10.11.1
-- 1.3.6.1.4.1.37950.1.1.5.10.11.1
-- 1.3.6.1.4.1.37950.1.1.5.10.11.1
-- 1.3.6.1.4.1.37950.1.1.5.10.11.1
-- 1.3.6.1.4.1.37950.1.1.5.10.11.1
		-- 1.3.6.1.4.1.37950.1.1.5.10.11.1
		staticRouteCfg OBJECT IDENTIFIER ::= { v1600dStaticRoute 1 }

		
--          1.3.6.1.4.1.37950.1.1.5.10.11.1.1
-- 1.3.6.1.4.1.37950.1.1.5.10.11.1.1
-- 1.3.6.1.4.1.37950.1.1.5.10.11.1.1
-- 1.3.6.1.4.1.37950.1.1.5.10.11.1.1
-- 1.3.6.1.4.1.37950.1.1.5.10.11.1.1
-- 1.3.6.1.4.1.37950.1.1.5.10.11.1.1
-- 1.3.6.1.4.1.37950.1.1.5.10.11.1.1
-- 1.3.6.1.4.1.37950.1.1.5.10.11.1.1
-- 1.3.6.1.4.1.37950.1.1.5.10.11.1.1
		-- 1.3.6.1.4.1.37950.1.1.5.10.11.1.1
		staticRouteIp OBJECT-TYPE
			SYNTAX IpAddress
			MAX-ACCESS read-write
			STATUS current
			DESCRIPTION
				"Description."
			::= { staticRouteCfg 1 }

		
--          1.3.6.1.4.1.37950.1.1.5.10.11.1.2
-- 1.3.6.1.4.1.37950.1.1.5.10.11.1.2
-- 1.3.6.1.4.1.37950.1.1.5.10.11.1.2
-- 1.3.6.1.4.1.37950.1.1.5.10.11.1.2
-- 1.3.6.1.4.1.37950.1.1.5.10.11.1.2
-- 1.3.6.1.4.1.37950.1.1.5.10.11.1.2
-- 1.3.6.1.4.1.37950.1.1.5.10.11.1.2
-- 1.3.6.1.4.1.37950.1.1.5.10.11.1.2
-- 1.3.6.1.4.1.37950.1.1.5.10.11.1.2
		-- 1.3.6.1.4.1.37950.1.1.5.10.11.1.2
		staticRouteIpMask OBJECT-TYPE
			SYNTAX IpAddress
			MAX-ACCESS read-write
			STATUS current
			DESCRIPTION
				"Description."
			::= { staticRouteCfg 2 }

		
--          1.3.6.1.4.1.37950.1.1.5.10.11.1.3
-- 1.3.6.1.4.1.37950.1.1.5.10.11.1.3
-- 1.3.6.1.4.1.37950.1.1.5.10.11.1.3
-- 1.3.6.1.4.1.37950.1.1.5.10.11.1.3
-- 1.3.6.1.4.1.37950.1.1.5.10.11.1.3
-- 1.3.6.1.4.1.37950.1.1.5.10.11.1.3
-- 1.3.6.1.4.1.37950.1.1.5.10.11.1.3
-- 1.3.6.1.4.1.37950.1.1.5.10.11.1.3
-- 1.3.6.1.4.1.37950.1.1.5.10.11.1.3
		-- 1.3.6.1.4.1.37950.1.1.5.10.11.1.3
		staticRouteIpGw OBJECT-TYPE
			SYNTAX IpAddress
			MAX-ACCESS read-write
			STATUS current
			DESCRIPTION
				"Description."
			::= { staticRouteCfg 3 }

		
--          1.3.6.1.4.1.37950.1.1.5.10.11.1.4
-- 1.3.6.1.4.1.37950.1.1.5.10.11.1.4
-- 1.3.6.1.4.1.37950.1.1.5.10.11.1.4
-- 1.3.6.1.4.1.37950.1.1.5.10.11.1.4
-- 1.3.6.1.4.1.37950.1.1.5.10.11.1.4
-- 1.3.6.1.4.1.37950.1.1.5.10.11.1.4
-- 1.3.6.1.4.1.37950.1.1.5.10.11.1.4
-- 1.3.6.1.4.1.37950.1.1.5.10.11.1.4
-- 1.3.6.1.4.1.37950.1.1.5.10.11.1.4
		-- 1.3.6.1.4.1.37950.1.1.5.10.11.1.4
		staticRouteAction OBJECT-TYPE
			SYNTAX INTEGER
				{
				add(1),
				delete(2)
				}
			MAX-ACCESS read-write
			STATUS current
			DESCRIPTION
				"Description."
			::= { staticRouteCfg 4 }

		
--          1.3.6.1.4.1.37950.1.1.5.10.11.2
-- 1.3.6.1.4.1.37950.1.1.5.10.11.2
-- 1.3.6.1.4.1.37950.1.1.5.10.11.2
-- 1.3.6.1.4.1.37950.1.1.5.10.11.2
-- 1.3.6.1.4.1.37950.1.1.5.10.11.2
-- 1.3.6.1.4.1.37950.1.1.5.10.11.2
-- 1.3.6.1.4.1.37950.1.1.5.10.11.2
-- 1.3.6.1.4.1.37950.1.1.5.10.11.2
-- 1.3.6.1.4.1.37950.1.1.5.10.11.2
		-- 1.3.6.1.4.1.37950.1.1.5.10.11.2
		staticRouteTable OBJECT-TYPE
			SYNTAX SEQUENCE OF StaticRouteEntry
			MAX-ACCESS not-accessible
			STATUS current
			DESCRIPTION
				"Description."
			::= { v1600dStaticRoute 2 }

		
--          1.3.6.1.4.1.37950.1.1.5.10.11.2.1
-- 1.3.6.1.4.1.37950.1.1.5.10.11.2.1
-- 1.3.6.1.4.1.37950.1.1.5.10.11.2.1
-- 1.3.6.1.4.1.37950.1.1.5.10.11.2.1
-- 1.3.6.1.4.1.37950.1.1.5.10.11.2.1
-- 1.3.6.1.4.1.37950.1.1.5.10.11.2.1
-- 1.3.6.1.4.1.37950.1.1.5.10.11.2.1
-- 1.3.6.1.4.1.37950.1.1.5.10.11.2.1
-- 1.3.6.1.4.1.37950.1.1.5.10.11.2.1
		-- 1.3.6.1.4.1.37950.1.1.5.10.11.2.1
		staticRouteEntry OBJECT-TYPE
			SYNTAX StaticRouteEntry
			MAX-ACCESS not-accessible
			STATUS current
			DESCRIPTION
				"Description."
			INDEX { staticRouteItem }
			::= { staticRouteTable 1 }

		
		StaticRouteEntry ::=
			SEQUENCE { 
				staticRouteItem
					INTEGER,
				staticRouteIpAddr
					IpAddress,
				staticRouteMask
					IpAddress,
				staticRouteGw
					IpAddress
			 }

--          1.3.6.1.4.1.37950.1.1.5.10.11.2.1.1
-- 1.3.6.1.4.1.37950.1.1.5.10.11.2.1.1
-- 1.3.6.1.4.1.37950.1.1.5.10.11.2.1.1
-- 1.3.6.1.4.1.37950.1.1.5.10.11.2.1.1
-- 1.3.6.1.4.1.37950.1.1.5.10.11.2.1.1
-- 1.3.6.1.4.1.37950.1.1.5.10.11.2.1.1
-- 1.3.6.1.4.1.37950.1.1.5.10.11.2.1.1
-- 1.3.6.1.4.1.37950.1.1.5.10.11.2.1.1
-- 1.3.6.1.4.1.37950.1.1.5.10.11.2.1.1
		-- 1.3.6.1.4.1.37950.1.1.5.10.11.2.1.1
		staticRouteItem OBJECT-TYPE
			SYNTAX INTEGER (1..512)
			MAX-ACCESS read-write
			STATUS current
			DESCRIPTION
				"Description."
			::= { staticRouteEntry 1 }

		
--          1.3.6.1.4.1.37950.1.1.5.10.11.2.1.2
-- 1.3.6.1.4.1.37950.1.1.5.10.11.2.1.2
-- 1.3.6.1.4.1.37950.1.1.5.10.11.2.1.2
-- 1.3.6.1.4.1.37950.1.1.5.10.11.2.1.2
-- 1.3.6.1.4.1.37950.1.1.5.10.11.2.1.2
-- 1.3.6.1.4.1.37950.1.1.5.10.11.2.1.2
-- 1.3.6.1.4.1.37950.1.1.5.10.11.2.1.2
-- 1.3.6.1.4.1.37950.1.1.5.10.11.2.1.2
-- 1.3.6.1.4.1.37950.1.1.5.10.11.2.1.2
		-- 1.3.6.1.4.1.37950.1.1.5.10.11.2.1.2
		staticRouteIpAddr OBJECT-TYPE
			SYNTAX IpAddress
			MAX-ACCESS read-write
			STATUS current
			DESCRIPTION
				"Description."
			::= { staticRouteEntry 2 }

		
--          1.3.6.1.4.1.37950.1.1.5.10.11.2.1.3
-- 1.3.6.1.4.1.37950.1.1.5.10.11.2.1.3
-- 1.3.6.1.4.1.37950.1.1.5.10.11.2.1.3
-- 1.3.6.1.4.1.37950.1.1.5.10.11.2.1.3
-- 1.3.6.1.4.1.37950.1.1.5.10.11.2.1.3
-- 1.3.6.1.4.1.37950.1.1.5.10.11.2.1.3
-- 1.3.6.1.4.1.37950.1.1.5.10.11.2.1.3
-- 1.3.6.1.4.1.37950.1.1.5.10.11.2.1.3
-- 1.3.6.1.4.1.37950.1.1.5.10.11.2.1.3
		-- 1.3.6.1.4.1.37950.1.1.5.10.11.2.1.3
		staticRouteMask OBJECT-TYPE
			SYNTAX IpAddress
			MAX-ACCESS read-write
			STATUS current
			DESCRIPTION
				"Description."
			::= { staticRouteEntry 3 }

		
--          1.3.6.1.4.1.37950.1.1.5.10.11.2.1.4
-- 1.3.6.1.4.1.37950.1.1.5.10.11.2.1.4
-- 1.3.6.1.4.1.37950.1.1.5.10.11.2.1.4
-- 1.3.6.1.4.1.37950.1.1.5.10.11.2.1.4
-- 1.3.6.1.4.1.37950.1.1.5.10.11.2.1.4
-- 1.3.6.1.4.1.37950.1.1.5.10.11.2.1.4
-- 1.3.6.1.4.1.37950.1.1.5.10.11.2.1.4
-- 1.3.6.1.4.1.37950.1.1.5.10.11.2.1.4
-- 1.3.6.1.4.1.37950.1.1.5.10.11.2.1.4
		-- 1.3.6.1.4.1.37950.1.1.5.10.11.2.1.4
		staticRouteGw OBJECT-TYPE
			SYNTAX IpAddress
			MAX-ACCESS read-write
			STATUS current
			DESCRIPTION
				"Description."
			::= { staticRouteEntry 4 }

		
--         1.3.6.1.4.1.37950.1.1.5.10.11.3
-- 1.3.6.1.4.1.37950.1.1.5.10.11.3
-- 1.3.6.1.4.1.37950.1.1.5.10.11.3
-- 1.3.6.1.4.1.37950.1.1.5.10.11.3
-- 1.3.6.1.4.1.37950.1.1.5.10.11.3
-- 1.3.6.1.4.1.37950.1.1.5.10.11.3
-- 1.3.6.1.4.1.37950.1.1.5.10.11.3
-- 1.3.6.1.4.1.37950.1.1.5.10.11.3
		-- 1.3.6.1.4.1.37950.1.1.5.10.11.3
		staticIPv6RouteCfg OBJECT IDENTIFIER ::= { v1600dStaticRoute 3 }

		
--         1.3.6.1.4.1.37950.1.1.5.10.11.3.1
-- 1.3.6.1.4.1.37950.1.1.5.10.11.3.1
-- 1.3.6.1.4.1.37950.1.1.5.10.11.3.1
-- 1.3.6.1.4.1.37950.1.1.5.10.11.3.1
-- 1.3.6.1.4.1.37950.1.1.5.10.11.3.1
-- 1.3.6.1.4.1.37950.1.1.5.10.11.3.1
-- 1.3.6.1.4.1.37950.1.1.5.10.11.3.1
-- 1.3.6.1.4.1.37950.1.1.5.10.11.3.1
		-- 1.3.6.1.4.1.37950.1.1.5.10.11.3.1
		ipv6RouteDestAddr OBJECT-TYPE
			SYNTAX OCTET STRING
			MAX-ACCESS read-write
			STATUS current
			DESCRIPTION
				"Description."
			::= { staticIPv6RouteCfg 1 }

		
--         1.3.6.1.4.1.37950.1.1.5.10.11.3.2
-- 1.3.6.1.4.1.37950.1.1.5.10.11.3.2
-- 1.3.6.1.4.1.37950.1.1.5.10.11.3.2
-- 1.3.6.1.4.1.37950.1.1.5.10.11.3.2
-- 1.3.6.1.4.1.37950.1.1.5.10.11.3.2
-- 1.3.6.1.4.1.37950.1.1.5.10.11.3.2
-- 1.3.6.1.4.1.37950.1.1.5.10.11.3.2
-- 1.3.6.1.4.1.37950.1.1.5.10.11.3.2
		-- 1.3.6.1.4.1.37950.1.1.5.10.11.3.2
		ipv6RouteDestAddrPLen OBJECT-TYPE
			SYNTAX Integer32
			MAX-ACCESS read-write
			STATUS current
			DESCRIPTION
				"Description."
			::= { staticIPv6RouteCfg 2 }

		
--         1.3.6.1.4.1.37950.1.1.5.10.11.3.3
-- 1.3.6.1.4.1.37950.1.1.5.10.11.3.3
-- 1.3.6.1.4.1.37950.1.1.5.10.11.3.3
-- 1.3.6.1.4.1.37950.1.1.5.10.11.3.3
-- 1.3.6.1.4.1.37950.1.1.5.10.11.3.3
-- 1.3.6.1.4.1.37950.1.1.5.10.11.3.3
-- 1.3.6.1.4.1.37950.1.1.5.10.11.3.3
-- 1.3.6.1.4.1.37950.1.1.5.10.11.3.3
		-- 1.3.6.1.4.1.37950.1.1.5.10.11.3.3
		ipv6RouteGwAddr OBJECT-TYPE
			SYNTAX OCTET STRING
			MAX-ACCESS read-write
			STATUS current
			DESCRIPTION
				"Description."
			::= { staticIPv6RouteCfg 3 }

		
--         1.3.6.1.4.1.37950.1.1.5.10.11.3.4
-- 1.3.6.1.4.1.37950.1.1.5.10.11.3.4
-- 1.3.6.1.4.1.37950.1.1.5.10.11.3.4
-- 1.3.6.1.4.1.37950.1.1.5.10.11.3.4
-- 1.3.6.1.4.1.37950.1.1.5.10.11.3.4
-- 1.3.6.1.4.1.37950.1.1.5.10.11.3.4
-- 1.3.6.1.4.1.37950.1.1.5.10.11.3.4
-- 1.3.6.1.4.1.37950.1.1.5.10.11.3.4
		-- 1.3.6.1.4.1.37950.1.1.5.10.11.3.4
		ipv6RouteAction OBJECT-TYPE
			SYNTAX INTEGER
				{
				add(1),
				delete(2)
				}
			MAX-ACCESS read-write
			STATUS current
			DESCRIPTION
				"Description."
			::= { staticIPv6RouteCfg 4 }

		
--         1.3.6.1.4.1.37950.1.1.5.10.11.4
-- 1.3.6.1.4.1.37950.1.1.5.10.11.4
-- 1.3.6.1.4.1.37950.1.1.5.10.11.4
-- 1.3.6.1.4.1.37950.1.1.5.10.11.4
-- 1.3.6.1.4.1.37950.1.1.5.10.11.4
-- 1.3.6.1.4.1.37950.1.1.5.10.11.4
-- 1.3.6.1.4.1.37950.1.1.5.10.11.4
-- 1.3.6.1.4.1.37950.1.1.5.10.11.4
		-- 1.3.6.1.4.1.37950.1.1.5.10.11.4
		staticIPv6RouteTable OBJECT-TYPE
			SYNTAX SEQUENCE OF StaticIPv6RouteEntry
			MAX-ACCESS not-accessible
			STATUS current
			DESCRIPTION
				"Description."
			::= { v1600dStaticRoute 4 }

		
--         1.3.6.1.4.1.37950.1.1.5.10.11.4.1
-- 1.3.6.1.4.1.37950.1.1.5.10.11.4.1
-- 1.3.6.1.4.1.37950.1.1.5.10.11.4.1
-- 1.3.6.1.4.1.37950.1.1.5.10.11.4.1
-- 1.3.6.1.4.1.37950.1.1.5.10.11.4.1
-- 1.3.6.1.4.1.37950.1.1.5.10.11.4.1
-- 1.3.6.1.4.1.37950.1.1.5.10.11.4.1
-- 1.3.6.1.4.1.37950.1.1.5.10.11.4.1
		-- 1.3.6.1.4.1.37950.1.1.5.10.11.4.1
		staticIPv6RouteEntry OBJECT-TYPE
			SYNTAX StaticIPv6RouteEntry
			MAX-ACCESS not-accessible
			STATUS current
			DESCRIPTION
				"Description."
			INDEX { ipv6RouteItem }
			::= { staticIPv6RouteTable 1 }

		
		StaticIPv6RouteEntry ::=
			SEQUENCE { 
				ipv6RouteItem
					Integer32,
				ipv6RouteDestin
					OCTET STRING,
				ipv6RouteGw
					OCTET STRING
			 }

--         1.3.6.1.4.1.37950.1.1.5.10.11.4.1.1
-- 1.3.6.1.4.1.37950.1.1.5.10.11.4.1.1
-- 1.3.6.1.4.1.37950.1.1.5.10.11.4.1.1
-- 1.3.6.1.4.1.37950.1.1.5.10.11.4.1.1
-- 1.3.6.1.4.1.37950.1.1.5.10.11.4.1.1
-- 1.3.6.1.4.1.37950.1.1.5.10.11.4.1.1
-- 1.3.6.1.4.1.37950.1.1.5.10.11.4.1.1
-- 1.3.6.1.4.1.37950.1.1.5.10.11.4.1.1
		-- 1.3.6.1.4.1.37950.1.1.5.10.11.4.1.1
		ipv6RouteItem OBJECT-TYPE
			SYNTAX Integer32
			MAX-ACCESS read-only
			STATUS current
			DESCRIPTION
				"Description."
			::= { staticIPv6RouteEntry 1 }

		
--         1.3.6.1.4.1.37950.1.1.5.10.11.4.1.2
-- 1.3.6.1.4.1.37950.1.1.5.10.11.4.1.2
-- 1.3.6.1.4.1.37950.1.1.5.10.11.4.1.2
-- 1.3.6.1.4.1.37950.1.1.5.10.11.4.1.2
-- 1.3.6.1.4.1.37950.1.1.5.10.11.4.1.2
-- 1.3.6.1.4.1.37950.1.1.5.10.11.4.1.2
-- 1.3.6.1.4.1.37950.1.1.5.10.11.4.1.2
-- 1.3.6.1.4.1.37950.1.1.5.10.11.4.1.2
		-- 1.3.6.1.4.1.37950.1.1.5.10.11.4.1.2
		ipv6RouteDestin OBJECT-TYPE
			SYNTAX OCTET STRING
			MAX-ACCESS read-only
			STATUS current
			DESCRIPTION
				"Description."
			::= { staticIPv6RouteEntry 2 }

		
--         1.3.6.1.4.1.37950.1.1.5.10.11.4.1.3
-- 1.3.6.1.4.1.37950.1.1.5.10.11.4.1.3
-- 1.3.6.1.4.1.37950.1.1.5.10.11.4.1.3
-- 1.3.6.1.4.1.37950.1.1.5.10.11.4.1.3
-- 1.3.6.1.4.1.37950.1.1.5.10.11.4.1.3
-- 1.3.6.1.4.1.37950.1.1.5.10.11.4.1.3
-- 1.3.6.1.4.1.37950.1.1.5.10.11.4.1.3
-- 1.3.6.1.4.1.37950.1.1.5.10.11.4.1.3
		-- 1.3.6.1.4.1.37950.1.1.5.10.11.4.1.3
		ipv6RouteGw OBJECT-TYPE
			SYNTAX OCTET STRING
			MAX-ACCESS read-only
			STATUS current
			DESCRIPTION
				"Description."
			::= { staticIPv6RouteEntry 3 }

		
--          1.3.6.1.4.1.37950.1.1.5.10.12
-- 1.3.6.1.4.1.37950.1.1.5.10.12
-- 1.3.6.1.4.1.37950.1.1.5.10.12
-- 1.3.6.1.4.1.37950.1.1.5.10.12
-- 1.3.6.1.4.1.37950.1.1.5.10.12
-- 1.3.6.1.4.1.37950.1.1.5.10.12
-- 1.3.6.1.4.1.37950.1.1.5.10.12
-- 1.3.6.1.4.1.37950.1.1.5.10.12
-- 1.3.6.1.4.1.37950.1.1.5.10.12
		-- 1.3.6.1.4.1.37950.1.1.5.10.12
		v1600dSysCfg OBJECT IDENTIFIER ::= { v1600dSwitch 12 }

		
--          1.3.6.1.4.1.37950.1.1.5.10.12.1
-- 1.3.6.1.4.1.37950.1.1.5.10.12.1
-- 1.3.6.1.4.1.37950.1.1.5.10.12.1
-- 1.3.6.1.4.1.37950.1.1.5.10.12.1
-- 1.3.6.1.4.1.37950.1.1.5.10.12.1
-- 1.3.6.1.4.1.37950.1.1.5.10.12.1
-- 1.3.6.1.4.1.37950.1.1.5.10.12.1
-- 1.3.6.1.4.1.37950.1.1.5.10.12.1
-- 1.3.6.1.4.1.37950.1.1.5.10.12.1
		-- 1.3.6.1.4.1.37950.1.1.5.10.12.1
		restartSystem OBJECT-TYPE
			SYNTAX INTEGER { enable(1) }
			MAX-ACCESS read-write
			STATUS current
			DESCRIPTION
				"Description."
			::= { v1600dSysCfg 1 }

		
--          1.3.6.1.4.1.37950.1.1.5.10.12.2
-- 1.3.6.1.4.1.37950.1.1.5.10.12.2
-- 1.3.6.1.4.1.37950.1.1.5.10.12.2
-- 1.3.6.1.4.1.37950.1.1.5.10.12.2
-- 1.3.6.1.4.1.37950.1.1.5.10.12.2
-- 1.3.6.1.4.1.37950.1.1.5.10.12.2
-- 1.3.6.1.4.1.37950.1.1.5.10.12.2
-- 1.3.6.1.4.1.37950.1.1.5.10.12.2
-- 1.3.6.1.4.1.37950.1.1.5.10.12.2
		-- 1.3.6.1.4.1.37950.1.1.5.10.12.2
		pingIP OBJECT-TYPE
			SYNTAX IpAddress
			MAX-ACCESS read-write
			STATUS current
			DESCRIPTION
				"Description."
			::= { v1600dSysCfg 2 }

		
--          1.3.6.1.4.1.37950.1.1.5.10.12.3
-- 1.3.6.1.4.1.37950.1.1.5.10.12.3
-- 1.3.6.1.4.1.37950.1.1.5.10.12.3
-- 1.3.6.1.4.1.37950.1.1.5.10.12.3
-- 1.3.6.1.4.1.37950.1.1.5.10.12.3
-- 1.3.6.1.4.1.37950.1.1.5.10.12.3
-- 1.3.6.1.4.1.37950.1.1.5.10.12.3
-- 1.3.6.1.4.1.37950.1.1.5.10.12.3
-- 1.3.6.1.4.1.37950.1.1.5.10.12.3
		-- 1.3.6.1.4.1.37950.1.1.5.10.12.3
		cpuLoad OBJECT-TYPE
			SYNTAX Integer32
			MAX-ACCESS read-only
			STATUS current
			DESCRIPTION
				"Description."
			::= { v1600dSysCfg 3 }

		
--          1.3.6.1.4.1.37950.1.1.5.10.12.4
-- 1.3.6.1.4.1.37950.1.1.5.10.12.4
-- 1.3.6.1.4.1.37950.1.1.5.10.12.4
-- 1.3.6.1.4.1.37950.1.1.5.10.12.4
-- 1.3.6.1.4.1.37950.1.1.5.10.12.4
-- 1.3.6.1.4.1.37950.1.1.5.10.12.4
-- 1.3.6.1.4.1.37950.1.1.5.10.12.4
-- 1.3.6.1.4.1.37950.1.1.5.10.12.4
-- 1.3.6.1.4.1.37950.1.1.5.10.12.4
		-- 1.3.6.1.4.1.37950.1.1.5.10.12.4
		memoryLoad OBJECT-TYPE
			SYNTAX Integer32
			MAX-ACCESS read-only
			STATUS current
			DESCRIPTION
				"Description."
			::= { v1600dSysCfg 4 }

		
--          1.3.6.1.4.1.37950.1.1.5.10.12.5
-- 1.3.6.1.4.1.37950.1.1.5.10.12.5
-- 1.3.6.1.4.1.37950.1.1.5.10.12.5
-- 1.3.6.1.4.1.37950.1.1.5.10.12.5
-- 1.3.6.1.4.1.37950.1.1.5.10.12.5
-- 1.3.6.1.4.1.37950.1.1.5.10.12.5
-- 1.3.6.1.4.1.37950.1.1.5.10.12.5
-- 1.3.6.1.4.1.37950.1.1.5.10.12.5
-- 1.3.6.1.4.1.37950.1.1.5.10.12.5
		-- 1.3.6.1.4.1.37950.1.1.5.10.12.5
		systemInfo OBJECT IDENTIFIER ::= { v1600dSysCfg 5 }

		
--          1.3.6.1.4.1.37950.1.1.5.10.12.5.1
-- 1.3.6.1.4.1.37950.1.1.5.10.12.5.1
-- 1.3.6.1.4.1.37950.1.1.5.10.12.5.1
-- 1.3.6.1.4.1.37950.1.1.5.10.12.5.1
-- 1.3.6.1.4.1.37950.1.1.5.10.12.5.1
-- 1.3.6.1.4.1.37950.1.1.5.10.12.5.1
-- 1.3.6.1.4.1.37950.1.1.5.10.12.5.1
-- 1.3.6.1.4.1.37950.1.1.5.10.12.5.1
-- 1.3.6.1.4.1.37950.1.1.5.10.12.5.1
		-- 1.3.6.1.4.1.37950.1.1.5.10.12.5.1
		sysHostName OBJECT-TYPE
			SYNTAX OCTET STRING
			MAX-ACCESS read-write
			STATUS current
			DESCRIPTION
				"Description."
			::= { systemInfo 1 }

		
--          1.3.6.1.4.1.37950.1.1.5.10.12.5.2
-- 1.3.6.1.4.1.37950.1.1.5.10.12.5.2
-- 1.3.6.1.4.1.37950.1.1.5.10.12.5.2
-- 1.3.6.1.4.1.37950.1.1.5.10.12.5.2
-- 1.3.6.1.4.1.37950.1.1.5.10.12.5.2
-- 1.3.6.1.4.1.37950.1.1.5.10.12.5.2
-- 1.3.6.1.4.1.37950.1.1.5.10.12.5.2
-- 1.3.6.1.4.1.37950.1.1.5.10.12.5.2
-- 1.3.6.1.4.1.37950.1.1.5.10.12.5.2
		-- 1.3.6.1.4.1.37950.1.1.5.10.12.5.2
		sysContact OBJECT-TYPE
			SYNTAX OCTET STRING
			MAX-ACCESS read-write
			STATUS current
			DESCRIPTION
				"Description."
			::= { systemInfo 2 }

		
--          1.3.6.1.4.1.37950.1.1.5.10.12.5.3
-- 1.3.6.1.4.1.37950.1.1.5.10.12.5.3
-- 1.3.6.1.4.1.37950.1.1.5.10.12.5.3
-- 1.3.6.1.4.1.37950.1.1.5.10.12.5.3
-- 1.3.6.1.4.1.37950.1.1.5.10.12.5.3
-- 1.3.6.1.4.1.37950.1.1.5.10.12.5.3
-- 1.3.6.1.4.1.37950.1.1.5.10.12.5.3
-- 1.3.6.1.4.1.37950.1.1.5.10.12.5.3
-- 1.3.6.1.4.1.37950.1.1.5.10.12.5.3
		-- 1.3.6.1.4.1.37950.1.1.5.10.12.5.3
		sysLocation OBJECT-TYPE
			SYNTAX OCTET STRING
			MAX-ACCESS read-write
			STATUS current
			DESCRIPTION
				"Description."
			::= { systemInfo 3 }

		
--          1.3.6.1.4.1.37950.1.1.5.10.12.5.4
-- 1.3.6.1.4.1.37950.1.1.5.10.12.5.4
-- 1.3.6.1.4.1.37950.1.1.5.10.12.5.4
-- 1.3.6.1.4.1.37950.1.1.5.10.12.5.4
-- 1.3.6.1.4.1.37950.1.1.5.10.12.5.4
-- 1.3.6.1.4.1.37950.1.1.5.10.12.5.4
-- 1.3.6.1.4.1.37950.1.1.5.10.12.5.4
-- 1.3.6.1.4.1.37950.1.1.5.10.12.5.4
-- 1.3.6.1.4.1.37950.1.1.5.10.12.5.4
		-- 1.3.6.1.4.1.37950.1.1.5.10.12.5.4
		sysFirmVersion OBJECT-TYPE
			SYNTAX OCTET STRING
			MAX-ACCESS read-only
			STATUS current
			DESCRIPTION
				"Description."
			::= { systemInfo 4 }

		
--          1.3.6.1.4.1.37950.1.1.5.10.12.5.5
-- 1.3.6.1.4.1.37950.1.1.5.10.12.5.5
-- 1.3.6.1.4.1.37950.1.1.5.10.12.5.5
-- 1.3.6.1.4.1.37950.1.1.5.10.12.5.5
-- 1.3.6.1.4.1.37950.1.1.5.10.12.5.5
-- 1.3.6.1.4.1.37950.1.1.5.10.12.5.5
-- 1.3.6.1.4.1.37950.1.1.5.10.12.5.5
-- 1.3.6.1.4.1.37950.1.1.5.10.12.5.5
-- 1.3.6.1.4.1.37950.1.1.5.10.12.5.5
		-- 1.3.6.1.4.1.37950.1.1.5.10.12.5.5
		sysHardVersion OBJECT-TYPE
			SYNTAX OCTET STRING
			MAX-ACCESS read-only
			STATUS current
			DESCRIPTION
				"Description."
			::= { systemInfo 5 }

		
--          1.3.6.1.4.1.37950.1.1.5.10.12.5.6
-- 1.3.6.1.4.1.37950.1.1.5.10.12.5.6
-- 1.3.6.1.4.1.37950.1.1.5.10.12.5.6
-- 1.3.6.1.4.1.37950.1.1.5.10.12.5.6
-- 1.3.6.1.4.1.37950.1.1.5.10.12.5.6
-- 1.3.6.1.4.1.37950.1.1.5.10.12.5.6
-- 1.3.6.1.4.1.37950.1.1.5.10.12.5.6
-- 1.3.6.1.4.1.37950.1.1.5.10.12.5.6
-- 1.3.6.1.4.1.37950.1.1.5.10.12.5.6
		-- 1.3.6.1.4.1.37950.1.1.5.10.12.5.6
		mibSup OBJECT-TYPE
			SYNTAX OCTET STRING
			MAX-ACCESS read-only
			STATUS current
			DESCRIPTION
				"Description."
			::= { systemInfo 6 }

		
--          1.3.6.1.4.1.37950.1.1.5.10.12.5.7
-- 1.3.6.1.4.1.37950.1.1.5.10.12.5.7
-- 1.3.6.1.4.1.37950.1.1.5.10.12.5.7
-- 1.3.6.1.4.1.37950.1.1.5.10.12.5.7
-- 1.3.6.1.4.1.37950.1.1.5.10.12.5.7
-- 1.3.6.1.4.1.37950.1.1.5.10.12.5.7
-- 1.3.6.1.4.1.37950.1.1.5.10.12.5.7
-- 1.3.6.1.4.1.37950.1.1.5.10.12.5.7
-- 1.3.6.1.4.1.37950.1.1.5.10.12.5.7
		-- 1.3.6.1.4.1.37950.1.1.5.10.12.5.7
		sysMac OBJECT-TYPE
			SYNTAX OCTET STRING
			MAX-ACCESS read-only
			STATUS current
			DESCRIPTION
				"Description."
			::= { systemInfo 7 }

		
--          1.3.6.1.4.1.37950.1.1.5.10.12.5.8
-- 1.3.6.1.4.1.37950.1.1.5.10.12.5.8
-- 1.3.6.1.4.1.37950.1.1.5.10.12.5.8
-- 1.3.6.1.4.1.37950.1.1.5.10.12.5.8
-- 1.3.6.1.4.1.37950.1.1.5.10.12.5.8
-- 1.3.6.1.4.1.37950.1.1.5.10.12.5.8
-- 1.3.6.1.4.1.37950.1.1.5.10.12.5.8
-- 1.3.6.1.4.1.37950.1.1.5.10.12.5.8
-- 1.3.6.1.4.1.37950.1.1.5.10.12.5.8
		-- 1.3.6.1.4.1.37950.1.1.5.10.12.5.8
		sysRunningTime OBJECT-TYPE
			SYNTAX OCTET STRING
			MAX-ACCESS read-only
			STATUS current
			DESCRIPTION
				"Description."
			::= { systemInfo 8 }

		
--          1.3.6.1.4.1.37950.1.1.5.10.12.5.9
-- 1.3.6.1.4.1.37950.1.1.5.10.12.5.9
-- 1.3.6.1.4.1.37950.1.1.5.10.12.5.9
-- 1.3.6.1.4.1.37950.1.1.5.10.12.5.9
-- 1.3.6.1.4.1.37950.1.1.5.10.12.5.9
-- 1.3.6.1.4.1.37950.1.1.5.10.12.5.9
-- 1.3.6.1.4.1.37950.1.1.5.10.12.5.9
-- 1.3.6.1.4.1.37950.1.1.5.10.12.5.9
-- 1.3.6.1.4.1.37950.1.1.5.10.12.5.9
		-- 1.3.6.1.4.1.37950.1.1.5.10.12.5.9
		sysTemperature OBJECT-TYPE
			SYNTAX Integer32
			MAX-ACCESS read-write
			STATUS current
			DESCRIPTION
				"Description."
			::= { systemInfo 9 }

		
--         1.3.6.1.4.1.37950.1.1.5.10.12.5.10
-- 1.3.6.1.4.1.37950.1.1.5.10.12.5.10
-- 1.3.6.1.4.1.37950.1.1.5.10.12.5.10
-- 1.3.6.1.4.1.37950.1.1.5.10.12.5.10
-- 1.3.6.1.4.1.37950.1.1.5.10.12.5.10
-- 1.3.6.1.4.1.37950.1.1.5.10.12.5.10
-- 1.3.6.1.4.1.37950.1.1.5.10.12.5.10
-- 1.3.6.1.4.1.37950.1.1.5.10.12.5.10
		-- 1.3.6.1.4.1.37950.1.1.5.10.12.5.10
		sysTime OBJECT-TYPE
			SYNTAX OCTET STRING
			MAX-ACCESS read-write
			STATUS current
			DESCRIPTION
				"Description."
			::= { systemInfo 10 }

		
--         1.3.6.1.4.1.37950.1.1.5.10.12.5.11
-- 1.3.6.1.4.1.37950.1.1.5.10.12.5.11
-- 1.3.6.1.4.1.37950.1.1.5.10.12.5.11
-- 1.3.6.1.4.1.37950.1.1.5.10.12.5.11
-- 1.3.6.1.4.1.37950.1.1.5.10.12.5.11
-- 1.3.6.1.4.1.37950.1.1.5.10.12.5.11
-- 1.3.6.1.4.1.37950.1.1.5.10.12.5.11
-- 1.3.6.1.4.1.37950.1.1.5.10.12.5.11
		-- 1.3.6.1.4.1.37950.1.1.5.10.12.5.11
		sysSerialNumber OBJECT-TYPE
			SYNTAX OCTET STRING
			MAX-ACCESS read-write
			STATUS current
			DESCRIPTION
				"Description."
			::= { systemInfo 11 }

		
--          1.3.6.1.4.1.37950.1.1.5.10.12.5.12
-- 1.3.6.1.4.1.37950.1.1.5.10.12.5.12
-- 1.3.6.1.4.1.37950.1.1.5.10.12.5.12
-- 1.3.6.1.4.1.37950.1.1.5.10.12.5.12
-- 1.3.6.1.4.1.37950.1.1.5.10.12.5.12
-- 1.3.6.1.4.1.37950.1.1.5.10.12.5.12
-- 1.3.6.1.4.1.37950.1.1.5.10.12.5.12
-- 1.3.6.1.4.1.37950.1.1.5.10.12.5.12
		-- 1.3.6.1.4.1.37950.1.1.5.10.12.5.12
		sysLicenselimit OBJECT-TYPE
			SYNTAX OCTET STRING
			MAX-ACCESS read-only
			STATUS current
			DESCRIPTION
				"Description."
			::= { systemInfo 12 }

		
--          1.3.6.1.4.1.37950.1.1.5.10.12.5.13
-- 1.3.6.1.4.1.37950.1.1.5.10.12.5.13
-- 1.3.6.1.4.1.37950.1.1.5.10.12.5.13
-- 1.3.6.1.4.1.37950.1.1.5.10.12.5.13
-- 1.3.6.1.4.1.37950.1.1.5.10.12.5.13
-- 1.3.6.1.4.1.37950.1.1.5.10.12.5.13
-- 1.3.6.1.4.1.37950.1.1.5.10.12.5.13
-- 1.3.6.1.4.1.37950.1.1.5.10.12.5.13
		-- 1.3.6.1.4.1.37950.1.1.5.10.12.5.13
		sysLicenseTime OBJECT-TYPE
			SYNTAX OCTET STRING
			MAX-ACCESS read-only
			STATUS current
			DESCRIPTION
				"Description."
			::= { systemInfo 13 }

		
--         1.3.6.1.4.1.37950.1.1.5.10.12.5.14
-- 1.3.6.1.4.1.37950.1.1.5.10.12.5.14
-- 1.3.6.1.4.1.37950.1.1.5.10.12.5.14
-- 1.3.6.1.4.1.37950.1.1.5.10.12.5.14
-- 1.3.6.1.4.1.37950.1.1.5.10.12.5.14
-- 1.3.6.1.4.1.37950.1.1.5.10.12.5.14
-- 1.3.6.1.4.1.37950.1.1.5.10.12.5.14
-- 1.3.6.1.4.1.37950.1.1.5.10.12.5.14
		-- 1.3.6.1.4.1.37950.1.1.5.10.12.5.14
		sysSoftwareCreatedTime OBJECT-TYPE
			SYNTAX OCTET STRING
			MAX-ACCESS read-only
			STATUS current
			DESCRIPTION
				"Description."
			::= { systemInfo 14 }

		
--         1.3.6.1.4.1.37950.1.1.5.10.12.5.15
-- 1.3.6.1.4.1.37950.1.1.5.10.12.5.15
-- 1.3.6.1.4.1.37950.1.1.5.10.12.5.15
-- 1.3.6.1.4.1.37950.1.1.5.10.12.5.15
-- 1.3.6.1.4.1.37950.1.1.5.10.12.5.15
-- 1.3.6.1.4.1.37950.1.1.5.10.12.5.15
-- 1.3.6.1.4.1.37950.1.1.5.10.12.5.15
-- 1.3.6.1.4.1.37950.1.1.5.10.12.5.15
		-- 1.3.6.1.4.1.37950.1.1.5.10.12.5.15
		sysDeviceModel OBJECT-TYPE
			SYNTAX OCTET STRING
			MAX-ACCESS read-write
			STATUS current
			DESCRIPTION
				"Description."
			::= { systemInfo 15 }

		
--          1.3.6.1.4.1.37950.1.1.5.10.12.6
-- 1.3.6.1.4.1.37950.1.1.5.10.12.6
-- 1.3.6.1.4.1.37950.1.1.5.10.12.6
-- 1.3.6.1.4.1.37950.1.1.5.10.12.6
-- 1.3.6.1.4.1.37950.1.1.5.10.12.6
-- 1.3.6.1.4.1.37950.1.1.5.10.12.6
-- 1.3.6.1.4.1.37950.1.1.5.10.12.6
-- 1.3.6.1.4.1.37950.1.1.5.10.12.6
-- 1.3.6.1.4.1.37950.1.1.5.10.12.6
		-- 1.3.6.1.4.1.37950.1.1.5.10.12.6
		arpTable OBJECT-TYPE
			SYNTAX SEQUENCE OF ArpEntry
			MAX-ACCESS not-accessible
			STATUS current
			DESCRIPTION
				"Description."
			::= { v1600dSysCfg 6 }

		
--          1.3.6.1.4.1.37950.1.1.5.10.12.6.1
-- 1.3.6.1.4.1.37950.1.1.5.10.12.6.1
-- 1.3.6.1.4.1.37950.1.1.5.10.12.6.1
-- 1.3.6.1.4.1.37950.1.1.5.10.12.6.1
-- 1.3.6.1.4.1.37950.1.1.5.10.12.6.1
-- 1.3.6.1.4.1.37950.1.1.5.10.12.6.1
-- 1.3.6.1.4.1.37950.1.1.5.10.12.6.1
-- 1.3.6.1.4.1.37950.1.1.5.10.12.6.1
-- 1.3.6.1.4.1.37950.1.1.5.10.12.6.1
		-- 1.3.6.1.4.1.37950.1.1.5.10.12.6.1
		arpEntry OBJECT-TYPE
			SYNTAX ArpEntry
			MAX-ACCESS not-accessible
			STATUS current
			DESCRIPTION
				"Description."
			INDEX { arpIndex }
			::= { arpTable 1 }

		
		ArpEntry ::=
			SEQUENCE { 
				arpIndex
					Integer32,
				arpmacAddr
					OCTET STRING,
				arpIPAddr
					IpAddress,
				arpType
					INTEGER
			 }

--          1.3.6.1.4.1.37950.1.1.5.10.12.6.1.1
-- 1.3.6.1.4.1.37950.1.1.5.10.12.6.1.1
-- 1.3.6.1.4.1.37950.1.1.5.10.12.6.1.1
-- 1.3.6.1.4.1.37950.1.1.5.10.12.6.1.1
-- 1.3.6.1.4.1.37950.1.1.5.10.12.6.1.1
-- 1.3.6.1.4.1.37950.1.1.5.10.12.6.1.1
-- 1.3.6.1.4.1.37950.1.1.5.10.12.6.1.1
-- 1.3.6.1.4.1.37950.1.1.5.10.12.6.1.1
-- 1.3.6.1.4.1.37950.1.1.5.10.12.6.1.1
		-- 1.3.6.1.4.1.37950.1.1.5.10.12.6.1.1
		arpIndex OBJECT-TYPE
			SYNTAX Integer32
			MAX-ACCESS read-only
			STATUS current
			DESCRIPTION
				"Description."
			::= { arpEntry 1 }

		
--          1.3.6.1.4.1.37950.1.1.5.10.12.6.1.2
-- 1.3.6.1.4.1.37950.1.1.5.10.12.6.1.2
-- 1.3.6.1.4.1.37950.1.1.5.10.12.6.1.2
-- 1.3.6.1.4.1.37950.1.1.5.10.12.6.1.2
-- 1.3.6.1.4.1.37950.1.1.5.10.12.6.1.2
-- 1.3.6.1.4.1.37950.1.1.5.10.12.6.1.2
-- 1.3.6.1.4.1.37950.1.1.5.10.12.6.1.2
-- 1.3.6.1.4.1.37950.1.1.5.10.12.6.1.2
-- 1.3.6.1.4.1.37950.1.1.5.10.12.6.1.2
		-- 1.3.6.1.4.1.37950.1.1.5.10.12.6.1.2
		arpmacAddr OBJECT-TYPE
			SYNTAX OCTET STRING
			MAX-ACCESS read-only
			STATUS current
			DESCRIPTION
				"Description."
			::= { arpEntry 2 }

		
--          1.3.6.1.4.1.37950.1.1.5.10.12.6.1.3
-- 1.3.6.1.4.1.37950.1.1.5.10.12.6.1.3
-- 1.3.6.1.4.1.37950.1.1.5.10.12.6.1.3
-- 1.3.6.1.4.1.37950.1.1.5.10.12.6.1.3
-- 1.3.6.1.4.1.37950.1.1.5.10.12.6.1.3
-- 1.3.6.1.4.1.37950.1.1.5.10.12.6.1.3
-- 1.3.6.1.4.1.37950.1.1.5.10.12.6.1.3
-- 1.3.6.1.4.1.37950.1.1.5.10.12.6.1.3
-- 1.3.6.1.4.1.37950.1.1.5.10.12.6.1.3
		-- 1.3.6.1.4.1.37950.1.1.5.10.12.6.1.3
		arpIPAddr OBJECT-TYPE
			SYNTAX IpAddress
			MAX-ACCESS read-only
			STATUS current
			DESCRIPTION
				"Description."
			::= { arpEntry 3 }

		
--          1.3.6.1.4.1.37950.1.1.5.10.12.6.1.4
-- 1.3.6.1.4.1.37950.1.1.5.10.12.6.1.4
-- 1.3.6.1.4.1.37950.1.1.5.10.12.6.1.4
-- 1.3.6.1.4.1.37950.1.1.5.10.12.6.1.4
-- 1.3.6.1.4.1.37950.1.1.5.10.12.6.1.4
-- 1.3.6.1.4.1.37950.1.1.5.10.12.6.1.4
-- 1.3.6.1.4.1.37950.1.1.5.10.12.6.1.4
-- 1.3.6.1.4.1.37950.1.1.5.10.12.6.1.4
-- 1.3.6.1.4.1.37950.1.1.5.10.12.6.1.4
		-- 1.3.6.1.4.1.37950.1.1.5.10.12.6.1.4
		arpType OBJECT-TYPE
			SYNTAX INTEGER
				{
				static(0),
				dynamic(1)
				}
			MAX-ACCESS read-write
			STATUS current
			DESCRIPTION
				"Description."
			::= { arpEntry 4 }

		
--          1.3.6.1.4.1.37950.1.1.5.10.12.7
-- 1.3.6.1.4.1.37950.1.1.5.10.12.7
-- 1.3.6.1.4.1.37950.1.1.5.10.12.7
-- 1.3.6.1.4.1.37950.1.1.5.10.12.7
-- 1.3.6.1.4.1.37950.1.1.5.10.12.7
-- 1.3.6.1.4.1.37950.1.1.5.10.12.7
-- 1.3.6.1.4.1.37950.1.1.5.10.12.7
-- 1.3.6.1.4.1.37950.1.1.5.10.12.7
-- 1.3.6.1.4.1.37950.1.1.5.10.12.7
		-- 1.3.6.1.4.1.37950.1.1.5.10.12.7
		snmpCfg OBJECT IDENTIFIER ::= { v1600dSysCfg 7 }

		
--          1.3.6.1.4.1.37950.1.1.5.10.12.7.1
-- 1.3.6.1.4.1.37950.1.1.5.10.12.7.1
-- 1.3.6.1.4.1.37950.1.1.5.10.12.7.1
-- 1.3.6.1.4.1.37950.1.1.5.10.12.7.1
-- 1.3.6.1.4.1.37950.1.1.5.10.12.7.1
-- 1.3.6.1.4.1.37950.1.1.5.10.12.7.1
-- 1.3.6.1.4.1.37950.1.1.5.10.12.7.1
-- 1.3.6.1.4.1.37950.1.1.5.10.12.7.1
-- 1.3.6.1.4.1.37950.1.1.5.10.12.7.1
		-- 1.3.6.1.4.1.37950.1.1.5.10.12.7.1
		snmpv1v2Config OBJECT IDENTIFIER ::= { snmpCfg 1 }

		
--          1.3.6.1.4.1.37950.1.1.5.10.12.7.1.1
-- 1.3.6.1.4.1.37950.1.1.5.10.12.7.1.1
-- 1.3.6.1.4.1.37950.1.1.5.10.12.7.1.1
-- 1.3.6.1.4.1.37950.1.1.5.10.12.7.1.1
-- 1.3.6.1.4.1.37950.1.1.5.10.12.7.1.1
-- 1.3.6.1.4.1.37950.1.1.5.10.12.7.1.1
-- 1.3.6.1.4.1.37950.1.1.5.10.12.7.1.1
-- 1.3.6.1.4.1.37950.1.1.5.10.12.7.1.1
-- 1.3.6.1.4.1.37950.1.1.5.10.12.7.1.1
		-- 1.3.6.1.4.1.37950.1.1.5.10.12.7.1.1
		communityNameSetting OBJECT-TYPE
			SYNTAX OCTET STRING
			MAX-ACCESS read-write
			STATUS current
			DESCRIPTION
				"Description."
			::= { snmpv1v2Config 1 }

		
--          1.3.6.1.4.1.37950.1.1.5.10.12.7.1.2
-- 1.3.6.1.4.1.37950.1.1.5.10.12.7.1.2
-- 1.3.6.1.4.1.37950.1.1.5.10.12.7.1.2
-- 1.3.6.1.4.1.37950.1.1.5.10.12.7.1.2
-- 1.3.6.1.4.1.37950.1.1.5.10.12.7.1.2
-- 1.3.6.1.4.1.37950.1.1.5.10.12.7.1.2
-- 1.3.6.1.4.1.37950.1.1.5.10.12.7.1.2
-- 1.3.6.1.4.1.37950.1.1.5.10.12.7.1.2
-- 1.3.6.1.4.1.37950.1.1.5.10.12.7.1.2
		-- 1.3.6.1.4.1.37950.1.1.5.10.12.7.1.2
		accessRightSetting OBJECT-TYPE
			SYNTAX INTEGER
				{
				read-only(1),
				read-write(2)
				}
			MAX-ACCESS read-write
			STATUS current
			DESCRIPTION
				"Description."
			::= { snmpv1v2Config 2 }

		
--          1.3.6.1.4.1.37950.1.1.5.10.12.7.1.3
-- 1.3.6.1.4.1.37950.1.1.5.10.12.7.1.3
-- 1.3.6.1.4.1.37950.1.1.5.10.12.7.1.3
-- 1.3.6.1.4.1.37950.1.1.5.10.12.7.1.3
-- 1.3.6.1.4.1.37950.1.1.5.10.12.7.1.3
-- 1.3.6.1.4.1.37950.1.1.5.10.12.7.1.3
-- 1.3.6.1.4.1.37950.1.1.5.10.12.7.1.3
-- 1.3.6.1.4.1.37950.1.1.5.10.12.7.1.3
-- 1.3.6.1.4.1.37950.1.1.5.10.12.7.1.3
		-- 1.3.6.1.4.1.37950.1.1.5.10.12.7.1.3
		communitycommit OBJECT-TYPE
			SYNTAX INTEGER
				{
				commit(1),
				delete(2)
				}
			MAX-ACCESS read-write
			STATUS current
			DESCRIPTION
				"Description."
			::= { snmpv1v2Config 3 }

		
--          1.3.6.1.4.1.37950.1.1.5.10.12.7.2
-- 1.3.6.1.4.1.37950.1.1.5.10.12.7.2
-- 1.3.6.1.4.1.37950.1.1.5.10.12.7.2
-- 1.3.6.1.4.1.37950.1.1.5.10.12.7.2
-- 1.3.6.1.4.1.37950.1.1.5.10.12.7.2
-- 1.3.6.1.4.1.37950.1.1.5.10.12.7.2
-- 1.3.6.1.4.1.37950.1.1.5.10.12.7.2
-- 1.3.6.1.4.1.37950.1.1.5.10.12.7.2
-- 1.3.6.1.4.1.37950.1.1.5.10.12.7.2
		-- 1.3.6.1.4.1.37950.1.1.5.10.12.7.2
		communityTable OBJECT-TYPE
			SYNTAX SEQUENCE OF CommunityEntry
			MAX-ACCESS not-accessible
			STATUS current
			DESCRIPTION
				"Description."
			::= { snmpCfg 2 }

		
--          1.3.6.1.4.1.37950.1.1.5.10.12.7.2.1
-- 1.3.6.1.4.1.37950.1.1.5.10.12.7.2.1
-- 1.3.6.1.4.1.37950.1.1.5.10.12.7.2.1
-- 1.3.6.1.4.1.37950.1.1.5.10.12.7.2.1
-- 1.3.6.1.4.1.37950.1.1.5.10.12.7.2.1
-- 1.3.6.1.4.1.37950.1.1.5.10.12.7.2.1
-- 1.3.6.1.4.1.37950.1.1.5.10.12.7.2.1
-- 1.3.6.1.4.1.37950.1.1.5.10.12.7.2.1
-- 1.3.6.1.4.1.37950.1.1.5.10.12.7.2.1
		-- 1.3.6.1.4.1.37950.1.1.5.10.12.7.2.1
		communityEntry OBJECT-TYPE
			SYNTAX CommunityEntry
			MAX-ACCESS not-accessible
			STATUS current
			DESCRIPTION
				"Description."
			INDEX { communityIndex }
			::= { communityTable 1 }

		
		CommunityEntry ::=
			SEQUENCE { 
				communityIndex
					Integer32,
				communityName
					OCTET STRING,
				accessRight
					INTEGER
			 }

--          1.3.6.1.4.1.37950.1.1.5.10.12.7.2.1.1
-- 1.3.6.1.4.1.37950.1.1.5.10.12.7.2.1.1
-- 1.3.6.1.4.1.37950.1.1.5.10.12.7.2.1.1
-- 1.3.6.1.4.1.37950.1.1.5.10.12.7.2.1.1
-- 1.3.6.1.4.1.37950.1.1.5.10.12.7.2.1.1
-- 1.3.6.1.4.1.37950.1.1.5.10.12.7.2.1.1
-- 1.3.6.1.4.1.37950.1.1.5.10.12.7.2.1.1
-- 1.3.6.1.4.1.37950.1.1.5.10.12.7.2.1.1
-- 1.3.6.1.4.1.37950.1.1.5.10.12.7.2.1.1
		-- 1.3.6.1.4.1.37950.1.1.5.10.12.7.2.1.1
		communityIndex OBJECT-TYPE
			SYNTAX Integer32
			MAX-ACCESS read-only
			STATUS current
			DESCRIPTION
				"Description."
			::= { communityEntry 1 }

		
--          1.3.6.1.4.1.37950.1.1.5.10.12.7.2.1.2
-- 1.3.6.1.4.1.37950.1.1.5.10.12.7.2.1.2
-- 1.3.6.1.4.1.37950.1.1.5.10.12.7.2.1.2
-- 1.3.6.1.4.1.37950.1.1.5.10.12.7.2.1.2
-- 1.3.6.1.4.1.37950.1.1.5.10.12.7.2.1.2
-- 1.3.6.1.4.1.37950.1.1.5.10.12.7.2.1.2
-- 1.3.6.1.4.1.37950.1.1.5.10.12.7.2.1.2
-- 1.3.6.1.4.1.37950.1.1.5.10.12.7.2.1.2
-- 1.3.6.1.4.1.37950.1.1.5.10.12.7.2.1.2
		-- 1.3.6.1.4.1.37950.1.1.5.10.12.7.2.1.2
		communityName OBJECT-TYPE
			SYNTAX OCTET STRING
			MAX-ACCESS read-only
			STATUS current
			DESCRIPTION
				"Description."
			::= { communityEntry 2 }

		
--          1.3.6.1.4.1.37950.1.1.5.10.12.7.2.1.3
-- 1.3.6.1.4.1.37950.1.1.5.10.12.7.2.1.3
-- 1.3.6.1.4.1.37950.1.1.5.10.12.7.2.1.3
-- 1.3.6.1.4.1.37950.1.1.5.10.12.7.2.1.3
-- 1.3.6.1.4.1.37950.1.1.5.10.12.7.2.1.3
-- 1.3.6.1.4.1.37950.1.1.5.10.12.7.2.1.3
-- 1.3.6.1.4.1.37950.1.1.5.10.12.7.2.1.3
-- 1.3.6.1.4.1.37950.1.1.5.10.12.7.2.1.3
-- 1.3.6.1.4.1.37950.1.1.5.10.12.7.2.1.3
		-- 1.3.6.1.4.1.37950.1.1.5.10.12.7.2.1.3
		accessRight OBJECT-TYPE
			SYNTAX INTEGER
				{
				read-only(1),
				read-write(2)
				}
			MAX-ACCESS read-only
			STATUS current
			DESCRIPTION
				"Description."
			::= { communityEntry 3 }

		
--          1.3.6.1.4.1.37950.1.1.5.10.12.7.3
-- 1.3.6.1.4.1.37950.1.1.5.10.12.7.3
-- 1.3.6.1.4.1.37950.1.1.5.10.12.7.3
-- 1.3.6.1.4.1.37950.1.1.5.10.12.7.3
-- 1.3.6.1.4.1.37950.1.1.5.10.12.7.3
-- 1.3.6.1.4.1.37950.1.1.5.10.12.7.3
-- 1.3.6.1.4.1.37950.1.1.5.10.12.7.3
-- 1.3.6.1.4.1.37950.1.1.5.10.12.7.3
-- 1.3.6.1.4.1.37950.1.1.5.10.12.7.3
		-- 1.3.6.1.4.1.37950.1.1.5.10.12.7.3
		snmpv1v2TrapConfig OBJECT IDENTIFIER ::= { snmpCfg 3 }

		
--          1.3.6.1.4.1.37950.1.1.5.10.12.7.3.1
-- 1.3.6.1.4.1.37950.1.1.5.10.12.7.3.1
-- 1.3.6.1.4.1.37950.1.1.5.10.12.7.3.1
-- 1.3.6.1.4.1.37950.1.1.5.10.12.7.3.1
-- 1.3.6.1.4.1.37950.1.1.5.10.12.7.3.1
-- 1.3.6.1.4.1.37950.1.1.5.10.12.7.3.1
-- 1.3.6.1.4.1.37950.1.1.5.10.12.7.3.1
-- 1.3.6.1.4.1.37950.1.1.5.10.12.7.3.1
-- 1.3.6.1.4.1.37950.1.1.5.10.12.7.3.1
		-- 1.3.6.1.4.1.37950.1.1.5.10.12.7.3.1
		trapHostIpSetting OBJECT-TYPE
			SYNTAX IpAddress
			MAX-ACCESS read-write
			STATUS current
			DESCRIPTION
				"Description."
			::= { snmpv1v2TrapConfig 1 }

		
--          1.3.6.1.4.1.37950.1.1.5.10.12.7.3.2
-- 1.3.6.1.4.1.37950.1.1.5.10.12.7.3.2
-- 1.3.6.1.4.1.37950.1.1.5.10.12.7.3.2
-- 1.3.6.1.4.1.37950.1.1.5.10.12.7.3.2
-- 1.3.6.1.4.1.37950.1.1.5.10.12.7.3.2
-- 1.3.6.1.4.1.37950.1.1.5.10.12.7.3.2
-- 1.3.6.1.4.1.37950.1.1.5.10.12.7.3.2
-- 1.3.6.1.4.1.37950.1.1.5.10.12.7.3.2
-- 1.3.6.1.4.1.37950.1.1.5.10.12.7.3.2
		-- 1.3.6.1.4.1.37950.1.1.5.10.12.7.3.2
		trapUdpPortSetting OBJECT-TYPE
			SYNTAX Integer32 (0..65535)
			MAX-ACCESS read-write
			STATUS current
			DESCRIPTION
				"Description."
			::= { snmpv1v2TrapConfig 2 }

		
--          1.3.6.1.4.1.37950.1.1.5.10.12.7.3.3
-- 1.3.6.1.4.1.37950.1.1.5.10.12.7.3.3
-- 1.3.6.1.4.1.37950.1.1.5.10.12.7.3.3
-- 1.3.6.1.4.1.37950.1.1.5.10.12.7.3.3
-- 1.3.6.1.4.1.37950.1.1.5.10.12.7.3.3
-- 1.3.6.1.4.1.37950.1.1.5.10.12.7.3.3
-- 1.3.6.1.4.1.37950.1.1.5.10.12.7.3.3
-- 1.3.6.1.4.1.37950.1.1.5.10.12.7.3.3
-- 1.3.6.1.4.1.37950.1.1.5.10.12.7.3.3
		-- 1.3.6.1.4.1.37950.1.1.5.10.12.7.3.3
		trapCommunityNameSetting OBJECT-TYPE
			SYNTAX OCTET STRING
			MAX-ACCESS read-write
			STATUS current
			DESCRIPTION
				"Description."
			::= { snmpv1v2TrapConfig 3 }

		
--          1.3.6.1.4.1.37950.1.1.5.10.12.7.3.4
-- 1.3.6.1.4.1.37950.1.1.5.10.12.7.3.4
-- 1.3.6.1.4.1.37950.1.1.5.10.12.7.3.4
-- 1.3.6.1.4.1.37950.1.1.5.10.12.7.3.4
-- 1.3.6.1.4.1.37950.1.1.5.10.12.7.3.4
-- 1.3.6.1.4.1.37950.1.1.5.10.12.7.3.4
-- 1.3.6.1.4.1.37950.1.1.5.10.12.7.3.4
-- 1.3.6.1.4.1.37950.1.1.5.10.12.7.3.4
-- 1.3.6.1.4.1.37950.1.1.5.10.12.7.3.4
		-- 1.3.6.1.4.1.37950.1.1.5.10.12.7.3.4
		trapVersionSetting OBJECT-TYPE
			SYNTAX INTEGER
				{
				snmp-v1(1),
				snmp-v2c(2)
				}
			MAX-ACCESS read-write
			STATUS current
			DESCRIPTION
				"Description."
			::= { snmpv1v2TrapConfig 4 }

		
--          1.3.6.1.4.1.37950.1.1.5.10.12.7.3.5
-- 1.3.6.1.4.1.37950.1.1.5.10.12.7.3.5
-- 1.3.6.1.4.1.37950.1.1.5.10.12.7.3.5
-- 1.3.6.1.4.1.37950.1.1.5.10.12.7.3.5
-- 1.3.6.1.4.1.37950.1.1.5.10.12.7.3.5
-- 1.3.6.1.4.1.37950.1.1.5.10.12.7.3.5
-- 1.3.6.1.4.1.37950.1.1.5.10.12.7.3.5
-- 1.3.6.1.4.1.37950.1.1.5.10.12.7.3.5
-- 1.3.6.1.4.1.37950.1.1.5.10.12.7.3.5
		-- 1.3.6.1.4.1.37950.1.1.5.10.12.7.3.5
		trapAction OBJECT-TYPE
			SYNTAX INTEGER
				{
				add(1),
				delete(2)
				}
			MAX-ACCESS read-write
			STATUS current
			DESCRIPTION
				"Description."
			::= { snmpv1v2TrapConfig 5 }

		
--          1.3.6.1.4.1.37950.1.1.5.10.12.7.4
-- 1.3.6.1.4.1.37950.1.1.5.10.12.7.4
-- 1.3.6.1.4.1.37950.1.1.5.10.12.7.4
-- 1.3.6.1.4.1.37950.1.1.5.10.12.7.4
-- 1.3.6.1.4.1.37950.1.1.5.10.12.7.4
-- 1.3.6.1.4.1.37950.1.1.5.10.12.7.4
-- 1.3.6.1.4.1.37950.1.1.5.10.12.7.4
-- 1.3.6.1.4.1.37950.1.1.5.10.12.7.4
-- 1.3.6.1.4.1.37950.1.1.5.10.12.7.4
		-- 1.3.6.1.4.1.37950.1.1.5.10.12.7.4
		snmpv1v2TrapTable OBJECT-TYPE
			SYNTAX SEQUENCE OF Snmpv1v2TrapEntry
			MAX-ACCESS not-accessible
			STATUS current
			DESCRIPTION
				"Description."
			::= { snmpCfg 4 }

		
--          1.3.6.1.4.1.37950.1.1.5.10.12.7.4.1
-- 1.3.6.1.4.1.37950.1.1.5.10.12.7.4.1
-- 1.3.6.1.4.1.37950.1.1.5.10.12.7.4.1
-- 1.3.6.1.4.1.37950.1.1.5.10.12.7.4.1
-- 1.3.6.1.4.1.37950.1.1.5.10.12.7.4.1
-- 1.3.6.1.4.1.37950.1.1.5.10.12.7.4.1
-- 1.3.6.1.4.1.37950.1.1.5.10.12.7.4.1
-- 1.3.6.1.4.1.37950.1.1.5.10.12.7.4.1
-- 1.3.6.1.4.1.37950.1.1.5.10.12.7.4.1
		-- 1.3.6.1.4.1.37950.1.1.5.10.12.7.4.1
		snmpv1v2TrapEntry OBJECT-TYPE
			SYNTAX Snmpv1v2TrapEntry
			MAX-ACCESS not-accessible
			STATUS current
			DESCRIPTION
				"Description."
			INDEX { trapIndex }
			::= { snmpv1v2TrapTable 1 }

		
		Snmpv1v2TrapEntry ::=
			SEQUENCE { 
				trapIndex
					Integer32,
				trapHostIp
					IpAddress,
				trapUdpPort
					Integer32,
				trapCommunityName
					OCTET STRING,
				trapVersion
					INTEGER
			 }

--          1.3.6.1.4.1.37950.1.1.5.10.12.7.4.1.1
-- 1.3.6.1.4.1.37950.1.1.5.10.12.7.4.1.1
-- 1.3.6.1.4.1.37950.1.1.5.10.12.7.4.1.1
-- 1.3.6.1.4.1.37950.1.1.5.10.12.7.4.1.1
-- 1.3.6.1.4.1.37950.1.1.5.10.12.7.4.1.1
-- 1.3.6.1.4.1.37950.1.1.5.10.12.7.4.1.1
-- 1.3.6.1.4.1.37950.1.1.5.10.12.7.4.1.1
-- 1.3.6.1.4.1.37950.1.1.5.10.12.7.4.1.1
-- 1.3.6.1.4.1.37950.1.1.5.10.12.7.4.1.1
		-- 1.3.6.1.4.1.37950.1.1.5.10.12.7.4.1.1
		trapIndex OBJECT-TYPE
			SYNTAX Integer32
			MAX-ACCESS read-only
			STATUS current
			DESCRIPTION
				"Description."
			::= { snmpv1v2TrapEntry 1 }

		
--          1.3.6.1.4.1.37950.1.1.5.10.12.7.4.1.2
-- 1.3.6.1.4.1.37950.1.1.5.10.12.7.4.1.2
-- 1.3.6.1.4.1.37950.1.1.5.10.12.7.4.1.2
-- 1.3.6.1.4.1.37950.1.1.5.10.12.7.4.1.2
-- 1.3.6.1.4.1.37950.1.1.5.10.12.7.4.1.2
-- 1.3.6.1.4.1.37950.1.1.5.10.12.7.4.1.2
-- 1.3.6.1.4.1.37950.1.1.5.10.12.7.4.1.2
-- 1.3.6.1.4.1.37950.1.1.5.10.12.7.4.1.2
-- 1.3.6.1.4.1.37950.1.1.5.10.12.7.4.1.2
		-- 1.3.6.1.4.1.37950.1.1.5.10.12.7.4.1.2
		trapHostIp OBJECT-TYPE
			SYNTAX IpAddress
			MAX-ACCESS read-only
			STATUS current
			DESCRIPTION
				"Description."
			::= { snmpv1v2TrapEntry 2 }

		
--          1.3.6.1.4.1.37950.1.1.5.10.12.7.4.1.3
-- 1.3.6.1.4.1.37950.1.1.5.10.12.7.4.1.3
-- 1.3.6.1.4.1.37950.1.1.5.10.12.7.4.1.3
-- 1.3.6.1.4.1.37950.1.1.5.10.12.7.4.1.3
-- 1.3.6.1.4.1.37950.1.1.5.10.12.7.4.1.3
-- 1.3.6.1.4.1.37950.1.1.5.10.12.7.4.1.3
-- 1.3.6.1.4.1.37950.1.1.5.10.12.7.4.1.3
-- 1.3.6.1.4.1.37950.1.1.5.10.12.7.4.1.3
-- 1.3.6.1.4.1.37950.1.1.5.10.12.7.4.1.3
		-- 1.3.6.1.4.1.37950.1.1.5.10.12.7.4.1.3
		trapUdpPort OBJECT-TYPE
			SYNTAX Integer32 (0..65535)
			MAX-ACCESS read-only
			STATUS current
			DESCRIPTION
				"Description."
			::= { snmpv1v2TrapEntry 3 }

		
--          1.3.6.1.4.1.37950.1.1.5.10.12.7.4.1.4
-- 1.3.6.1.4.1.37950.1.1.5.10.12.7.4.1.4
-- 1.3.6.1.4.1.37950.1.1.5.10.12.7.4.1.4
-- 1.3.6.1.4.1.37950.1.1.5.10.12.7.4.1.4
-- 1.3.6.1.4.1.37950.1.1.5.10.12.7.4.1.4
-- 1.3.6.1.4.1.37950.1.1.5.10.12.7.4.1.4
-- 1.3.6.1.4.1.37950.1.1.5.10.12.7.4.1.4
-- 1.3.6.1.4.1.37950.1.1.5.10.12.7.4.1.4
-- 1.3.6.1.4.1.37950.1.1.5.10.12.7.4.1.4
		-- 1.3.6.1.4.1.37950.1.1.5.10.12.7.4.1.4
		trapCommunityName OBJECT-TYPE
			SYNTAX OCTET STRING
			MAX-ACCESS read-only
			STATUS current
			DESCRIPTION
				"Description."
			::= { snmpv1v2TrapEntry 4 }

		
--          1.3.6.1.4.1.37950.1.1.5.10.12.7.4.1.5
-- 1.3.6.1.4.1.37950.1.1.5.10.12.7.4.1.5
-- 1.3.6.1.4.1.37950.1.1.5.10.12.7.4.1.5
-- 1.3.6.1.4.1.37950.1.1.5.10.12.7.4.1.5
-- 1.3.6.1.4.1.37950.1.1.5.10.12.7.4.1.5
-- 1.3.6.1.4.1.37950.1.1.5.10.12.7.4.1.5
-- 1.3.6.1.4.1.37950.1.1.5.10.12.7.4.1.5
-- 1.3.6.1.4.1.37950.1.1.5.10.12.7.4.1.5
-- 1.3.6.1.4.1.37950.1.1.5.10.12.7.4.1.5
		-- 1.3.6.1.4.1.37950.1.1.5.10.12.7.4.1.5
		trapVersion OBJECT-TYPE
			SYNTAX INTEGER
				{
				snmp-v1(1),
				snmp-v2c(2)
				}
			MAX-ACCESS read-only
			STATUS current
			DESCRIPTION
				"Description."
			::= { snmpv1v2TrapEntry 5 }

		
--         1.3.6.1.4.1.37950.1.1.5.10.12.7.5
-- 1.3.6.1.4.1.37950.1.1.5.10.12.7.5
-- 1.3.6.1.4.1.37950.1.1.5.10.12.7.5
-- 1.3.6.1.4.1.37950.1.1.5.10.12.7.5
-- 1.3.6.1.4.1.37950.1.1.5.10.12.7.5
-- 1.3.6.1.4.1.37950.1.1.5.10.12.7.5
-- 1.3.6.1.4.1.37950.1.1.5.10.12.7.5
-- 1.3.6.1.4.1.37950.1.1.5.10.12.7.5
		-- 1.3.6.1.4.1.37950.1.1.5.10.12.7.5
		snmpv3ViewConfig OBJECT IDENTIFIER ::= { snmpCfg 5 }

		
--         1.3.6.1.4.1.37950.1.1.5.10.12.7.5.1
-- 1.3.6.1.4.1.37950.1.1.5.10.12.7.5.1
-- 1.3.6.1.4.1.37950.1.1.5.10.12.7.5.1
-- 1.3.6.1.4.1.37950.1.1.5.10.12.7.5.1
-- 1.3.6.1.4.1.37950.1.1.5.10.12.7.5.1
-- 1.3.6.1.4.1.37950.1.1.5.10.12.7.5.1
-- 1.3.6.1.4.1.37950.1.1.5.10.12.7.5.1
-- 1.3.6.1.4.1.37950.1.1.5.10.12.7.5.1
		-- 1.3.6.1.4.1.37950.1.1.5.10.12.7.5.1
		snmpv3Viewname OBJECT-TYPE
			SYNTAX OCTET STRING
			MAX-ACCESS read-write
			STATUS current
			DESCRIPTION
				"Description."
			::= { snmpv3ViewConfig 1 }

		
--         1.3.6.1.4.1.37950.1.1.5.10.12.7.5.2
-- 1.3.6.1.4.1.37950.1.1.5.10.12.7.5.2
-- 1.3.6.1.4.1.37950.1.1.5.10.12.7.5.2
-- 1.3.6.1.4.1.37950.1.1.5.10.12.7.5.2
-- 1.3.6.1.4.1.37950.1.1.5.10.12.7.5.2
-- 1.3.6.1.4.1.37950.1.1.5.10.12.7.5.2
-- 1.3.6.1.4.1.37950.1.1.5.10.12.7.5.2
-- 1.3.6.1.4.1.37950.1.1.5.10.12.7.5.2
		-- 1.3.6.1.4.1.37950.1.1.5.10.12.7.5.2
		snmpv3Viewsubtree OBJECT-TYPE
			SYNTAX OCTET STRING
			MAX-ACCESS read-write
			STATUS current
			DESCRIPTION
				"Description."
			::= { snmpv3ViewConfig 2 }

		
--         1.3.6.1.4.1.37950.1.1.5.10.12.7.5.3
-- 1.3.6.1.4.1.37950.1.1.5.10.12.7.5.3
-- 1.3.6.1.4.1.37950.1.1.5.10.12.7.5.3
-- 1.3.6.1.4.1.37950.1.1.5.10.12.7.5.3
-- 1.3.6.1.4.1.37950.1.1.5.10.12.7.5.3
-- 1.3.6.1.4.1.37950.1.1.5.10.12.7.5.3
-- 1.3.6.1.4.1.37950.1.1.5.10.12.7.5.3
-- 1.3.6.1.4.1.37950.1.1.5.10.12.7.5.3
		-- 1.3.6.1.4.1.37950.1.1.5.10.12.7.5.3
		snmpv3Viewtype OBJECT-TYPE
			SYNTAX INTEGER
				{
				include(1),
				exclude(2)
				}
			MAX-ACCESS read-write
			STATUS current
			DESCRIPTION
				"Description."
			::= { snmpv3ViewConfig 3 }

		
--         1.3.6.1.4.1.37950.1.1.5.10.12.7.5.4
-- 1.3.6.1.4.1.37950.1.1.5.10.12.7.5.4
-- 1.3.6.1.4.1.37950.1.1.5.10.12.7.5.4
-- 1.3.6.1.4.1.37950.1.1.5.10.12.7.5.4
-- 1.3.6.1.4.1.37950.1.1.5.10.12.7.5.4
-- 1.3.6.1.4.1.37950.1.1.5.10.12.7.5.4
-- 1.3.6.1.4.1.37950.1.1.5.10.12.7.5.4
-- 1.3.6.1.4.1.37950.1.1.5.10.12.7.5.4
		-- 1.3.6.1.4.1.37950.1.1.5.10.12.7.5.4
		snmpv3ViewAction OBJECT-TYPE
			SYNTAX INTEGER
				{
				add(1),
				del(2)
				}
			MAX-ACCESS read-write
			STATUS current
			DESCRIPTION
				"Description."
			::= { snmpv3ViewConfig 4 }

		
--         1.3.6.1.4.1.37950.1.1.5.10.12.7.6
-- 1.3.6.1.4.1.37950.1.1.5.10.12.7.6
-- 1.3.6.1.4.1.37950.1.1.5.10.12.7.6
-- 1.3.6.1.4.1.37950.1.1.5.10.12.7.6
-- 1.3.6.1.4.1.37950.1.1.5.10.12.7.6
-- 1.3.6.1.4.1.37950.1.1.5.10.12.7.6
-- 1.3.6.1.4.1.37950.1.1.5.10.12.7.6
-- 1.3.6.1.4.1.37950.1.1.5.10.12.7.6
		-- 1.3.6.1.4.1.37950.1.1.5.10.12.7.6
		snmpv3ViewTable OBJECT-TYPE
			SYNTAX SEQUENCE OF Snmpv3ViewEntry
			MAX-ACCESS not-accessible
			STATUS current
			DESCRIPTION
				"Description."
			::= { snmpCfg 6 }

		
--         1.3.6.1.4.1.37950.1.1.5.10.12.7.6.1
-- 1.3.6.1.4.1.37950.1.1.5.10.12.7.6.1
-- 1.3.6.1.4.1.37950.1.1.5.10.12.7.6.1
-- 1.3.6.1.4.1.37950.1.1.5.10.12.7.6.1
-- 1.3.6.1.4.1.37950.1.1.5.10.12.7.6.1
-- 1.3.6.1.4.1.37950.1.1.5.10.12.7.6.1
-- 1.3.6.1.4.1.37950.1.1.5.10.12.7.6.1
-- 1.3.6.1.4.1.37950.1.1.5.10.12.7.6.1
		-- 1.3.6.1.4.1.37950.1.1.5.10.12.7.6.1
		snmpv3ViewEntry OBJECT-TYPE
			SYNTAX Snmpv3ViewEntry
			MAX-ACCESS not-accessible
			STATUS current
			DESCRIPTION
				"Description."
			INDEX { snmpv3ViewIndex }
			::= { snmpv3ViewTable 1 }

		
		Snmpv3ViewEntry ::=
			SEQUENCE { 
				snmpv3ViewIndex
					Integer32,
				snmpv3ViewName
					OCTET STRING,
				snmpv3ViewSubtree
					OCTET STRING,
				snmpv3ViewType
					INTEGER
			 }

--         1.3.6.1.4.1.37950.1.1.5.10.12.7.6.1.1
-- 1.3.6.1.4.1.37950.1.1.5.10.12.7.6.1.1
-- 1.3.6.1.4.1.37950.1.1.5.10.12.7.6.1.1
-- 1.3.6.1.4.1.37950.1.1.5.10.12.7.6.1.1
-- 1.3.6.1.4.1.37950.1.1.5.10.12.7.6.1.1
-- 1.3.6.1.4.1.37950.1.1.5.10.12.7.6.1.1
-- 1.3.6.1.4.1.37950.1.1.5.10.12.7.6.1.1
-- 1.3.6.1.4.1.37950.1.1.5.10.12.7.6.1.1
		-- 1.3.6.1.4.1.37950.1.1.5.10.12.7.6.1.1
		snmpv3ViewIndex OBJECT-TYPE
			SYNTAX Integer32
			MAX-ACCESS read-only
			STATUS current
			DESCRIPTION
				"Description."
			::= { snmpv3ViewEntry 1 }

		
--         1.3.6.1.4.1.37950.1.1.5.10.12.7.6.1.2
-- 1.3.6.1.4.1.37950.1.1.5.10.12.7.6.1.2
-- 1.3.6.1.4.1.37950.1.1.5.10.12.7.6.1.2
-- 1.3.6.1.4.1.37950.1.1.5.10.12.7.6.1.2
-- 1.3.6.1.4.1.37950.1.1.5.10.12.7.6.1.2
-- 1.3.6.1.4.1.37950.1.1.5.10.12.7.6.1.2
-- 1.3.6.1.4.1.37950.1.1.5.10.12.7.6.1.2
-- 1.3.6.1.4.1.37950.1.1.5.10.12.7.6.1.2
		-- 1.3.6.1.4.1.37950.1.1.5.10.12.7.6.1.2
		snmpv3ViewName OBJECT-TYPE
			SYNTAX OCTET STRING
			MAX-ACCESS read-only
			STATUS current
			DESCRIPTION
				"Description."
			::= { snmpv3ViewEntry 2 }

		
--         1.3.6.1.4.1.37950.1.1.5.10.12.7.6.1.3
-- 1.3.6.1.4.1.37950.1.1.5.10.12.7.6.1.3
-- 1.3.6.1.4.1.37950.1.1.5.10.12.7.6.1.3
-- 1.3.6.1.4.1.37950.1.1.5.10.12.7.6.1.3
-- 1.3.6.1.4.1.37950.1.1.5.10.12.7.6.1.3
-- 1.3.6.1.4.1.37950.1.1.5.10.12.7.6.1.3
-- 1.3.6.1.4.1.37950.1.1.5.10.12.7.6.1.3
-- 1.3.6.1.4.1.37950.1.1.5.10.12.7.6.1.3
		-- 1.3.6.1.4.1.37950.1.1.5.10.12.7.6.1.3
		snmpv3ViewSubtree OBJECT-TYPE
			SYNTAX OCTET STRING
			MAX-ACCESS read-only
			STATUS current
			DESCRIPTION
				"Description."
			::= { snmpv3ViewEntry 3 }

		
--         1.3.6.1.4.1.37950.1.1.5.10.12.7.6.1.4
-- 1.3.6.1.4.1.37950.1.1.5.10.12.7.6.1.4
-- 1.3.6.1.4.1.37950.1.1.5.10.12.7.6.1.4
-- 1.3.6.1.4.1.37950.1.1.5.10.12.7.6.1.4
-- 1.3.6.1.4.1.37950.1.1.5.10.12.7.6.1.4
-- 1.3.6.1.4.1.37950.1.1.5.10.12.7.6.1.4
-- 1.3.6.1.4.1.37950.1.1.5.10.12.7.6.1.4
-- 1.3.6.1.4.1.37950.1.1.5.10.12.7.6.1.4
		-- 1.3.6.1.4.1.37950.1.1.5.10.12.7.6.1.4
		snmpv3ViewType OBJECT-TYPE
			SYNTAX INTEGER
				{
				include(1),
				exclude(2)
				}
			MAX-ACCESS read-only
			STATUS current
			DESCRIPTION
				"Description."
			::= { snmpv3ViewEntry 4 }

		
--         1.3.6.1.4.1.37950.1.1.5.10.12.7.7
-- 1.3.6.1.4.1.37950.1.1.5.10.12.7.7
-- 1.3.6.1.4.1.37950.1.1.5.10.12.7.7
-- 1.3.6.1.4.1.37950.1.1.5.10.12.7.7
-- 1.3.6.1.4.1.37950.1.1.5.10.12.7.7
-- 1.3.6.1.4.1.37950.1.1.5.10.12.7.7
-- 1.3.6.1.4.1.37950.1.1.5.10.12.7.7
-- 1.3.6.1.4.1.37950.1.1.5.10.12.7.7
		-- 1.3.6.1.4.1.37950.1.1.5.10.12.7.7
		snmpv3GroupConfig OBJECT IDENTIFIER ::= { snmpCfg 7 }

		
--         1.3.6.1.4.1.37950.1.1.5.10.12.7.7.1
-- 1.3.6.1.4.1.37950.1.1.5.10.12.7.7.1
-- 1.3.6.1.4.1.37950.1.1.5.10.12.7.7.1
-- 1.3.6.1.4.1.37950.1.1.5.10.12.7.7.1
-- 1.3.6.1.4.1.37950.1.1.5.10.12.7.7.1
-- 1.3.6.1.4.1.37950.1.1.5.10.12.7.7.1
-- 1.3.6.1.4.1.37950.1.1.5.10.12.7.7.1
-- 1.3.6.1.4.1.37950.1.1.5.10.12.7.7.1
		-- 1.3.6.1.4.1.37950.1.1.5.10.12.7.7.1
		groupNameSetting OBJECT-TYPE
			SYNTAX OCTET STRING
			MAX-ACCESS read-write
			STATUS current
			DESCRIPTION
				"Description."
			::= { snmpv3GroupConfig 1 }

		
--         1.3.6.1.4.1.37950.1.1.5.10.12.7.7.2
-- 1.3.6.1.4.1.37950.1.1.5.10.12.7.7.2
-- 1.3.6.1.4.1.37950.1.1.5.10.12.7.7.2
-- 1.3.6.1.4.1.37950.1.1.5.10.12.7.7.2
-- 1.3.6.1.4.1.37950.1.1.5.10.12.7.7.2
-- 1.3.6.1.4.1.37950.1.1.5.10.12.7.7.2
-- 1.3.6.1.4.1.37950.1.1.5.10.12.7.7.2
-- 1.3.6.1.4.1.37950.1.1.5.10.12.7.7.2
		-- 1.3.6.1.4.1.37950.1.1.5.10.12.7.7.2
		accessLevelSetting OBJECT-TYPE
			SYNTAX INTEGER
				{
				noauth(1),
				authnopri(2),
				authpri(3)
				}
			MAX-ACCESS read-write
			STATUS current
			DESCRIPTION
				"Description."
			::= { snmpv3GroupConfig 2 }

		
--         1.3.6.1.4.1.37950.1.1.5.10.12.7.7.3
-- 1.3.6.1.4.1.37950.1.1.5.10.12.7.7.3
-- 1.3.6.1.4.1.37950.1.1.5.10.12.7.7.3
-- 1.3.6.1.4.1.37950.1.1.5.10.12.7.7.3
-- 1.3.6.1.4.1.37950.1.1.5.10.12.7.7.3
-- 1.3.6.1.4.1.37950.1.1.5.10.12.7.7.3
-- 1.3.6.1.4.1.37950.1.1.5.10.12.7.7.3
-- 1.3.6.1.4.1.37950.1.1.5.10.12.7.7.3
		-- 1.3.6.1.4.1.37950.1.1.5.10.12.7.7.3
		readViewSetting OBJECT-TYPE
			SYNTAX OCTET STRING
			MAX-ACCESS read-write
			STATUS current
			DESCRIPTION
				"Description."
			::= { snmpv3GroupConfig 3 }

		
--         1.3.6.1.4.1.37950.1.1.5.10.12.7.7.4
-- 1.3.6.1.4.1.37950.1.1.5.10.12.7.7.4
-- 1.3.6.1.4.1.37950.1.1.5.10.12.7.7.4
-- 1.3.6.1.4.1.37950.1.1.5.10.12.7.7.4
-- 1.3.6.1.4.1.37950.1.1.5.10.12.7.7.4
-- 1.3.6.1.4.1.37950.1.1.5.10.12.7.7.4
-- 1.3.6.1.4.1.37950.1.1.5.10.12.7.7.4
-- 1.3.6.1.4.1.37950.1.1.5.10.12.7.7.4
		-- 1.3.6.1.4.1.37950.1.1.5.10.12.7.7.4
		writeViewSetting OBJECT-TYPE
			SYNTAX OCTET STRING
			MAX-ACCESS read-write
			STATUS current
			DESCRIPTION
				"Description."
			::= { snmpv3GroupConfig 4 }

		
--         1.3.6.1.4.1.37950.1.1.5.10.12.7.7.5
-- 1.3.6.1.4.1.37950.1.1.5.10.12.7.7.5
-- 1.3.6.1.4.1.37950.1.1.5.10.12.7.7.5
-- 1.3.6.1.4.1.37950.1.1.5.10.12.7.7.5
-- 1.3.6.1.4.1.37950.1.1.5.10.12.7.7.5
-- 1.3.6.1.4.1.37950.1.1.5.10.12.7.7.5
-- 1.3.6.1.4.1.37950.1.1.5.10.12.7.7.5
-- 1.3.6.1.4.1.37950.1.1.5.10.12.7.7.5
		-- 1.3.6.1.4.1.37950.1.1.5.10.12.7.7.5
		notifyViewSetting OBJECT-TYPE
			SYNTAX OCTET STRING
			MAX-ACCESS read-write
			STATUS current
			DESCRIPTION
				"Description."
			::= { snmpv3GroupConfig 5 }

		
--         1.3.6.1.4.1.37950.1.1.5.10.12.7.7.6
-- 1.3.6.1.4.1.37950.1.1.5.10.12.7.7.6
-- 1.3.6.1.4.1.37950.1.1.5.10.12.7.7.6
-- 1.3.6.1.4.1.37950.1.1.5.10.12.7.7.6
-- 1.3.6.1.4.1.37950.1.1.5.10.12.7.7.6
-- 1.3.6.1.4.1.37950.1.1.5.10.12.7.7.6
-- 1.3.6.1.4.1.37950.1.1.5.10.12.7.7.6
-- 1.3.6.1.4.1.37950.1.1.5.10.12.7.7.6
		-- 1.3.6.1.4.1.37950.1.1.5.10.12.7.7.6
		groupCommit OBJECT-TYPE
			SYNTAX INTEGER
				{
				add(1),
				del(2)
				}
			MAX-ACCESS read-write
			STATUS current
			DESCRIPTION
				"Description."
			::= { snmpv3GroupConfig 6 }

		
--         1.3.6.1.4.1.37950.1.1.5.10.12.7.8
-- 1.3.6.1.4.1.37950.1.1.5.10.12.7.8
-- 1.3.6.1.4.1.37950.1.1.5.10.12.7.8
-- 1.3.6.1.4.1.37950.1.1.5.10.12.7.8
-- 1.3.6.1.4.1.37950.1.1.5.10.12.7.8
-- 1.3.6.1.4.1.37950.1.1.5.10.12.7.8
-- 1.3.6.1.4.1.37950.1.1.5.10.12.7.8
-- 1.3.6.1.4.1.37950.1.1.5.10.12.7.8
		-- 1.3.6.1.4.1.37950.1.1.5.10.12.7.8
		snmpv3GroupTable OBJECT-TYPE
			SYNTAX SEQUENCE OF Snmpv3GroupEntry
			MAX-ACCESS not-accessible
			STATUS current
			DESCRIPTION
				"Description."
			::= { snmpCfg 8 }

		
--         1.3.6.1.4.1.37950.1.1.5.10.12.7.8.1
-- 1.3.6.1.4.1.37950.1.1.5.10.12.7.8.1
-- 1.3.6.1.4.1.37950.1.1.5.10.12.7.8.1
-- 1.3.6.1.4.1.37950.1.1.5.10.12.7.8.1
-- 1.3.6.1.4.1.37950.1.1.5.10.12.7.8.1
-- 1.3.6.1.4.1.37950.1.1.5.10.12.7.8.1
-- 1.3.6.1.4.1.37950.1.1.5.10.12.7.8.1
-- 1.3.6.1.4.1.37950.1.1.5.10.12.7.8.1
		-- 1.3.6.1.4.1.37950.1.1.5.10.12.7.8.1
		snmpv3GroupEntry OBJECT-TYPE
			SYNTAX Snmpv3GroupEntry
			MAX-ACCESS not-accessible
			STATUS current
			DESCRIPTION
				"Description."
			INDEX { snmpv3GroupIndex }
			::= { snmpv3GroupTable 1 }

		
		Snmpv3GroupEntry ::=
			SEQUENCE { 
				snmpv3GroupIndex
					Integer32,
				snmpv3GroupName
					OCTET STRING,
				snmpv3GroupAccessLevel
					INTEGER,
				snmpv3GroupReadView
					OCTET STRING,
				snmpv3GroupWriteView
					OCTET STRING,
				snmpv3GroupNotifyView
					OCTET STRING
			 }

--         1.3.6.1.4.1.37950.1.1.5.10.12.7.8.1.1
-- 1.3.6.1.4.1.37950.1.1.5.10.12.7.8.1.1
-- 1.3.6.1.4.1.37950.1.1.5.10.12.7.8.1.1
-- 1.3.6.1.4.1.37950.1.1.5.10.12.7.8.1.1
-- 1.3.6.1.4.1.37950.1.1.5.10.12.7.8.1.1
-- 1.3.6.1.4.1.37950.1.1.5.10.12.7.8.1.1
-- 1.3.6.1.4.1.37950.1.1.5.10.12.7.8.1.1
-- 1.3.6.1.4.1.37950.1.1.5.10.12.7.8.1.1
		-- 1.3.6.1.4.1.37950.1.1.5.10.12.7.8.1.1
		snmpv3GroupIndex OBJECT-TYPE
			SYNTAX Integer32
			MAX-ACCESS read-only
			STATUS current
			DESCRIPTION
				"Description."
			::= { snmpv3GroupEntry 1 }

		
--         1.3.6.1.4.1.37950.1.1.5.10.12.7.8.1.2
-- 1.3.6.1.4.1.37950.1.1.5.10.12.7.8.1.2
-- 1.3.6.1.4.1.37950.1.1.5.10.12.7.8.1.2
-- 1.3.6.1.4.1.37950.1.1.5.10.12.7.8.1.2
-- 1.3.6.1.4.1.37950.1.1.5.10.12.7.8.1.2
-- 1.3.6.1.4.1.37950.1.1.5.10.12.7.8.1.2
-- 1.3.6.1.4.1.37950.1.1.5.10.12.7.8.1.2
-- 1.3.6.1.4.1.37950.1.1.5.10.12.7.8.1.2
		-- 1.3.6.1.4.1.37950.1.1.5.10.12.7.8.1.2
		snmpv3GroupName OBJECT-TYPE
			SYNTAX OCTET STRING
			MAX-ACCESS read-only
			STATUS current
			DESCRIPTION
				"Description."
			::= { snmpv3GroupEntry 2 }

		
--         1.3.6.1.4.1.37950.1.1.5.10.12.7.8.1.3
-- 1.3.6.1.4.1.37950.1.1.5.10.12.7.8.1.3
-- 1.3.6.1.4.1.37950.1.1.5.10.12.7.8.1.3
-- 1.3.6.1.4.1.37950.1.1.5.10.12.7.8.1.3
-- 1.3.6.1.4.1.37950.1.1.5.10.12.7.8.1.3
-- 1.3.6.1.4.1.37950.1.1.5.10.12.7.8.1.3
-- 1.3.6.1.4.1.37950.1.1.5.10.12.7.8.1.3
-- 1.3.6.1.4.1.37950.1.1.5.10.12.7.8.1.3
		-- 1.3.6.1.4.1.37950.1.1.5.10.12.7.8.1.3
		snmpv3GroupAccessLevel OBJECT-TYPE
			SYNTAX INTEGER
				{
				noauth(1),
				authnopri(2),
				authpri(3)
				}
			MAX-ACCESS read-only
			STATUS current
			DESCRIPTION
				"Description."
			::= { snmpv3GroupEntry 3 }

		
--         1.3.6.1.4.1.37950.1.1.5.10.12.7.8.1.4
-- 1.3.6.1.4.1.37950.1.1.5.10.12.7.8.1.4
-- 1.3.6.1.4.1.37950.1.1.5.10.12.7.8.1.4
-- 1.3.6.1.4.1.37950.1.1.5.10.12.7.8.1.4
-- 1.3.6.1.4.1.37950.1.1.5.10.12.7.8.1.4
-- 1.3.6.1.4.1.37950.1.1.5.10.12.7.8.1.4
-- 1.3.6.1.4.1.37950.1.1.5.10.12.7.8.1.4
-- 1.3.6.1.4.1.37950.1.1.5.10.12.7.8.1.4
		-- 1.3.6.1.4.1.37950.1.1.5.10.12.7.8.1.4
		snmpv3GroupReadView OBJECT-TYPE
			SYNTAX OCTET STRING
			MAX-ACCESS read-only
			STATUS current
			DESCRIPTION
				"Description."
			::= { snmpv3GroupEntry 4 }

		
--         1.3.6.1.4.1.37950.1.1.5.10.12.7.8.1.5
-- 1.3.6.1.4.1.37950.1.1.5.10.12.7.8.1.5
-- 1.3.6.1.4.1.37950.1.1.5.10.12.7.8.1.5
-- 1.3.6.1.4.1.37950.1.1.5.10.12.7.8.1.5
-- 1.3.6.1.4.1.37950.1.1.5.10.12.7.8.1.5
-- 1.3.6.1.4.1.37950.1.1.5.10.12.7.8.1.5
-- 1.3.6.1.4.1.37950.1.1.5.10.12.7.8.1.5
-- 1.3.6.1.4.1.37950.1.1.5.10.12.7.8.1.5
		-- 1.3.6.1.4.1.37950.1.1.5.10.12.7.8.1.5
		snmpv3GroupWriteView OBJECT-TYPE
			SYNTAX OCTET STRING
			MAX-ACCESS read-only
			STATUS current
			DESCRIPTION
				"Description."
			::= { snmpv3GroupEntry 5 }

		
--         1.3.6.1.4.1.37950.1.1.5.10.12.7.8.1.6
-- 1.3.6.1.4.1.37950.1.1.5.10.12.7.8.1.6
-- 1.3.6.1.4.1.37950.1.1.5.10.12.7.8.1.6
-- 1.3.6.1.4.1.37950.1.1.5.10.12.7.8.1.6
-- 1.3.6.1.4.1.37950.1.1.5.10.12.7.8.1.6
-- 1.3.6.1.4.1.37950.1.1.5.10.12.7.8.1.6
-- 1.3.6.1.4.1.37950.1.1.5.10.12.7.8.1.6
-- 1.3.6.1.4.1.37950.1.1.5.10.12.7.8.1.6
		-- 1.3.6.1.4.1.37950.1.1.5.10.12.7.8.1.6
		snmpv3GroupNotifyView OBJECT-TYPE
			SYNTAX OCTET STRING
			MAX-ACCESS read-only
			STATUS current
			DESCRIPTION
				"Description."
			::= { snmpv3GroupEntry 6 }

		
--         1.3.6.1.4.1.37950.1.1.5.10.12.7.9
-- 1.3.6.1.4.1.37950.1.1.5.10.12.7.9
-- 1.3.6.1.4.1.37950.1.1.5.10.12.7.9
-- 1.3.6.1.4.1.37950.1.1.5.10.12.7.9
-- 1.3.6.1.4.1.37950.1.1.5.10.12.7.9
-- 1.3.6.1.4.1.37950.1.1.5.10.12.7.9
-- 1.3.6.1.4.1.37950.1.1.5.10.12.7.9
-- 1.3.6.1.4.1.37950.1.1.5.10.12.7.9
		-- 1.3.6.1.4.1.37950.1.1.5.10.12.7.9
		snmpv3UserConfig OBJECT IDENTIFIER ::= { snmpCfg 9 }

		
--         1.3.6.1.4.1.37950.1.1.5.10.12.7.9.1
-- 1.3.6.1.4.1.37950.1.1.5.10.12.7.9.1
-- 1.3.6.1.4.1.37950.1.1.5.10.12.7.9.1
-- 1.3.6.1.4.1.37950.1.1.5.10.12.7.9.1
-- 1.3.6.1.4.1.37950.1.1.5.10.12.7.9.1
-- 1.3.6.1.4.1.37950.1.1.5.10.12.7.9.1
-- 1.3.6.1.4.1.37950.1.1.5.10.12.7.9.1
-- 1.3.6.1.4.1.37950.1.1.5.10.12.7.9.1
		-- 1.3.6.1.4.1.37950.1.1.5.10.12.7.9.1
		userName OBJECT-TYPE
			SYNTAX OCTET STRING
			MAX-ACCESS read-write
			STATUS current
			DESCRIPTION
				"Description."
			::= { snmpv3UserConfig 1 }

		
--         1.3.6.1.4.1.37950.1.1.5.10.12.7.9.2
-- 1.3.6.1.4.1.37950.1.1.5.10.12.7.9.2
-- 1.3.6.1.4.1.37950.1.1.5.10.12.7.9.2
-- 1.3.6.1.4.1.37950.1.1.5.10.12.7.9.2
-- 1.3.6.1.4.1.37950.1.1.5.10.12.7.9.2
-- 1.3.6.1.4.1.37950.1.1.5.10.12.7.9.2
-- 1.3.6.1.4.1.37950.1.1.5.10.12.7.9.2
-- 1.3.6.1.4.1.37950.1.1.5.10.12.7.9.2
		-- 1.3.6.1.4.1.37950.1.1.5.10.12.7.9.2
		groupName OBJECT-TYPE
			SYNTAX OCTET STRING
			MAX-ACCESS read-write
			STATUS current
			DESCRIPTION
				"Description."
			::= { snmpv3UserConfig 2 }

		
--         1.3.6.1.4.1.37950.1.1.5.10.12.7.9.3
-- 1.3.6.1.4.1.37950.1.1.5.10.12.7.9.3
-- 1.3.6.1.4.1.37950.1.1.5.10.12.7.9.3
-- 1.3.6.1.4.1.37950.1.1.5.10.12.7.9.3
-- 1.3.6.1.4.1.37950.1.1.5.10.12.7.9.3
-- 1.3.6.1.4.1.37950.1.1.5.10.12.7.9.3
-- 1.3.6.1.4.1.37950.1.1.5.10.12.7.9.3
-- 1.3.6.1.4.1.37950.1.1.5.10.12.7.9.3
		-- 1.3.6.1.4.1.37950.1.1.5.10.12.7.9.3
		authProtocol OBJECT-TYPE
			SYNTAX INTEGER
				{
				none(1),
				md5(2),
				sha(3)
				}
			MAX-ACCESS read-write
			STATUS current
			DESCRIPTION
				"Description."
			::= { snmpv3UserConfig 3 }

		
--         1.3.6.1.4.1.37950.1.1.5.10.12.7.9.4
-- 1.3.6.1.4.1.37950.1.1.5.10.12.7.9.4
-- 1.3.6.1.4.1.37950.1.1.5.10.12.7.9.4
-- 1.3.6.1.4.1.37950.1.1.5.10.12.7.9.4
-- 1.3.6.1.4.1.37950.1.1.5.10.12.7.9.4
-- 1.3.6.1.4.1.37950.1.1.5.10.12.7.9.4
-- 1.3.6.1.4.1.37950.1.1.5.10.12.7.9.4
-- 1.3.6.1.4.1.37950.1.1.5.10.12.7.9.4
		-- 1.3.6.1.4.1.37950.1.1.5.10.12.7.9.4
		authPassword OBJECT-TYPE
			SYNTAX OCTET STRING
			MAX-ACCESS read-write
			STATUS current
			DESCRIPTION
				"Description."
			::= { snmpv3UserConfig 4 }

		
--         1.3.6.1.4.1.37950.1.1.5.10.12.7.9.5
-- 1.3.6.1.4.1.37950.1.1.5.10.12.7.9.5
-- 1.3.6.1.4.1.37950.1.1.5.10.12.7.9.5
-- 1.3.6.1.4.1.37950.1.1.5.10.12.7.9.5
-- 1.3.6.1.4.1.37950.1.1.5.10.12.7.9.5
-- 1.3.6.1.4.1.37950.1.1.5.10.12.7.9.5
-- 1.3.6.1.4.1.37950.1.1.5.10.12.7.9.5
-- 1.3.6.1.4.1.37950.1.1.5.10.12.7.9.5
		-- 1.3.6.1.4.1.37950.1.1.5.10.12.7.9.5
		privateType OBJECT-TYPE
			SYNTAX INTEGER
				{
				none(1),
				cbc-des(2)
				}
			MAX-ACCESS read-write
			STATUS current
			DESCRIPTION
				"Description."
			::= { snmpv3UserConfig 5 }

		
--         1.3.6.1.4.1.37950.1.1.5.10.12.7.9.6
-- 1.3.6.1.4.1.37950.1.1.5.10.12.7.9.6
-- 1.3.6.1.4.1.37950.1.1.5.10.12.7.9.6
-- 1.3.6.1.4.1.37950.1.1.5.10.12.7.9.6
-- 1.3.6.1.4.1.37950.1.1.5.10.12.7.9.6
-- 1.3.6.1.4.1.37950.1.1.5.10.12.7.9.6
-- 1.3.6.1.4.1.37950.1.1.5.10.12.7.9.6
-- 1.3.6.1.4.1.37950.1.1.5.10.12.7.9.6
		-- 1.3.6.1.4.1.37950.1.1.5.10.12.7.9.6
		privatePassword OBJECT-TYPE
			SYNTAX OCTET STRING
			MAX-ACCESS read-write
			STATUS current
			DESCRIPTION
				"Description."
			::= { snmpv3UserConfig 6 }

		
--         1.3.6.1.4.1.37950.1.1.5.10.12.7.9.7
-- 1.3.6.1.4.1.37950.1.1.5.10.12.7.9.7
-- 1.3.6.1.4.1.37950.1.1.5.10.12.7.9.7
-- 1.3.6.1.4.1.37950.1.1.5.10.12.7.9.7
-- 1.3.6.1.4.1.37950.1.1.5.10.12.7.9.7
-- 1.3.6.1.4.1.37950.1.1.5.10.12.7.9.7
-- 1.3.6.1.4.1.37950.1.1.5.10.12.7.9.7
-- 1.3.6.1.4.1.37950.1.1.5.10.12.7.9.7
		-- 1.3.6.1.4.1.37950.1.1.5.10.12.7.9.7
		snmpv3UserAction OBJECT-TYPE
			SYNTAX INTEGER
				{
				add(1),
				del(2)
				}
			MAX-ACCESS read-write
			STATUS current
			DESCRIPTION
				"Description."
			::= { snmpv3UserConfig 7 }

		
--         1.3.6.1.4.1.37950.1.1.5.10.12.7.10
-- 1.3.6.1.4.1.37950.1.1.5.10.12.7.10
-- 1.3.6.1.4.1.37950.1.1.5.10.12.7.10
-- 1.3.6.1.4.1.37950.1.1.5.10.12.7.10
-- 1.3.6.1.4.1.37950.1.1.5.10.12.7.10
-- 1.3.6.1.4.1.37950.1.1.5.10.12.7.10
-- 1.3.6.1.4.1.37950.1.1.5.10.12.7.10
-- 1.3.6.1.4.1.37950.1.1.5.10.12.7.10
		-- 1.3.6.1.4.1.37950.1.1.5.10.12.7.10
		snmpv3UserTable OBJECT-TYPE
			SYNTAX SEQUENCE OF Snmpv3UserEntry
			MAX-ACCESS not-accessible
			STATUS current
			DESCRIPTION
				"Description."
			::= { snmpCfg 10 }

		
--         1.3.6.1.4.1.37950.1.1.5.10.12.7.10.1
-- 1.3.6.1.4.1.37950.1.1.5.10.12.7.10.1
-- 1.3.6.1.4.1.37950.1.1.5.10.12.7.10.1
-- 1.3.6.1.4.1.37950.1.1.5.10.12.7.10.1
-- 1.3.6.1.4.1.37950.1.1.5.10.12.7.10.1
-- 1.3.6.1.4.1.37950.1.1.5.10.12.7.10.1
-- 1.3.6.1.4.1.37950.1.1.5.10.12.7.10.1
-- 1.3.6.1.4.1.37950.1.1.5.10.12.7.10.1
		-- 1.3.6.1.4.1.37950.1.1.5.10.12.7.10.1
		snmpv3UserEntry OBJECT-TYPE
			SYNTAX Snmpv3UserEntry
			MAX-ACCESS not-accessible
			STATUS current
			DESCRIPTION
				"Description."
			INDEX { snmpv3UserIndex }
			::= { snmpv3UserTable 1 }

		
		Snmpv3UserEntry ::=
			SEQUENCE { 
				snmpv3UserIndex
					Integer32,
				snmpv3UserName
					OCTET STRING,
				snmpv3UserGroupName
					OCTET STRING,
				snmpv3UserAuthType
					INTEGER,
				snmpv3UserPrivateType
					INTEGER
			 }

--         1.3.6.1.4.1.37950.1.1.5.10.12.7.10.1.1
-- 1.3.6.1.4.1.37950.1.1.5.10.12.7.10.1.1
-- 1.3.6.1.4.1.37950.1.1.5.10.12.7.10.1.1
-- 1.3.6.1.4.1.37950.1.1.5.10.12.7.10.1.1
-- 1.3.6.1.4.1.37950.1.1.5.10.12.7.10.1.1
-- 1.3.6.1.4.1.37950.1.1.5.10.12.7.10.1.1
-- 1.3.6.1.4.1.37950.1.1.5.10.12.7.10.1.1
-- 1.3.6.1.4.1.37950.1.1.5.10.12.7.10.1.1
		-- 1.3.6.1.4.1.37950.1.1.5.10.12.7.10.1.1
		snmpv3UserIndex OBJECT-TYPE
			SYNTAX Integer32
			MAX-ACCESS read-only
			STATUS current
			DESCRIPTION
				"Description."
			::= { snmpv3UserEntry 1 }

		
--         1.3.6.1.4.1.37950.1.1.5.10.12.7.10.1.2
-- 1.3.6.1.4.1.37950.1.1.5.10.12.7.10.1.2
-- 1.3.6.1.4.1.37950.1.1.5.10.12.7.10.1.2
-- 1.3.6.1.4.1.37950.1.1.5.10.12.7.10.1.2
-- 1.3.6.1.4.1.37950.1.1.5.10.12.7.10.1.2
-- 1.3.6.1.4.1.37950.1.1.5.10.12.7.10.1.2
-- 1.3.6.1.4.1.37950.1.1.5.10.12.7.10.1.2
-- 1.3.6.1.4.1.37950.1.1.5.10.12.7.10.1.2
		-- 1.3.6.1.4.1.37950.1.1.5.10.12.7.10.1.2
		snmpv3UserName OBJECT-TYPE
			SYNTAX OCTET STRING
			MAX-ACCESS read-only
			STATUS current
			DESCRIPTION
				"Description."
			::= { snmpv3UserEntry 2 }

		
--         1.3.6.1.4.1.37950.1.1.5.10.12.7.10.1.3
-- 1.3.6.1.4.1.37950.1.1.5.10.12.7.10.1.3
-- 1.3.6.1.4.1.37950.1.1.5.10.12.7.10.1.3
-- 1.3.6.1.4.1.37950.1.1.5.10.12.7.10.1.3
-- 1.3.6.1.4.1.37950.1.1.5.10.12.7.10.1.3
-- 1.3.6.1.4.1.37950.1.1.5.10.12.7.10.1.3
-- 1.3.6.1.4.1.37950.1.1.5.10.12.7.10.1.3
-- 1.3.6.1.4.1.37950.1.1.5.10.12.7.10.1.3
		-- 1.3.6.1.4.1.37950.1.1.5.10.12.7.10.1.3
		snmpv3UserGroupName OBJECT-TYPE
			SYNTAX OCTET STRING
			MAX-ACCESS read-only
			STATUS current
			DESCRIPTION
				"Description."
			::= { snmpv3UserEntry 3 }

		
--         1.3.6.1.4.1.37950.1.1.5.10.12.7.10.1.4
-- 1.3.6.1.4.1.37950.1.1.5.10.12.7.10.1.4
-- 1.3.6.1.4.1.37950.1.1.5.10.12.7.10.1.4
-- 1.3.6.1.4.1.37950.1.1.5.10.12.7.10.1.4
-- 1.3.6.1.4.1.37950.1.1.5.10.12.7.10.1.4
-- 1.3.6.1.4.1.37950.1.1.5.10.12.7.10.1.4
-- 1.3.6.1.4.1.37950.1.1.5.10.12.7.10.1.4
-- 1.3.6.1.4.1.37950.1.1.5.10.12.7.10.1.4
		-- 1.3.6.1.4.1.37950.1.1.5.10.12.7.10.1.4
		snmpv3UserAuthType OBJECT-TYPE
			SYNTAX INTEGER
				{
				none(1),
				md5(2),
				sha(3)
				}
			MAX-ACCESS read-write
			STATUS current
			DESCRIPTION
				"Description."
			::= { snmpv3UserEntry 4 }

		
--         1.3.6.1.4.1.37950.1.1.5.10.12.7.10.1.5
-- 1.3.6.1.4.1.37950.1.1.5.10.12.7.10.1.5
-- 1.3.6.1.4.1.37950.1.1.5.10.12.7.10.1.5
-- 1.3.6.1.4.1.37950.1.1.5.10.12.7.10.1.5
-- 1.3.6.1.4.1.37950.1.1.5.10.12.7.10.1.5
-- 1.3.6.1.4.1.37950.1.1.5.10.12.7.10.1.5
-- 1.3.6.1.4.1.37950.1.1.5.10.12.7.10.1.5
-- 1.3.6.1.4.1.37950.1.1.5.10.12.7.10.1.5
		-- 1.3.6.1.4.1.37950.1.1.5.10.12.7.10.1.5
		snmpv3UserPrivateType OBJECT-TYPE
			SYNTAX INTEGER
				{
				none(1),
				cbc-des(2)
				}
			MAX-ACCESS read-only
			STATUS current
			DESCRIPTION
				"Description."
			::= { snmpv3UserEntry 5 }

		
--         1.3.6.1.4.1.37950.1.1.5.10.12.7.11
-- 1.3.6.1.4.1.37950.1.1.5.10.12.7.11
-- 1.3.6.1.4.1.37950.1.1.5.10.12.7.11
-- 1.3.6.1.4.1.37950.1.1.5.10.12.7.11
-- 1.3.6.1.4.1.37950.1.1.5.10.12.7.11
-- 1.3.6.1.4.1.37950.1.1.5.10.12.7.11
-- 1.3.6.1.4.1.37950.1.1.5.10.12.7.11
-- 1.3.6.1.4.1.37950.1.1.5.10.12.7.11
		-- 1.3.6.1.4.1.37950.1.1.5.10.12.7.11
		snmpv3TrapConfig OBJECT IDENTIFIER ::= { snmpCfg 11 }

		
--         1.3.6.1.4.1.37950.1.1.5.10.12.7.11.1
-- 1.3.6.1.4.1.37950.1.1.5.10.12.7.11.1
-- 1.3.6.1.4.1.37950.1.1.5.10.12.7.11.1
-- 1.3.6.1.4.1.37950.1.1.5.10.12.7.11.1
-- 1.3.6.1.4.1.37950.1.1.5.10.12.7.11.1
-- 1.3.6.1.4.1.37950.1.1.5.10.12.7.11.1
-- 1.3.6.1.4.1.37950.1.1.5.10.12.7.11.1
-- 1.3.6.1.4.1.37950.1.1.5.10.12.7.11.1
		-- 1.3.6.1.4.1.37950.1.1.5.10.12.7.11.1
		snmpv3trapHostIPSetting OBJECT-TYPE
			SYNTAX OCTET STRING
			MAX-ACCESS read-write
			STATUS current
			DESCRIPTION
				"Description."
			::= { snmpv3TrapConfig 1 }

		
--         1.3.6.1.4.1.37950.1.1.5.10.12.7.11.2
-- 1.3.6.1.4.1.37950.1.1.5.10.12.7.11.2
-- 1.3.6.1.4.1.37950.1.1.5.10.12.7.11.2
-- 1.3.6.1.4.1.37950.1.1.5.10.12.7.11.2
-- 1.3.6.1.4.1.37950.1.1.5.10.12.7.11.2
-- 1.3.6.1.4.1.37950.1.1.5.10.12.7.11.2
-- 1.3.6.1.4.1.37950.1.1.5.10.12.7.11.2
-- 1.3.6.1.4.1.37950.1.1.5.10.12.7.11.2
		-- 1.3.6.1.4.1.37950.1.1.5.10.12.7.11.2
		snmpv3UDPPortSetting OBJECT-TYPE
			SYNTAX Integer32 (0..65535)
			MAX-ACCESS read-write
			STATUS current
			DESCRIPTION
				"Description."
			::= { snmpv3TrapConfig 2 }

		
--         1.3.6.1.4.1.37950.1.1.5.10.12.7.11.3
-- 1.3.6.1.4.1.37950.1.1.5.10.12.7.11.3
-- 1.3.6.1.4.1.37950.1.1.5.10.12.7.11.3
-- 1.3.6.1.4.1.37950.1.1.5.10.12.7.11.3
-- 1.3.6.1.4.1.37950.1.1.5.10.12.7.11.3
-- 1.3.6.1.4.1.37950.1.1.5.10.12.7.11.3
-- 1.3.6.1.4.1.37950.1.1.5.10.12.7.11.3
-- 1.3.6.1.4.1.37950.1.1.5.10.12.7.11.3
		-- 1.3.6.1.4.1.37950.1.1.5.10.12.7.11.3
		snmpv3trapUserName OBJECT-TYPE
			SYNTAX OCTET STRING
			MAX-ACCESS read-write
			STATUS current
			DESCRIPTION
				"Description."
			::= { snmpv3TrapConfig 3 }

		
--         1.3.6.1.4.1.37950.1.1.5.10.12.7.11.4
-- 1.3.6.1.4.1.37950.1.1.5.10.12.7.11.4
-- 1.3.6.1.4.1.37950.1.1.5.10.12.7.11.4
-- 1.3.6.1.4.1.37950.1.1.5.10.12.7.11.4
-- 1.3.6.1.4.1.37950.1.1.5.10.12.7.11.4
-- 1.3.6.1.4.1.37950.1.1.5.10.12.7.11.4
-- 1.3.6.1.4.1.37950.1.1.5.10.12.7.11.4
-- 1.3.6.1.4.1.37950.1.1.5.10.12.7.11.4
		-- 1.3.6.1.4.1.37950.1.1.5.10.12.7.11.4
		snmpv3trapUserLevel OBJECT-TYPE
			SYNTAX INTEGER
				{
				noauth(1),
				authnoprivate(2),
				authprivate(3)
				}
			MAX-ACCESS read-write
			STATUS current
			DESCRIPTION
				"Description."
			::= { snmpv3TrapConfig 4 }

		
--         1.3.6.1.4.1.37950.1.1.5.10.12.7.11.5
-- 1.3.6.1.4.1.37950.1.1.5.10.12.7.11.5
-- 1.3.6.1.4.1.37950.1.1.5.10.12.7.11.5
-- 1.3.6.1.4.1.37950.1.1.5.10.12.7.11.5
-- 1.3.6.1.4.1.37950.1.1.5.10.12.7.11.5
-- 1.3.6.1.4.1.37950.1.1.5.10.12.7.11.5
-- 1.3.6.1.4.1.37950.1.1.5.10.12.7.11.5
-- 1.3.6.1.4.1.37950.1.1.5.10.12.7.11.5
		-- 1.3.6.1.4.1.37950.1.1.5.10.12.7.11.5
		snmpv3tagList OBJECT-TYPE
			SYNTAX INTEGER
				{
				trap(1),
				inform(2)
				}
			MAX-ACCESS read-write
			STATUS current
			DESCRIPTION
				"Description."
			::= { snmpv3TrapConfig 5 }

		
--         1.3.6.1.4.1.37950.1.1.5.10.12.7.11.6
-- 1.3.6.1.4.1.37950.1.1.5.10.12.7.11.6
-- 1.3.6.1.4.1.37950.1.1.5.10.12.7.11.6
-- 1.3.6.1.4.1.37950.1.1.5.10.12.7.11.6
-- 1.3.6.1.4.1.37950.1.1.5.10.12.7.11.6
-- 1.3.6.1.4.1.37950.1.1.5.10.12.7.11.6
-- 1.3.6.1.4.1.37950.1.1.5.10.12.7.11.6
-- 1.3.6.1.4.1.37950.1.1.5.10.12.7.11.6
		-- 1.3.6.1.4.1.37950.1.1.5.10.12.7.11.6
		snmpv3Timeout OBJECT-TYPE
			SYNTAX Unsigned32
			MAX-ACCESS read-write
			STATUS current
			DESCRIPTION
				"Description."
			::= { snmpv3TrapConfig 6 }

		
--         1.3.6.1.4.1.37950.1.1.5.10.12.7.11.7
-- 1.3.6.1.4.1.37950.1.1.5.10.12.7.11.7
-- 1.3.6.1.4.1.37950.1.1.5.10.12.7.11.7
-- 1.3.6.1.4.1.37950.1.1.5.10.12.7.11.7
-- 1.3.6.1.4.1.37950.1.1.5.10.12.7.11.7
-- 1.3.6.1.4.1.37950.1.1.5.10.12.7.11.7
-- 1.3.6.1.4.1.37950.1.1.5.10.12.7.11.7
-- 1.3.6.1.4.1.37950.1.1.5.10.12.7.11.7
		-- 1.3.6.1.4.1.37950.1.1.5.10.12.7.11.7
		snmpv3RetryCount OBJECT-TYPE
			SYNTAX Integer32
			MAX-ACCESS read-write
			STATUS current
			DESCRIPTION
				"Description."
			::= { snmpv3TrapConfig 7 }

		
--         1.3.6.1.4.1.37950.1.1.5.10.12.7.11.8
-- 1.3.6.1.4.1.37950.1.1.5.10.12.7.11.8
-- 1.3.6.1.4.1.37950.1.1.5.10.12.7.11.8
-- 1.3.6.1.4.1.37950.1.1.5.10.12.7.11.8
-- 1.3.6.1.4.1.37950.1.1.5.10.12.7.11.8
-- 1.3.6.1.4.1.37950.1.1.5.10.12.7.11.8
-- 1.3.6.1.4.1.37950.1.1.5.10.12.7.11.8
-- 1.3.6.1.4.1.37950.1.1.5.10.12.7.11.8
		-- 1.3.6.1.4.1.37950.1.1.5.10.12.7.11.8
		snmpv3trapAction OBJECT-TYPE
			SYNTAX INTEGER
				{
				add(1),
				delete(2)
				}
			MAX-ACCESS read-write
			STATUS current
			DESCRIPTION
				"Description."
			::= { snmpv3TrapConfig 8 }

		
--         1.3.6.1.4.1.37950.1.1.5.10.12.7.12
-- 1.3.6.1.4.1.37950.1.1.5.10.12.7.12
-- 1.3.6.1.4.1.37950.1.1.5.10.12.7.12
-- 1.3.6.1.4.1.37950.1.1.5.10.12.7.12
-- 1.3.6.1.4.1.37950.1.1.5.10.12.7.12
-- 1.3.6.1.4.1.37950.1.1.5.10.12.7.12
-- 1.3.6.1.4.1.37950.1.1.5.10.12.7.12
-- 1.3.6.1.4.1.37950.1.1.5.10.12.7.12
		-- 1.3.6.1.4.1.37950.1.1.5.10.12.7.12
		snmpv3TrapTable OBJECT-TYPE
			SYNTAX SEQUENCE OF Snmpv3TrapEntry
			MAX-ACCESS not-accessible
			STATUS current
			DESCRIPTION
				"Description."
			::= { snmpCfg 12 }

		
--         1.3.6.1.4.1.37950.1.1.5.10.12.7.12.1
-- 1.3.6.1.4.1.37950.1.1.5.10.12.7.12.1
-- 1.3.6.1.4.1.37950.1.1.5.10.12.7.12.1
-- 1.3.6.1.4.1.37950.1.1.5.10.12.7.12.1
-- 1.3.6.1.4.1.37950.1.1.5.10.12.7.12.1
-- 1.3.6.1.4.1.37950.1.1.5.10.12.7.12.1
-- 1.3.6.1.4.1.37950.1.1.5.10.12.7.12.1
-- 1.3.6.1.4.1.37950.1.1.5.10.12.7.12.1
		-- 1.3.6.1.4.1.37950.1.1.5.10.12.7.12.1
		snmpv3TrapEntry OBJECT-TYPE
			SYNTAX Snmpv3TrapEntry
			MAX-ACCESS not-accessible
			STATUS current
			DESCRIPTION
				"Description."
			INDEX { snmpv3TrapIndex }
			::= { snmpv3TrapTable 1 }

		
		Snmpv3TrapEntry ::=
			SEQUENCE { 
				snmpv3TrapIndex
					Integer32,
				snmpv3TrapHostIP
					OCTET STRING,
				snmpv3TrapUDPPort
					Integer32,
				snmpv3TrapVersion
					INTEGER,
				snmpv3TrapUserName
					OCTET STRING,
				snmpv3TrapTrapUserLevel
					INTEGER,
				snmpv3TrapTagList
					INTEGER,
				snmpv3TrapTimeout
					Unsigned32,
				snmpv3TrapRetryCount
					Integer32
			 }

--         1.3.6.1.4.1.37950.1.1.5.10.12.7.12.1.1
-- 1.3.6.1.4.1.37950.1.1.5.10.12.7.12.1.1
-- 1.3.6.1.4.1.37950.1.1.5.10.12.7.12.1.1
-- 1.3.6.1.4.1.37950.1.1.5.10.12.7.12.1.1
-- 1.3.6.1.4.1.37950.1.1.5.10.12.7.12.1.1
-- 1.3.6.1.4.1.37950.1.1.5.10.12.7.12.1.1
-- 1.3.6.1.4.1.37950.1.1.5.10.12.7.12.1.1
-- 1.3.6.1.4.1.37950.1.1.5.10.12.7.12.1.1
		-- 1.3.6.1.4.1.37950.1.1.5.10.12.7.12.1.1
		snmpv3TrapIndex OBJECT-TYPE
			SYNTAX Integer32
			MAX-ACCESS read-only
			STATUS current
			DESCRIPTION
				"Description."
			::= { snmpv3TrapEntry 1 }

		
--         1.3.6.1.4.1.37950.1.1.5.10.12.7.12.1.2
-- 1.3.6.1.4.1.37950.1.1.5.10.12.7.12.1.2
-- 1.3.6.1.4.1.37950.1.1.5.10.12.7.12.1.2
-- 1.3.6.1.4.1.37950.1.1.5.10.12.7.12.1.2
-- 1.3.6.1.4.1.37950.1.1.5.10.12.7.12.1.2
-- 1.3.6.1.4.1.37950.1.1.5.10.12.7.12.1.2
-- 1.3.6.1.4.1.37950.1.1.5.10.12.7.12.1.2
-- 1.3.6.1.4.1.37950.1.1.5.10.12.7.12.1.2
		-- 1.3.6.1.4.1.37950.1.1.5.10.12.7.12.1.2
		snmpv3TrapHostIP OBJECT-TYPE
			SYNTAX OCTET STRING
			MAX-ACCESS read-only
			STATUS deprecated
			DESCRIPTION
				"Description."
			::= { snmpv3TrapEntry 2 }

		
--         1.3.6.1.4.1.37950.1.1.5.10.12.7.12.1.3
-- 1.3.6.1.4.1.37950.1.1.5.10.12.7.12.1.3
-- 1.3.6.1.4.1.37950.1.1.5.10.12.7.12.1.3
-- 1.3.6.1.4.1.37950.1.1.5.10.12.7.12.1.3
-- 1.3.6.1.4.1.37950.1.1.5.10.12.7.12.1.3
-- 1.3.6.1.4.1.37950.1.1.5.10.12.7.12.1.3
-- 1.3.6.1.4.1.37950.1.1.5.10.12.7.12.1.3
-- 1.3.6.1.4.1.37950.1.1.5.10.12.7.12.1.3
		-- 1.3.6.1.4.1.37950.1.1.5.10.12.7.12.1.3
		snmpv3TrapUDPPort OBJECT-TYPE
			SYNTAX Integer32 (0..65535)
			MAX-ACCESS read-only
			STATUS current
			DESCRIPTION
				"Description."
			::= { snmpv3TrapEntry 3 }

		
--         1.3.6.1.4.1.37950.1.1.5.10.12.7.12.1.4
-- 1.3.6.1.4.1.37950.1.1.5.10.12.7.12.1.4
-- 1.3.6.1.4.1.37950.1.1.5.10.12.7.12.1.4
-- 1.3.6.1.4.1.37950.1.1.5.10.12.7.12.1.4
-- 1.3.6.1.4.1.37950.1.1.5.10.12.7.12.1.4
-- 1.3.6.1.4.1.37950.1.1.5.10.12.7.12.1.4
-- 1.3.6.1.4.1.37950.1.1.5.10.12.7.12.1.4
-- 1.3.6.1.4.1.37950.1.1.5.10.12.7.12.1.4
		-- 1.3.6.1.4.1.37950.1.1.5.10.12.7.12.1.4
		snmpv3TrapVersion OBJECT-TYPE
			SYNTAX INTEGER
				{
				v1(1),
				v2c(2),
				v3(3)
				}
			MAX-ACCESS read-only
			STATUS current
			DESCRIPTION
				"Description."
			::= { snmpv3TrapEntry 4 }

		
--         1.3.6.1.4.1.37950.1.1.5.10.12.7.12.1.5
-- 1.3.6.1.4.1.37950.1.1.5.10.12.7.12.1.5
-- 1.3.6.1.4.1.37950.1.1.5.10.12.7.12.1.5
-- 1.3.6.1.4.1.37950.1.1.5.10.12.7.12.1.5
-- 1.3.6.1.4.1.37950.1.1.5.10.12.7.12.1.5
-- 1.3.6.1.4.1.37950.1.1.5.10.12.7.12.1.5
-- 1.3.6.1.4.1.37950.1.1.5.10.12.7.12.1.5
-- 1.3.6.1.4.1.37950.1.1.5.10.12.7.12.1.5
		-- 1.3.6.1.4.1.37950.1.1.5.10.12.7.12.1.5
		snmpv3TrapUserName OBJECT-TYPE
			SYNTAX OCTET STRING
			MAX-ACCESS read-only
			STATUS current
			DESCRIPTION
				"Description."
			::= { snmpv3TrapEntry 5 }

		
--         1.3.6.1.4.1.37950.1.1.5.10.12.7.12.1.6
-- 1.3.6.1.4.1.37950.1.1.5.10.12.7.12.1.6
-- 1.3.6.1.4.1.37950.1.1.5.10.12.7.12.1.6
-- 1.3.6.1.4.1.37950.1.1.5.10.12.7.12.1.6
-- 1.3.6.1.4.1.37950.1.1.5.10.12.7.12.1.6
-- 1.3.6.1.4.1.37950.1.1.5.10.12.7.12.1.6
-- 1.3.6.1.4.1.37950.1.1.5.10.12.7.12.1.6
-- 1.3.6.1.4.1.37950.1.1.5.10.12.7.12.1.6
		-- 1.3.6.1.4.1.37950.1.1.5.10.12.7.12.1.6
		snmpv3TrapTrapUserLevel OBJECT-TYPE
			SYNTAX INTEGER
				{
				noauth(1),
				authnoprivate(2),
				authpprivate(3)
				}
			MAX-ACCESS read-only
			STATUS current
			DESCRIPTION
				"Description."
			::= { snmpv3TrapEntry 6 }

		
--         1.3.6.1.4.1.37950.1.1.5.10.12.7.12.1.7
-- 1.3.6.1.4.1.37950.1.1.5.10.12.7.12.1.7
-- 1.3.6.1.4.1.37950.1.1.5.10.12.7.12.1.7
-- 1.3.6.1.4.1.37950.1.1.5.10.12.7.12.1.7
-- 1.3.6.1.4.1.37950.1.1.5.10.12.7.12.1.7
-- 1.3.6.1.4.1.37950.1.1.5.10.12.7.12.1.7
-- 1.3.6.1.4.1.37950.1.1.5.10.12.7.12.1.7
-- 1.3.6.1.4.1.37950.1.1.5.10.12.7.12.1.7
		-- 1.3.6.1.4.1.37950.1.1.5.10.12.7.12.1.7
		snmpv3TrapTagList OBJECT-TYPE
			SYNTAX INTEGER
				{
				trap(1),
				inform(2)
				}
			MAX-ACCESS read-only
			STATUS current
			DESCRIPTION
				"Description."
			::= { snmpv3TrapEntry 7 }

		
--         1.3.6.1.4.1.37950.1.1.5.10.12.7.12.1.8
-- 1.3.6.1.4.1.37950.1.1.5.10.12.7.12.1.8
-- 1.3.6.1.4.1.37950.1.1.5.10.12.7.12.1.8
-- 1.3.6.1.4.1.37950.1.1.5.10.12.7.12.1.8
-- 1.3.6.1.4.1.37950.1.1.5.10.12.7.12.1.8
-- 1.3.6.1.4.1.37950.1.1.5.10.12.7.12.1.8
-- 1.3.6.1.4.1.37950.1.1.5.10.12.7.12.1.8
-- 1.3.6.1.4.1.37950.1.1.5.10.12.7.12.1.8
		-- 1.3.6.1.4.1.37950.1.1.5.10.12.7.12.1.8
		snmpv3TrapTimeout OBJECT-TYPE
			SYNTAX Unsigned32
			MAX-ACCESS read-only
			STATUS current
			DESCRIPTION
				"Description."
			::= { snmpv3TrapEntry 8 }

		
--         1.3.6.1.4.1.37950.1.1.5.10.12.7.12.1.9
-- 1.3.6.1.4.1.37950.1.1.5.10.12.7.12.1.9
-- 1.3.6.1.4.1.37950.1.1.5.10.12.7.12.1.9
-- 1.3.6.1.4.1.37950.1.1.5.10.12.7.12.1.9
-- 1.3.6.1.4.1.37950.1.1.5.10.12.7.12.1.9
-- 1.3.6.1.4.1.37950.1.1.5.10.12.7.12.1.9
-- 1.3.6.1.4.1.37950.1.1.5.10.12.7.12.1.9
-- 1.3.6.1.4.1.37950.1.1.5.10.12.7.12.1.9
		-- 1.3.6.1.4.1.37950.1.1.5.10.12.7.12.1.9
		snmpv3TrapRetryCount OBJECT-TYPE
			SYNTAX Integer32
			MAX-ACCESS read-only
			STATUS current
			DESCRIPTION
				"Description."
			::= { snmpv3TrapEntry 9 }

		
--         1.3.6.1.4.1.37950.1.1.5.10.12.7.13
-- 1.3.6.1.4.1.37950.1.1.5.10.12.7.13
-- 1.3.6.1.4.1.37950.1.1.5.10.12.7.13
-- 1.3.6.1.4.1.37950.1.1.5.10.12.7.13
-- 1.3.6.1.4.1.37950.1.1.5.10.12.7.13
-- 1.3.6.1.4.1.37950.1.1.5.10.12.7.13
-- 1.3.6.1.4.1.37950.1.1.5.10.12.7.13
-- 1.3.6.1.4.1.37950.1.1.5.10.12.7.13
		-- 1.3.6.1.4.1.37950.1.1.5.10.12.7.13
		snmpv1v2TrapIPv6Config OBJECT IDENTIFIER ::= { snmpCfg 13 }

		
--         1.3.6.1.4.1.37950.1.1.5.10.12.7.13.1
-- 1.3.6.1.4.1.37950.1.1.5.10.12.7.13.1
-- 1.3.6.1.4.1.37950.1.1.5.10.12.7.13.1
-- 1.3.6.1.4.1.37950.1.1.5.10.12.7.13.1
-- 1.3.6.1.4.1.37950.1.1.5.10.12.7.13.1
-- 1.3.6.1.4.1.37950.1.1.5.10.12.7.13.1
-- 1.3.6.1.4.1.37950.1.1.5.10.12.7.13.1
-- 1.3.6.1.4.1.37950.1.1.5.10.12.7.13.1
		-- 1.3.6.1.4.1.37950.1.1.5.10.12.7.13.1
		trapHostIpv6Setting OBJECT-TYPE
			SYNTAX OCTET STRING
			MAX-ACCESS read-write
			STATUS current
			DESCRIPTION
				"Description."
			::= { snmpv1v2TrapIPv6Config 1 }

		
--              snmpv1v2 trap IPv6 Address
-- 1.3.6.1.4.1.37950.1.1.5.10.12.7.13.2
-- 1.3.6.1.4.1.37950.1.1.5.10.12.7.13.2
-- 1.3.6.1.4.1.37950.1.1.5.10.12.7.13.2
-- 1.3.6.1.4.1.37950.1.1.5.10.12.7.13.2
-- 1.3.6.1.4.1.37950.1.1.5.10.12.7.13.2
-- 1.3.6.1.4.1.37950.1.1.5.10.12.7.13.2
-- 1.3.6.1.4.1.37950.1.1.5.10.12.7.13.2
-- 1.3.6.1.4.1.37950.1.1.5.10.12.7.13.2
		-- 1.3.6.1.4.1.37950.1.1.5.10.12.7.13.2
		trapIpv6UdpPortSetting OBJECT-TYPE
			SYNTAX Integer32 (0..65535)
			MAX-ACCESS read-write
			STATUS current
			DESCRIPTION
				"Description."
			::= { snmpv1v2TrapIPv6Config 2 }

		
--              snmpv1v2 trap udp port
-- 1.3.6.1.4.1.37950.1.1.5.10.12.7.13.3
-- 1.3.6.1.4.1.37950.1.1.5.10.12.7.13.3
-- 1.3.6.1.4.1.37950.1.1.5.10.12.7.13.3
-- 1.3.6.1.4.1.37950.1.1.5.10.12.7.13.3
-- 1.3.6.1.4.1.37950.1.1.5.10.12.7.13.3
-- 1.3.6.1.4.1.37950.1.1.5.10.12.7.13.3
-- 1.3.6.1.4.1.37950.1.1.5.10.12.7.13.3
-- 1.3.6.1.4.1.37950.1.1.5.10.12.7.13.3
		-- 1.3.6.1.4.1.37950.1.1.5.10.12.7.13.3
		trapIpv6CommunityNameSetting OBJECT-TYPE
			SYNTAX OCTET STRING
			MAX-ACCESS read-write
			STATUS current
			DESCRIPTION
				"Description."
			::= { snmpv1v2TrapIPv6Config 3 }

		
--              snmpv1v2 trap community name
-- 1.3.6.1.4.1.37950.1.1.5.10.12.7.13.4
-- 1.3.6.1.4.1.37950.1.1.5.10.12.7.13.4
-- 1.3.6.1.4.1.37950.1.1.5.10.12.7.13.4
-- 1.3.6.1.4.1.37950.1.1.5.10.12.7.13.4
-- 1.3.6.1.4.1.37950.1.1.5.10.12.7.13.4
-- 1.3.6.1.4.1.37950.1.1.5.10.12.7.13.4
-- 1.3.6.1.4.1.37950.1.1.5.10.12.7.13.4
-- 1.3.6.1.4.1.37950.1.1.5.10.12.7.13.4
		-- 1.3.6.1.4.1.37950.1.1.5.10.12.7.13.4
		trapIpv6VersionSetting OBJECT-TYPE
			SYNTAX INTEGER
				{
				snmp-v1(1),
				snmp-v2c(2)
				}
			MAX-ACCESS read-write
			STATUS current
			DESCRIPTION
				"Description."
			::= { snmpv1v2TrapIPv6Config 4 }

		
--              snmpv1v2 trap version
-- 1.3.6.1.4.1.37950.1.1.5.10.12.7.13.5
-- 1.3.6.1.4.1.37950.1.1.5.10.12.7.13.5
-- 1.3.6.1.4.1.37950.1.1.5.10.12.7.13.5
-- 1.3.6.1.4.1.37950.1.1.5.10.12.7.13.5
-- 1.3.6.1.4.1.37950.1.1.5.10.12.7.13.5
-- 1.3.6.1.4.1.37950.1.1.5.10.12.7.13.5
-- 1.3.6.1.4.1.37950.1.1.5.10.12.7.13.5
-- 1.3.6.1.4.1.37950.1.1.5.10.12.7.13.5
		-- 1.3.6.1.4.1.37950.1.1.5.10.12.7.13.5
		trapIpv6Action OBJECT-TYPE
			SYNTAX INTEGER
				{
				add(1),
				delete(2)
				}
			MAX-ACCESS read-write
			STATUS current
			DESCRIPTION
				"Description."
			::= { snmpv1v2TrapIPv6Config 5 }

		
--         1.3.6.1.4.1.37950.1.1.5.10.12.7.14
-- 1.3.6.1.4.1.37950.1.1.5.10.12.7.14
-- 1.3.6.1.4.1.37950.1.1.5.10.12.7.14
-- 1.3.6.1.4.1.37950.1.1.5.10.12.7.14
-- 1.3.6.1.4.1.37950.1.1.5.10.12.7.14
-- 1.3.6.1.4.1.37950.1.1.5.10.12.7.14
-- 1.3.6.1.4.1.37950.1.1.5.10.12.7.14
-- 1.3.6.1.4.1.37950.1.1.5.10.12.7.14
		-- 1.3.6.1.4.1.37950.1.1.5.10.12.7.14
		snmpv1v2TrapIPv6Table OBJECT-TYPE
			SYNTAX SEQUENCE OF Snmpv1v2TrapIPv6Entry
			MAX-ACCESS not-accessible
			STATUS current
			DESCRIPTION
				"Description."
			::= { snmpCfg 14 }

		
--         1.3.6.1.4.1.37950.1.1.5.10.12.7.14.1
-- 1.3.6.1.4.1.37950.1.1.5.10.12.7.14.1
-- 1.3.6.1.4.1.37950.1.1.5.10.12.7.14.1
-- 1.3.6.1.4.1.37950.1.1.5.10.12.7.14.1
-- 1.3.6.1.4.1.37950.1.1.5.10.12.7.14.1
-- 1.3.6.1.4.1.37950.1.1.5.10.12.7.14.1
-- 1.3.6.1.4.1.37950.1.1.5.10.12.7.14.1
-- 1.3.6.1.4.1.37950.1.1.5.10.12.7.14.1
		-- 1.3.6.1.4.1.37950.1.1.5.10.12.7.14.1
		snmpv1v2TrapIPv6Entry OBJECT-TYPE
			SYNTAX Snmpv1v2TrapIPv6Entry
			MAX-ACCESS not-accessible
			STATUS current
			DESCRIPTION
				"Description."
			INDEX { trapIPv6Index }
			::= { snmpv1v2TrapIPv6Table 1 }

		
		Snmpv1v2TrapIPv6Entry ::=
			SEQUENCE { 
				trapIPv6Index
					Integer32,
				trapHostIPv6
					OCTET STRING,
				trapIPv6UdpPort
					Integer32,
				trapIPv6CommunityName
					OCTET STRING,
				trapIPv6Version
					INTEGER
			 }

--         1.3.6.1.4.1.37950.1.1.5.10.12.7.14.1.1
-- 1.3.6.1.4.1.37950.1.1.5.10.12.7.14.1.1
-- 1.3.6.1.4.1.37950.1.1.5.10.12.7.14.1.1
-- 1.3.6.1.4.1.37950.1.1.5.10.12.7.14.1.1
-- 1.3.6.1.4.1.37950.1.1.5.10.12.7.14.1.1
-- 1.3.6.1.4.1.37950.1.1.5.10.12.7.14.1.1
-- 1.3.6.1.4.1.37950.1.1.5.10.12.7.14.1.1
-- 1.3.6.1.4.1.37950.1.1.5.10.12.7.14.1.1
		-- 1.3.6.1.4.1.37950.1.1.5.10.12.7.14.1.1
		trapIPv6Index OBJECT-TYPE
			SYNTAX Integer32
			MAX-ACCESS read-only
			STATUS current
			DESCRIPTION
				"Description."
			::= { snmpv1v2TrapIPv6Entry 1 }

		
--         1.3.6.1.4.1.37950.1.1.5.10.12.7.14.1.2
-- 1.3.6.1.4.1.37950.1.1.5.10.12.7.14.1.2
-- 1.3.6.1.4.1.37950.1.1.5.10.12.7.14.1.2
-- 1.3.6.1.4.1.37950.1.1.5.10.12.7.14.1.2
-- 1.3.6.1.4.1.37950.1.1.5.10.12.7.14.1.2
-- 1.3.6.1.4.1.37950.1.1.5.10.12.7.14.1.2
-- 1.3.6.1.4.1.37950.1.1.5.10.12.7.14.1.2
-- 1.3.6.1.4.1.37950.1.1.5.10.12.7.14.1.2
		-- 1.3.6.1.4.1.37950.1.1.5.10.12.7.14.1.2
		trapHostIPv6 OBJECT-TYPE
			SYNTAX OCTET STRING
			MAX-ACCESS read-only
			STATUS current
			DESCRIPTION
				"Description."
			::= { snmpv1v2TrapIPv6Entry 2 }

		
--         1.3.6.1.4.1.37950.1.1.5.10.12.7.14.1.3
-- 1.3.6.1.4.1.37950.1.1.5.10.12.7.14.1.3
-- 1.3.6.1.4.1.37950.1.1.5.10.12.7.14.1.3
-- 1.3.6.1.4.1.37950.1.1.5.10.12.7.14.1.3
-- 1.3.6.1.4.1.37950.1.1.5.10.12.7.14.1.3
-- 1.3.6.1.4.1.37950.1.1.5.10.12.7.14.1.3
-- 1.3.6.1.4.1.37950.1.1.5.10.12.7.14.1.3
-- 1.3.6.1.4.1.37950.1.1.5.10.12.7.14.1.3
		-- 1.3.6.1.4.1.37950.1.1.5.10.12.7.14.1.3
		trapIPv6UdpPort OBJECT-TYPE
			SYNTAX Integer32
			MAX-ACCESS read-only
			STATUS current
			DESCRIPTION
				"Description."
			::= { snmpv1v2TrapIPv6Entry 3 }

		
--         1.3.6.1.4.1.37950.1.1.5.10.12.7.14.1.4
-- 1.3.6.1.4.1.37950.1.1.5.10.12.7.14.1.4
-- 1.3.6.1.4.1.37950.1.1.5.10.12.7.14.1.4
-- 1.3.6.1.4.1.37950.1.1.5.10.12.7.14.1.4
-- 1.3.6.1.4.1.37950.1.1.5.10.12.7.14.1.4
-- 1.3.6.1.4.1.37950.1.1.5.10.12.7.14.1.4
-- 1.3.6.1.4.1.37950.1.1.5.10.12.7.14.1.4
-- 1.3.6.1.4.1.37950.1.1.5.10.12.7.14.1.4
		-- 1.3.6.1.4.1.37950.1.1.5.10.12.7.14.1.4
		trapIPv6CommunityName OBJECT-TYPE
			SYNTAX OCTET STRING
			MAX-ACCESS read-only
			STATUS current
			DESCRIPTION
				"Description."
			::= { snmpv1v2TrapIPv6Entry 4 }

		
--         1.3.6.1.4.1.37950.1.1.5.10.12.7.14.1.5
-- 1.3.6.1.4.1.37950.1.1.5.10.12.7.14.1.5
-- 1.3.6.1.4.1.37950.1.1.5.10.12.7.14.1.5
-- 1.3.6.1.4.1.37950.1.1.5.10.12.7.14.1.5
-- 1.3.6.1.4.1.37950.1.1.5.10.12.7.14.1.5
-- 1.3.6.1.4.1.37950.1.1.5.10.12.7.14.1.5
-- 1.3.6.1.4.1.37950.1.1.5.10.12.7.14.1.5
-- 1.3.6.1.4.1.37950.1.1.5.10.12.7.14.1.5
		-- 1.3.6.1.4.1.37950.1.1.5.10.12.7.14.1.5
		trapIPv6Version OBJECT-TYPE
			SYNTAX INTEGER
				{
				snmp-v1(1),
				snmp-v2c(2)
				}
			MAX-ACCESS read-only
			STATUS current
			DESCRIPTION
				"Description."
			::= { snmpv1v2TrapIPv6Entry 5 }

		
--          1.3.6.1.4.1.37950.1.1.5.10.12.8
-- 1.3.6.1.4.1.37950.1.1.5.10.12.8
-- 1.3.6.1.4.1.37950.1.1.5.10.12.8
-- 1.3.6.1.4.1.37950.1.1.5.10.12.8
-- 1.3.6.1.4.1.37950.1.1.5.10.12.8
-- 1.3.6.1.4.1.37950.1.1.5.10.12.8
-- 1.3.6.1.4.1.37950.1.1.5.10.12.8
-- 1.3.6.1.4.1.37950.1.1.5.10.12.8
-- 1.3.6.1.4.1.37950.1.1.5.10.12.8
		-- 1.3.6.1.4.1.37950.1.1.5.10.12.8
		configFile OBJECT IDENTIFIER ::= { v1600dSysCfg 8 }

		
--          1.3.6.1.4.1.37950.1.1.5.10.12.8.1
-- 1.3.6.1.4.1.37950.1.1.5.10.12.8.1
-- 1.3.6.1.4.1.37950.1.1.5.10.12.8.1
-- 1.3.6.1.4.1.37950.1.1.5.10.12.8.1
-- 1.3.6.1.4.1.37950.1.1.5.10.12.8.1
-- 1.3.6.1.4.1.37950.1.1.5.10.12.8.1
-- 1.3.6.1.4.1.37950.1.1.5.10.12.8.1
-- 1.3.6.1.4.1.37950.1.1.5.10.12.8.1
-- 1.3.6.1.4.1.37950.1.1.5.10.12.8.1
		-- 1.3.6.1.4.1.37950.1.1.5.10.12.8.1
		restoreConfiguration OBJECT-TYPE
			SYNTAX INTEGER { enable(1) }
			MAX-ACCESS read-write
			STATUS current
			DESCRIPTION
				"Description."
			::= { configFile 1 }

		
--          1.3.6.1.4.1.37950.1.1.5.10.12.8.2
-- 1.3.6.1.4.1.37950.1.1.5.10.12.8.2
-- 1.3.6.1.4.1.37950.1.1.5.10.12.8.2
-- 1.3.6.1.4.1.37950.1.1.5.10.12.8.2
-- 1.3.6.1.4.1.37950.1.1.5.10.12.8.2
-- 1.3.6.1.4.1.37950.1.1.5.10.12.8.2
-- 1.3.6.1.4.1.37950.1.1.5.10.12.8.2
-- 1.3.6.1.4.1.37950.1.1.5.10.12.8.2
-- 1.3.6.1.4.1.37950.1.1.5.10.12.8.2
		-- 1.3.6.1.4.1.37950.1.1.5.10.12.8.2
		saveConfiguration OBJECT-TYPE
			SYNTAX INTEGER { enable(1) }
			MAX-ACCESS read-write
			STATUS current
			DESCRIPTION
				"Description."
			::= { configFile 2 }

		
--          1.3.6.1.4.1.37950.1.1.5.10.12.8.3
-- 1.3.6.1.4.1.37950.1.1.5.10.12.8.3
-- 1.3.6.1.4.1.37950.1.1.5.10.12.8.3
-- 1.3.6.1.4.1.37950.1.1.5.10.12.8.3
-- 1.3.6.1.4.1.37950.1.1.5.10.12.8.3
-- 1.3.6.1.4.1.37950.1.1.5.10.12.8.3
-- 1.3.6.1.4.1.37950.1.1.5.10.12.8.3
-- 1.3.6.1.4.1.37950.1.1.5.10.12.8.3
-- 1.3.6.1.4.1.37950.1.1.5.10.12.8.3
		-- 1.3.6.1.4.1.37950.1.1.5.10.12.8.3
		uploadDownloadCfgFile OBJECT IDENTIFIER ::= { configFile 3 }

		
--          1.3.6.1.4.1.37950.1.1.5.10.12.8.3.1
-- 1.3.6.1.4.1.37950.1.1.5.10.12.8.3.1
-- 1.3.6.1.4.1.37950.1.1.5.10.12.8.3.1
-- 1.3.6.1.4.1.37950.1.1.5.10.12.8.3.1
-- 1.3.6.1.4.1.37950.1.1.5.10.12.8.3.1
-- 1.3.6.1.4.1.37950.1.1.5.10.12.8.3.1
-- 1.3.6.1.4.1.37950.1.1.5.10.12.8.3.1
-- 1.3.6.1.4.1.37950.1.1.5.10.12.8.3.1
-- 1.3.6.1.4.1.37950.1.1.5.10.12.8.3.1
		-- 1.3.6.1.4.1.37950.1.1.5.10.12.8.3.1
		cfgFileName OBJECT-TYPE
			SYNTAX OCTET STRING
			MAX-ACCESS read-write
			STATUS current
			DESCRIPTION
				"Description."
			::= { uploadDownloadCfgFile 1 }

		
--          1.3.6.1.4.1.37950.1.1.5.10.12.8.3.2
-- 1.3.6.1.4.1.37950.1.1.5.10.12.8.3.2
-- 1.3.6.1.4.1.37950.1.1.5.10.12.8.3.2
-- 1.3.6.1.4.1.37950.1.1.5.10.12.8.3.2
-- 1.3.6.1.4.1.37950.1.1.5.10.12.8.3.2
-- 1.3.6.1.4.1.37950.1.1.5.10.12.8.3.2
-- 1.3.6.1.4.1.37950.1.1.5.10.12.8.3.2
-- 1.3.6.1.4.1.37950.1.1.5.10.12.8.3.2
-- 1.3.6.1.4.1.37950.1.1.5.10.12.8.3.2
		-- 1.3.6.1.4.1.37950.1.1.5.10.12.8.3.2
		tftpServerIPAddr OBJECT-TYPE
			SYNTAX IpAddress
			MAX-ACCESS read-write
			STATUS current
			DESCRIPTION
				"Description."
			::= { uploadDownloadCfgFile 2 }

		
--          1.3.6.1.4.1.37950.1.1.5.10.12.8.3.3
-- 1.3.6.1.4.1.37950.1.1.5.10.12.8.3.3
-- 1.3.6.1.4.1.37950.1.1.5.10.12.8.3.3
-- 1.3.6.1.4.1.37950.1.1.5.10.12.8.3.3
-- 1.3.6.1.4.1.37950.1.1.5.10.12.8.3.3
-- 1.3.6.1.4.1.37950.1.1.5.10.12.8.3.3
-- 1.3.6.1.4.1.37950.1.1.5.10.12.8.3.3
-- 1.3.6.1.4.1.37950.1.1.5.10.12.8.3.3
-- 1.3.6.1.4.1.37950.1.1.5.10.12.8.3.3
		-- 1.3.6.1.4.1.37950.1.1.5.10.12.8.3.3
		cfgFileAction OBJECT-TYPE
			SYNTAX INTEGER
				{
				upload(1),
				download(2)
				}
			MAX-ACCESS read-write
			STATUS current
			DESCRIPTION
				"Description."
			::= { uploadDownloadCfgFile 3 }

		
--         1.3.6.1.4.1.37950.1.1.5.10.12.8.4
-- 1.3.6.1.4.1.37950.1.1.5.10.12.8.4
-- 1.3.6.1.4.1.37950.1.1.5.10.12.8.4
-- 1.3.6.1.4.1.37950.1.1.5.10.12.8.4
-- 1.3.6.1.4.1.37950.1.1.5.10.12.8.4
-- 1.3.6.1.4.1.37950.1.1.5.10.12.8.4
-- 1.3.6.1.4.1.37950.1.1.5.10.12.8.4
-- 1.3.6.1.4.1.37950.1.1.5.10.12.8.4
		-- 1.3.6.1.4.1.37950.1.1.5.10.12.8.4
		ipv6UploadDownloadCfgFile OBJECT IDENTIFIER ::= { configFile 4 }

		
--         1.3.6.1.4.1.37950.1.1.5.10.12.8.4.1
-- 1.3.6.1.4.1.37950.1.1.5.10.12.8.4.1
-- 1.3.6.1.4.1.37950.1.1.5.10.12.8.4.1
-- 1.3.6.1.4.1.37950.1.1.5.10.12.8.4.1
-- 1.3.6.1.4.1.37950.1.1.5.10.12.8.4.1
-- 1.3.6.1.4.1.37950.1.1.5.10.12.8.4.1
-- 1.3.6.1.4.1.37950.1.1.5.10.12.8.4.1
-- 1.3.6.1.4.1.37950.1.1.5.10.12.8.4.1
		-- 1.3.6.1.4.1.37950.1.1.5.10.12.8.4.1
		ipv6CfgFileName OBJECT-TYPE
			SYNTAX OCTET STRING
			MAX-ACCESS read-write
			STATUS current
			DESCRIPTION
				"Description."
			::= { ipv6UploadDownloadCfgFile 1 }

		
--         1.3.6.1.4.1.37950.1.1.5.10.12.8.4.2
-- 1.3.6.1.4.1.37950.1.1.5.10.12.8.4.2
-- 1.3.6.1.4.1.37950.1.1.5.10.12.8.4.2
-- 1.3.6.1.4.1.37950.1.1.5.10.12.8.4.2
-- 1.3.6.1.4.1.37950.1.1.5.10.12.8.4.2
-- 1.3.6.1.4.1.37950.1.1.5.10.12.8.4.2
-- 1.3.6.1.4.1.37950.1.1.5.10.12.8.4.2
-- 1.3.6.1.4.1.37950.1.1.5.10.12.8.4.2
		-- 1.3.6.1.4.1.37950.1.1.5.10.12.8.4.2
		tftpServerIPv6Addr OBJECT-TYPE
			SYNTAX OCTET STRING
			MAX-ACCESS read-write
			STATUS current
			DESCRIPTION
				"Description."
			::= { ipv6UploadDownloadCfgFile 2 }

		
--         1.3.6.1.4.1.37950.1.1.5.10.12.8.4.3
-- 1.3.6.1.4.1.37950.1.1.5.10.12.8.4.3
-- 1.3.6.1.4.1.37950.1.1.5.10.12.8.4.3
-- 1.3.6.1.4.1.37950.1.1.5.10.12.8.4.3
-- 1.3.6.1.4.1.37950.1.1.5.10.12.8.4.3
-- 1.3.6.1.4.1.37950.1.1.5.10.12.8.4.3
-- 1.3.6.1.4.1.37950.1.1.5.10.12.8.4.3
-- 1.3.6.1.4.1.37950.1.1.5.10.12.8.4.3
		-- 1.3.6.1.4.1.37950.1.1.5.10.12.8.4.3
		ipv6CfgFileAction OBJECT-TYPE
			SYNTAX INTEGER
				{
				upload(1),
				download(2)
				}
			MAX-ACCESS read-write
			STATUS current
			DESCRIPTION
				"Description."
			::= { ipv6UploadDownloadCfgFile 3 }

		
--         1.3.6.1.4.1.37950.1.1.5.10.12.8.5
-- 1.3.6.1.4.1.37950.1.1.5.10.12.8.5
-- 1.3.6.1.4.1.37950.1.1.5.10.12.8.5
-- 1.3.6.1.4.1.37950.1.1.5.10.12.8.5
-- 1.3.6.1.4.1.37950.1.1.5.10.12.8.5
-- 1.3.6.1.4.1.37950.1.1.5.10.12.8.5
-- 1.3.6.1.4.1.37950.1.1.5.10.12.8.5
-- 1.3.6.1.4.1.37950.1.1.5.10.12.8.5
		-- 1.3.6.1.4.1.37950.1.1.5.10.12.8.5
		autoSaveConfiguration OBJECT IDENTIFIER ::= { configFile 5 }

		
--         1.3.6.1.4.1.37950.1.1.5.10.12.8.5.1
-- 1.3.6.1.4.1.37950.1.1.5.10.12.8.5.1
-- 1.3.6.1.4.1.37950.1.1.5.10.12.8.5.1
-- 1.3.6.1.4.1.37950.1.1.5.10.12.8.5.1
-- 1.3.6.1.4.1.37950.1.1.5.10.12.8.5.1
-- 1.3.6.1.4.1.37950.1.1.5.10.12.8.5.1
-- 1.3.6.1.4.1.37950.1.1.5.10.12.8.5.1
-- 1.3.6.1.4.1.37950.1.1.5.10.12.8.5.1
		-- 1.3.6.1.4.1.37950.1.1.5.10.12.8.5.1
		autoSaveType OBJECT-TYPE
			SYNTAX INTEGER
				{
				timeout(0),
				fix-time(1),
				week-day(2)
				}
			MAX-ACCESS read-write
			STATUS current
			DESCRIPTION
				"Description."
			::= { autoSaveConfiguration 1 }

		
--         1.3.6.1.4.1.37950.1.1.5.10.12.8.5.2
-- 1.3.6.1.4.1.37950.1.1.5.10.12.8.5.2
-- 1.3.6.1.4.1.37950.1.1.5.10.12.8.5.2
-- 1.3.6.1.4.1.37950.1.1.5.10.12.8.5.2
-- 1.3.6.1.4.1.37950.1.1.5.10.12.8.5.2
-- 1.3.6.1.4.1.37950.1.1.5.10.12.8.5.2
-- 1.3.6.1.4.1.37950.1.1.5.10.12.8.5.2
-- 1.3.6.1.4.1.37950.1.1.5.10.12.8.5.2
		-- 1.3.6.1.4.1.37950.1.1.5.10.12.8.5.2
		autoSaveTimeoutValue OBJECT-TYPE
			SYNTAX Unsigned32 (60..2678400)
			MAX-ACCESS read-write
			STATUS current
			DESCRIPTION
				"Description."
			::= { autoSaveConfiguration 2 }

		
--         1.3.6.1.4.1.37950.1.1.5.10.12.8.5.3
-- 1.3.6.1.4.1.37950.1.1.5.10.12.8.5.3
-- 1.3.6.1.4.1.37950.1.1.5.10.12.8.5.3
-- 1.3.6.1.4.1.37950.1.1.5.10.12.8.5.3
-- 1.3.6.1.4.1.37950.1.1.5.10.12.8.5.3
-- 1.3.6.1.4.1.37950.1.1.5.10.12.8.5.3
-- 1.3.6.1.4.1.37950.1.1.5.10.12.8.5.3
-- 1.3.6.1.4.1.37950.1.1.5.10.12.8.5.3
		-- 1.3.6.1.4.1.37950.1.1.5.10.12.8.5.3
		autoSaveFixTimeDay OBJECT-TYPE
			SYNTAX Integer32 (1..31)
			MAX-ACCESS read-write
			STATUS current
			DESCRIPTION
				"Description."
			::= { autoSaveConfiguration 3 }

		
--         1.3.6.1.4.1.37950.1.1.5.10.12.8.5.4
-- 1.3.6.1.4.1.37950.1.1.5.10.12.8.5.4
-- 1.3.6.1.4.1.37950.1.1.5.10.12.8.5.4
-- 1.3.6.1.4.1.37950.1.1.5.10.12.8.5.4
-- 1.3.6.1.4.1.37950.1.1.5.10.12.8.5.4
-- 1.3.6.1.4.1.37950.1.1.5.10.12.8.5.4
-- 1.3.6.1.4.1.37950.1.1.5.10.12.8.5.4
-- 1.3.6.1.4.1.37950.1.1.5.10.12.8.5.4
		-- 1.3.6.1.4.1.37950.1.1.5.10.12.8.5.4
		autoSaveFixTimeHour OBJECT-TYPE
			SYNTAX Integer32 (0..23)
			MAX-ACCESS read-write
			STATUS current
			DESCRIPTION
				"Description."
			::= { autoSaveConfiguration 4 }

		
--         1.3.6.1.4.1.37950.1.1.5.10.12.8.5.5
-- 1.3.6.1.4.1.37950.1.1.5.10.12.8.5.5
-- 1.3.6.1.4.1.37950.1.1.5.10.12.8.5.5
-- 1.3.6.1.4.1.37950.1.1.5.10.12.8.5.5
-- 1.3.6.1.4.1.37950.1.1.5.10.12.8.5.5
-- 1.3.6.1.4.1.37950.1.1.5.10.12.8.5.5
-- 1.3.6.1.4.1.37950.1.1.5.10.12.8.5.5
-- 1.3.6.1.4.1.37950.1.1.5.10.12.8.5.5
		-- 1.3.6.1.4.1.37950.1.1.5.10.12.8.5.5
		autoSaveFixTimeMinute OBJECT-TYPE
			SYNTAX Integer32 (0..59)
			MAX-ACCESS read-write
			STATUS current
			DESCRIPTION
				"Description."
			::= { autoSaveConfiguration 5 }

		
--         1.3.6.1.4.1.37950.1.1.5.10.12.8.5.6
-- 1.3.6.1.4.1.37950.1.1.5.10.12.8.5.6
-- 1.3.6.1.4.1.37950.1.1.5.10.12.8.5.6
-- 1.3.6.1.4.1.37950.1.1.5.10.12.8.5.6
-- 1.3.6.1.4.1.37950.1.1.5.10.12.8.5.6
-- 1.3.6.1.4.1.37950.1.1.5.10.12.8.5.6
-- 1.3.6.1.4.1.37950.1.1.5.10.12.8.5.6
-- 1.3.6.1.4.1.37950.1.1.5.10.12.8.5.6
		-- 1.3.6.1.4.1.37950.1.1.5.10.12.8.5.6
		autoSaveWeekMon OBJECT-TYPE
			SYNTAX INTEGER
				{
				disable(0),
				enable(1)
				}
			MAX-ACCESS read-write
			STATUS current
			DESCRIPTION
				"Description."
			::= { autoSaveConfiguration 6 }

		
--         1.3.6.1.4.1.37950.1.1.5.10.12.8.5.7
-- 1.3.6.1.4.1.37950.1.1.5.10.12.8.5.7
-- 1.3.6.1.4.1.37950.1.1.5.10.12.8.5.7
-- 1.3.6.1.4.1.37950.1.1.5.10.12.8.5.7
-- 1.3.6.1.4.1.37950.1.1.5.10.12.8.5.7
-- 1.3.6.1.4.1.37950.1.1.5.10.12.8.5.7
-- 1.3.6.1.4.1.37950.1.1.5.10.12.8.5.7
-- 1.3.6.1.4.1.37950.1.1.5.10.12.8.5.7
		-- 1.3.6.1.4.1.37950.1.1.5.10.12.8.5.7
		autoSaveWeekTues OBJECT-TYPE
			SYNTAX INTEGER
				{
				disable(0),
				enable(1)
				}
			MAX-ACCESS read-write
			STATUS current
			DESCRIPTION
				"Description."
			::= { autoSaveConfiguration 7 }

		
--         1.3.6.1.4.1.37950.1.1.5.10.12.8.5.8
-- 1.3.6.1.4.1.37950.1.1.5.10.12.8.5.8
-- 1.3.6.1.4.1.37950.1.1.5.10.12.8.5.8
-- 1.3.6.1.4.1.37950.1.1.5.10.12.8.5.8
-- 1.3.6.1.4.1.37950.1.1.5.10.12.8.5.8
-- 1.3.6.1.4.1.37950.1.1.5.10.12.8.5.8
-- 1.3.6.1.4.1.37950.1.1.5.10.12.8.5.8
-- 1.3.6.1.4.1.37950.1.1.5.10.12.8.5.8
		-- 1.3.6.1.4.1.37950.1.1.5.10.12.8.5.8
		autoSaveWeekWed OBJECT-TYPE
			SYNTAX INTEGER
				{
				disable(0),
				enable(1)
				}
			MAX-ACCESS read-write
			STATUS current
			DESCRIPTION
				"Description."
			::= { autoSaveConfiguration 8 }

		
--         1.3.6.1.4.1.37950.1.1.5.10.12.8.5.9
-- 1.3.6.1.4.1.37950.1.1.5.10.12.8.5.9
-- 1.3.6.1.4.1.37950.1.1.5.10.12.8.5.9
-- 1.3.6.1.4.1.37950.1.1.5.10.12.8.5.9
-- 1.3.6.1.4.1.37950.1.1.5.10.12.8.5.9
-- 1.3.6.1.4.1.37950.1.1.5.10.12.8.5.9
-- 1.3.6.1.4.1.37950.1.1.5.10.12.8.5.9
-- 1.3.6.1.4.1.37950.1.1.5.10.12.8.5.9
		-- 1.3.6.1.4.1.37950.1.1.5.10.12.8.5.9
		autoSaveWeekThur OBJECT-TYPE
			SYNTAX INTEGER
				{
				disable(0),
				enable(1)
				}
			MAX-ACCESS read-write
			STATUS current
			DESCRIPTION
				"Description."
			::= { autoSaveConfiguration 9 }

		
--         1.3.6.1.4.1.37950.1.1.5.10.12.8.5.10
-- 1.3.6.1.4.1.37950.1.1.5.10.12.8.5.10
-- 1.3.6.1.4.1.37950.1.1.5.10.12.8.5.10
-- 1.3.6.1.4.1.37950.1.1.5.10.12.8.5.10
-- 1.3.6.1.4.1.37950.1.1.5.10.12.8.5.10
-- 1.3.6.1.4.1.37950.1.1.5.10.12.8.5.10
-- 1.3.6.1.4.1.37950.1.1.5.10.12.8.5.10
-- 1.3.6.1.4.1.37950.1.1.5.10.12.8.5.10
		-- 1.3.6.1.4.1.37950.1.1.5.10.12.8.5.10
		autoSaveWeekFri OBJECT-TYPE
			SYNTAX INTEGER
				{
				disable(0),
				enable(1)
				}
			MAX-ACCESS read-write
			STATUS current
			DESCRIPTION
				"Description."
			::= { autoSaveConfiguration 10 }

		
--         1.3.6.1.4.1.37950.1.1.5.10.12.8.5.11
-- 1.3.6.1.4.1.37950.1.1.5.10.12.8.5.11
-- 1.3.6.1.4.1.37950.1.1.5.10.12.8.5.11
-- 1.3.6.1.4.1.37950.1.1.5.10.12.8.5.11
-- 1.3.6.1.4.1.37950.1.1.5.10.12.8.5.11
-- 1.3.6.1.4.1.37950.1.1.5.10.12.8.5.11
-- 1.3.6.1.4.1.37950.1.1.5.10.12.8.5.11
-- 1.3.6.1.4.1.37950.1.1.5.10.12.8.5.11
		-- 1.3.6.1.4.1.37950.1.1.5.10.12.8.5.11
		autoSaveWeekSat OBJECT-TYPE
			SYNTAX INTEGER
				{
				disable(0),
				enable(1)
				}
			MAX-ACCESS read-write
			STATUS current
			DESCRIPTION
				"Description."
			::= { autoSaveConfiguration 11 }

		
--         1.3.6.1.4.1.37950.1.1.5.10.12.8.5.12
-- 1.3.6.1.4.1.37950.1.1.5.10.12.8.5.12
-- 1.3.6.1.4.1.37950.1.1.5.10.12.8.5.12
-- 1.3.6.1.4.1.37950.1.1.5.10.12.8.5.12
-- 1.3.6.1.4.1.37950.1.1.5.10.12.8.5.12
-- 1.3.6.1.4.1.37950.1.1.5.10.12.8.5.12
-- 1.3.6.1.4.1.37950.1.1.5.10.12.8.5.12
-- 1.3.6.1.4.1.37950.1.1.5.10.12.8.5.12
		-- 1.3.6.1.4.1.37950.1.1.5.10.12.8.5.12
		autoSaveWeekSun OBJECT-TYPE
			SYNTAX INTEGER
				{
				disable(0),
				enable(1)
				}
			MAX-ACCESS read-write
			STATUS current
			DESCRIPTION
				"Description."
			::= { autoSaveConfiguration 12 }

		
--         1.3.6.1.4.1.37950.1.1.5.10.12.8.5.13
-- 1.3.6.1.4.1.37950.1.1.5.10.12.8.5.13
-- 1.3.6.1.4.1.37950.1.1.5.10.12.8.5.13
-- 1.3.6.1.4.1.37950.1.1.5.10.12.8.5.13
-- 1.3.6.1.4.1.37950.1.1.5.10.12.8.5.13
-- 1.3.6.1.4.1.37950.1.1.5.10.12.8.5.13
-- 1.3.6.1.4.1.37950.1.1.5.10.12.8.5.13
-- 1.3.6.1.4.1.37950.1.1.5.10.12.8.5.13
		-- 1.3.6.1.4.1.37950.1.1.5.10.12.8.5.13
		autoSaveWeekHour OBJECT-TYPE
			SYNTAX Integer32 (0..23)
			MAX-ACCESS read-write
			STATUS current
			DESCRIPTION
				"Description."
			::= { autoSaveConfiguration 13 }

		
--         1.3.6.1.4.1.37950.1.1.5.10.12.8.5.14
-- 1.3.6.1.4.1.37950.1.1.5.10.12.8.5.14
-- 1.3.6.1.4.1.37950.1.1.5.10.12.8.5.14
-- 1.3.6.1.4.1.37950.1.1.5.10.12.8.5.14
-- 1.3.6.1.4.1.37950.1.1.5.10.12.8.5.14
-- 1.3.6.1.4.1.37950.1.1.5.10.12.8.5.14
-- 1.3.6.1.4.1.37950.1.1.5.10.12.8.5.14
-- 1.3.6.1.4.1.37950.1.1.5.10.12.8.5.14
		-- 1.3.6.1.4.1.37950.1.1.5.10.12.8.5.14
		autoSaveWeekMinute OBJECT-TYPE
			SYNTAX Integer32 (0..59)
			MAX-ACCESS read-write
			STATUS current
			DESCRIPTION
				"Description."
			::= { autoSaveConfiguration 14 }

		
--         1.3.6.1.4.1.37950.1.1.5.10.12.8.5.15
-- 1.3.6.1.4.1.37950.1.1.5.10.12.8.5.15
-- 1.3.6.1.4.1.37950.1.1.5.10.12.8.5.15
-- 1.3.6.1.4.1.37950.1.1.5.10.12.8.5.15
-- 1.3.6.1.4.1.37950.1.1.5.10.12.8.5.15
-- 1.3.6.1.4.1.37950.1.1.5.10.12.8.5.15
-- 1.3.6.1.4.1.37950.1.1.5.10.12.8.5.15
-- 1.3.6.1.4.1.37950.1.1.5.10.12.8.5.15
		-- 1.3.6.1.4.1.37950.1.1.5.10.12.8.5.15
		autoSaveAction OBJECT-TYPE
			SYNTAX INTEGER
				{
				disable(0),
				enable(1)
				}
			MAX-ACCESS read-write
			STATUS current
			DESCRIPTION
				"Description."
			::= { autoSaveConfiguration 15 }

		
--         1.3.6.1.4.1.37950.1.1.5.10.12.8.6
-- 1.3.6.1.4.1.37950.1.1.5.10.12.8.6
-- 1.3.6.1.4.1.37950.1.1.5.10.12.8.6
-- 1.3.6.1.4.1.37950.1.1.5.10.12.8.6
-- 1.3.6.1.4.1.37950.1.1.5.10.12.8.6
-- 1.3.6.1.4.1.37950.1.1.5.10.12.8.6
-- 1.3.6.1.4.1.37950.1.1.5.10.12.8.6
-- 1.3.6.1.4.1.37950.1.1.5.10.12.8.6
		-- 1.3.6.1.4.1.37950.1.1.5.10.12.8.6
		autoSaveConfigTable OBJECT-TYPE
			SYNTAX SEQUENCE OF AutoSaveConfigEntry
			MAX-ACCESS not-accessible
			STATUS current
			DESCRIPTION
				"Description."
			::= { configFile 6 }

		
--         1.3.6.1.4.1.37950.1.1.5.10.12.8.6.1
-- 1.3.6.1.4.1.37950.1.1.5.10.12.8.6.1
-- 1.3.6.1.4.1.37950.1.1.5.10.12.8.6.1
-- 1.3.6.1.4.1.37950.1.1.5.10.12.8.6.1
-- 1.3.6.1.4.1.37950.1.1.5.10.12.8.6.1
-- 1.3.6.1.4.1.37950.1.1.5.10.12.8.6.1
-- 1.3.6.1.4.1.37950.1.1.5.10.12.8.6.1
-- 1.3.6.1.4.1.37950.1.1.5.10.12.8.6.1
		-- 1.3.6.1.4.1.37950.1.1.5.10.12.8.6.1
		autoSaveConfigEntry OBJECT-TYPE
			SYNTAX AutoSaveConfigEntry
			MAX-ACCESS not-accessible
			STATUS current
			DESCRIPTION
				"Description."
			INDEX { autoSaveEnable }
			::= { autoSaveConfigTable 1 }

		
		AutoSaveConfigEntry ::=
			SEQUENCE { 
				autoSaveEnable
					INTEGER,
				autoSaveTypeS
					INTEGER,
				autoSaveTimeoutValueS
					Unsigned32,
				autoSaveFixTimeDayS
					Integer32,
				autoSaveFixTimeHourS
					Integer32,
				autoSaveFixTimeMinuteS
					Integer32,
				autoSaveWeekMonS
					INTEGER,
				autoSaveWeekTuesS
					INTEGER,
				autoSaveWeekWedS
					INTEGER,
				autoSaveWeekThurS
					INTEGER,
				autoSaveWeekFriS
					INTEGER,
				autoSaveWeekSatS
					INTEGER,
				autoSaveWeekSunS
					INTEGER,
				autoSaveWeekHourS
					Integer32,
				autoSaveWeekMinuteS
					Integer32
			 }

--         1.3.6.1.4.1.37950.1.1.5.10.12.8.6.1.1
-- 1.3.6.1.4.1.37950.1.1.5.10.12.8.6.1.1
-- 1.3.6.1.4.1.37950.1.1.5.10.12.8.6.1.1
-- 1.3.6.1.4.1.37950.1.1.5.10.12.8.6.1.1
-- 1.3.6.1.4.1.37950.1.1.5.10.12.8.6.1.1
-- 1.3.6.1.4.1.37950.1.1.5.10.12.8.6.1.1
-- 1.3.6.1.4.1.37950.1.1.5.10.12.8.6.1.1
-- 1.3.6.1.4.1.37950.1.1.5.10.12.8.6.1.1
		-- 1.3.6.1.4.1.37950.1.1.5.10.12.8.6.1.1
		autoSaveEnable OBJECT-TYPE
			SYNTAX INTEGER
				{
				disable(0),
				enable(1)
				}
			MAX-ACCESS read-write
			STATUS current
			DESCRIPTION
				"Description."
			::= { autoSaveConfigEntry 1 }

		
--         1.3.6.1.4.1.37950.1.1.5.10.12.8.6.1.2
-- 1.3.6.1.4.1.37950.1.1.5.10.12.8.6.1.2
-- 1.3.6.1.4.1.37950.1.1.5.10.12.8.6.1.2
-- 1.3.6.1.4.1.37950.1.1.5.10.12.8.6.1.2
-- 1.3.6.1.4.1.37950.1.1.5.10.12.8.6.1.2
-- 1.3.6.1.4.1.37950.1.1.5.10.12.8.6.1.2
-- 1.3.6.1.4.1.37950.1.1.5.10.12.8.6.1.2
-- 1.3.6.1.4.1.37950.1.1.5.10.12.8.6.1.2
		-- 1.3.6.1.4.1.37950.1.1.5.10.12.8.6.1.2
		autoSaveTypeS OBJECT-TYPE
			SYNTAX INTEGER
				{
				timeout(0),
				fix-time(1),
				week-day(2)
				}
			MAX-ACCESS read-write
			STATUS current
			DESCRIPTION
				"Description."
			::= { autoSaveConfigEntry 2 }

		
--         1.3.6.1.4.1.37950.1.1.5.10.12.8.6.1.3
-- 1.3.6.1.4.1.37950.1.1.5.10.12.8.6.1.3
-- 1.3.6.1.4.1.37950.1.1.5.10.12.8.6.1.3
-- 1.3.6.1.4.1.37950.1.1.5.10.12.8.6.1.3
-- 1.3.6.1.4.1.37950.1.1.5.10.12.8.6.1.3
-- 1.3.6.1.4.1.37950.1.1.5.10.12.8.6.1.3
-- 1.3.6.1.4.1.37950.1.1.5.10.12.8.6.1.3
-- 1.3.6.1.4.1.37950.1.1.5.10.12.8.6.1.3
		-- 1.3.6.1.4.1.37950.1.1.5.10.12.8.6.1.3
		autoSaveTimeoutValueS OBJECT-TYPE
			SYNTAX Unsigned32 (60..2678400)
			MAX-ACCESS read-write
			STATUS current
			DESCRIPTION
				"Description."
			::= { autoSaveConfigEntry 3 }

		
--         1.3.6.1.4.1.37950.1.1.5.10.12.8.6.1.4
-- 1.3.6.1.4.1.37950.1.1.5.10.12.8.6.1.4
-- 1.3.6.1.4.1.37950.1.1.5.10.12.8.6.1.4
-- 1.3.6.1.4.1.37950.1.1.5.10.12.8.6.1.4
-- 1.3.6.1.4.1.37950.1.1.5.10.12.8.6.1.4
-- 1.3.6.1.4.1.37950.1.1.5.10.12.8.6.1.4
-- 1.3.6.1.4.1.37950.1.1.5.10.12.8.6.1.4
-- 1.3.6.1.4.1.37950.1.1.5.10.12.8.6.1.4
		-- 1.3.6.1.4.1.37950.1.1.5.10.12.8.6.1.4
		autoSaveFixTimeDayS OBJECT-TYPE
			SYNTAX Integer32 (1..31)
			MAX-ACCESS read-write
			STATUS current
			DESCRIPTION
				"Description."
			::= { autoSaveConfigEntry 4 }

		
--         1.3.6.1.4.1.37950.1.1.5.10.12.8.6.1.5
-- 1.3.6.1.4.1.37950.1.1.5.10.12.8.6.1.5
-- 1.3.6.1.4.1.37950.1.1.5.10.12.8.6.1.5
-- 1.3.6.1.4.1.37950.1.1.5.10.12.8.6.1.5
-- 1.3.6.1.4.1.37950.1.1.5.10.12.8.6.1.5
-- 1.3.6.1.4.1.37950.1.1.5.10.12.8.6.1.5
-- 1.3.6.1.4.1.37950.1.1.5.10.12.8.6.1.5
-- 1.3.6.1.4.1.37950.1.1.5.10.12.8.6.1.5
		-- 1.3.6.1.4.1.37950.1.1.5.10.12.8.6.1.5
		autoSaveFixTimeHourS OBJECT-TYPE
			SYNTAX Integer32 (0..23)
			MAX-ACCESS read-write
			STATUS current
			DESCRIPTION
				"Description."
			::= { autoSaveConfigEntry 5 }

		
--         1.3.6.1.4.1.37950.1.1.5.10.12.8.6.1.6
-- 1.3.6.1.4.1.37950.1.1.5.10.12.8.6.1.6
-- 1.3.6.1.4.1.37950.1.1.5.10.12.8.6.1.6
-- 1.3.6.1.4.1.37950.1.1.5.10.12.8.6.1.6
-- 1.3.6.1.4.1.37950.1.1.5.10.12.8.6.1.6
-- 1.3.6.1.4.1.37950.1.1.5.10.12.8.6.1.6
-- 1.3.6.1.4.1.37950.1.1.5.10.12.8.6.1.6
-- 1.3.6.1.4.1.37950.1.1.5.10.12.8.6.1.6
		-- 1.3.6.1.4.1.37950.1.1.5.10.12.8.6.1.6
		autoSaveFixTimeMinuteS OBJECT-TYPE
			SYNTAX Integer32 (0..59)
			MAX-ACCESS read-write
			STATUS current
			DESCRIPTION
				"Description."
			::= { autoSaveConfigEntry 6 }

		
--         1.3.6.1.4.1.37950.1.1.5.10.12.8.6.1.7
-- 1.3.6.1.4.1.37950.1.1.5.10.12.8.6.1.7
-- 1.3.6.1.4.1.37950.1.1.5.10.12.8.6.1.7
-- 1.3.6.1.4.1.37950.1.1.5.10.12.8.6.1.7
-- 1.3.6.1.4.1.37950.1.1.5.10.12.8.6.1.7
-- 1.3.6.1.4.1.37950.1.1.5.10.12.8.6.1.7
-- 1.3.6.1.4.1.37950.1.1.5.10.12.8.6.1.7
-- 1.3.6.1.4.1.37950.1.1.5.10.12.8.6.1.7
		-- 1.3.6.1.4.1.37950.1.1.5.10.12.8.6.1.7
		autoSaveWeekMonS OBJECT-TYPE
			SYNTAX INTEGER
				{
				disable(0),
				enable(1)
				}
			MAX-ACCESS read-write
			STATUS current
			DESCRIPTION
				"Description."
			::= { autoSaveConfigEntry 7 }

		
--         1.3.6.1.4.1.37950.1.1.5.10.12.8.6.1.8
-- 1.3.6.1.4.1.37950.1.1.5.10.12.8.6.1.8
-- 1.3.6.1.4.1.37950.1.1.5.10.12.8.6.1.8
-- 1.3.6.1.4.1.37950.1.1.5.10.12.8.6.1.8
-- 1.3.6.1.4.1.37950.1.1.5.10.12.8.6.1.8
-- 1.3.6.1.4.1.37950.1.1.5.10.12.8.6.1.8
-- 1.3.6.1.4.1.37950.1.1.5.10.12.8.6.1.8
-- 1.3.6.1.4.1.37950.1.1.5.10.12.8.6.1.8
		-- 1.3.6.1.4.1.37950.1.1.5.10.12.8.6.1.8
		autoSaveWeekTuesS OBJECT-TYPE
			SYNTAX INTEGER
				{
				disable(0),
				enable(1)
				}
			MAX-ACCESS read-write
			STATUS current
			DESCRIPTION
				"Description."
			::= { autoSaveConfigEntry 8 }

		
--         1.3.6.1.4.1.37950.1.1.5.10.12.8.6.1.9
-- 1.3.6.1.4.1.37950.1.1.5.10.12.8.6.1.9
-- 1.3.6.1.4.1.37950.1.1.5.10.12.8.6.1.9
-- 1.3.6.1.4.1.37950.1.1.5.10.12.8.6.1.9
-- 1.3.6.1.4.1.37950.1.1.5.10.12.8.6.1.9
-- 1.3.6.1.4.1.37950.1.1.5.10.12.8.6.1.9
-- 1.3.6.1.4.1.37950.1.1.5.10.12.8.6.1.9
-- 1.3.6.1.4.1.37950.1.1.5.10.12.8.6.1.9
		-- 1.3.6.1.4.1.37950.1.1.5.10.12.8.6.1.9
		autoSaveWeekWedS OBJECT-TYPE
			SYNTAX INTEGER
				{
				disable(0),
				enable(1)
				}
			MAX-ACCESS read-write
			STATUS current
			DESCRIPTION
				"Description."
			::= { autoSaveConfigEntry 9 }

		
--         1.3.6.1.4.1.37950.1.1.5.10.12.8.6.1.10
-- 1.3.6.1.4.1.37950.1.1.5.10.12.8.6.1.10
-- 1.3.6.1.4.1.37950.1.1.5.10.12.8.6.1.10
-- 1.3.6.1.4.1.37950.1.1.5.10.12.8.6.1.10
-- 1.3.6.1.4.1.37950.1.1.5.10.12.8.6.1.10
-- 1.3.6.1.4.1.37950.1.1.5.10.12.8.6.1.10
-- 1.3.6.1.4.1.37950.1.1.5.10.12.8.6.1.10
-- 1.3.6.1.4.1.37950.1.1.5.10.12.8.6.1.10
		-- 1.3.6.1.4.1.37950.1.1.5.10.12.8.6.1.10
		autoSaveWeekThurS OBJECT-TYPE
			SYNTAX INTEGER
				{
				disable(0),
				enable(1)
				}
			MAX-ACCESS read-write
			STATUS current
			DESCRIPTION
				"Description."
			::= { autoSaveConfigEntry 10 }

		
--         1.3.6.1.4.1.37950.1.1.5.10.12.8.6.1.11
-- 1.3.6.1.4.1.37950.1.1.5.10.12.8.6.1.11
-- 1.3.6.1.4.1.37950.1.1.5.10.12.8.6.1.11
-- 1.3.6.1.4.1.37950.1.1.5.10.12.8.6.1.11
-- 1.3.6.1.4.1.37950.1.1.5.10.12.8.6.1.11
-- 1.3.6.1.4.1.37950.1.1.5.10.12.8.6.1.11
-- 1.3.6.1.4.1.37950.1.1.5.10.12.8.6.1.11
-- 1.3.6.1.4.1.37950.1.1.5.10.12.8.6.1.11
		-- 1.3.6.1.4.1.37950.1.1.5.10.12.8.6.1.11
		autoSaveWeekFriS OBJECT-TYPE
			SYNTAX INTEGER
				{
				disable(0),
				enable(1)
				}
			MAX-ACCESS read-write
			STATUS current
			DESCRIPTION
				"Description."
			::= { autoSaveConfigEntry 11 }

		
--         1.3.6.1.4.1.37950.1.1.5.10.12.8.6.1.12
-- 1.3.6.1.4.1.37950.1.1.5.10.12.8.6.1.12
-- 1.3.6.1.4.1.37950.1.1.5.10.12.8.6.1.12
-- 1.3.6.1.4.1.37950.1.1.5.10.12.8.6.1.12
-- 1.3.6.1.4.1.37950.1.1.5.10.12.8.6.1.12
-- 1.3.6.1.4.1.37950.1.1.5.10.12.8.6.1.12
-- 1.3.6.1.4.1.37950.1.1.5.10.12.8.6.1.12
-- 1.3.6.1.4.1.37950.1.1.5.10.12.8.6.1.12
		-- 1.3.6.1.4.1.37950.1.1.5.10.12.8.6.1.12
		autoSaveWeekSatS OBJECT-TYPE
			SYNTAX INTEGER
				{
				disable(0),
				enable(1)
				}
			MAX-ACCESS read-write
			STATUS current
			DESCRIPTION
				"Description."
			::= { autoSaveConfigEntry 12 }

		
--         1.3.6.1.4.1.37950.1.1.5.10.12.8.6.1.13
-- 1.3.6.1.4.1.37950.1.1.5.10.12.8.6.1.13
-- 1.3.6.1.4.1.37950.1.1.5.10.12.8.6.1.13
-- 1.3.6.1.4.1.37950.1.1.5.10.12.8.6.1.13
-- 1.3.6.1.4.1.37950.1.1.5.10.12.8.6.1.13
-- 1.3.6.1.4.1.37950.1.1.5.10.12.8.6.1.13
-- 1.3.6.1.4.1.37950.1.1.5.10.12.8.6.1.13
-- 1.3.6.1.4.1.37950.1.1.5.10.12.8.6.1.13
		-- 1.3.6.1.4.1.37950.1.1.5.10.12.8.6.1.13
		autoSaveWeekSunS OBJECT-TYPE
			SYNTAX INTEGER
				{
				disable(0),
				enable(1)
				}
			MAX-ACCESS read-write
			STATUS current
			DESCRIPTION
				"Description."
			::= { autoSaveConfigEntry 13 }

		
--         1.3.6.1.4.1.37950.1.1.5.10.12.8.6.1.14
-- 1.3.6.1.4.1.37950.1.1.5.10.12.8.6.1.14
-- 1.3.6.1.4.1.37950.1.1.5.10.12.8.6.1.14
-- 1.3.6.1.4.1.37950.1.1.5.10.12.8.6.1.14
-- 1.3.6.1.4.1.37950.1.1.5.10.12.8.6.1.14
-- 1.3.6.1.4.1.37950.1.1.5.10.12.8.6.1.14
-- 1.3.6.1.4.1.37950.1.1.5.10.12.8.6.1.14
-- 1.3.6.1.4.1.37950.1.1.5.10.12.8.6.1.14
		-- 1.3.6.1.4.1.37950.1.1.5.10.12.8.6.1.14
		autoSaveWeekHourS OBJECT-TYPE
			SYNTAX Integer32 (0..23)
			MAX-ACCESS read-write
			STATUS current
			DESCRIPTION
				"Description."
			::= { autoSaveConfigEntry 14 }

		
--         1.3.6.1.4.1.37950.1.1.5.10.12.8.6.1.15
-- 1.3.6.1.4.1.37950.1.1.5.10.12.8.6.1.15
-- 1.3.6.1.4.1.37950.1.1.5.10.12.8.6.1.15
-- 1.3.6.1.4.1.37950.1.1.5.10.12.8.6.1.15
-- 1.3.6.1.4.1.37950.1.1.5.10.12.8.6.1.15
-- 1.3.6.1.4.1.37950.1.1.5.10.12.8.6.1.15
-- 1.3.6.1.4.1.37950.1.1.5.10.12.8.6.1.15
-- 1.3.6.1.4.1.37950.1.1.5.10.12.8.6.1.15
		-- 1.3.6.1.4.1.37950.1.1.5.10.12.8.6.1.15
		autoSaveWeekMinuteS OBJECT-TYPE
			SYNTAX Integer32 (0..59)
			MAX-ACCESS read-write
			STATUS current
			DESCRIPTION
				"Description."
			::= { autoSaveConfigEntry 15 }

		
--         1.3.6.1.4.1.37950.1.1.5.10.12.8.7
-- 1.3.6.1.4.1.37950.1.1.5.10.12.8.7
-- 1.3.6.1.4.1.37950.1.1.5.10.12.8.7
-- 1.3.6.1.4.1.37950.1.1.5.10.12.8.7
-- 1.3.6.1.4.1.37950.1.1.5.10.12.8.7
-- 1.3.6.1.4.1.37950.1.1.5.10.12.8.7
-- 1.3.6.1.4.1.37950.1.1.5.10.12.8.7
-- 1.3.6.1.4.1.37950.1.1.5.10.12.8.7
		-- 1.3.6.1.4.1.37950.1.1.5.10.12.8.7
		autoBackupConfiguration OBJECT IDENTIFIER ::= { configFile 7 }

		
--         1.3.6.1.4.1.37950.1.1.5.10.12.8.7.1
-- 1.3.6.1.4.1.37950.1.1.5.10.12.8.7.1
-- 1.3.6.1.4.1.37950.1.1.5.10.12.8.7.1
-- 1.3.6.1.4.1.37950.1.1.5.10.12.8.7.1
-- 1.3.6.1.4.1.37950.1.1.5.10.12.8.7.1
-- 1.3.6.1.4.1.37950.1.1.5.10.12.8.7.1
-- 1.3.6.1.4.1.37950.1.1.5.10.12.8.7.1
-- 1.3.6.1.4.1.37950.1.1.5.10.12.8.7.1
		-- 1.3.6.1.4.1.37950.1.1.5.10.12.8.7.1
		autoBackupType OBJECT-TYPE
			SYNTAX INTEGER
				{
				timeout(0),
				fix-time(1),
				week-day(2)
				}
			MAX-ACCESS read-write
			STATUS current
			DESCRIPTION
				"Description."
			::= { autoBackupConfiguration 1 }

		
--         1.3.6.1.4.1.37950.1.1.5.10.12.8.7.2
-- 1.3.6.1.4.1.37950.1.1.5.10.12.8.7.2
-- 1.3.6.1.4.1.37950.1.1.5.10.12.8.7.2
-- 1.3.6.1.4.1.37950.1.1.5.10.12.8.7.2
-- 1.3.6.1.4.1.37950.1.1.5.10.12.8.7.2
-- 1.3.6.1.4.1.37950.1.1.5.10.12.8.7.2
-- 1.3.6.1.4.1.37950.1.1.5.10.12.8.7.2
-- 1.3.6.1.4.1.37950.1.1.5.10.12.8.7.2
		-- 1.3.6.1.4.1.37950.1.1.5.10.12.8.7.2
		autoBackupTimeoutValue OBJECT-TYPE
			SYNTAX Unsigned32 (60..2678400)
			MAX-ACCESS read-write
			STATUS current
			DESCRIPTION
				"Description."
			::= { autoBackupConfiguration 2 }

		
--         1.3.6.1.4.1.37950.1.1.5.10.12.8.7.3
-- 1.3.6.1.4.1.37950.1.1.5.10.12.8.7.3
-- 1.3.6.1.4.1.37950.1.1.5.10.12.8.7.3
-- 1.3.6.1.4.1.37950.1.1.5.10.12.8.7.3
-- 1.3.6.1.4.1.37950.1.1.5.10.12.8.7.3
-- 1.3.6.1.4.1.37950.1.1.5.10.12.8.7.3
-- 1.3.6.1.4.1.37950.1.1.5.10.12.8.7.3
-- 1.3.6.1.4.1.37950.1.1.5.10.12.8.7.3
		-- 1.3.6.1.4.1.37950.1.1.5.10.12.8.7.3
		autoBackupFixTimeDay OBJECT-TYPE
			SYNTAX Integer32 (1..31)
			MAX-ACCESS read-write
			STATUS current
			DESCRIPTION
				"Description."
			::= { autoBackupConfiguration 3 }

		
--         1.3.6.1.4.1.37950.1.1.5.10.12.8.7.4
-- 1.3.6.1.4.1.37950.1.1.5.10.12.8.7.4
-- 1.3.6.1.4.1.37950.1.1.5.10.12.8.7.4
-- 1.3.6.1.4.1.37950.1.1.5.10.12.8.7.4
-- 1.3.6.1.4.1.37950.1.1.5.10.12.8.7.4
-- 1.3.6.1.4.1.37950.1.1.5.10.12.8.7.4
-- 1.3.6.1.4.1.37950.1.1.5.10.12.8.7.4
-- 1.3.6.1.4.1.37950.1.1.5.10.12.8.7.4
		-- 1.3.6.1.4.1.37950.1.1.5.10.12.8.7.4
		autoBackupFixTimeHour OBJECT-TYPE
			SYNTAX Integer32 (0..23)
			MAX-ACCESS read-write
			STATUS current
			DESCRIPTION
				"Description."
			::= { autoBackupConfiguration 4 }

		
--         1.3.6.1.4.1.37950.1.1.5.10.12.8.7.5
-- 1.3.6.1.4.1.37950.1.1.5.10.12.8.7.5
-- 1.3.6.1.4.1.37950.1.1.5.10.12.8.7.5
-- 1.3.6.1.4.1.37950.1.1.5.10.12.8.7.5
-- 1.3.6.1.4.1.37950.1.1.5.10.12.8.7.5
-- 1.3.6.1.4.1.37950.1.1.5.10.12.8.7.5
-- 1.3.6.1.4.1.37950.1.1.5.10.12.8.7.5
-- 1.3.6.1.4.1.37950.1.1.5.10.12.8.7.5
		-- 1.3.6.1.4.1.37950.1.1.5.10.12.8.7.5
		autoBackupFixTimeMinute OBJECT-TYPE
			SYNTAX Integer32 (0..59)
			MAX-ACCESS read-write
			STATUS current
			DESCRIPTION
				"Description."
			::= { autoBackupConfiguration 5 }

		
--         1.3.6.1.4.1.37950.1.1.5.10.12.8.7.6
-- 1.3.6.1.4.1.37950.1.1.5.10.12.8.7.6
-- 1.3.6.1.4.1.37950.1.1.5.10.12.8.7.6
-- 1.3.6.1.4.1.37950.1.1.5.10.12.8.7.6
-- 1.3.6.1.4.1.37950.1.1.5.10.12.8.7.6
-- 1.3.6.1.4.1.37950.1.1.5.10.12.8.7.6
-- 1.3.6.1.4.1.37950.1.1.5.10.12.8.7.6
-- 1.3.6.1.4.1.37950.1.1.5.10.12.8.7.6
		-- 1.3.6.1.4.1.37950.1.1.5.10.12.8.7.6
		autoBackupWeekMon OBJECT-TYPE
			SYNTAX INTEGER
				{
				disable(0),
				enable(1)
				}
			MAX-ACCESS read-write
			STATUS current
			DESCRIPTION
				"Description."
			::= { autoBackupConfiguration 6 }

		
--         1.3.6.1.4.1.37950.1.1.5.10.12.8.7.7
-- 1.3.6.1.4.1.37950.1.1.5.10.12.8.7.7
-- 1.3.6.1.4.1.37950.1.1.5.10.12.8.7.7
-- 1.3.6.1.4.1.37950.1.1.5.10.12.8.7.7
-- 1.3.6.1.4.1.37950.1.1.5.10.12.8.7.7
-- 1.3.6.1.4.1.37950.1.1.5.10.12.8.7.7
-- 1.3.6.1.4.1.37950.1.1.5.10.12.8.7.7
-- 1.3.6.1.4.1.37950.1.1.5.10.12.8.7.7
		-- 1.3.6.1.4.1.37950.1.1.5.10.12.8.7.7
		autoBackupWeekTues OBJECT-TYPE
			SYNTAX INTEGER
				{
				disable(0),
				enable(1)
				}
			MAX-ACCESS read-write
			STATUS current
			DESCRIPTION
				"Description."
			::= { autoBackupConfiguration 7 }

		
--         1.3.6.1.4.1.37950.1.1.5.10.12.8.7.8
-- 1.3.6.1.4.1.37950.1.1.5.10.12.8.7.8
-- 1.3.6.1.4.1.37950.1.1.5.10.12.8.7.8
-- 1.3.6.1.4.1.37950.1.1.5.10.12.8.7.8
-- 1.3.6.1.4.1.37950.1.1.5.10.12.8.7.8
-- 1.3.6.1.4.1.37950.1.1.5.10.12.8.7.8
-- 1.3.6.1.4.1.37950.1.1.5.10.12.8.7.8
-- 1.3.6.1.4.1.37950.1.1.5.10.12.8.7.8
		-- 1.3.6.1.4.1.37950.1.1.5.10.12.8.7.8
		autoBackupWeekWed OBJECT-TYPE
			SYNTAX INTEGER
				{
				disable(0),
				enable(1)
				}
			MAX-ACCESS read-write
			STATUS current
			DESCRIPTION
				"Description."
			::= { autoBackupConfiguration 8 }

		
--         1.3.6.1.4.1.37950.1.1.5.10.12.8.7.9
-- 1.3.6.1.4.1.37950.1.1.5.10.12.8.7.9
-- 1.3.6.1.4.1.37950.1.1.5.10.12.8.7.9
-- 1.3.6.1.4.1.37950.1.1.5.10.12.8.7.9
-- 1.3.6.1.4.1.37950.1.1.5.10.12.8.7.9
-- 1.3.6.1.4.1.37950.1.1.5.10.12.8.7.9
-- 1.3.6.1.4.1.37950.1.1.5.10.12.8.7.9
-- 1.3.6.1.4.1.37950.1.1.5.10.12.8.7.9
		-- 1.3.6.1.4.1.37950.1.1.5.10.12.8.7.9
		autoBackupWeekThur OBJECT-TYPE
			SYNTAX INTEGER
				{
				disable(0),
				enable(1)
				}
			MAX-ACCESS read-write
			STATUS current
			DESCRIPTION
				"Description."
			::= { autoBackupConfiguration 9 }

		
--         1.3.6.1.4.1.37950.1.1.5.10.12.8.7.10
-- 1.3.6.1.4.1.37950.1.1.5.10.12.8.7.10
-- 1.3.6.1.4.1.37950.1.1.5.10.12.8.7.10
-- 1.3.6.1.4.1.37950.1.1.5.10.12.8.7.10
-- 1.3.6.1.4.1.37950.1.1.5.10.12.8.7.10
-- 1.3.6.1.4.1.37950.1.1.5.10.12.8.7.10
-- 1.3.6.1.4.1.37950.1.1.5.10.12.8.7.10
-- 1.3.6.1.4.1.37950.1.1.5.10.12.8.7.10
		-- 1.3.6.1.4.1.37950.1.1.5.10.12.8.7.10
		autoBackupWeekFri OBJECT-TYPE
			SYNTAX INTEGER
				{
				disable(0),
				enable(1)
				}
			MAX-ACCESS read-write
			STATUS current
			DESCRIPTION
				"Description."
			::= { autoBackupConfiguration 10 }

		
--         1.3.6.1.4.1.37950.1.1.5.10.12.8.7.11
-- 1.3.6.1.4.1.37950.1.1.5.10.12.8.7.11
-- 1.3.6.1.4.1.37950.1.1.5.10.12.8.7.11
-- 1.3.6.1.4.1.37950.1.1.5.10.12.8.7.11
-- 1.3.6.1.4.1.37950.1.1.5.10.12.8.7.11
-- 1.3.6.1.4.1.37950.1.1.5.10.12.8.7.11
-- 1.3.6.1.4.1.37950.1.1.5.10.12.8.7.11
-- 1.3.6.1.4.1.37950.1.1.5.10.12.8.7.11
		-- 1.3.6.1.4.1.37950.1.1.5.10.12.8.7.11
		autoBackupWeekSat OBJECT-TYPE
			SYNTAX INTEGER
				{
				disable(0),
				enable(1)
				}
			MAX-ACCESS read-write
			STATUS current
			DESCRIPTION
				"Description."
			::= { autoBackupConfiguration 11 }

		
--         1.3.6.1.4.1.37950.1.1.5.10.12.8.7.12
-- 1.3.6.1.4.1.37950.1.1.5.10.12.8.7.12
-- 1.3.6.1.4.1.37950.1.1.5.10.12.8.7.12
-- 1.3.6.1.4.1.37950.1.1.5.10.12.8.7.12
-- 1.3.6.1.4.1.37950.1.1.5.10.12.8.7.12
-- 1.3.6.1.4.1.37950.1.1.5.10.12.8.7.12
-- 1.3.6.1.4.1.37950.1.1.5.10.12.8.7.12
-- 1.3.6.1.4.1.37950.1.1.5.10.12.8.7.12
		-- 1.3.6.1.4.1.37950.1.1.5.10.12.8.7.12
		autoBackupWeekSun OBJECT-TYPE
			SYNTAX INTEGER
				{
				disable(0),
				enable(1)
				}
			MAX-ACCESS read-write
			STATUS current
			DESCRIPTION
				"Description."
			::= { autoBackupConfiguration 12 }

		
--         1.3.6.1.4.1.37950.1.1.5.10.12.8.7.13
-- 1.3.6.1.4.1.37950.1.1.5.10.12.8.7.13
-- 1.3.6.1.4.1.37950.1.1.5.10.12.8.7.13
-- 1.3.6.1.4.1.37950.1.1.5.10.12.8.7.13
-- 1.3.6.1.4.1.37950.1.1.5.10.12.8.7.13
-- 1.3.6.1.4.1.37950.1.1.5.10.12.8.7.13
-- 1.3.6.1.4.1.37950.1.1.5.10.12.8.7.13
-- 1.3.6.1.4.1.37950.1.1.5.10.12.8.7.13
		-- 1.3.6.1.4.1.37950.1.1.5.10.12.8.7.13
		autoBackupWeekHour OBJECT-TYPE
			SYNTAX Integer32 (0..23)
			MAX-ACCESS read-write
			STATUS current
			DESCRIPTION
				"Description."
			::= { autoBackupConfiguration 13 }

		
--         1.3.6.1.4.1.37950.1.1.5.10.12.8.7.14
-- 1.3.6.1.4.1.37950.1.1.5.10.12.8.7.14
-- 1.3.6.1.4.1.37950.1.1.5.10.12.8.7.14
-- 1.3.6.1.4.1.37950.1.1.5.10.12.8.7.14
-- 1.3.6.1.4.1.37950.1.1.5.10.12.8.7.14
-- 1.3.6.1.4.1.37950.1.1.5.10.12.8.7.14
-- 1.3.6.1.4.1.37950.1.1.5.10.12.8.7.14
-- 1.3.6.1.4.1.37950.1.1.5.10.12.8.7.14
		-- 1.3.6.1.4.1.37950.1.1.5.10.12.8.7.14
		autoBackupWeekMinute OBJECT-TYPE
			SYNTAX Integer32 (0..59)
			MAX-ACCESS read-write
			STATUS current
			DESCRIPTION
				"Description."
			::= { autoBackupConfiguration 14 }

		
--         1.3.6.1.4.1.37950.1.1.5.10.12.8.7.15
-- 1.3.6.1.4.1.37950.1.1.5.10.12.8.7.15
-- 1.3.6.1.4.1.37950.1.1.5.10.12.8.7.15
-- 1.3.6.1.4.1.37950.1.1.5.10.12.8.7.15
-- 1.3.6.1.4.1.37950.1.1.5.10.12.8.7.15
-- 1.3.6.1.4.1.37950.1.1.5.10.12.8.7.15
-- 1.3.6.1.4.1.37950.1.1.5.10.12.8.7.15
-- 1.3.6.1.4.1.37950.1.1.5.10.12.8.7.15
		-- 1.3.6.1.4.1.37950.1.1.5.10.12.8.7.15
		autoBackupTftpServerIP OBJECT-TYPE
			SYNTAX OCTET STRING
			MAX-ACCESS read-write
			STATUS current
			DESCRIPTION
				"Description."
			::= { autoBackupConfiguration 15 }

		
--         1.3.6.1.4.1.37950.1.1.5.10.12.8.7.16
-- 1.3.6.1.4.1.37950.1.1.5.10.12.8.7.16
-- 1.3.6.1.4.1.37950.1.1.5.10.12.8.7.16
-- 1.3.6.1.4.1.37950.1.1.5.10.12.8.7.16
-- 1.3.6.1.4.1.37950.1.1.5.10.12.8.7.16
-- 1.3.6.1.4.1.37950.1.1.5.10.12.8.7.16
-- 1.3.6.1.4.1.37950.1.1.5.10.12.8.7.16
-- 1.3.6.1.4.1.37950.1.1.5.10.12.8.7.16
		-- 1.3.6.1.4.1.37950.1.1.5.10.12.8.7.16
		autoBackupAction OBJECT-TYPE
			SYNTAX INTEGER
				{
				disable(0),
				enable(1)
				}
			MAX-ACCESS read-write
			STATUS current
			DESCRIPTION
				"Description."
			::= { autoBackupConfiguration 16 }

		
--         1.3.6.1.4.1.37950.1.1.5.10.12.8.8
-- 1.3.6.1.4.1.37950.1.1.5.10.12.8.8
-- 1.3.6.1.4.1.37950.1.1.5.10.12.8.8
-- 1.3.6.1.4.1.37950.1.1.5.10.12.8.8
-- 1.3.6.1.4.1.37950.1.1.5.10.12.8.8
-- 1.3.6.1.4.1.37950.1.1.5.10.12.8.8
-- 1.3.6.1.4.1.37950.1.1.5.10.12.8.8
-- 1.3.6.1.4.1.37950.1.1.5.10.12.8.8
		-- 1.3.6.1.4.1.37950.1.1.5.10.12.8.8
		autoBackupConfigTable OBJECT-TYPE
			SYNTAX SEQUENCE OF AutoBackupConfigEntry
			MAX-ACCESS not-accessible
			STATUS current
			DESCRIPTION
				"Description."
			::= { configFile 8 }

		
--         1.3.6.1.4.1.37950.1.1.5.10.12.8.8.1
-- 1.3.6.1.4.1.37950.1.1.5.10.12.8.8.1
-- 1.3.6.1.4.1.37950.1.1.5.10.12.8.8.1
-- 1.3.6.1.4.1.37950.1.1.5.10.12.8.8.1
-- 1.3.6.1.4.1.37950.1.1.5.10.12.8.8.1
-- 1.3.6.1.4.1.37950.1.1.5.10.12.8.8.1
-- 1.3.6.1.4.1.37950.1.1.5.10.12.8.8.1
-- 1.3.6.1.4.1.37950.1.1.5.10.12.8.8.1
		-- 1.3.6.1.4.1.37950.1.1.5.10.12.8.8.1
		autoBackupConfigEntry OBJECT-TYPE
			SYNTAX AutoBackupConfigEntry
			MAX-ACCESS not-accessible
			STATUS current
			DESCRIPTION
				"Description."
			INDEX { autoBackupEnable }
			::= { autoBackupConfigTable 1 }

		
		AutoBackupConfigEntry ::=
			SEQUENCE { 
				autoBackupEnable
					INTEGER,
				autoBackupTypeS
					INTEGER,
				autoBackupTimeoutValueS
					Unsigned32,
				autoBackupFixTimeDayS
					Integer32,
				autoBackupFixTimeHourS
					Integer32,
				autoBackupFixTimeMinuteS
					Integer32,
				autoBackupWeekMonS
					INTEGER,
				autoBackupWeekTuesS
					INTEGER,
				autoBackupWeekWedS
					INTEGER,
				autoBackupWeekThurS
					INTEGER,
				autoBackupWeekFriS
					INTEGER,
				autoBackupWeekSatS
					INTEGER,
				autoBackupWeekSunS
					INTEGER,
				autoBackupWeekHourS
					Integer32,
				autoBackupWeekMinuteS
					Integer32,
				autoBackupTftpServerIPS
					OCTET STRING
			 }

--         1.3.6.1.4.1.37950.1.1.5.10.12.8.8.1.1
-- 1.3.6.1.4.1.37950.1.1.5.10.12.8.8.1.1
-- 1.3.6.1.4.1.37950.1.1.5.10.12.8.8.1.1
-- 1.3.6.1.4.1.37950.1.1.5.10.12.8.8.1.1
-- 1.3.6.1.4.1.37950.1.1.5.10.12.8.8.1.1
-- 1.3.6.1.4.1.37950.1.1.5.10.12.8.8.1.1
-- 1.3.6.1.4.1.37950.1.1.5.10.12.8.8.1.1
-- 1.3.6.1.4.1.37950.1.1.5.10.12.8.8.1.1
		-- 1.3.6.1.4.1.37950.1.1.5.10.12.8.8.1.1
		autoBackupEnable OBJECT-TYPE
			SYNTAX INTEGER
				{
				disable(0),
				enable(1)
				}
			MAX-ACCESS read-write
			STATUS current
			DESCRIPTION
				"Description."
			::= { autoBackupConfigEntry 1 }

		
--         1.3.6.1.4.1.37950.1.1.5.10.12.8.8.1.2
-- 1.3.6.1.4.1.37950.1.1.5.10.12.8.8.1.2
-- 1.3.6.1.4.1.37950.1.1.5.10.12.8.8.1.2
-- 1.3.6.1.4.1.37950.1.1.5.10.12.8.8.1.2
-- 1.3.6.1.4.1.37950.1.1.5.10.12.8.8.1.2
-- 1.3.6.1.4.1.37950.1.1.5.10.12.8.8.1.2
-- 1.3.6.1.4.1.37950.1.1.5.10.12.8.8.1.2
-- 1.3.6.1.4.1.37950.1.1.5.10.12.8.8.1.2
		-- 1.3.6.1.4.1.37950.1.1.5.10.12.8.8.1.2
		autoBackupTypeS OBJECT-TYPE
			SYNTAX INTEGER
				{
				timeout(0),
				fix-time(1),
				week-day(2)
				}
			MAX-ACCESS read-write
			STATUS current
			DESCRIPTION
				"Description."
			::= { autoBackupConfigEntry 2 }

		
--         1.3.6.1.4.1.37950.1.1.5.10.12.8.8.1.3
-- 1.3.6.1.4.1.37950.1.1.5.10.12.8.8.1.3
-- 1.3.6.1.4.1.37950.1.1.5.10.12.8.8.1.3
-- 1.3.6.1.4.1.37950.1.1.5.10.12.8.8.1.3
-- 1.3.6.1.4.1.37950.1.1.5.10.12.8.8.1.3
-- 1.3.6.1.4.1.37950.1.1.5.10.12.8.8.1.3
-- 1.3.6.1.4.1.37950.1.1.5.10.12.8.8.1.3
-- 1.3.6.1.4.1.37950.1.1.5.10.12.8.8.1.3
		-- 1.3.6.1.4.1.37950.1.1.5.10.12.8.8.1.3
		autoBackupTimeoutValueS OBJECT-TYPE
			SYNTAX Unsigned32 (60..2678400)
			MAX-ACCESS read-write
			STATUS current
			DESCRIPTION
				"Description."
			::= { autoBackupConfigEntry 3 }

		
--         1.3.6.1.4.1.37950.1.1.5.10.12.8.8.1.4
-- 1.3.6.1.4.1.37950.1.1.5.10.12.8.8.1.4
-- 1.3.6.1.4.1.37950.1.1.5.10.12.8.8.1.4
-- 1.3.6.1.4.1.37950.1.1.5.10.12.8.8.1.4
-- 1.3.6.1.4.1.37950.1.1.5.10.12.8.8.1.4
-- 1.3.6.1.4.1.37950.1.1.5.10.12.8.8.1.4
-- 1.3.6.1.4.1.37950.1.1.5.10.12.8.8.1.4
-- 1.3.6.1.4.1.37950.1.1.5.10.12.8.8.1.4
		-- 1.3.6.1.4.1.37950.1.1.5.10.12.8.8.1.4
		autoBackupFixTimeDayS OBJECT-TYPE
			SYNTAX Integer32 (1..31)
			MAX-ACCESS read-write
			STATUS current
			DESCRIPTION
				"Description."
			::= { autoBackupConfigEntry 4 }

		
--         1.3.6.1.4.1.37950.1.1.5.10.12.8.8.1.5
-- 1.3.6.1.4.1.37950.1.1.5.10.12.8.8.1.5
-- 1.3.6.1.4.1.37950.1.1.5.10.12.8.8.1.5
-- 1.3.6.1.4.1.37950.1.1.5.10.12.8.8.1.5
-- 1.3.6.1.4.1.37950.1.1.5.10.12.8.8.1.5
-- 1.3.6.1.4.1.37950.1.1.5.10.12.8.8.1.5
-- 1.3.6.1.4.1.37950.1.1.5.10.12.8.8.1.5
-- 1.3.6.1.4.1.37950.1.1.5.10.12.8.8.1.5
		-- 1.3.6.1.4.1.37950.1.1.5.10.12.8.8.1.5
		autoBackupFixTimeHourS OBJECT-TYPE
			SYNTAX Integer32 (0..23)
			MAX-ACCESS read-write
			STATUS current
			DESCRIPTION
				"Description."
			::= { autoBackupConfigEntry 5 }

		
--         1.3.6.1.4.1.37950.1.1.5.10.12.8.8.1.6
-- 1.3.6.1.4.1.37950.1.1.5.10.12.8.8.1.6
-- 1.3.6.1.4.1.37950.1.1.5.10.12.8.8.1.6
-- 1.3.6.1.4.1.37950.1.1.5.10.12.8.8.1.6
-- 1.3.6.1.4.1.37950.1.1.5.10.12.8.8.1.6
-- 1.3.6.1.4.1.37950.1.1.5.10.12.8.8.1.6
-- 1.3.6.1.4.1.37950.1.1.5.10.12.8.8.1.6
-- 1.3.6.1.4.1.37950.1.1.5.10.12.8.8.1.6
		-- 1.3.6.1.4.1.37950.1.1.5.10.12.8.8.1.6
		autoBackupFixTimeMinuteS OBJECT-TYPE
			SYNTAX Integer32 (0..59)
			MAX-ACCESS read-write
			STATUS current
			DESCRIPTION
				"Description."
			::= { autoBackupConfigEntry 6 }

		
--         1.3.6.1.4.1.37950.1.1.5.10.12.8.8.1.7
-- 1.3.6.1.4.1.37950.1.1.5.10.12.8.8.1.7
-- 1.3.6.1.4.1.37950.1.1.5.10.12.8.8.1.7
-- 1.3.6.1.4.1.37950.1.1.5.10.12.8.8.1.7
-- 1.3.6.1.4.1.37950.1.1.5.10.12.8.8.1.7
-- 1.3.6.1.4.1.37950.1.1.5.10.12.8.8.1.7
-- 1.3.6.1.4.1.37950.1.1.5.10.12.8.8.1.7
-- 1.3.6.1.4.1.37950.1.1.5.10.12.8.8.1.7
		-- 1.3.6.1.4.1.37950.1.1.5.10.12.8.8.1.7
		autoBackupWeekMonS OBJECT-TYPE
			SYNTAX INTEGER
				{
				disable(0),
				enable(1)
				}
			MAX-ACCESS read-write
			STATUS current
			DESCRIPTION
				"Description."
			::= { autoBackupConfigEntry 7 }

		
--         1.3.6.1.4.1.37950.1.1.5.10.12.8.8.1.8
-- 1.3.6.1.4.1.37950.1.1.5.10.12.8.8.1.8
-- 1.3.6.1.4.1.37950.1.1.5.10.12.8.8.1.8
-- 1.3.6.1.4.1.37950.1.1.5.10.12.8.8.1.8
-- 1.3.6.1.4.1.37950.1.1.5.10.12.8.8.1.8
-- 1.3.6.1.4.1.37950.1.1.5.10.12.8.8.1.8
-- 1.3.6.1.4.1.37950.1.1.5.10.12.8.8.1.8
-- 1.3.6.1.4.1.37950.1.1.5.10.12.8.8.1.8
		-- 1.3.6.1.4.1.37950.1.1.5.10.12.8.8.1.8
		autoBackupWeekTuesS OBJECT-TYPE
			SYNTAX INTEGER
				{
				disable(0),
				enable(1)
				}
			MAX-ACCESS read-write
			STATUS current
			DESCRIPTION
				"Description."
			::= { autoBackupConfigEntry 8 }

		
--         1.3.6.1.4.1.37950.1.1.5.10.12.8.8.1.9
-- 1.3.6.1.4.1.37950.1.1.5.10.12.8.8.1.9
-- 1.3.6.1.4.1.37950.1.1.5.10.12.8.8.1.9
-- 1.3.6.1.4.1.37950.1.1.5.10.12.8.8.1.9
-- 1.3.6.1.4.1.37950.1.1.5.10.12.8.8.1.9
-- 1.3.6.1.4.1.37950.1.1.5.10.12.8.8.1.9
-- 1.3.6.1.4.1.37950.1.1.5.10.12.8.8.1.9
-- 1.3.6.1.4.1.37950.1.1.5.10.12.8.8.1.9
		-- 1.3.6.1.4.1.37950.1.1.5.10.12.8.8.1.9
		autoBackupWeekWedS OBJECT-TYPE
			SYNTAX INTEGER
				{
				disable(0),
				enable(1)
				}
			MAX-ACCESS read-write
			STATUS current
			DESCRIPTION
				"Description."
			::= { autoBackupConfigEntry 9 }

		
--         1.3.6.1.4.1.37950.1.1.5.10.12.8.8.1.10
-- 1.3.6.1.4.1.37950.1.1.5.10.12.8.8.1.10
-- 1.3.6.1.4.1.37950.1.1.5.10.12.8.8.1.10
-- 1.3.6.1.4.1.37950.1.1.5.10.12.8.8.1.10
-- 1.3.6.1.4.1.37950.1.1.5.10.12.8.8.1.10
-- 1.3.6.1.4.1.37950.1.1.5.10.12.8.8.1.10
-- 1.3.6.1.4.1.37950.1.1.5.10.12.8.8.1.10
-- 1.3.6.1.4.1.37950.1.1.5.10.12.8.8.1.10
		-- 1.3.6.1.4.1.37950.1.1.5.10.12.8.8.1.10
		autoBackupWeekThurS OBJECT-TYPE
			SYNTAX INTEGER
				{
				disable(0),
				enable(1)
				}
			MAX-ACCESS read-write
			STATUS current
			DESCRIPTION
				"Description."
			::= { autoBackupConfigEntry 10 }

		
--         1.3.6.1.4.1.37950.1.1.5.10.12.8.8.1.11
-- 1.3.6.1.4.1.37950.1.1.5.10.12.8.8.1.11
-- 1.3.6.1.4.1.37950.1.1.5.10.12.8.8.1.11
-- 1.3.6.1.4.1.37950.1.1.5.10.12.8.8.1.11
-- 1.3.6.1.4.1.37950.1.1.5.10.12.8.8.1.11
-- 1.3.6.1.4.1.37950.1.1.5.10.12.8.8.1.11
-- 1.3.6.1.4.1.37950.1.1.5.10.12.8.8.1.11
-- 1.3.6.1.4.1.37950.1.1.5.10.12.8.8.1.11
		-- 1.3.6.1.4.1.37950.1.1.5.10.12.8.8.1.11
		autoBackupWeekFriS OBJECT-TYPE
			SYNTAX INTEGER
				{
				disable(0),
				enable(1)
				}
			MAX-ACCESS read-write
			STATUS current
			DESCRIPTION
				"Description."
			::= { autoBackupConfigEntry 11 }

		
--         1.3.6.1.4.1.37950.1.1.5.10.12.8.8.1.12
-- 1.3.6.1.4.1.37950.1.1.5.10.12.8.8.1.12
-- 1.3.6.1.4.1.37950.1.1.5.10.12.8.8.1.12
-- 1.3.6.1.4.1.37950.1.1.5.10.12.8.8.1.12
-- 1.3.6.1.4.1.37950.1.1.5.10.12.8.8.1.12
-- 1.3.6.1.4.1.37950.1.1.5.10.12.8.8.1.12
-- 1.3.6.1.4.1.37950.1.1.5.10.12.8.8.1.12
-- 1.3.6.1.4.1.37950.1.1.5.10.12.8.8.1.12
		-- 1.3.6.1.4.1.37950.1.1.5.10.12.8.8.1.12
		autoBackupWeekSatS OBJECT-TYPE
			SYNTAX INTEGER
				{
				disable(0),
				enable(1)
				}
			MAX-ACCESS read-write
			STATUS current
			DESCRIPTION
				"Description."
			::= { autoBackupConfigEntry 12 }

		
--         1.3.6.1.4.1.37950.1.1.5.10.12.8.8.1.13
-- 1.3.6.1.4.1.37950.1.1.5.10.12.8.8.1.13
-- 1.3.6.1.4.1.37950.1.1.5.10.12.8.8.1.13
-- 1.3.6.1.4.1.37950.1.1.5.10.12.8.8.1.13
-- 1.3.6.1.4.1.37950.1.1.5.10.12.8.8.1.13
-- 1.3.6.1.4.1.37950.1.1.5.10.12.8.8.1.13
-- 1.3.6.1.4.1.37950.1.1.5.10.12.8.8.1.13
-- 1.3.6.1.4.1.37950.1.1.5.10.12.8.8.1.13
		-- 1.3.6.1.4.1.37950.1.1.5.10.12.8.8.1.13
		autoBackupWeekSunS OBJECT-TYPE
			SYNTAX INTEGER
				{
				disable(0),
				enable(1)
				}
			MAX-ACCESS read-write
			STATUS current
			DESCRIPTION
				"Description."
			::= { autoBackupConfigEntry 13 }

		
--         1.3.6.1.4.1.37950.1.1.5.10.12.8.8.1.14
-- 1.3.6.1.4.1.37950.1.1.5.10.12.8.8.1.14
-- 1.3.6.1.4.1.37950.1.1.5.10.12.8.8.1.14
-- 1.3.6.1.4.1.37950.1.1.5.10.12.8.8.1.14
-- 1.3.6.1.4.1.37950.1.1.5.10.12.8.8.1.14
-- 1.3.6.1.4.1.37950.1.1.5.10.12.8.8.1.14
-- 1.3.6.1.4.1.37950.1.1.5.10.12.8.8.1.14
-- 1.3.6.1.4.1.37950.1.1.5.10.12.8.8.1.14
		-- 1.3.6.1.4.1.37950.1.1.5.10.12.8.8.1.14
		autoBackupWeekHourS OBJECT-TYPE
			SYNTAX Integer32 (0..23)
			MAX-ACCESS read-write
			STATUS current
			DESCRIPTION
				"Description."
			::= { autoBackupConfigEntry 14 }

		
--         1.3.6.1.4.1.37950.1.1.5.10.12.8.8.1.15
-- 1.3.6.1.4.1.37950.1.1.5.10.12.8.8.1.15
-- 1.3.6.1.4.1.37950.1.1.5.10.12.8.8.1.15
-- 1.3.6.1.4.1.37950.1.1.5.10.12.8.8.1.15
-- 1.3.6.1.4.1.37950.1.1.5.10.12.8.8.1.15
-- 1.3.6.1.4.1.37950.1.1.5.10.12.8.8.1.15
-- 1.3.6.1.4.1.37950.1.1.5.10.12.8.8.1.15
-- 1.3.6.1.4.1.37950.1.1.5.10.12.8.8.1.15
		-- 1.3.6.1.4.1.37950.1.1.5.10.12.8.8.1.15
		autoBackupWeekMinuteS OBJECT-TYPE
			SYNTAX Integer32 (0..59)
			MAX-ACCESS read-write
			STATUS current
			DESCRIPTION
				"Description."
			::= { autoBackupConfigEntry 15 }

		
--         1.3.6.1.4.1.37950.1.1.5.10.12.8.8.1.16
-- 1.3.6.1.4.1.37950.1.1.5.10.12.8.8.1.16
-- 1.3.6.1.4.1.37950.1.1.5.10.12.8.8.1.16
-- 1.3.6.1.4.1.37950.1.1.5.10.12.8.8.1.16
-- 1.3.6.1.4.1.37950.1.1.5.10.12.8.8.1.16
-- 1.3.6.1.4.1.37950.1.1.5.10.12.8.8.1.16
-- 1.3.6.1.4.1.37950.1.1.5.10.12.8.8.1.16
-- 1.3.6.1.4.1.37950.1.1.5.10.12.8.8.1.16
		-- 1.3.6.1.4.1.37950.1.1.5.10.12.8.8.1.16
		autoBackupTftpServerIPS OBJECT-TYPE
			SYNTAX OCTET STRING
			MAX-ACCESS read-write
			STATUS current
			DESCRIPTION
				"Description."
			::= { autoBackupConfigEntry 16 }

		
--          1.3.6.1.4.1.37950.1.1.5.10.12.9
-- 1.3.6.1.4.1.37950.1.1.5.10.12.9
-- 1.3.6.1.4.1.37950.1.1.5.10.12.9
-- 1.3.6.1.4.1.37950.1.1.5.10.12.9
-- 1.3.6.1.4.1.37950.1.1.5.10.12.9
-- 1.3.6.1.4.1.37950.1.1.5.10.12.9
-- 1.3.6.1.4.1.37950.1.1.5.10.12.9
-- 1.3.6.1.4.1.37950.1.1.5.10.12.9
-- 1.3.6.1.4.1.37950.1.1.5.10.12.9
		-- 1.3.6.1.4.1.37950.1.1.5.10.12.9
		systemUpgrade OBJECT IDENTIFIER ::= { v1600dSysCfg 9 }

		
--          1.3.6.1.4.1.37950.1.1.5.10.12.9.1
-- 1.3.6.1.4.1.37950.1.1.5.10.12.9.1
-- 1.3.6.1.4.1.37950.1.1.5.10.12.9.1
-- 1.3.6.1.4.1.37950.1.1.5.10.12.9.1
-- 1.3.6.1.4.1.37950.1.1.5.10.12.9.1
-- 1.3.6.1.4.1.37950.1.1.5.10.12.9.1
-- 1.3.6.1.4.1.37950.1.1.5.10.12.9.1
-- 1.3.6.1.4.1.37950.1.1.5.10.12.9.1
-- 1.3.6.1.4.1.37950.1.1.5.10.12.9.1
		-- 1.3.6.1.4.1.37950.1.1.5.10.12.9.1
		tftpServerIP OBJECT-TYPE
			SYNTAX IpAddress
			MAX-ACCESS read-write
			STATUS current
			DESCRIPTION
				"Description."
			::= { systemUpgrade 1 }

		
--          1.3.6.1.4.1.37950.1.1.5.10.12.9.2
-- 1.3.6.1.4.1.37950.1.1.5.10.12.9.2
-- 1.3.6.1.4.1.37950.1.1.5.10.12.9.2
-- 1.3.6.1.4.1.37950.1.1.5.10.12.9.2
-- 1.3.6.1.4.1.37950.1.1.5.10.12.9.2
-- 1.3.6.1.4.1.37950.1.1.5.10.12.9.2
-- 1.3.6.1.4.1.37950.1.1.5.10.12.9.2
-- 1.3.6.1.4.1.37950.1.1.5.10.12.9.2
-- 1.3.6.1.4.1.37950.1.1.5.10.12.9.2
		-- 1.3.6.1.4.1.37950.1.1.5.10.12.9.2
		fileType OBJECT-TYPE
			SYNTAX INTEGER
				{
				bld(1),
				kernel(2),
				rootfs(3)
				}
			MAX-ACCESS read-write
			STATUS current
			DESCRIPTION
				"Description."
			::= { systemUpgrade 2 }

		
--          1.3.6.1.4.1.37950.1.1.5.10.12.9.3
-- 1.3.6.1.4.1.37950.1.1.5.10.12.9.3
-- 1.3.6.1.4.1.37950.1.1.5.10.12.9.3
-- 1.3.6.1.4.1.37950.1.1.5.10.12.9.3
-- 1.3.6.1.4.1.37950.1.1.5.10.12.9.3
-- 1.3.6.1.4.1.37950.1.1.5.10.12.9.3
-- 1.3.6.1.4.1.37950.1.1.5.10.12.9.3
-- 1.3.6.1.4.1.37950.1.1.5.10.12.9.3
-- 1.3.6.1.4.1.37950.1.1.5.10.12.9.3
		-- 1.3.6.1.4.1.37950.1.1.5.10.12.9.3
		fileName OBJECT-TYPE
			SYNTAX OCTET STRING
			MAX-ACCESS read-write
			STATUS current
			DESCRIPTION
				"Description."
			::= { systemUpgrade 3 }

		
--          1.3.6.1.4.1.37950.1.1.5.10.12.9.4
-- 1.3.6.1.4.1.37950.1.1.5.10.12.9.4
-- 1.3.6.1.4.1.37950.1.1.5.10.12.9.4
-- 1.3.6.1.4.1.37950.1.1.5.10.12.9.4
-- 1.3.6.1.4.1.37950.1.1.5.10.12.9.4
-- 1.3.6.1.4.1.37950.1.1.5.10.12.9.4
-- 1.3.6.1.4.1.37950.1.1.5.10.12.9.4
-- 1.3.6.1.4.1.37950.1.1.5.10.12.9.4
-- 1.3.6.1.4.1.37950.1.1.5.10.12.9.4
		-- 1.3.6.1.4.1.37950.1.1.5.10.12.9.4
		upgradeCommit OBJECT-TYPE
			SYNTAX INTEGER { commit(1) }
			MAX-ACCESS read-write
			STATUS current
			DESCRIPTION
				"Description."
			::= { systemUpgrade 4 }

		
--         1.3.6.1.4.1.37950.1.1.5.10.12.9.5
-- 1.3.6.1.4.1.37950.1.1.5.10.12.9.5
-- 1.3.6.1.4.1.37950.1.1.5.10.12.9.5
-- 1.3.6.1.4.1.37950.1.1.5.10.12.9.5
-- 1.3.6.1.4.1.37950.1.1.5.10.12.9.5
-- 1.3.6.1.4.1.37950.1.1.5.10.12.9.5
-- 1.3.6.1.4.1.37950.1.1.5.10.12.9.5
-- 1.3.6.1.4.1.37950.1.1.5.10.12.9.5
		-- 1.3.6.1.4.1.37950.1.1.5.10.12.9.5
		upgradeStatus OBJECT-TYPE
			SYNTAX OCTET STRING (SIZE (1..48))
			MAX-ACCESS read-only
			STATUS current
			DESCRIPTION
				"Description."
			::= { systemUpgrade 5 }

		
--            1.3.6.1.4.1.37950.1.1.5.10.12.10
-- 1.3.6.1.4.1.37950.1.1.5.10.12.10
-- 1.3.6.1.4.1.37950.1.1.5.10.12.10
-- 1.3.6.1.4.1.37950.1.1.5.10.12.10
-- 1.3.6.1.4.1.37950.1.1.5.10.12.10
-- 1.3.6.1.4.1.37950.1.1.5.10.12.10
-- 1.3.6.1.4.1.37950.1.1.5.10.12.10
-- 1.3.6.1.4.1.37950.1.1.5.10.12.10
-- 1.3.6.1.4.1.37950.1.1.5.10.12.10
-- 1.3.6.1.4.1.37950.1.1.5.10.12.10
-- 1.3.6.1.4.1.37950.1.1.5.10.12.10
		-- 1.3.6.1.4.1.37950.1.1.5.10.12.10
		auxPortCfg OBJECT IDENTIFIER ::= { v1600dSysCfg 10 }

		
--          1.3.6.1.4.1.37950.1.1.5.10.12.10.1
-- 1.3.6.1.4.1.37950.1.1.5.10.12.10.1
-- 1.3.6.1.4.1.37950.1.1.5.10.12.10.1
-- 1.3.6.1.4.1.37950.1.1.5.10.12.10.1
-- 1.3.6.1.4.1.37950.1.1.5.10.12.10.1
-- 1.3.6.1.4.1.37950.1.1.5.10.12.10.1
-- 1.3.6.1.4.1.37950.1.1.5.10.12.10.1
-- 1.3.6.1.4.1.37950.1.1.5.10.12.10.1
-- 1.3.6.1.4.1.37950.1.1.5.10.12.10.1
		-- 1.3.6.1.4.1.37950.1.1.5.10.12.10.1
		auxIP OBJECT-TYPE
			SYNTAX IpAddress
			MAX-ACCESS read-write
			STATUS current
			DESCRIPTION
				"Description."
			::= { auxPortCfg 1 }

		
--          1.3.6.1.4.1.37950.1.1.5.10.12.10.2
-- 1.3.6.1.4.1.37950.1.1.5.10.12.10.2
-- 1.3.6.1.4.1.37950.1.1.5.10.12.10.2
-- 1.3.6.1.4.1.37950.1.1.5.10.12.10.2
-- 1.3.6.1.4.1.37950.1.1.5.10.12.10.2
-- 1.3.6.1.4.1.37950.1.1.5.10.12.10.2
-- 1.3.6.1.4.1.37950.1.1.5.10.12.10.2
-- 1.3.6.1.4.1.37950.1.1.5.10.12.10.2
-- 1.3.6.1.4.1.37950.1.1.5.10.12.10.2
		-- 1.3.6.1.4.1.37950.1.1.5.10.12.10.2
		auxIPMask OBJECT-TYPE
			SYNTAX IpAddress
			MAX-ACCESS read-write
			STATUS current
			DESCRIPTION
				"Description."
			::= { auxPortCfg 2 }

		
--          1.3.6.1.4.1.37950.1.1.5.10.12.10.3
-- 1.3.6.1.4.1.37950.1.1.5.10.12.10.3
-- 1.3.6.1.4.1.37950.1.1.5.10.12.10.3
-- 1.3.6.1.4.1.37950.1.1.5.10.12.10.3
-- 1.3.6.1.4.1.37950.1.1.5.10.12.10.3
-- 1.3.6.1.4.1.37950.1.1.5.10.12.10.3
-- 1.3.6.1.4.1.37950.1.1.5.10.12.10.3
-- 1.3.6.1.4.1.37950.1.1.5.10.12.10.3
-- 1.3.6.1.4.1.37950.1.1.5.10.12.10.3
		-- 1.3.6.1.4.1.37950.1.1.5.10.12.10.3
		auxIPAction OBJECT-TYPE
			SYNTAX INTEGER
				{
				edit(1),
				delete(2)
				}
			MAX-ACCESS read-write
			STATUS current
			DESCRIPTION
				"Description."
			::= { auxPortCfg 3 }

		
--         1.3.6.1.4.1.37950.1.1.5.10.12.10.4
-- 1.3.6.1.4.1.37950.1.1.5.10.12.10.4
-- 1.3.6.1.4.1.37950.1.1.5.10.12.10.4
-- 1.3.6.1.4.1.37950.1.1.5.10.12.10.4
-- 1.3.6.1.4.1.37950.1.1.5.10.12.10.4
-- 1.3.6.1.4.1.37950.1.1.5.10.12.10.4
-- 1.3.6.1.4.1.37950.1.1.5.10.12.10.4
-- 1.3.6.1.4.1.37950.1.1.5.10.12.10.4
		-- 1.3.6.1.4.1.37950.1.1.5.10.12.10.4
		auxIPGateway OBJECT-TYPE
			SYNTAX IpAddress
			MAX-ACCESS read-write
			STATUS current
			DESCRIPTION
				"Description."
			::= { auxPortCfg 4 }

		
--         1.3.6.1.4.1.37950.1.1.5.10.12.10.5
-- 1.3.6.1.4.1.37950.1.1.5.10.12.10.5
-- 1.3.6.1.4.1.37950.1.1.5.10.12.10.5
-- 1.3.6.1.4.1.37950.1.1.5.10.12.10.5
-- 1.3.6.1.4.1.37950.1.1.5.10.12.10.5
-- 1.3.6.1.4.1.37950.1.1.5.10.12.10.5
-- 1.3.6.1.4.1.37950.1.1.5.10.12.10.5
-- 1.3.6.1.4.1.37950.1.1.5.10.12.10.5
		-- 1.3.6.1.4.1.37950.1.1.5.10.12.10.5
		auxIPMasterDNS OBJECT-TYPE
			SYNTAX IpAddress
			MAX-ACCESS read-write
			STATUS current
			DESCRIPTION
				"Description."
			::= { auxPortCfg 5 }

		
--         1.3.6.1.4.1.37950.1.1.5.10.12.10.6
-- 1.3.6.1.4.1.37950.1.1.5.10.12.10.6
-- 1.3.6.1.4.1.37950.1.1.5.10.12.10.6
-- 1.3.6.1.4.1.37950.1.1.5.10.12.10.6
-- 1.3.6.1.4.1.37950.1.1.5.10.12.10.6
-- 1.3.6.1.4.1.37950.1.1.5.10.12.10.6
-- 1.3.6.1.4.1.37950.1.1.5.10.12.10.6
-- 1.3.6.1.4.1.37950.1.1.5.10.12.10.6
		-- 1.3.6.1.4.1.37950.1.1.5.10.12.10.6
		auxIPSlaveDNS OBJECT-TYPE
			SYNTAX IpAddress
			MAX-ACCESS read-write
			STATUS current
			DESCRIPTION
				"Description."
			::= { auxPortCfg 6 }

		
--         1.3.6.1.4.1.37950.1.1.5.10.12.10.7
-- 1.3.6.1.4.1.37950.1.1.5.10.12.10.7
-- 1.3.6.1.4.1.37950.1.1.5.10.12.10.7
-- 1.3.6.1.4.1.37950.1.1.5.10.12.10.7
-- 1.3.6.1.4.1.37950.1.1.5.10.12.10.7
-- 1.3.6.1.4.1.37950.1.1.5.10.12.10.7
-- 1.3.6.1.4.1.37950.1.1.5.10.12.10.7
-- 1.3.6.1.4.1.37950.1.1.5.10.12.10.7
		-- 1.3.6.1.4.1.37950.1.1.5.10.12.10.7
		auxIPv6 OBJECT IDENTIFIER ::= { auxPortCfg 7 }

		
--         1.3.6.1.4.1.37950.1.1.5.10.12.10.7.1
-- 1.3.6.1.4.1.37950.1.1.5.10.12.10.7.1
-- 1.3.6.1.4.1.37950.1.1.5.10.12.10.7.1
-- 1.3.6.1.4.1.37950.1.1.5.10.12.10.7.1
-- 1.3.6.1.4.1.37950.1.1.5.10.12.10.7.1
-- 1.3.6.1.4.1.37950.1.1.5.10.12.10.7.1
-- 1.3.6.1.4.1.37950.1.1.5.10.12.10.7.1
-- 1.3.6.1.4.1.37950.1.1.5.10.12.10.7.1
		-- 1.3.6.1.4.1.37950.1.1.5.10.12.10.7.1
		auxIPv6Addr OBJECT-TYPE
			SYNTAX OCTET STRING
			MAX-ACCESS read-write
			STATUS current
			DESCRIPTION
				"Description."
			::= { auxIPv6 1 }

		
--         1.3.6.1.4.1.37950.1.1.5.10.12.10.7.2
-- 1.3.6.1.4.1.37950.1.1.5.10.12.10.7.2
-- 1.3.6.1.4.1.37950.1.1.5.10.12.10.7.2
-- 1.3.6.1.4.1.37950.1.1.5.10.12.10.7.2
-- 1.3.6.1.4.1.37950.1.1.5.10.12.10.7.2
-- 1.3.6.1.4.1.37950.1.1.5.10.12.10.7.2
-- 1.3.6.1.4.1.37950.1.1.5.10.12.10.7.2
-- 1.3.6.1.4.1.37950.1.1.5.10.12.10.7.2
		-- 1.3.6.1.4.1.37950.1.1.5.10.12.10.7.2
		auxIPv6AddrLength OBJECT-TYPE
			SYNTAX Integer32
			MAX-ACCESS read-write
			STATUS current
			DESCRIPTION
				"Description."
			::= { auxIPv6 2 }

		
--         1.3.6.1.4.1.37950.1.1.5.10.12.10.7.3
-- 1.3.6.1.4.1.37950.1.1.5.10.12.10.7.3
-- 1.3.6.1.4.1.37950.1.1.5.10.12.10.7.3
-- 1.3.6.1.4.1.37950.1.1.5.10.12.10.7.3
-- 1.3.6.1.4.1.37950.1.1.5.10.12.10.7.3
-- 1.3.6.1.4.1.37950.1.1.5.10.12.10.7.3
-- 1.3.6.1.4.1.37950.1.1.5.10.12.10.7.3
-- 1.3.6.1.4.1.37950.1.1.5.10.12.10.7.3
		-- 1.3.6.1.4.1.37950.1.1.5.10.12.10.7.3
		auxIPv6AddrType OBJECT-TYPE
			SYNTAX INTEGER
				{
				normal(1),
				eui64(2)
				}
			MAX-ACCESS read-write
			STATUS current
			DESCRIPTION
				"Description."
			::= { auxIPv6 3 }

		
--         1.3.6.1.4.1.37950.1.1.5.10.12.10.7.4
-- 1.3.6.1.4.1.37950.1.1.5.10.12.10.7.4
-- 1.3.6.1.4.1.37950.1.1.5.10.12.10.7.4
-- 1.3.6.1.4.1.37950.1.1.5.10.12.10.7.4
-- 1.3.6.1.4.1.37950.1.1.5.10.12.10.7.4
-- 1.3.6.1.4.1.37950.1.1.5.10.12.10.7.4
-- 1.3.6.1.4.1.37950.1.1.5.10.12.10.7.4
-- 1.3.6.1.4.1.37950.1.1.5.10.12.10.7.4
		-- 1.3.6.1.4.1.37950.1.1.5.10.12.10.7.4
		auxIPv6Gateway OBJECT-TYPE
			SYNTAX OCTET STRING
			MAX-ACCESS read-write
			STATUS current
			DESCRIPTION
				"Description."
			::= { auxIPv6 4 }

		
--         1.3.6.1.4.1.37950.1.1.5.10.12.10.7.5
-- 1.3.6.1.4.1.37950.1.1.5.10.12.10.7.5
-- 1.3.6.1.4.1.37950.1.1.5.10.12.10.7.5
-- 1.3.6.1.4.1.37950.1.1.5.10.12.10.7.5
-- 1.3.6.1.4.1.37950.1.1.5.10.12.10.7.5
-- 1.3.6.1.4.1.37950.1.1.5.10.12.10.7.5
-- 1.3.6.1.4.1.37950.1.1.5.10.12.10.7.5
-- 1.3.6.1.4.1.37950.1.1.5.10.12.10.7.5
		-- 1.3.6.1.4.1.37950.1.1.5.10.12.10.7.5
		auxIPv6AddrAction OBJECT-TYPE
			SYNTAX INTEGER
				{
				add(1),
				del(2)
				}
			MAX-ACCESS read-write
			STATUS current
			DESCRIPTION
				"Description."
			::= { auxIPv6 5 }

		
--         1.3.6.1.4.1.37950.1.1.5.10.12.10.7.6
-- 1.3.6.1.4.1.37950.1.1.5.10.12.10.7.6
-- 1.3.6.1.4.1.37950.1.1.5.10.12.10.7.6
-- 1.3.6.1.4.1.37950.1.1.5.10.12.10.7.6
-- 1.3.6.1.4.1.37950.1.1.5.10.12.10.7.6
-- 1.3.6.1.4.1.37950.1.1.5.10.12.10.7.6
-- 1.3.6.1.4.1.37950.1.1.5.10.12.10.7.6
-- 1.3.6.1.4.1.37950.1.1.5.10.12.10.7.6
		-- 1.3.6.1.4.1.37950.1.1.5.10.12.10.7.6
		auxIPv6Table OBJECT-TYPE
			SYNTAX SEQUENCE OF AuxIPv6Entry
			MAX-ACCESS not-accessible
			STATUS current
			DESCRIPTION
				"Description."
			::= { auxIPv6 6 }

		
--         1.3.6.1.4.1.37950.1.1.5.10.12.10.7.6.1
-- 1.3.6.1.4.1.37950.1.1.5.10.12.10.7.6.1
-- 1.3.6.1.4.1.37950.1.1.5.10.12.10.7.6.1
-- 1.3.6.1.4.1.37950.1.1.5.10.12.10.7.6.1
-- 1.3.6.1.4.1.37950.1.1.5.10.12.10.7.6.1
-- 1.3.6.1.4.1.37950.1.1.5.10.12.10.7.6.1
-- 1.3.6.1.4.1.37950.1.1.5.10.12.10.7.6.1
-- 1.3.6.1.4.1.37950.1.1.5.10.12.10.7.6.1
		-- 1.3.6.1.4.1.37950.1.1.5.10.12.10.7.6.1
		auxIPv6Entry OBJECT-TYPE
			SYNTAX AuxIPv6Entry
			MAX-ACCESS not-accessible
			STATUS current
			DESCRIPTION
				"Description."
			INDEX { auxIPv6Address, auxIPv6AddressLength }
			::= { auxIPv6Table 1 }

		
		AuxIPv6Entry ::=
			SEQUENCE { 
				auxIPv6Address
					OCTET STRING,
				auxIPv6AddressLength
					Integer32,
				auxIPv6AddressType
					OCTET STRING,
				auxIPv6GatewayAddr
					OCTET STRING
			 }

--         1.3.6.1.4.1.37950.1.1.5.10.12.10.7.6.1.1
-- 1.3.6.1.4.1.37950.1.1.5.10.12.10.7.6.1.1
-- 1.3.6.1.4.1.37950.1.1.5.10.12.10.7.6.1.1
-- 1.3.6.1.4.1.37950.1.1.5.10.12.10.7.6.1.1
-- 1.3.6.1.4.1.37950.1.1.5.10.12.10.7.6.1.1
-- 1.3.6.1.4.1.37950.1.1.5.10.12.10.7.6.1.1
-- 1.3.6.1.4.1.37950.1.1.5.10.12.10.7.6.1.1
-- 1.3.6.1.4.1.37950.1.1.5.10.12.10.7.6.1.1
		-- 1.3.6.1.4.1.37950.1.1.5.10.12.10.7.6.1.1
		auxIPv6Address OBJECT-TYPE
			SYNTAX OCTET STRING
			MAX-ACCESS read-only
			STATUS current
			DESCRIPTION
				"Description."
			::= { auxIPv6Entry 1 }

		
--         1.3.6.1.4.1.37950.1.1.5.10.12.10.7.6.1.2
-- 1.3.6.1.4.1.37950.1.1.5.10.12.10.7.6.1.2
-- 1.3.6.1.4.1.37950.1.1.5.10.12.10.7.6.1.2
-- 1.3.6.1.4.1.37950.1.1.5.10.12.10.7.6.1.2
-- 1.3.6.1.4.1.37950.1.1.5.10.12.10.7.6.1.2
-- 1.3.6.1.4.1.37950.1.1.5.10.12.10.7.6.1.2
-- 1.3.6.1.4.1.37950.1.1.5.10.12.10.7.6.1.2
-- 1.3.6.1.4.1.37950.1.1.5.10.12.10.7.6.1.2
		-- 1.3.6.1.4.1.37950.1.1.5.10.12.10.7.6.1.2
		auxIPv6AddressLength OBJECT-TYPE
			SYNTAX Integer32
			MAX-ACCESS read-only
			STATUS current
			DESCRIPTION
				"Description."
			::= { auxIPv6Entry 2 }

		
--         1.3.6.1.4.1.37950.1.1.5.10.12.10.7.6.1.3
-- 1.3.6.1.4.1.37950.1.1.5.10.12.10.7.6.1.3
-- 1.3.6.1.4.1.37950.1.1.5.10.12.10.7.6.1.3
-- 1.3.6.1.4.1.37950.1.1.5.10.12.10.7.6.1.3
-- 1.3.6.1.4.1.37950.1.1.5.10.12.10.7.6.1.3
-- 1.3.6.1.4.1.37950.1.1.5.10.12.10.7.6.1.3
-- 1.3.6.1.4.1.37950.1.1.5.10.12.10.7.6.1.3
-- 1.3.6.1.4.1.37950.1.1.5.10.12.10.7.6.1.3
		-- 1.3.6.1.4.1.37950.1.1.5.10.12.10.7.6.1.3
		auxIPv6AddressType OBJECT-TYPE
			SYNTAX OCTET STRING
			MAX-ACCESS read-write
			STATUS current
			DESCRIPTION
				"Description."
			::= { auxIPv6Entry 3 }

		
--         1.3.6.1.4.1.37950.1.1.5.10.12.10.7.6.1.4
-- 1.3.6.1.4.1.37950.1.1.5.10.12.10.7.6.1.4
-- 1.3.6.1.4.1.37950.1.1.5.10.12.10.7.6.1.4
-- 1.3.6.1.4.1.37950.1.1.5.10.12.10.7.6.1.4
-- 1.3.6.1.4.1.37950.1.1.5.10.12.10.7.6.1.4
-- 1.3.6.1.4.1.37950.1.1.5.10.12.10.7.6.1.4
-- 1.3.6.1.4.1.37950.1.1.5.10.12.10.7.6.1.4
-- 1.3.6.1.4.1.37950.1.1.5.10.12.10.7.6.1.4
		-- 1.3.6.1.4.1.37950.1.1.5.10.12.10.7.6.1.4
		auxIPv6GatewayAddr OBJECT-TYPE
			SYNTAX OCTET STRING
			MAX-ACCESS read-only
			STATUS current
			DESCRIPTION
				"Description."
			::= { auxIPv6Entry 4 }

		
--          1.3.6.1.4.1.37950.1.1.5.10.12.11
-- 1.3.6.1.4.1.37950.1.1.5.10.12.11
-- 1.3.6.1.4.1.37950.1.1.5.10.12.11
-- 1.3.6.1.4.1.37950.1.1.5.10.12.11
-- 1.3.6.1.4.1.37950.1.1.5.10.12.11
-- 1.3.6.1.4.1.37950.1.1.5.10.12.11
-- 1.3.6.1.4.1.37950.1.1.5.10.12.11
-- 1.3.6.1.4.1.37950.1.1.5.10.12.11
-- 1.3.6.1.4.1.37950.1.1.5.10.12.11
		-- 1.3.6.1.4.1.37950.1.1.5.10.12.11
		fanCfg OBJECT IDENTIFIER ::= { v1600dSysCfg 11 }

		
--          1.3.6.1.4.1.37950.1.1.5.10.12.11.1
-- 1.3.6.1.4.1.37950.1.1.5.10.12.11.1
-- 1.3.6.1.4.1.37950.1.1.5.10.12.11.1
-- 1.3.6.1.4.1.37950.1.1.5.10.12.11.1
-- 1.3.6.1.4.1.37950.1.1.5.10.12.11.1
-- 1.3.6.1.4.1.37950.1.1.5.10.12.11.1
-- 1.3.6.1.4.1.37950.1.1.5.10.12.11.1
-- 1.3.6.1.4.1.37950.1.1.5.10.12.11.1
-- 1.3.6.1.4.1.37950.1.1.5.10.12.11.1
		-- 1.3.6.1.4.1.37950.1.1.5.10.12.11.1
		fanMode OBJECT-TYPE
			SYNTAX INTEGER
				{
				open(1),
				close(2),
				auto(3)
				}
			MAX-ACCESS read-write
			STATUS current
			DESCRIPTION
				"Description."
			::= { fanCfg 1 }

		
--          1.3.6.1.4.1.37950.1.1.5.10.12.11.2
-- 1.3.6.1.4.1.37950.1.1.5.10.12.11.2
-- 1.3.6.1.4.1.37950.1.1.5.10.12.11.2
-- 1.3.6.1.4.1.37950.1.1.5.10.12.11.2
-- 1.3.6.1.4.1.37950.1.1.5.10.12.11.2
-- 1.3.6.1.4.1.37950.1.1.5.10.12.11.2
-- 1.3.6.1.4.1.37950.1.1.5.10.12.11.2
-- 1.3.6.1.4.1.37950.1.1.5.10.12.11.2
-- 1.3.6.1.4.1.37950.1.1.5.10.12.11.2
		-- 1.3.6.1.4.1.37950.1.1.5.10.12.11.2
		fanOpenTemperature OBJECT-TYPE
			SYNTAX INTEGER (20..80)
			MAX-ACCESS read-write
			STATUS current
			DESCRIPTION
				"Description."
			::= { fanCfg 2 }

		
--          1.3.6.1.4.1.37950.1.1.5.10.12.12
-- 1.3.6.1.4.1.37950.1.1.5.10.12.12
-- 1.3.6.1.4.1.37950.1.1.5.10.12.12
-- 1.3.6.1.4.1.37950.1.1.5.10.12.12
-- 1.3.6.1.4.1.37950.1.1.5.10.12.12
-- 1.3.6.1.4.1.37950.1.1.5.10.12.12
-- 1.3.6.1.4.1.37950.1.1.5.10.12.12
-- 1.3.6.1.4.1.37950.1.1.5.10.12.12
-- 1.3.6.1.4.1.37950.1.1.5.10.12.12
		-- 1.3.6.1.4.1.37950.1.1.5.10.12.12
		rtcCfg OBJECT IDENTIFIER ::= { v1600dSysCfg 12 }

		
--          1.3.6.1.4.1.37950.1.1.5.10.12.12.1
-- 1.3.6.1.4.1.37950.1.1.5.10.12.12.1
-- 1.3.6.1.4.1.37950.1.1.5.10.12.12.1
-- 1.3.6.1.4.1.37950.1.1.5.10.12.12.1
-- 1.3.6.1.4.1.37950.1.1.5.10.12.12.1
-- 1.3.6.1.4.1.37950.1.1.5.10.12.12.1
-- 1.3.6.1.4.1.37950.1.1.5.10.12.12.1
-- 1.3.6.1.4.1.37950.1.1.5.10.12.12.1
-- 1.3.6.1.4.1.37950.1.1.5.10.12.12.1
		-- 1.3.6.1.4.1.37950.1.1.5.10.12.12.1
		year OBJECT-TYPE
			SYNTAX INTEGER (2000..2099)
			MAX-ACCESS read-write
			STATUS current
			DESCRIPTION
				"Description."
			::= { rtcCfg 1 }

		
--          1.3.6.1.4.1.37950.1.1.5.10.12.12.2
-- 1.3.6.1.4.1.37950.1.1.5.10.12.12.2
-- 1.3.6.1.4.1.37950.1.1.5.10.12.12.2
-- 1.3.6.1.4.1.37950.1.1.5.10.12.12.2
-- 1.3.6.1.4.1.37950.1.1.5.10.12.12.2
-- 1.3.6.1.4.1.37950.1.1.5.10.12.12.2
-- 1.3.6.1.4.1.37950.1.1.5.10.12.12.2
-- 1.3.6.1.4.1.37950.1.1.5.10.12.12.2
-- 1.3.6.1.4.1.37950.1.1.5.10.12.12.2
		-- 1.3.6.1.4.1.37950.1.1.5.10.12.12.2
		month OBJECT-TYPE
			SYNTAX INTEGER (1..12)
			MAX-ACCESS read-write
			STATUS current
			DESCRIPTION
				"Description."
			::= { rtcCfg 2 }

		
--          1.3.6.1.4.1.37950.1.1.5.10.12.12.3
-- 1.3.6.1.4.1.37950.1.1.5.10.12.12.3
-- 1.3.6.1.4.1.37950.1.1.5.10.12.12.3
-- 1.3.6.1.4.1.37950.1.1.5.10.12.12.3
-- 1.3.6.1.4.1.37950.1.1.5.10.12.12.3
-- 1.3.6.1.4.1.37950.1.1.5.10.12.12.3
-- 1.3.6.1.4.1.37950.1.1.5.10.12.12.3
-- 1.3.6.1.4.1.37950.1.1.5.10.12.12.3
-- 1.3.6.1.4.1.37950.1.1.5.10.12.12.3
		-- 1.3.6.1.4.1.37950.1.1.5.10.12.12.3
		day OBJECT-TYPE
			SYNTAX INTEGER (1..31)
			MAX-ACCESS read-write
			STATUS current
			DESCRIPTION
				"Description."
			::= { rtcCfg 3 }

		
--          1.3.6.1.4.1.37950.1.1.5.10.12.12.4
-- 1.3.6.1.4.1.37950.1.1.5.10.12.12.4
-- 1.3.6.1.4.1.37950.1.1.5.10.12.12.4
-- 1.3.6.1.4.1.37950.1.1.5.10.12.12.4
-- 1.3.6.1.4.1.37950.1.1.5.10.12.12.4
-- 1.3.6.1.4.1.37950.1.1.5.10.12.12.4
-- 1.3.6.1.4.1.37950.1.1.5.10.12.12.4
-- 1.3.6.1.4.1.37950.1.1.5.10.12.12.4
-- 1.3.6.1.4.1.37950.1.1.5.10.12.12.4
		-- 1.3.6.1.4.1.37950.1.1.5.10.12.12.4
		hour OBJECT-TYPE
			SYNTAX INTEGER (0..23)
			MAX-ACCESS read-write
			STATUS current
			DESCRIPTION
				"Description."
			::= { rtcCfg 4 }

		
--          1.3.6.1.4.1.37950.1.1.5.10.12.12.5
-- 1.3.6.1.4.1.37950.1.1.5.10.12.12.5
-- 1.3.6.1.4.1.37950.1.1.5.10.12.12.5
-- 1.3.6.1.4.1.37950.1.1.5.10.12.12.5
-- 1.3.6.1.4.1.37950.1.1.5.10.12.12.5
-- 1.3.6.1.4.1.37950.1.1.5.10.12.12.5
-- 1.3.6.1.4.1.37950.1.1.5.10.12.12.5
-- 1.3.6.1.4.1.37950.1.1.5.10.12.12.5
-- 1.3.6.1.4.1.37950.1.1.5.10.12.12.5
		-- 1.3.6.1.4.1.37950.1.1.5.10.12.12.5
		minute OBJECT-TYPE
			SYNTAX INTEGER (0..59)
			MAX-ACCESS read-write
			STATUS current
			DESCRIPTION
				"Description."
			::= { rtcCfg 5 }

		
--          1.3.6.1.4.1.37950.1.1.5.10.12.12.6
-- 1.3.6.1.4.1.37950.1.1.5.10.12.12.6
-- 1.3.6.1.4.1.37950.1.1.5.10.12.12.6
-- 1.3.6.1.4.1.37950.1.1.5.10.12.12.6
-- 1.3.6.1.4.1.37950.1.1.5.10.12.12.6
-- 1.3.6.1.4.1.37950.1.1.5.10.12.12.6
-- 1.3.6.1.4.1.37950.1.1.5.10.12.12.6
-- 1.3.6.1.4.1.37950.1.1.5.10.12.12.6
-- 1.3.6.1.4.1.37950.1.1.5.10.12.12.6
		-- 1.3.6.1.4.1.37950.1.1.5.10.12.12.6
		second OBJECT-TYPE
			SYNTAX INTEGER (0..59)
			MAX-ACCESS read-write
			STATUS current
			DESCRIPTION
				"Description."
			::= { rtcCfg 6 }

		
--          1.3.6.1.4.1.37950.1.1.5.10.12.12.7
-- 1.3.6.1.4.1.37950.1.1.5.10.12.12.7
-- 1.3.6.1.4.1.37950.1.1.5.10.12.12.7
-- 1.3.6.1.4.1.37950.1.1.5.10.12.12.7
-- 1.3.6.1.4.1.37950.1.1.5.10.12.12.7
-- 1.3.6.1.4.1.37950.1.1.5.10.12.12.7
-- 1.3.6.1.4.1.37950.1.1.5.10.12.12.7
-- 1.3.6.1.4.1.37950.1.1.5.10.12.12.7
-- 1.3.6.1.4.1.37950.1.1.5.10.12.12.7
		-- 1.3.6.1.4.1.37950.1.1.5.10.12.12.7
		rtcAction OBJECT-TYPE
			SYNTAX INTEGER { commit(1) }
			MAX-ACCESS read-write
			STATUS current
			DESCRIPTION
				"Description."
			::= { rtcCfg 7 }

		
--          1.3.6.1.4.1.37950.1.1.5.10.12.13
-- 1.3.6.1.4.1.37950.1.1.5.10.12.13
-- 1.3.6.1.4.1.37950.1.1.5.10.12.13
-- 1.3.6.1.4.1.37950.1.1.5.10.12.13
-- 1.3.6.1.4.1.37950.1.1.5.10.12.13
-- 1.3.6.1.4.1.37950.1.1.5.10.12.13
-- 1.3.6.1.4.1.37950.1.1.5.10.12.13
-- 1.3.6.1.4.1.37950.1.1.5.10.12.13
-- 1.3.6.1.4.1.37950.1.1.5.10.12.13
		-- 1.3.6.1.4.1.37950.1.1.5.10.12.13
		syslogcfg OBJECT IDENTIFIER ::= { v1600dSysCfg 13 }

		
--          1.3.6.1.4.1.37950.1.1.5.10.12.13.1
-- 1.3.6.1.4.1.37950.1.1.5.10.12.13.1
-- 1.3.6.1.4.1.37950.1.1.5.10.12.13.1
-- 1.3.6.1.4.1.37950.1.1.5.10.12.13.1
-- 1.3.6.1.4.1.37950.1.1.5.10.12.13.1
-- 1.3.6.1.4.1.37950.1.1.5.10.12.13.1
-- 1.3.6.1.4.1.37950.1.1.5.10.12.13.1
-- 1.3.6.1.4.1.37950.1.1.5.10.12.13.1
-- 1.3.6.1.4.1.37950.1.1.5.10.12.13.1
		-- 1.3.6.1.4.1.37950.1.1.5.10.12.13.1
		syslogServerIp OBJECT-TYPE
			SYNTAX IpAddress
			MAX-ACCESS read-write
			STATUS current
			DESCRIPTION
				"Description."
			::= { syslogcfg 1 }

		
--          1.3.6.1.4.1.37950.1.1.5.10.12.13.2
-- 1.3.6.1.4.1.37950.1.1.5.10.12.13.2
-- 1.3.6.1.4.1.37950.1.1.5.10.12.13.2
-- 1.3.6.1.4.1.37950.1.1.5.10.12.13.2
-- 1.3.6.1.4.1.37950.1.1.5.10.12.13.2
-- 1.3.6.1.4.1.37950.1.1.5.10.12.13.2
-- 1.3.6.1.4.1.37950.1.1.5.10.12.13.2
-- 1.3.6.1.4.1.37950.1.1.5.10.12.13.2
-- 1.3.6.1.4.1.37950.1.1.5.10.12.13.2
		-- 1.3.6.1.4.1.37950.1.1.5.10.12.13.2
		syslogServerPort OBJECT-TYPE
			SYNTAX INTEGER (1..65535)
			MAX-ACCESS read-write
			STATUS current
			DESCRIPTION
				"Description."
			::= { syslogcfg 2 }

		
--          1.3.6.1.4.1.37950.1.1.5.10.12.13.3
-- 1.3.6.1.4.1.37950.1.1.5.10.12.13.3
-- 1.3.6.1.4.1.37950.1.1.5.10.12.13.3
-- 1.3.6.1.4.1.37950.1.1.5.10.12.13.3
-- 1.3.6.1.4.1.37950.1.1.5.10.12.13.3
-- 1.3.6.1.4.1.37950.1.1.5.10.12.13.3
-- 1.3.6.1.4.1.37950.1.1.5.10.12.13.3
-- 1.3.6.1.4.1.37950.1.1.5.10.12.13.3
-- 1.3.6.1.4.1.37950.1.1.5.10.12.13.3
		-- 1.3.6.1.4.1.37950.1.1.5.10.12.13.3
		syslogFlashLevel OBJECT-TYPE
			SYNTAX INTEGER
				{
				debug(0),
				info(1),
				notice(2),
				warning(3),
				major(4),
				critical(5),
				alert(6),
				emerg(7)
				}
			MAX-ACCESS read-write
			STATUS current
			DESCRIPTION
				"Description."
			::= { syslogcfg 3 }

		
--          1.3.6.1.4.1.37950.1.1.5.10.12.13.4
-- 1.3.6.1.4.1.37950.1.1.5.10.12.13.4
-- 1.3.6.1.4.1.37950.1.1.5.10.12.13.4
-- 1.3.6.1.4.1.37950.1.1.5.10.12.13.4
-- 1.3.6.1.4.1.37950.1.1.5.10.12.13.4
-- 1.3.6.1.4.1.37950.1.1.5.10.12.13.4
-- 1.3.6.1.4.1.37950.1.1.5.10.12.13.4
-- 1.3.6.1.4.1.37950.1.1.5.10.12.13.4
-- 1.3.6.1.4.1.37950.1.1.5.10.12.13.4
		-- 1.3.6.1.4.1.37950.1.1.5.10.12.13.4
		restoreSyslog OBJECT-TYPE
			SYNTAX INTEGER { commit(1) }
			MAX-ACCESS read-write
			STATUS current
			DESCRIPTION
				"Description."
			::= { syslogcfg 4 }

		
--          1.3.6.1.4.1.37950.1.1.5.10.12.13.5
-- 1.3.6.1.4.1.37950.1.1.5.10.12.13.5
-- 1.3.6.1.4.1.37950.1.1.5.10.12.13.5
-- 1.3.6.1.4.1.37950.1.1.5.10.12.13.5
-- 1.3.6.1.4.1.37950.1.1.5.10.12.13.5
-- 1.3.6.1.4.1.37950.1.1.5.10.12.13.5
-- 1.3.6.1.4.1.37950.1.1.5.10.12.13.5
-- 1.3.6.1.4.1.37950.1.1.5.10.12.13.5
-- 1.3.6.1.4.1.37950.1.1.5.10.12.13.5
		-- 1.3.6.1.4.1.37950.1.1.5.10.12.13.5
		saveSyslog OBJECT-TYPE
			SYNTAX INTEGER { commit(1) }
			MAX-ACCESS read-write
			STATUS current
			DESCRIPTION
				"Description."
			::= { syslogcfg 5 }

		
--          1.3.6.1.4.1.37950.1.1.5.10.12.13.6
-- 1.3.6.1.4.1.37950.1.1.5.10.12.13.6
-- 1.3.6.1.4.1.37950.1.1.5.10.12.13.6
-- 1.3.6.1.4.1.37950.1.1.5.10.12.13.6
-- 1.3.6.1.4.1.37950.1.1.5.10.12.13.6
-- 1.3.6.1.4.1.37950.1.1.5.10.12.13.6
-- 1.3.6.1.4.1.37950.1.1.5.10.12.13.6
-- 1.3.6.1.4.1.37950.1.1.5.10.12.13.6
-- 1.3.6.1.4.1.37950.1.1.5.10.12.13.6
		-- 1.3.6.1.4.1.37950.1.1.5.10.12.13.6
		uploadSyslog OBJECT IDENTIFIER ::= { syslogcfg 6 }

		
--          1.3.6.1.4.1.37950.1.1.5.10.12.13.6.1
-- 1.3.6.1.4.1.37950.1.1.5.10.12.13.6.1
-- 1.3.6.1.4.1.37950.1.1.5.10.12.13.6.1
-- 1.3.6.1.4.1.37950.1.1.5.10.12.13.6.1
-- 1.3.6.1.4.1.37950.1.1.5.10.12.13.6.1
-- 1.3.6.1.4.1.37950.1.1.5.10.12.13.6.1
-- 1.3.6.1.4.1.37950.1.1.5.10.12.13.6.1
-- 1.3.6.1.4.1.37950.1.1.5.10.12.13.6.1
-- 1.3.6.1.4.1.37950.1.1.5.10.12.13.6.1
		-- 1.3.6.1.4.1.37950.1.1.5.10.12.13.6.1
		uploadSyslogName OBJECT-TYPE
			SYNTAX OCTET STRING
			MAX-ACCESS read-write
			STATUS current
			DESCRIPTION
				"Description."
			::= { uploadSyslog 1 }

		
--          1.3.6.1.4.1.37950.1.1.5.10.12.13.6.2
-- 1.3.6.1.4.1.37950.1.1.5.10.12.13.6.2
-- 1.3.6.1.4.1.37950.1.1.5.10.12.13.6.2
-- 1.3.6.1.4.1.37950.1.1.5.10.12.13.6.2
-- 1.3.6.1.4.1.37950.1.1.5.10.12.13.6.2
-- 1.3.6.1.4.1.37950.1.1.5.10.12.13.6.2
-- 1.3.6.1.4.1.37950.1.1.5.10.12.13.6.2
-- 1.3.6.1.4.1.37950.1.1.5.10.12.13.6.2
-- 1.3.6.1.4.1.37950.1.1.5.10.12.13.6.2
		-- 1.3.6.1.4.1.37950.1.1.5.10.12.13.6.2
		tftpSeverSyslog OBJECT-TYPE
			SYNTAX IpAddress
			MAX-ACCESS read-write
			STATUS current
			DESCRIPTION
				"Description."
			::= { uploadSyslog 2 }

		
--          1.3.6.1.4.1.37950.1.1.5.10.12.13.6.3
-- 1.3.6.1.4.1.37950.1.1.5.10.12.13.6.3
-- 1.3.6.1.4.1.37950.1.1.5.10.12.13.6.3
-- 1.3.6.1.4.1.37950.1.1.5.10.12.13.6.3
-- 1.3.6.1.4.1.37950.1.1.5.10.12.13.6.3
-- 1.3.6.1.4.1.37950.1.1.5.10.12.13.6.3
-- 1.3.6.1.4.1.37950.1.1.5.10.12.13.6.3
-- 1.3.6.1.4.1.37950.1.1.5.10.12.13.6.3
-- 1.3.6.1.4.1.37950.1.1.5.10.12.13.6.3
		-- 1.3.6.1.4.1.37950.1.1.5.10.12.13.6.3
		uploadAction OBJECT-TYPE
			SYNTAX INTEGER { commit(1) }
			MAX-ACCESS read-write
			STATUS current
			DESCRIPTION
				"Description."
			::= { uploadSyslog 3 }

		
--         1.3.6.1.4.1.37950.1.1.5.10.12.13.7
-- 1.3.6.1.4.1.37950.1.1.5.10.12.13.7
-- 1.3.6.1.4.1.37950.1.1.5.10.12.13.7
-- 1.3.6.1.4.1.37950.1.1.5.10.12.13.7
-- 1.3.6.1.4.1.37950.1.1.5.10.12.13.7
-- 1.3.6.1.4.1.37950.1.1.5.10.12.13.7
-- 1.3.6.1.4.1.37950.1.1.5.10.12.13.7
-- 1.3.6.1.4.1.37950.1.1.5.10.12.13.7
		-- 1.3.6.1.4.1.37950.1.1.5.10.12.13.7
		syslogServerIpv6 OBJECT IDENTIFIER ::= { syslogcfg 7 }

		
--         1.3.6.1.4.1.37950.1.1.5.10.12.13.7.1
-- 1.3.6.1.4.1.37950.1.1.5.10.12.13.7.1
-- 1.3.6.1.4.1.37950.1.1.5.10.12.13.7.1
-- 1.3.6.1.4.1.37950.1.1.5.10.12.13.7.1
-- 1.3.6.1.4.1.37950.1.1.5.10.12.13.7.1
-- 1.3.6.1.4.1.37950.1.1.5.10.12.13.7.1
-- 1.3.6.1.4.1.37950.1.1.5.10.12.13.7.1
-- 1.3.6.1.4.1.37950.1.1.5.10.12.13.7.1
		-- 1.3.6.1.4.1.37950.1.1.5.10.12.13.7.1
		syslogServerIpv6Addr OBJECT-TYPE
			SYNTAX OCTET STRING
			MAX-ACCESS read-write
			STATUS current
			DESCRIPTION
				"Description."
			::= { syslogServerIpv6 1 }

		
--         1.3.6.1.4.1.37950.1.1.5.10.12.13.7.2
-- 1.3.6.1.4.1.37950.1.1.5.10.12.13.7.2
-- 1.3.6.1.4.1.37950.1.1.5.10.12.13.7.2
-- 1.3.6.1.4.1.37950.1.1.5.10.12.13.7.2
-- 1.3.6.1.4.1.37950.1.1.5.10.12.13.7.2
-- 1.3.6.1.4.1.37950.1.1.5.10.12.13.7.2
-- 1.3.6.1.4.1.37950.1.1.5.10.12.13.7.2
-- 1.3.6.1.4.1.37950.1.1.5.10.12.13.7.2
		-- 1.3.6.1.4.1.37950.1.1.5.10.12.13.7.2
		syslogServerIpv6Port OBJECT-TYPE
			SYNTAX INTEGER (1..65535)
			MAX-ACCESS read-write
			STATUS current
			DESCRIPTION
				"Description."
			::= { syslogServerIpv6 2 }

		
--          1.3.6.1.4.1.37950.1.1.5.10.12.14
-- 1.3.6.1.4.1.37950.1.1.5.10.12.14
-- 1.3.6.1.4.1.37950.1.1.5.10.12.14
-- 1.3.6.1.4.1.37950.1.1.5.10.12.14
-- 1.3.6.1.4.1.37950.1.1.5.10.12.14
-- 1.3.6.1.4.1.37950.1.1.5.10.12.14
-- 1.3.6.1.4.1.37950.1.1.5.10.12.14
-- 1.3.6.1.4.1.37950.1.1.5.10.12.14
-- 1.3.6.1.4.1.37950.1.1.5.10.12.14
		-- 1.3.6.1.4.1.37950.1.1.5.10.12.14
		timeParam OBJECT IDENTIFIER ::= { v1600dSysCfg 14 }

		
--          1.3.6.1.4.1.37950.1.1.5.10.12.14.1
-- 1.3.6.1.4.1.37950.1.1.5.10.12.14.1
-- 1.3.6.1.4.1.37950.1.1.5.10.12.14.1
-- 1.3.6.1.4.1.37950.1.1.5.10.12.14.1
-- 1.3.6.1.4.1.37950.1.1.5.10.12.14.1
-- 1.3.6.1.4.1.37950.1.1.5.10.12.14.1
-- 1.3.6.1.4.1.37950.1.1.5.10.12.14.1
-- 1.3.6.1.4.1.37950.1.1.5.10.12.14.1
-- 1.3.6.1.4.1.37950.1.1.5.10.12.14.1
		-- 1.3.6.1.4.1.37950.1.1.5.10.12.14.1
		timeZone OBJECT-TYPE
			SYNTAX OCTET STRING
			MAX-ACCESS read-write
			STATUS current
			DESCRIPTION
				"Description."
			::= { timeParam 1 }

		
--          1.3.6.1.4.1.37950.1.1.5.10.12.14.2
-- 1.3.6.1.4.1.37950.1.1.5.10.12.14.2
-- 1.3.6.1.4.1.37950.1.1.5.10.12.14.2
-- 1.3.6.1.4.1.37950.1.1.5.10.12.14.2
-- 1.3.6.1.4.1.37950.1.1.5.10.12.14.2
-- 1.3.6.1.4.1.37950.1.1.5.10.12.14.2
-- 1.3.6.1.4.1.37950.1.1.5.10.12.14.2
-- 1.3.6.1.4.1.37950.1.1.5.10.12.14.2
-- 1.3.6.1.4.1.37950.1.1.5.10.12.14.2
		-- 1.3.6.1.4.1.37950.1.1.5.10.12.14.2
		ntpServer OBJECT-TYPE
			SYNTAX OCTET STRING
			MAX-ACCESS read-write
			STATUS current
			DESCRIPTION
				"Description."
			::= { timeParam 2 }

		
--         1.3.6.1.4.1.37950.1.1.5.10.12.14.3
-- 1.3.6.1.4.1.37950.1.1.5.10.12.14.3
-- 1.3.6.1.4.1.37950.1.1.5.10.12.14.3
-- 1.3.6.1.4.1.37950.1.1.5.10.12.14.3
-- 1.3.6.1.4.1.37950.1.1.5.10.12.14.3
-- 1.3.6.1.4.1.37950.1.1.5.10.12.14.3
-- 1.3.6.1.4.1.37950.1.1.5.10.12.14.3
-- 1.3.6.1.4.1.37950.1.1.5.10.12.14.3
		-- 1.3.6.1.4.1.37950.1.1.5.10.12.14.3
		timeZoneOffset OBJECT-TYPE
			SYNTAX Integer32
			MAX-ACCESS read-write
			STATUS current
			DESCRIPTION
				"Description."
			::= { timeParam 3 }

		
--         1.3.6.1.4.1.37950.1.1.5.10.12.14.4
-- 1.3.6.1.4.1.37950.1.1.5.10.12.14.4
-- 1.3.6.1.4.1.37950.1.1.5.10.12.14.4
-- 1.3.6.1.4.1.37950.1.1.5.10.12.14.4
-- 1.3.6.1.4.1.37950.1.1.5.10.12.14.4
-- 1.3.6.1.4.1.37950.1.1.5.10.12.14.4
-- 1.3.6.1.4.1.37950.1.1.5.10.12.14.4
-- 1.3.6.1.4.1.37950.1.1.5.10.12.14.4
		-- 1.3.6.1.4.1.37950.1.1.5.10.12.14.4
		backupNtpServer OBJECT-TYPE
			SYNTAX OCTET STRING
			MAX-ACCESS read-write
			STATUS current
			DESCRIPTION
				"Description."
			::= { timeParam 4 }

		
--          1.3.6.1.4.1.37950.1.1.5.10.12.15
-- 1.3.6.1.4.1.37950.1.1.5.10.12.15
-- 1.3.6.1.4.1.37950.1.1.5.10.12.15
-- 1.3.6.1.4.1.37950.1.1.5.10.12.15
-- 1.3.6.1.4.1.37950.1.1.5.10.12.15
-- 1.3.6.1.4.1.37950.1.1.5.10.12.15
-- 1.3.6.1.4.1.37950.1.1.5.10.12.15
-- 1.3.6.1.4.1.37950.1.1.5.10.12.15
-- 1.3.6.1.4.1.37950.1.1.5.10.12.15
		-- 1.3.6.1.4.1.37950.1.1.5.10.12.15
		dasParam OBJECT IDENTIFIER ::= { v1600dSysCfg 15 }

		
--          1.3.6.1.4.1.37950.1.1.5.10.12.15.1
-- 1.3.6.1.4.1.37950.1.1.5.10.12.15.1
-- 1.3.6.1.4.1.37950.1.1.5.10.12.15.1
-- 1.3.6.1.4.1.37950.1.1.5.10.12.15.1
-- 1.3.6.1.4.1.37950.1.1.5.10.12.15.1
-- 1.3.6.1.4.1.37950.1.1.5.10.12.15.1
-- 1.3.6.1.4.1.37950.1.1.5.10.12.15.1
-- 1.3.6.1.4.1.37950.1.1.5.10.12.15.1
-- 1.3.6.1.4.1.37950.1.1.5.10.12.15.1
		-- 1.3.6.1.4.1.37950.1.1.5.10.12.15.1
		primaryDNS OBJECT-TYPE
			SYNTAX IpAddress
			MAX-ACCESS read-write
			STATUS current
			DESCRIPTION
				"Description."
			::= { dasParam 1 }

		
--          1.3.6.1.4.1.37950.1.1.5.10.12.15.2
-- 1.3.6.1.4.1.37950.1.1.5.10.12.15.2
-- 1.3.6.1.4.1.37950.1.1.5.10.12.15.2
-- 1.3.6.1.4.1.37950.1.1.5.10.12.15.2
-- 1.3.6.1.4.1.37950.1.1.5.10.12.15.2
-- 1.3.6.1.4.1.37950.1.1.5.10.12.15.2
-- 1.3.6.1.4.1.37950.1.1.5.10.12.15.2
-- 1.3.6.1.4.1.37950.1.1.5.10.12.15.2
-- 1.3.6.1.4.1.37950.1.1.5.10.12.15.2
		-- 1.3.6.1.4.1.37950.1.1.5.10.12.15.2
		secondDNS OBJECT-TYPE
			SYNTAX IpAddress
			MAX-ACCESS read-write
			STATUS current
			DESCRIPTION
				"Description."
			::= { dasParam 2 }

		
--          1.3.6.1.4.1.37950.1.1.5.10.12.15.3
-- 1.3.6.1.4.1.37950.1.1.5.10.12.15.3
-- 1.3.6.1.4.1.37950.1.1.5.10.12.15.3
-- 1.3.6.1.4.1.37950.1.1.5.10.12.15.3
-- 1.3.6.1.4.1.37950.1.1.5.10.12.15.3
-- 1.3.6.1.4.1.37950.1.1.5.10.12.15.3
-- 1.3.6.1.4.1.37950.1.1.5.10.12.15.3
-- 1.3.6.1.4.1.37950.1.1.5.10.12.15.3
-- 1.3.6.1.4.1.37950.1.1.5.10.12.15.3
		-- 1.3.6.1.4.1.37950.1.1.5.10.12.15.3
		commit OBJECT-TYPE
			SYNTAX INTEGER { commit(1) }
			MAX-ACCESS read-write
			STATUS current
			DESCRIPTION
				"Description."
			::= { dasParam 3 }

		
--         1.3.6.1.4.1.37950.1.1.5.10.12.16
-- 1.3.6.1.4.1.37950.1.1.5.10.12.16
-- 1.3.6.1.4.1.37950.1.1.5.10.12.16
-- 1.3.6.1.4.1.37950.1.1.5.10.12.16
-- 1.3.6.1.4.1.37950.1.1.5.10.12.16
-- 1.3.6.1.4.1.37950.1.1.5.10.12.16
-- 1.3.6.1.4.1.37950.1.1.5.10.12.16
-- 1.3.6.1.4.1.37950.1.1.5.10.12.16
		-- 1.3.6.1.4.1.37950.1.1.5.10.12.16
		loginAccessList OBJECT IDENTIFIER ::= { v1600dSysCfg 16 }

		
--         1.3.6.1.4.1.37950.1.1.5.10.12.16.1
-- 1.3.6.1.4.1.37950.1.1.5.10.12.16.1
-- 1.3.6.1.4.1.37950.1.1.5.10.12.16.1
-- 1.3.6.1.4.1.37950.1.1.5.10.12.16.1
-- 1.3.6.1.4.1.37950.1.1.5.10.12.16.1
-- 1.3.6.1.4.1.37950.1.1.5.10.12.16.1
-- 1.3.6.1.4.1.37950.1.1.5.10.12.16.1
-- 1.3.6.1.4.1.37950.1.1.5.10.12.16.1
		-- 1.3.6.1.4.1.37950.1.1.5.10.12.16.1
		loginAccessListEn OBJECT-TYPE
			SYNTAX INTEGER
				{
				disable(0),
				enable(1),
				clear(2)
				}
			MAX-ACCESS read-write
			STATUS current
			DESCRIPTION
				"Description."
			::= { loginAccessList 1 }

		
--         1.3.6.1.4.1.37950.1.1.5.10.12.16.2
-- 1.3.6.1.4.1.37950.1.1.5.10.12.16.2
-- 1.3.6.1.4.1.37950.1.1.5.10.12.16.2
-- 1.3.6.1.4.1.37950.1.1.5.10.12.16.2
-- 1.3.6.1.4.1.37950.1.1.5.10.12.16.2
-- 1.3.6.1.4.1.37950.1.1.5.10.12.16.2
-- 1.3.6.1.4.1.37950.1.1.5.10.12.16.2
-- 1.3.6.1.4.1.37950.1.1.5.10.12.16.2
		-- 1.3.6.1.4.1.37950.1.1.5.10.12.16.2
		loginAccessListCfg OBJECT IDENTIFIER ::= { loginAccessList 2 }

		
--         1.3.6.1.4.1.37950.1.1.5.10.12.16.2.1
-- 1.3.6.1.4.1.37950.1.1.5.10.12.16.2.1
-- 1.3.6.1.4.1.37950.1.1.5.10.12.16.2.1
-- 1.3.6.1.4.1.37950.1.1.5.10.12.16.2.1
-- 1.3.6.1.4.1.37950.1.1.5.10.12.16.2.1
-- 1.3.6.1.4.1.37950.1.1.5.10.12.16.2.1
-- 1.3.6.1.4.1.37950.1.1.5.10.12.16.2.1
-- 1.3.6.1.4.1.37950.1.1.5.10.12.16.2.1
		-- 1.3.6.1.4.1.37950.1.1.5.10.12.16.2.1
		filterAction OBJECT-TYPE
			SYNTAX INTEGER
				{
				deny(0),
				permit(1)
				}
			MAX-ACCESS read-write
			STATUS current
			DESCRIPTION
				"Description."
			::= { loginAccessListCfg 1 }

		
--         1.3.6.1.4.1.37950.1.1.5.10.12.16.2.2
-- 1.3.6.1.4.1.37950.1.1.5.10.12.16.2.2
-- 1.3.6.1.4.1.37950.1.1.5.10.12.16.2.2
-- 1.3.6.1.4.1.37950.1.1.5.10.12.16.2.2
-- 1.3.6.1.4.1.37950.1.1.5.10.12.16.2.2
-- 1.3.6.1.4.1.37950.1.1.5.10.12.16.2.2
-- 1.3.6.1.4.1.37950.1.1.5.10.12.16.2.2
-- 1.3.6.1.4.1.37950.1.1.5.10.12.16.2.2
		-- 1.3.6.1.4.1.37950.1.1.5.10.12.16.2.2
		protocol OBJECT-TYPE
			SYNTAX INTEGER
				{
				telnet(0),
				web(1),
				snmp(2),
				ssh(3),
				ping(4)
				}
			MAX-ACCESS read-write
			STATUS current
			DESCRIPTION
				"Description."
			::= { loginAccessListCfg 2 }

		
--         1.3.6.1.4.1.37950.1.1.5.10.12.16.2.3
-- 1.3.6.1.4.1.37950.1.1.5.10.12.16.2.3
-- 1.3.6.1.4.1.37950.1.1.5.10.12.16.2.3
-- 1.3.6.1.4.1.37950.1.1.5.10.12.16.2.3
-- 1.3.6.1.4.1.37950.1.1.5.10.12.16.2.3
-- 1.3.6.1.4.1.37950.1.1.5.10.12.16.2.3
-- 1.3.6.1.4.1.37950.1.1.5.10.12.16.2.3
-- 1.3.6.1.4.1.37950.1.1.5.10.12.16.2.3
		-- 1.3.6.1.4.1.37950.1.1.5.10.12.16.2.3
		sourceIp OBJECT-TYPE
			SYNTAX IpAddress
			MAX-ACCESS read-write
			STATUS current
			DESCRIPTION
				"Description."
			::= { loginAccessListCfg 3 }

		
--         1.3.6.1.4.1.37950.1.1.5.10.12.16.2.4
-- 1.3.6.1.4.1.37950.1.1.5.10.12.16.2.4
-- 1.3.6.1.4.1.37950.1.1.5.10.12.16.2.4
-- 1.3.6.1.4.1.37950.1.1.5.10.12.16.2.4
-- 1.3.6.1.4.1.37950.1.1.5.10.12.16.2.4
-- 1.3.6.1.4.1.37950.1.1.5.10.12.16.2.4
-- 1.3.6.1.4.1.37950.1.1.5.10.12.16.2.4
-- 1.3.6.1.4.1.37950.1.1.5.10.12.16.2.4
		-- 1.3.6.1.4.1.37950.1.1.5.10.12.16.2.4
		ipMask OBJECT-TYPE
			SYNTAX IpAddress
			MAX-ACCESS read-write
			STATUS current
			DESCRIPTION
				"Description."
			::= { loginAccessListCfg 4 }

		
--         1.3.6.1.4.1.37950.1.1.5.10.12.16.2.5
-- 1.3.6.1.4.1.37950.1.1.5.10.12.16.2.5
-- 1.3.6.1.4.1.37950.1.1.5.10.12.16.2.5
-- 1.3.6.1.4.1.37950.1.1.5.10.12.16.2.5
-- 1.3.6.1.4.1.37950.1.1.5.10.12.16.2.5
-- 1.3.6.1.4.1.37950.1.1.5.10.12.16.2.5
-- 1.3.6.1.4.1.37950.1.1.5.10.12.16.2.5
-- 1.3.6.1.4.1.37950.1.1.5.10.12.16.2.5
		-- 1.3.6.1.4.1.37950.1.1.5.10.12.16.2.5
		action OBJECT-TYPE
			SYNTAX INTEGER
				{
				add(1),
				del(2)
				}
			MAX-ACCESS read-write
			STATUS current
			DESCRIPTION
				"Description."
			::= { loginAccessListCfg 5 }

		
--         1.3.6.1.4.1.37950.1.1.5.10.12.16.3
-- 1.3.6.1.4.1.37950.1.1.5.10.12.16.3
-- 1.3.6.1.4.1.37950.1.1.5.10.12.16.3
-- 1.3.6.1.4.1.37950.1.1.5.10.12.16.3
-- 1.3.6.1.4.1.37950.1.1.5.10.12.16.3
-- 1.3.6.1.4.1.37950.1.1.5.10.12.16.3
-- 1.3.6.1.4.1.37950.1.1.5.10.12.16.3
-- 1.3.6.1.4.1.37950.1.1.5.10.12.16.3
		-- 1.3.6.1.4.1.37950.1.1.5.10.12.16.3
		loginAccessListTable OBJECT-TYPE
			SYNTAX SEQUENCE OF LoginAccessListEntry
			MAX-ACCESS not-accessible
			STATUS current
			DESCRIPTION
				"Description."
			::= { loginAccessList 3 }

		
--         1.3.6.1.4.1.37950.1.1.5.10.12.16.3.1
-- 1.3.6.1.4.1.37950.1.1.5.10.12.16.3.1
-- 1.3.6.1.4.1.37950.1.1.5.10.12.16.3.1
-- 1.3.6.1.4.1.37950.1.1.5.10.12.16.3.1
-- 1.3.6.1.4.1.37950.1.1.5.10.12.16.3.1
-- 1.3.6.1.4.1.37950.1.1.5.10.12.16.3.1
-- 1.3.6.1.4.1.37950.1.1.5.10.12.16.3.1
-- 1.3.6.1.4.1.37950.1.1.5.10.12.16.3.1
		-- 1.3.6.1.4.1.37950.1.1.5.10.12.16.3.1
		loginAccessListEntry OBJECT-TYPE
			SYNTAX LoginAccessListEntry
			MAX-ACCESS not-accessible
			STATUS current
			DESCRIPTION
				"Description."
			INDEX { filterActionS, protocolS, sourceIpS, ipMaskS }
			::= { loginAccessListTable 1 }

		
		LoginAccessListEntry ::=
			SEQUENCE { 
				filterActionS
					INTEGER,
				protocolS
					INTEGER,
				sourceIpS
					IpAddress,
				ipMaskS
					IpAddress
			 }

--         1.3.6.1.4.1.37950.1.1.5.10.12.16.3.1.1
-- 1.3.6.1.4.1.37950.1.1.5.10.12.16.3.1.1
-- 1.3.6.1.4.1.37950.1.1.5.10.12.16.3.1.1
-- 1.3.6.1.4.1.37950.1.1.5.10.12.16.3.1.1
-- 1.3.6.1.4.1.37950.1.1.5.10.12.16.3.1.1
-- 1.3.6.1.4.1.37950.1.1.5.10.12.16.3.1.1
-- 1.3.6.1.4.1.37950.1.1.5.10.12.16.3.1.1
-- 1.3.6.1.4.1.37950.1.1.5.10.12.16.3.1.1
		-- 1.3.6.1.4.1.37950.1.1.5.10.12.16.3.1.1
		filterActionS OBJECT-TYPE
			SYNTAX INTEGER
				{
				deny(1),
				permit(2)
				}
			MAX-ACCESS read-only
			STATUS current
			DESCRIPTION
				"Description."
			::= { loginAccessListEntry 1 }

		
--         1.3.6.1.4.1.37950.1.1.5.10.12.16.3.1.2
-- 1.3.6.1.4.1.37950.1.1.5.10.12.16.3.1.2
-- 1.3.6.1.4.1.37950.1.1.5.10.12.16.3.1.2
-- 1.3.6.1.4.1.37950.1.1.5.10.12.16.3.1.2
-- 1.3.6.1.4.1.37950.1.1.5.10.12.16.3.1.2
-- 1.3.6.1.4.1.37950.1.1.5.10.12.16.3.1.2
-- 1.3.6.1.4.1.37950.1.1.5.10.12.16.3.1.2
-- 1.3.6.1.4.1.37950.1.1.5.10.12.16.3.1.2
		-- 1.3.6.1.4.1.37950.1.1.5.10.12.16.3.1.2
		protocolS OBJECT-TYPE
			SYNTAX INTEGER
				{
				telnet(1),
				web(2),
				snmp(3),
				ssh(4),
				ping(5)
				}
			MAX-ACCESS read-only
			STATUS current
			DESCRIPTION
				"Description."
			::= { loginAccessListEntry 2 }

		
--         1.3.6.1.4.1.37950.1.1.5.10.12.16.3.1.3
-- 1.3.6.1.4.1.37950.1.1.5.10.12.16.3.1.3
-- 1.3.6.1.4.1.37950.1.1.5.10.12.16.3.1.3
-- 1.3.6.1.4.1.37950.1.1.5.10.12.16.3.1.3
-- 1.3.6.1.4.1.37950.1.1.5.10.12.16.3.1.3
-- 1.3.6.1.4.1.37950.1.1.5.10.12.16.3.1.3
-- 1.3.6.1.4.1.37950.1.1.5.10.12.16.3.1.3
-- 1.3.6.1.4.1.37950.1.1.5.10.12.16.3.1.3
		-- 1.3.6.1.4.1.37950.1.1.5.10.12.16.3.1.3
		sourceIpS OBJECT-TYPE
			SYNTAX IpAddress
			MAX-ACCESS read-only
			STATUS current
			DESCRIPTION
				"Description."
			::= { loginAccessListEntry 3 }

		
--         1.3.6.1.4.1.37950.1.1.5.10.12.16.3.1.4
-- 1.3.6.1.4.1.37950.1.1.5.10.12.16.3.1.4
-- 1.3.6.1.4.1.37950.1.1.5.10.12.16.3.1.4
-- 1.3.6.1.4.1.37950.1.1.5.10.12.16.3.1.4
-- 1.3.6.1.4.1.37950.1.1.5.10.12.16.3.1.4
-- 1.3.6.1.4.1.37950.1.1.5.10.12.16.3.1.4
-- 1.3.6.1.4.1.37950.1.1.5.10.12.16.3.1.4
-- 1.3.6.1.4.1.37950.1.1.5.10.12.16.3.1.4
		-- 1.3.6.1.4.1.37950.1.1.5.10.12.16.3.1.4
		ipMaskS OBJECT-TYPE
			SYNTAX IpAddress
			MAX-ACCESS read-only
			STATUS current
			DESCRIPTION
				"Description."
			::= { loginAccessListEntry 4 }

		
--         1.3.6.1.4.1.37950.1.1.5.10.12.16.4
-- 1.3.6.1.4.1.37950.1.1.5.10.12.16.4
-- 1.3.6.1.4.1.37950.1.1.5.10.12.16.4
-- 1.3.6.1.4.1.37950.1.1.5.10.12.16.4
-- 1.3.6.1.4.1.37950.1.1.5.10.12.16.4
-- 1.3.6.1.4.1.37950.1.1.5.10.12.16.4
-- 1.3.6.1.4.1.37950.1.1.5.10.12.16.4
-- 1.3.6.1.4.1.37950.1.1.5.10.12.16.4
		-- 1.3.6.1.4.1.37950.1.1.5.10.12.16.4
		ipv6loginAccessListCfg OBJECT IDENTIFIER ::= { loginAccessList 4 }

		
--         1.3.6.1.4.1.37950.1.1.5.10.12.16.4.1
-- 1.3.6.1.4.1.37950.1.1.5.10.12.16.4.1
-- 1.3.6.1.4.1.37950.1.1.5.10.12.16.4.1
-- 1.3.6.1.4.1.37950.1.1.5.10.12.16.4.1
-- 1.3.6.1.4.1.37950.1.1.5.10.12.16.4.1
-- 1.3.6.1.4.1.37950.1.1.5.10.12.16.4.1
-- 1.3.6.1.4.1.37950.1.1.5.10.12.16.4.1
-- 1.3.6.1.4.1.37950.1.1.5.10.12.16.4.1
		-- 1.3.6.1.4.1.37950.1.1.5.10.12.16.4.1
		ipv6filterAction OBJECT-TYPE
			SYNTAX INTEGER
				{
				deny(0),
				permit(1)
				}
			MAX-ACCESS read-write
			STATUS current
			DESCRIPTION
				"Description."
			::= { ipv6loginAccessListCfg 1 }

		
--         1.3.6.1.4.1.37950.1.1.5.10.12.16.4.2
-- 1.3.6.1.4.1.37950.1.1.5.10.12.16.4.2
-- 1.3.6.1.4.1.37950.1.1.5.10.12.16.4.2
-- 1.3.6.1.4.1.37950.1.1.5.10.12.16.4.2
-- 1.3.6.1.4.1.37950.1.1.5.10.12.16.4.2
-- 1.3.6.1.4.1.37950.1.1.5.10.12.16.4.2
-- 1.3.6.1.4.1.37950.1.1.5.10.12.16.4.2
-- 1.3.6.1.4.1.37950.1.1.5.10.12.16.4.2
		-- 1.3.6.1.4.1.37950.1.1.5.10.12.16.4.2
		ipv6protocol OBJECT-TYPE
			SYNTAX INTEGER
				{
				telnet(0),
				web(1),
				snmp(2),
				ssh(3),
				ping(4)
				}
			MAX-ACCESS read-write
			STATUS current
			DESCRIPTION
				"Description."
			::= { ipv6loginAccessListCfg 2 }

		
--         1.3.6.1.4.1.37950.1.1.5.10.12.16.4.3
-- 1.3.6.1.4.1.37950.1.1.5.10.12.16.4.3
-- 1.3.6.1.4.1.37950.1.1.5.10.12.16.4.3
-- 1.3.6.1.4.1.37950.1.1.5.10.12.16.4.3
-- 1.3.6.1.4.1.37950.1.1.5.10.12.16.4.3
-- 1.3.6.1.4.1.37950.1.1.5.10.12.16.4.3
-- 1.3.6.1.4.1.37950.1.1.5.10.12.16.4.3
-- 1.3.6.1.4.1.37950.1.1.5.10.12.16.4.3
		-- 1.3.6.1.4.1.37950.1.1.5.10.12.16.4.3
		sourceIpv6 OBJECT-TYPE
			SYNTAX OCTET STRING
			MAX-ACCESS read-write
			STATUS current
			DESCRIPTION
				"Description."
			::= { ipv6loginAccessListCfg 3 }

		
--         1.3.6.1.4.1.37950.1.1.5.10.12.16.4.4
-- 1.3.6.1.4.1.37950.1.1.5.10.12.16.4.4
-- 1.3.6.1.4.1.37950.1.1.5.10.12.16.4.4
-- 1.3.6.1.4.1.37950.1.1.5.10.12.16.4.4
-- 1.3.6.1.4.1.37950.1.1.5.10.12.16.4.4
-- 1.3.6.1.4.1.37950.1.1.5.10.12.16.4.4
-- 1.3.6.1.4.1.37950.1.1.5.10.12.16.4.4
-- 1.3.6.1.4.1.37950.1.1.5.10.12.16.4.4
		-- 1.3.6.1.4.1.37950.1.1.5.10.12.16.4.4
		prefixlen OBJECT-TYPE
			SYNTAX Integer32 (-1..128)
			MAX-ACCESS read-write
			STATUS current
			DESCRIPTION
				"Description."
			::= { ipv6loginAccessListCfg 4 }

		
--         1.3.6.1.4.1.37950.1.1.5.10.12.16.4.5
-- 1.3.6.1.4.1.37950.1.1.5.10.12.16.4.5
-- 1.3.6.1.4.1.37950.1.1.5.10.12.16.4.5
-- 1.3.6.1.4.1.37950.1.1.5.10.12.16.4.5
-- 1.3.6.1.4.1.37950.1.1.5.10.12.16.4.5
-- 1.3.6.1.4.1.37950.1.1.5.10.12.16.4.5
-- 1.3.6.1.4.1.37950.1.1.5.10.12.16.4.5
-- 1.3.6.1.4.1.37950.1.1.5.10.12.16.4.5
		-- 1.3.6.1.4.1.37950.1.1.5.10.12.16.4.5
		ipv6action OBJECT-TYPE
			SYNTAX INTEGER
				{
				add(1),
				del(2)
				}
			MAX-ACCESS read-write
			STATUS current
			DESCRIPTION
				"Description."
			::= { ipv6loginAccessListCfg 5 }

		
--         1.3.6.1.4.1.37950.1.1.5.10.12.16.5
-- 1.3.6.1.4.1.37950.1.1.5.10.12.16.5
-- 1.3.6.1.4.1.37950.1.1.5.10.12.16.5
-- 1.3.6.1.4.1.37950.1.1.5.10.12.16.5
-- 1.3.6.1.4.1.37950.1.1.5.10.12.16.5
-- 1.3.6.1.4.1.37950.1.1.5.10.12.16.5
-- 1.3.6.1.4.1.37950.1.1.5.10.12.16.5
-- 1.3.6.1.4.1.37950.1.1.5.10.12.16.5
		-- 1.3.6.1.4.1.37950.1.1.5.10.12.16.5
		ipv6loginAccessListTable OBJECT-TYPE
			SYNTAX SEQUENCE OF Ipv6loginAccessListEntry
			MAX-ACCESS not-accessible
			STATUS current
			DESCRIPTION
				"Description."
			::= { loginAccessList 5 }

		
--         1.3.6.1.4.1.37950.1.1.5.10.12.16.5.1
-- 1.3.6.1.4.1.37950.1.1.5.10.12.16.5.1
-- 1.3.6.1.4.1.37950.1.1.5.10.12.16.5.1
-- 1.3.6.1.4.1.37950.1.1.5.10.12.16.5.1
-- 1.3.6.1.4.1.37950.1.1.5.10.12.16.5.1
-- 1.3.6.1.4.1.37950.1.1.5.10.12.16.5.1
-- 1.3.6.1.4.1.37950.1.1.5.10.12.16.5.1
-- 1.3.6.1.4.1.37950.1.1.5.10.12.16.5.1
		-- 1.3.6.1.4.1.37950.1.1.5.10.12.16.5.1
		ipv6loginAccessListEntry OBJECT-TYPE
			SYNTAX Ipv6loginAccessListEntry
			MAX-ACCESS not-accessible
			STATUS current
			DESCRIPTION
				"Description."
			INDEX { ipv6filterActionS, ipv6protocolS, sourceIpv6S, prefixlenS }
			::= { ipv6loginAccessListTable 1 }

		
		Ipv6loginAccessListEntry ::=
			SEQUENCE { 
				ipv6filterActionS
					INTEGER,
				ipv6protocolS
					INTEGER,
				sourceIpv6S
					OCTET STRING,
				prefixlenS
					Integer32
			 }

--         1.3.6.1.4.1.37950.1.1.5.10.12.16.5.1.1
-- 1.3.6.1.4.1.37950.1.1.5.10.12.16.5.1.1
-- 1.3.6.1.4.1.37950.1.1.5.10.12.16.5.1.1
-- 1.3.6.1.4.1.37950.1.1.5.10.12.16.5.1.1
-- 1.3.6.1.4.1.37950.1.1.5.10.12.16.5.1.1
-- 1.3.6.1.4.1.37950.1.1.5.10.12.16.5.1.1
-- 1.3.6.1.4.1.37950.1.1.5.10.12.16.5.1.1
-- 1.3.6.1.4.1.37950.1.1.5.10.12.16.5.1.1
		-- 1.3.6.1.4.1.37950.1.1.5.10.12.16.5.1.1
		ipv6filterActionS OBJECT-TYPE
			SYNTAX INTEGER
				{
				deny(1),
				permit(2)
				}
			MAX-ACCESS read-only
			STATUS current
			DESCRIPTION
				"Description."
			::= { ipv6loginAccessListEntry 1 }

		
--         1.3.6.1.4.1.37950.1.1.5.10.12.16.5.1.2
-- 1.3.6.1.4.1.37950.1.1.5.10.12.16.5.1.2
-- 1.3.6.1.4.1.37950.1.1.5.10.12.16.5.1.2
-- 1.3.6.1.4.1.37950.1.1.5.10.12.16.5.1.2
-- 1.3.6.1.4.1.37950.1.1.5.10.12.16.5.1.2
-- 1.3.6.1.4.1.37950.1.1.5.10.12.16.5.1.2
-- 1.3.6.1.4.1.37950.1.1.5.10.12.16.5.1.2
-- 1.3.6.1.4.1.37950.1.1.5.10.12.16.5.1.2
		-- 1.3.6.1.4.1.37950.1.1.5.10.12.16.5.1.2
		ipv6protocolS OBJECT-TYPE
			SYNTAX INTEGER
				{
				telnet(1),
				web(2),
				snmp(3),
				ssh(4),
				ping(5)
				}
			MAX-ACCESS read-only
			STATUS current
			DESCRIPTION
				"Description."
			::= { ipv6loginAccessListEntry 2 }

		
--         1.3.6.1.4.1.37950.1.1.5.10.12.16.5.1.3
-- 1.3.6.1.4.1.37950.1.1.5.10.12.16.5.1.3
-- 1.3.6.1.4.1.37950.1.1.5.10.12.16.5.1.3
-- 1.3.6.1.4.1.37950.1.1.5.10.12.16.5.1.3
-- 1.3.6.1.4.1.37950.1.1.5.10.12.16.5.1.3
-- 1.3.6.1.4.1.37950.1.1.5.10.12.16.5.1.3
-- 1.3.6.1.4.1.37950.1.1.5.10.12.16.5.1.3
-- 1.3.6.1.4.1.37950.1.1.5.10.12.16.5.1.3
		-- 1.3.6.1.4.1.37950.1.1.5.10.12.16.5.1.3
		sourceIpv6S OBJECT-TYPE
			SYNTAX OCTET STRING
			MAX-ACCESS read-only
			STATUS current
			DESCRIPTION
				"Description."
			::= { ipv6loginAccessListEntry 3 }

		
--         1.3.6.1.4.1.37950.1.1.5.10.12.16.5.1.4
-- 1.3.6.1.4.1.37950.1.1.5.10.12.16.5.1.4
-- 1.3.6.1.4.1.37950.1.1.5.10.12.16.5.1.4
-- 1.3.6.1.4.1.37950.1.1.5.10.12.16.5.1.4
-- 1.3.6.1.4.1.37950.1.1.5.10.12.16.5.1.4
-- 1.3.6.1.4.1.37950.1.1.5.10.12.16.5.1.4
-- 1.3.6.1.4.1.37950.1.1.5.10.12.16.5.1.4
-- 1.3.6.1.4.1.37950.1.1.5.10.12.16.5.1.4
		-- 1.3.6.1.4.1.37950.1.1.5.10.12.16.5.1.4
		prefixlenS OBJECT-TYPE
			SYNTAX Integer32 (-1..128)
			MAX-ACCESS read-only
			STATUS current
			DESCRIPTION
				"Description."
			::= { ipv6loginAccessListEntry 4 }

		
--         1.3.6.1.4.1.37950.1.1.5.10.12.17
-- 1.3.6.1.4.1.37950.1.1.5.10.12.17
-- 1.3.6.1.4.1.37950.1.1.5.10.12.17
-- 1.3.6.1.4.1.37950.1.1.5.10.12.17
-- 1.3.6.1.4.1.37950.1.1.5.10.12.17
-- 1.3.6.1.4.1.37950.1.1.5.10.12.17
-- 1.3.6.1.4.1.37950.1.1.5.10.12.17
-- 1.3.6.1.4.1.37950.1.1.5.10.12.17
		-- 1.3.6.1.4.1.37950.1.1.5.10.12.17
		ipv6DNS OBJECT IDENTIFIER ::= { v1600dSysCfg 17 }

		
--         1.3.6.1.4.1.37950.1.1.5.10.12.17.1
-- 1.3.6.1.4.1.37950.1.1.5.10.12.17.1
-- 1.3.6.1.4.1.37950.1.1.5.10.12.17.1
-- 1.3.6.1.4.1.37950.1.1.5.10.12.17.1
-- 1.3.6.1.4.1.37950.1.1.5.10.12.17.1
-- 1.3.6.1.4.1.37950.1.1.5.10.12.17.1
-- 1.3.6.1.4.1.37950.1.1.5.10.12.17.1
-- 1.3.6.1.4.1.37950.1.1.5.10.12.17.1
		-- 1.3.6.1.4.1.37950.1.1.5.10.12.17.1
		ipv6MasterDNS OBJECT-TYPE
			SYNTAX OCTET STRING
			MAX-ACCESS read-write
			STATUS current
			DESCRIPTION
				"Description."
			::= { ipv6DNS 1 }

		
--         1.3.6.1.4.1.37950.1.1.5.10.12.17.2
-- 1.3.6.1.4.1.37950.1.1.5.10.12.17.2
-- 1.3.6.1.4.1.37950.1.1.5.10.12.17.2
-- 1.3.6.1.4.1.37950.1.1.5.10.12.17.2
-- 1.3.6.1.4.1.37950.1.1.5.10.12.17.2
-- 1.3.6.1.4.1.37950.1.1.5.10.12.17.2
-- 1.3.6.1.4.1.37950.1.1.5.10.12.17.2
-- 1.3.6.1.4.1.37950.1.1.5.10.12.17.2
		-- 1.3.6.1.4.1.37950.1.1.5.10.12.17.2
		ipv6SlaveDNS OBJECT-TYPE
			SYNTAX OCTET STRING
			MAX-ACCESS read-write
			STATUS current
			DESCRIPTION
				"Description."
			::= { ipv6DNS 2 }

		
--         1.3.6.1.4.1.37950.1.1.5.10.12.17.3
-- 1.3.6.1.4.1.37950.1.1.5.10.12.17.3
-- 1.3.6.1.4.1.37950.1.1.5.10.12.17.3
-- 1.3.6.1.4.1.37950.1.1.5.10.12.17.3
-- 1.3.6.1.4.1.37950.1.1.5.10.12.17.3
-- 1.3.6.1.4.1.37950.1.1.5.10.12.17.3
-- 1.3.6.1.4.1.37950.1.1.5.10.12.17.3
-- 1.3.6.1.4.1.37950.1.1.5.10.12.17.3
		-- 1.3.6.1.4.1.37950.1.1.5.10.12.17.3
		ipv6DNSAction OBJECT-TYPE
			SYNTAX INTEGER { submit(1) }
			MAX-ACCESS read-write
			STATUS current
			DESCRIPTION
				"Description."
			::= { ipv6DNS 3 }

		
--         1.3.6.1.4.1.37950.1.1.5.10.12.18
-- 1.3.6.1.4.1.37950.1.1.5.10.12.18
-- 1.3.6.1.4.1.37950.1.1.5.10.12.18
-- 1.3.6.1.4.1.37950.1.1.5.10.12.18
-- 1.3.6.1.4.1.37950.1.1.5.10.12.18
-- 1.3.6.1.4.1.37950.1.1.5.10.12.18
-- 1.3.6.1.4.1.37950.1.1.5.10.12.18
-- 1.3.6.1.4.1.37950.1.1.5.10.12.18
		-- 1.3.6.1.4.1.37950.1.1.5.10.12.18
		systemIPv6Upgrade OBJECT IDENTIFIER ::= { v1600dSysCfg 18 }

		
--         1.3.6.1.4.1.37950.1.1.5.10.12.18.1
-- 1.3.6.1.4.1.37950.1.1.5.10.12.18.1
-- 1.3.6.1.4.1.37950.1.1.5.10.12.18.1
-- 1.3.6.1.4.1.37950.1.1.5.10.12.18.1
-- 1.3.6.1.4.1.37950.1.1.5.10.12.18.1
-- 1.3.6.1.4.1.37950.1.1.5.10.12.18.1
-- 1.3.6.1.4.1.37950.1.1.5.10.12.18.1
-- 1.3.6.1.4.1.37950.1.1.5.10.12.18.1
		-- 1.3.6.1.4.1.37950.1.1.5.10.12.18.1
		tftpServerIPv6 OBJECT-TYPE
			SYNTAX OCTET STRING
			MAX-ACCESS read-write
			STATUS current
			DESCRIPTION
				"Description."
			::= { systemIPv6Upgrade 1 }

		
--         1.3.6.1.4.1.37950.1.1.5.10.12.18.2
-- 1.3.6.1.4.1.37950.1.1.5.10.12.18.2
-- 1.3.6.1.4.1.37950.1.1.5.10.12.18.2
-- 1.3.6.1.4.1.37950.1.1.5.10.12.18.2
-- 1.3.6.1.4.1.37950.1.1.5.10.12.18.2
-- 1.3.6.1.4.1.37950.1.1.5.10.12.18.2
-- 1.3.6.1.4.1.37950.1.1.5.10.12.18.2
-- 1.3.6.1.4.1.37950.1.1.5.10.12.18.2
		-- 1.3.6.1.4.1.37950.1.1.5.10.12.18.2
		filetype OBJECT-TYPE
			SYNTAX INTEGER
				{
				bld(1),
				kernel(2),
				rootfs(3)
				}
			MAX-ACCESS read-write
			STATUS current
			DESCRIPTION
				"Description."
			::= { systemIPv6Upgrade 2 }

		
--         1.3.6.1.4.1.37950.1.1.5.10.12.18.3
-- 1.3.6.1.4.1.37950.1.1.5.10.12.18.3
-- 1.3.6.1.4.1.37950.1.1.5.10.12.18.3
-- 1.3.6.1.4.1.37950.1.1.5.10.12.18.3
-- 1.3.6.1.4.1.37950.1.1.5.10.12.18.3
-- 1.3.6.1.4.1.37950.1.1.5.10.12.18.3
-- 1.3.6.1.4.1.37950.1.1.5.10.12.18.3
-- 1.3.6.1.4.1.37950.1.1.5.10.12.18.3
		-- 1.3.6.1.4.1.37950.1.1.5.10.12.18.3
		fileNAME OBJECT-TYPE
			SYNTAX OCTET STRING
			MAX-ACCESS read-write
			STATUS current
			DESCRIPTION
				"Description."
			::= { systemIPv6Upgrade 3 }

		
--         1.3.6.1.4.1.37950.1.1.5.10.12.18.4
-- 1.3.6.1.4.1.37950.1.1.5.10.12.18.4
-- 1.3.6.1.4.1.37950.1.1.5.10.12.18.4
-- 1.3.6.1.4.1.37950.1.1.5.10.12.18.4
-- 1.3.6.1.4.1.37950.1.1.5.10.12.18.4
-- 1.3.6.1.4.1.37950.1.1.5.10.12.18.4
-- 1.3.6.1.4.1.37950.1.1.5.10.12.18.4
-- 1.3.6.1.4.1.37950.1.1.5.10.12.18.4
		-- 1.3.6.1.4.1.37950.1.1.5.10.12.18.4
		ipv6UpgradeCommit OBJECT-TYPE
			SYNTAX INTEGER { commit(1) }
			MAX-ACCESS read-write
			STATUS current
			DESCRIPTION
				"Description."
			::= { systemIPv6Upgrade 4 }

		
--         1.3.6.1.4.1.37950.1.1.5.10.12.19
-- 1.3.6.1.4.1.37950.1.1.5.10.12.19
-- 1.3.6.1.4.1.37950.1.1.5.10.12.19
-- 1.3.6.1.4.1.37950.1.1.5.10.12.19
-- 1.3.6.1.4.1.37950.1.1.5.10.12.19
-- 1.3.6.1.4.1.37950.1.1.5.10.12.19
-- 1.3.6.1.4.1.37950.1.1.5.10.12.19
-- 1.3.6.1.4.1.37950.1.1.5.10.12.19
		-- 1.3.6.1.4.1.37950.1.1.5.10.12.19
		userManagement OBJECT IDENTIFIER ::= { v1600dSysCfg 19 }

		
--         1.3.6.1.4.1.37950.1.1.5.10.12.19.1
-- 1.3.6.1.4.1.37950.1.1.5.10.12.19.1
-- 1.3.6.1.4.1.37950.1.1.5.10.12.19.1
-- 1.3.6.1.4.1.37950.1.1.5.10.12.19.1
-- 1.3.6.1.4.1.37950.1.1.5.10.12.19.1
-- 1.3.6.1.4.1.37950.1.1.5.10.12.19.1
-- 1.3.6.1.4.1.37950.1.1.5.10.12.19.1
-- 1.3.6.1.4.1.37950.1.1.5.10.12.19.1
		-- 1.3.6.1.4.1.37950.1.1.5.10.12.19.1
		userManagementCfg OBJECT IDENTIFIER ::= { userManagement 1 }

		
--         1.3.6.1.4.1.37950.1.1.5.10.12.19.1.1
-- 1.3.6.1.4.1.37950.1.1.5.10.12.19.1.1
-- 1.3.6.1.4.1.37950.1.1.5.10.12.19.1.1
-- 1.3.6.1.4.1.37950.1.1.5.10.12.19.1.1
-- 1.3.6.1.4.1.37950.1.1.5.10.12.19.1.1
-- 1.3.6.1.4.1.37950.1.1.5.10.12.19.1.1
-- 1.3.6.1.4.1.37950.1.1.5.10.12.19.1.1
-- 1.3.6.1.4.1.37950.1.1.5.10.12.19.1.1
		-- 1.3.6.1.4.1.37950.1.1.5.10.12.19.1.1
		userNameC OBJECT-TYPE
			SYNTAX OCTET STRING
			MAX-ACCESS read-write
			STATUS current
			DESCRIPTION
				"Description."
			::= { userManagementCfg 1 }

		
--         1.3.6.1.4.1.37950.1.1.5.10.12.19.1.2
-- 1.3.6.1.4.1.37950.1.1.5.10.12.19.1.2
-- 1.3.6.1.4.1.37950.1.1.5.10.12.19.1.2
-- 1.3.6.1.4.1.37950.1.1.5.10.12.19.1.2
-- 1.3.6.1.4.1.37950.1.1.5.10.12.19.1.2
-- 1.3.6.1.4.1.37950.1.1.5.10.12.19.1.2
-- 1.3.6.1.4.1.37950.1.1.5.10.12.19.1.2
-- 1.3.6.1.4.1.37950.1.1.5.10.12.19.1.2
		-- 1.3.6.1.4.1.37950.1.1.5.10.12.19.1.2
		userPassword OBJECT-TYPE
			SYNTAX OCTET STRING
			MAX-ACCESS read-write
			STATUS current
			DESCRIPTION
				"Description."
			::= { userManagementCfg 2 }

		
--         1.3.6.1.4.1.37950.1.1.5.10.12.19.1.3
-- 1.3.6.1.4.1.37950.1.1.5.10.12.19.1.3
-- 1.3.6.1.4.1.37950.1.1.5.10.12.19.1.3
-- 1.3.6.1.4.1.37950.1.1.5.10.12.19.1.3
-- 1.3.6.1.4.1.37950.1.1.5.10.12.19.1.3
-- 1.3.6.1.4.1.37950.1.1.5.10.12.19.1.3
-- 1.3.6.1.4.1.37950.1.1.5.10.12.19.1.3
-- 1.3.6.1.4.1.37950.1.1.5.10.12.19.1.3
		-- 1.3.6.1.4.1.37950.1.1.5.10.12.19.1.3
		confirmPassword OBJECT-TYPE
			SYNTAX OCTET STRING
			MAX-ACCESS read-write
			STATUS current
			DESCRIPTION
				"Description."
			::= { userManagementCfg 3 }

		
--         1.3.6.1.4.1.37950.1.1.5.10.12.19.1.4
-- 1.3.6.1.4.1.37950.1.1.5.10.12.19.1.4
-- 1.3.6.1.4.1.37950.1.1.5.10.12.19.1.4
-- 1.3.6.1.4.1.37950.1.1.5.10.12.19.1.4
-- 1.3.6.1.4.1.37950.1.1.5.10.12.19.1.4
-- 1.3.6.1.4.1.37950.1.1.5.10.12.19.1.4
-- 1.3.6.1.4.1.37950.1.1.5.10.12.19.1.4
-- 1.3.6.1.4.1.37950.1.1.5.10.12.19.1.4
		-- 1.3.6.1.4.1.37950.1.1.5.10.12.19.1.4
		userRole OBJECT-TYPE
			SYNTAX INTEGER
				{
				normal(0),
				admin(1)
				}
			MAX-ACCESS read-write
			STATUS current
			DESCRIPTION
				"Description."
			::= { userManagementCfg 4 }

		
--         1.3.6.1.4.1.37950.1.1.5.10.12.19.1.5
-- 1.3.6.1.4.1.37950.1.1.5.10.12.19.1.5
-- 1.3.6.1.4.1.37950.1.1.5.10.12.19.1.5
-- 1.3.6.1.4.1.37950.1.1.5.10.12.19.1.5
-- 1.3.6.1.4.1.37950.1.1.5.10.12.19.1.5
-- 1.3.6.1.4.1.37950.1.1.5.10.12.19.1.5
-- 1.3.6.1.4.1.37950.1.1.5.10.12.19.1.5
-- 1.3.6.1.4.1.37950.1.1.5.10.12.19.1.5
		-- 1.3.6.1.4.1.37950.1.1.5.10.12.19.1.5
		userCfgaction OBJECT-TYPE
			SYNTAX INTEGER
				{
				add(1),
				del(2),
				edit(3)
				}
			MAX-ACCESS read-write
			STATUS current
			DESCRIPTION
				"Description."
			::= { userManagementCfg 5 }

		
--         1.3.6.1.4.1.37950.1.1.5.10.12.19.2
-- 1.3.6.1.4.1.37950.1.1.5.10.12.19.2
-- 1.3.6.1.4.1.37950.1.1.5.10.12.19.2
-- 1.3.6.1.4.1.37950.1.1.5.10.12.19.2
-- 1.3.6.1.4.1.37950.1.1.5.10.12.19.2
-- 1.3.6.1.4.1.37950.1.1.5.10.12.19.2
-- 1.3.6.1.4.1.37950.1.1.5.10.12.19.2
-- 1.3.6.1.4.1.37950.1.1.5.10.12.19.2
		-- 1.3.6.1.4.1.37950.1.1.5.10.12.19.2
		userManagementTable OBJECT-TYPE
			SYNTAX SEQUENCE OF UserManagementEntry
			MAX-ACCESS not-accessible
			STATUS current
			DESCRIPTION
				"Description."
			::= { userManagement 2 }

		
--         1.3.6.1.4.1.37950.1.1.5.10.12.19.2.1
-- 1.3.6.1.4.1.37950.1.1.5.10.12.19.2.1
-- 1.3.6.1.4.1.37950.1.1.5.10.12.19.2.1
-- 1.3.6.1.4.1.37950.1.1.5.10.12.19.2.1
-- 1.3.6.1.4.1.37950.1.1.5.10.12.19.2.1
-- 1.3.6.1.4.1.37950.1.1.5.10.12.19.2.1
-- 1.3.6.1.4.1.37950.1.1.5.10.12.19.2.1
-- 1.3.6.1.4.1.37950.1.1.5.10.12.19.2.1
		-- 1.3.6.1.4.1.37950.1.1.5.10.12.19.2.1
		userManagementEntry OBJECT-TYPE
			SYNTAX UserManagementEntry
			MAX-ACCESS not-accessible
			STATUS current
			DESCRIPTION
				"Description."
			INDEX { userNameS, userRoleS }
			::= { userManagementTable 1 }

		
		UserManagementEntry ::=
			SEQUENCE { 
				userNameS
					OCTET STRING,
				userRoleS
					INTEGER
			 }

--         1.3.6.1.4.1.37950.1.1.5.10.12.19.2.1.1
-- 1.3.6.1.4.1.37950.1.1.5.10.12.19.2.1.1
-- 1.3.6.1.4.1.37950.1.1.5.10.12.19.2.1.1
-- 1.3.6.1.4.1.37950.1.1.5.10.12.19.2.1.1
-- 1.3.6.1.4.1.37950.1.1.5.10.12.19.2.1.1
-- 1.3.6.1.4.1.37950.1.1.5.10.12.19.2.1.1
-- 1.3.6.1.4.1.37950.1.1.5.10.12.19.2.1.1
-- 1.3.6.1.4.1.37950.1.1.5.10.12.19.2.1.1
		-- 1.3.6.1.4.1.37950.1.1.5.10.12.19.2.1.1
		userNameS OBJECT-TYPE
			SYNTAX OCTET STRING
			MAX-ACCESS read-write
			STATUS current
			DESCRIPTION
				"Description."
			::= { userManagementEntry 1 }

		
--         1.3.6.1.4.1.37950.1.1.5.10.12.19.2.1.2
-- 1.3.6.1.4.1.37950.1.1.5.10.12.19.2.1.2
-- 1.3.6.1.4.1.37950.1.1.5.10.12.19.2.1.2
-- 1.3.6.1.4.1.37950.1.1.5.10.12.19.2.1.2
-- 1.3.6.1.4.1.37950.1.1.5.10.12.19.2.1.2
-- 1.3.6.1.4.1.37950.1.1.5.10.12.19.2.1.2
-- 1.3.6.1.4.1.37950.1.1.5.10.12.19.2.1.2
-- 1.3.6.1.4.1.37950.1.1.5.10.12.19.2.1.2
		-- 1.3.6.1.4.1.37950.1.1.5.10.12.19.2.1.2
		userRoleS OBJECT-TYPE
			SYNTAX INTEGER
				{
				normal(1),
				admin(2)
				}
			MAX-ACCESS read-write
			STATUS current
			DESCRIPTION
				"Description."
			::= { userManagementEntry 2 }

		
--       1.3.6.1.4.1.37950.1.1.5.10.12.19.3
-- 1.3.6.1.4.1.37950.1.1.5.10.12.19.3
-- 1.3.6.1.4.1.37950.1.1.5.10.12.19.3
-- 1.3.6.1.4.1.37950.1.1.5.10.12.19.3
-- 1.3.6.1.4.1.37950.1.1.5.10.12.19.3
-- 1.3.6.1.4.1.37950.1.1.5.10.12.19.3
		-- 1.3.6.1.4.1.37950.1.1.5.10.12.19.3
		newRoleAdd OBJECT IDENTIFIER ::= { userManagement 3 }

		
--       1.3.6.1.4.1.37950.1.1.5.10.12.19.3.1
-- 1.3.6.1.4.1.37950.1.1.5.10.12.19.3.1
-- 1.3.6.1.4.1.37950.1.1.5.10.12.19.3.1
-- 1.3.6.1.4.1.37950.1.1.5.10.12.19.3.1
-- 1.3.6.1.4.1.37950.1.1.5.10.12.19.3.1
-- 1.3.6.1.4.1.37950.1.1.5.10.12.19.3.1
		-- 1.3.6.1.4.1.37950.1.1.5.10.12.19.3.1
		roleDescriptionName OBJECT-TYPE
			SYNTAX OCTET STRING
			MAX-ACCESS read-write
			STATUS current
			DESCRIPTION
				"Description."
			::= { newRoleAdd 1 }

		
--       1.3.6.1.4.1.37950.1.1.5.10.12.19.4
-- 1.3.6.1.4.1.37950.1.1.5.10.12.19.4
-- 1.3.6.1.4.1.37950.1.1.5.10.12.19.4
-- 1.3.6.1.4.1.37950.1.1.5.10.12.19.4
-- 1.3.6.1.4.1.37950.1.1.5.10.12.19.4
-- 1.3.6.1.4.1.37950.1.1.5.10.12.19.4
		-- 1.3.6.1.4.1.37950.1.1.5.10.12.19.4
		roleManagementCfg OBJECT IDENTIFIER ::= { userManagement 4 }

		
--       1.3.6.1.4.1.37950.1.1.5.10.12.19.4.1
-- 1.3.6.1.4.1.37950.1.1.5.10.12.19.4.1
-- 1.3.6.1.4.1.37950.1.1.5.10.12.19.4.1
-- 1.3.6.1.4.1.37950.1.1.5.10.12.19.4.1
-- 1.3.6.1.4.1.37950.1.1.5.10.12.19.4.1
-- 1.3.6.1.4.1.37950.1.1.5.10.12.19.4.1
		-- 1.3.6.1.4.1.37950.1.1.5.10.12.19.4.1
		roleManaRoleGroupNameCfg OBJECT-TYPE
			SYNTAX OCTET STRING
			MAX-ACCESS read-write
			STATUS current
			DESCRIPTION
				"Description."
			::= { roleManagementCfg 1 }

		
--       1.3.6.1.4.1.37950.1.1.5.10.12.19.4.2
-- 1.3.6.1.4.1.37950.1.1.5.10.12.19.4.2
-- 1.3.6.1.4.1.37950.1.1.5.10.12.19.4.2
-- 1.3.6.1.4.1.37950.1.1.5.10.12.19.4.2
-- 1.3.6.1.4.1.37950.1.1.5.10.12.19.4.2
-- 1.3.6.1.4.1.37950.1.1.5.10.12.19.4.2
		-- 1.3.6.1.4.1.37950.1.1.5.10.12.19.4.2
		roleManaReadWriteCfg OBJECT-TYPE
			SYNTAX OCTET STRING
			MAX-ACCESS read-write
			STATUS current
			DESCRIPTION
				"Description."
			::= { roleManagementCfg 2 }

		
--       1.3.6.1.4.1.37950.1.1.5.10.12.19.4.3
-- 1.3.6.1.4.1.37950.1.1.5.10.12.19.4.3
-- 1.3.6.1.4.1.37950.1.1.5.10.12.19.4.3
-- 1.3.6.1.4.1.37950.1.1.5.10.12.19.4.3
-- 1.3.6.1.4.1.37950.1.1.5.10.12.19.4.3
-- 1.3.6.1.4.1.37950.1.1.5.10.12.19.4.3
		-- 1.3.6.1.4.1.37950.1.1.5.10.12.19.4.3
		roleManaActionCfg OBJECT-TYPE
			SYNTAX Integer32
			MAX-ACCESS read-write
			STATUS current
			DESCRIPTION
				"Description."
			::= { roleManagementCfg 3 }

		
--       1.3.6.1.4.1.37950.1.1.5.10.12.19.5
-- 1.3.6.1.4.1.37950.1.1.5.10.12.19.5
-- 1.3.6.1.4.1.37950.1.1.5.10.12.19.5
-- 1.3.6.1.4.1.37950.1.1.5.10.12.19.5
-- 1.3.6.1.4.1.37950.1.1.5.10.12.19.5
-- 1.3.6.1.4.1.37950.1.1.5.10.12.19.5
		-- 1.3.6.1.4.1.37950.1.1.5.10.12.19.5
		roleManagementTable OBJECT-TYPE
			SYNTAX SEQUENCE OF RoleManagementEntry
			MAX-ACCESS not-accessible
			STATUS current
			DESCRIPTION
				"Description."
			::= { userManagement 5 }

		
--       1.3.6.1.4.1.37950.1.1.5.10.12.19.5.1
-- 1.3.6.1.4.1.37950.1.1.5.10.12.19.5.1
-- 1.3.6.1.4.1.37950.1.1.5.10.12.19.5.1
-- 1.3.6.1.4.1.37950.1.1.5.10.12.19.5.1
-- 1.3.6.1.4.1.37950.1.1.5.10.12.19.5.1
-- 1.3.6.1.4.1.37950.1.1.5.10.12.19.5.1
		-- 1.3.6.1.4.1.37950.1.1.5.10.12.19.5.1
		roleManagementEntry OBJECT-TYPE
			SYNTAX RoleManagementEntry
			MAX-ACCESS not-accessible
			STATUS current
			DESCRIPTION
				"Description."
			INDEX { roleManaIndex }
			::= { roleManagementTable 1 }

		
		RoleManagementEntry ::=
			SEQUENCE { 
				roleManaIndex
					Integer32,
				roleManaRoleGroupName
					OCTET STRING,
				roleManaReadWrite
					OCTET STRING
			 }

--       1.3.6.1.4.1.37950.1.1.5.10.12.19.5.1.1
-- 1.3.6.1.4.1.37950.1.1.5.10.12.19.5.1.1
-- 1.3.6.1.4.1.37950.1.1.5.10.12.19.5.1.1
-- 1.3.6.1.4.1.37950.1.1.5.10.12.19.5.1.1
-- 1.3.6.1.4.1.37950.1.1.5.10.12.19.5.1.1
-- 1.3.6.1.4.1.37950.1.1.5.10.12.19.5.1.1
		-- 1.3.6.1.4.1.37950.1.1.5.10.12.19.5.1.1
		roleManaIndex OBJECT-TYPE
			SYNTAX Integer32
			MAX-ACCESS read-only
			STATUS current
			DESCRIPTION
				"Description."
			::= { roleManagementEntry 1 }

		
--       1.3.6.1.4.1.37950.1.1.5.10.12.19.5.1.2
-- 1.3.6.1.4.1.37950.1.1.5.10.12.19.5.1.2
-- 1.3.6.1.4.1.37950.1.1.5.10.12.19.5.1.2
-- 1.3.6.1.4.1.37950.1.1.5.10.12.19.5.1.2
-- 1.3.6.1.4.1.37950.1.1.5.10.12.19.5.1.2
-- 1.3.6.1.4.1.37950.1.1.5.10.12.19.5.1.2
		-- 1.3.6.1.4.1.37950.1.1.5.10.12.19.5.1.2
		roleManaRoleGroupName OBJECT-TYPE
			SYNTAX OCTET STRING
			MAX-ACCESS read-only
			STATUS current
			DESCRIPTION
				"Description."
			::= { roleManagementEntry 2 }

		
--       1.3.6.1.4.1.37950.1.1.5.10.12.19.5.1.3
-- 1.3.6.1.4.1.37950.1.1.5.10.12.19.5.1.3
-- 1.3.6.1.4.1.37950.1.1.5.10.12.19.5.1.3
-- 1.3.6.1.4.1.37950.1.1.5.10.12.19.5.1.3
-- 1.3.6.1.4.1.37950.1.1.5.10.12.19.5.1.3
-- 1.3.6.1.4.1.37950.1.1.5.10.12.19.5.1.3
		-- 1.3.6.1.4.1.37950.1.1.5.10.12.19.5.1.3
		roleManaReadWrite OBJECT-TYPE
			SYNTAX OCTET STRING
			MAX-ACCESS read-only
			STATUS current
			DESCRIPTION
				"Description."
			::= { roleManagementEntry 3 }

		
--         1.3.6.1.4.1.37950.1.1.5.10.12.20 
-- 1.3.6.1.4.1.37950.1.1.5.10.12.20
-- 1.3.6.1.4.1.37950.1.1.5.10.12.20
-- 1.3.6.1.4.1.37950.1.1.5.10.12.20
-- 1.3.6.1.4.1.37950.1.1.5.10.12.20
-- 1.3.6.1.4.1.37950.1.1.5.10.12.20
-- 1.3.6.1.4.1.37950.1.1.5.10.12.20
-- 1.3.6.1.4.1.37950.1.1.5.10.12.20
		-- 1.3.6.1.4.1.37950.1.1.5.10.12.20
		netWorkSecurity OBJECT IDENTIFIER ::= { v1600dSysCfg 20 }

		
--         1.3.6.1.4.1.37950.1.1.5.10.12.20.1
-- 1.3.6.1.4.1.37950.1.1.5.10.12.20.1
-- 1.3.6.1.4.1.37950.1.1.5.10.12.20.1
-- 1.3.6.1.4.1.37950.1.1.5.10.12.20.1
-- 1.3.6.1.4.1.37950.1.1.5.10.12.20.1
-- 1.3.6.1.4.1.37950.1.1.5.10.12.20.1
-- 1.3.6.1.4.1.37950.1.1.5.10.12.20.1
-- 1.3.6.1.4.1.37950.1.1.5.10.12.20.1
		-- 1.3.6.1.4.1.37950.1.1.5.10.12.20.1
		prevenceLevel OBJECT-TYPE
			SYNTAX INTEGER
				{
				off(0),
				low(1),
				middle(2),
				high(3),
				flexiable(4)
				}
			MAX-ACCESS read-write
			STATUS current
			DESCRIPTION
				"Description."
			::= { netWorkSecurity 1 }

		
--         1.3.6.1.4.1.37950.1.1.5.10.12.20.2
-- 1.3.6.1.4.1.37950.1.1.5.10.12.20.2
-- 1.3.6.1.4.1.37950.1.1.5.10.12.20.2
-- 1.3.6.1.4.1.37950.1.1.5.10.12.20.2
-- 1.3.6.1.4.1.37950.1.1.5.10.12.20.2
-- 1.3.6.1.4.1.37950.1.1.5.10.12.20.2
-- 1.3.6.1.4.1.37950.1.1.5.10.12.20.2
-- 1.3.6.1.4.1.37950.1.1.5.10.12.20.2
		-- 1.3.6.1.4.1.37950.1.1.5.10.12.20.2
		ipFirstFragCheck OBJECT-TYPE
			SYNTAX INTEGER
				{
				disable(0),
				enable(1)
				}
			MAX-ACCESS read-write
			STATUS current
			DESCRIPTION
				"Description."
			::= { netWorkSecurity 2 }

		
--         1.3.6.1.4.1.37950.1.1.5.10.12.20.3
-- 1.3.6.1.4.1.37950.1.1.5.10.12.20.3
-- 1.3.6.1.4.1.37950.1.1.5.10.12.20.3
-- 1.3.6.1.4.1.37950.1.1.5.10.12.20.3
-- 1.3.6.1.4.1.37950.1.1.5.10.12.20.3
-- 1.3.6.1.4.1.37950.1.1.5.10.12.20.3
-- 1.3.6.1.4.1.37950.1.1.5.10.12.20.3
-- 1.3.6.1.4.1.37950.1.1.5.10.12.20.3
		-- 1.3.6.1.4.1.37950.1.1.5.10.12.20.3
		srcIpDstIpCheck OBJECT-TYPE
			SYNTAX INTEGER
				{
				disable(0),
				enable(1)
				}
			MAX-ACCESS read-write
			STATUS current
			DESCRIPTION
				"Description."
			::= { netWorkSecurity 3 }

		
--         1.3.6.1.4.1.37950.1.1.5.10.12.20.4
-- 1.3.6.1.4.1.37950.1.1.5.10.12.20.4
-- 1.3.6.1.4.1.37950.1.1.5.10.12.20.4
-- 1.3.6.1.4.1.37950.1.1.5.10.12.20.4
-- 1.3.6.1.4.1.37950.1.1.5.10.12.20.4
-- 1.3.6.1.4.1.37950.1.1.5.10.12.20.4
-- 1.3.6.1.4.1.37950.1.1.5.10.12.20.4
-- 1.3.6.1.4.1.37950.1.1.5.10.12.20.4
		-- 1.3.6.1.4.1.37950.1.1.5.10.12.20.4
		srcMacDstMacCheck OBJECT-TYPE
			SYNTAX INTEGER
				{
				disable(0),
				enable(1)
				}
			MAX-ACCESS read-write
			STATUS current
			DESCRIPTION
				"Description."
			::= { netWorkSecurity 4 }

		
--         1.3.6.1.4.1.37950.1.1.5.10.12.20.5
-- 1.3.6.1.4.1.37950.1.1.5.10.12.20.5
-- 1.3.6.1.4.1.37950.1.1.5.10.12.20.5
-- 1.3.6.1.4.1.37950.1.1.5.10.12.20.5
-- 1.3.6.1.4.1.37950.1.1.5.10.12.20.5
-- 1.3.6.1.4.1.37950.1.1.5.10.12.20.5
-- 1.3.6.1.4.1.37950.1.1.5.10.12.20.5
-- 1.3.6.1.4.1.37950.1.1.5.10.12.20.5
		-- 1.3.6.1.4.1.37950.1.1.5.10.12.20.5
		tcpFlagsSynFragCheck OBJECT-TYPE
			SYNTAX INTEGER
				{
				disable(0),
				enable(1)
				}
			MAX-ACCESS read-write
			STATUS current
			DESCRIPTION
				"Description."
			::= { netWorkSecurity 5 }

		
--         1.3.6.1.4.1.37950.1.1.5.10.12.20.6
-- 1.3.6.1.4.1.37950.1.1.5.10.12.20.6
-- 1.3.6.1.4.1.37950.1.1.5.10.12.20.6
-- 1.3.6.1.4.1.37950.1.1.5.10.12.20.6
-- 1.3.6.1.4.1.37950.1.1.5.10.12.20.6
-- 1.3.6.1.4.1.37950.1.1.5.10.12.20.6
-- 1.3.6.1.4.1.37950.1.1.5.10.12.20.6
-- 1.3.6.1.4.1.37950.1.1.5.10.12.20.6
		-- 1.3.6.1.4.1.37950.1.1.5.10.12.20.6
		tcpFlagsCrtl0Seq0Check OBJECT-TYPE
			SYNTAX INTEGER
				{
				disable(0),
				enable(1)
				}
			MAX-ACCESS read-write
			STATUS current
			DESCRIPTION
				"Description."
			::= { netWorkSecurity 6 }

		
--         1.3.6.1.4.1.37950.1.1.5.10.12.20.7
-- 1.3.6.1.4.1.37950.1.1.5.10.12.20.7
-- 1.3.6.1.4.1.37950.1.1.5.10.12.20.7
-- 1.3.6.1.4.1.37950.1.1.5.10.12.20.7
-- 1.3.6.1.4.1.37950.1.1.5.10.12.20.7
-- 1.3.6.1.4.1.37950.1.1.5.10.12.20.7
-- 1.3.6.1.4.1.37950.1.1.5.10.12.20.7
-- 1.3.6.1.4.1.37950.1.1.5.10.12.20.7
		-- 1.3.6.1.4.1.37950.1.1.5.10.12.20.7
		tcpFlagFinUrgPshSeq0Check OBJECT-TYPE
			SYNTAX INTEGER
				{
				disable(0),
				enable(1)
				}
			MAX-ACCESS read-write
			STATUS current
			DESCRIPTION
				"Description."
			::= { netWorkSecurity 7 }

		
--         1.3.6.1.4.1.37950.1.1.5.10.12.20.8
-- 1.3.6.1.4.1.37950.1.1.5.10.12.20.8
-- 1.3.6.1.4.1.37950.1.1.5.10.12.20.8
-- 1.3.6.1.4.1.37950.1.1.5.10.12.20.8
-- 1.3.6.1.4.1.37950.1.1.5.10.12.20.8
-- 1.3.6.1.4.1.37950.1.1.5.10.12.20.8
-- 1.3.6.1.4.1.37950.1.1.5.10.12.20.8
-- 1.3.6.1.4.1.37950.1.1.5.10.12.20.8
		-- 1.3.6.1.4.1.37950.1.1.5.10.12.20.8
		tcpFlagsSynFinCheck OBJECT-TYPE
			SYNTAX INTEGER
				{
				disable(0),
				enable(1)
				}
			MAX-ACCESS read-write
			STATUS current
			DESCRIPTION
				"Description."
			::= { netWorkSecurity 8 }

		
--         1.3.6.1.4.1.37950.1.1.5.10.12.20.9
-- 1.3.6.1.4.1.37950.1.1.5.10.12.20.9
-- 1.3.6.1.4.1.37950.1.1.5.10.12.20.9
-- 1.3.6.1.4.1.37950.1.1.5.10.12.20.9
-- 1.3.6.1.4.1.37950.1.1.5.10.12.20.9
-- 1.3.6.1.4.1.37950.1.1.5.10.12.20.9
-- 1.3.6.1.4.1.37950.1.1.5.10.12.20.9
-- 1.3.6.1.4.1.37950.1.1.5.10.12.20.9
		-- 1.3.6.1.4.1.37950.1.1.5.10.12.20.9
		tcpSrcportEqDstportCheck OBJECT-TYPE
			SYNTAX INTEGER
				{
				disable(0),
				enable(1)
				}
			MAX-ACCESS read-write
			STATUS current
			DESCRIPTION
				"Description."
			::= { netWorkSecurity 9 }

		
--         1.3.6.1.4.1.37950.1.1.5.10.12.20.10
-- 1.3.6.1.4.1.37950.1.1.5.10.12.20.10
-- 1.3.6.1.4.1.37950.1.1.5.10.12.20.10
-- 1.3.6.1.4.1.37950.1.1.5.10.12.20.10
-- 1.3.6.1.4.1.37950.1.1.5.10.12.20.10
-- 1.3.6.1.4.1.37950.1.1.5.10.12.20.10
-- 1.3.6.1.4.1.37950.1.1.5.10.12.20.10
-- 1.3.6.1.4.1.37950.1.1.5.10.12.20.10
		-- 1.3.6.1.4.1.37950.1.1.5.10.12.20.10
		udpSrcportEqDstportCheck OBJECT-TYPE
			SYNTAX INTEGER
				{
				disable(0),
				enable(1)
				}
			MAX-ACCESS read-write
			STATUS current
			DESCRIPTION
				"Description."
			::= { netWorkSecurity 10 }

		
--         1.3.6.1.4.1.37950.1.1.5.10.12.20.11
-- 1.3.6.1.4.1.37950.1.1.5.10.12.20.11
-- 1.3.6.1.4.1.37950.1.1.5.10.12.20.11
-- 1.3.6.1.4.1.37950.1.1.5.10.12.20.11
-- 1.3.6.1.4.1.37950.1.1.5.10.12.20.11
-- 1.3.6.1.4.1.37950.1.1.5.10.12.20.11
-- 1.3.6.1.4.1.37950.1.1.5.10.12.20.11
-- 1.3.6.1.4.1.37950.1.1.5.10.12.20.11
		-- 1.3.6.1.4.1.37950.1.1.5.10.12.20.11
		tcpHdrPartialCheck OBJECT-TYPE
			SYNTAX INTEGER
				{
				disable(0),
				enable(1)
				}
			MAX-ACCESS read-write
			STATUS current
			DESCRIPTION
				"Description."
			::= { netWorkSecurity 11 }

		
--         1.3.6.1.4.1.37950.1.1.5.10.12.20.12
-- 1.3.6.1.4.1.37950.1.1.5.10.12.20.12
-- 1.3.6.1.4.1.37950.1.1.5.10.12.20.12
-- 1.3.6.1.4.1.37950.1.1.5.10.12.20.12
-- 1.3.6.1.4.1.37950.1.1.5.10.12.20.12
-- 1.3.6.1.4.1.37950.1.1.5.10.12.20.12
-- 1.3.6.1.4.1.37950.1.1.5.10.12.20.12
-- 1.3.6.1.4.1.37950.1.1.5.10.12.20.12
		-- 1.3.6.1.4.1.37950.1.1.5.10.12.20.12
		tcpHdrPartialChecksize OBJECT-TYPE
			SYNTAX INTEGER (0..255)
			MAX-ACCESS read-write
			STATUS current
			DESCRIPTION
				"Description."
			::= { netWorkSecurity 12 }

		
--         1.3.6.1.4.1.37950.1.1.5.10.12.20.13
-- 1.3.6.1.4.1.37950.1.1.5.10.12.20.13
-- 1.3.6.1.4.1.37950.1.1.5.10.12.20.13
-- 1.3.6.1.4.1.37950.1.1.5.10.12.20.13
-- 1.3.6.1.4.1.37950.1.1.5.10.12.20.13
-- 1.3.6.1.4.1.37950.1.1.5.10.12.20.13
-- 1.3.6.1.4.1.37950.1.1.5.10.12.20.13
-- 1.3.6.1.4.1.37950.1.1.5.10.12.20.13
		-- 1.3.6.1.4.1.37950.1.1.5.10.12.20.13
		tcpHdrOffsetEq1Check OBJECT-TYPE
			SYNTAX INTEGER
				{
				disable(0),
				enable(1)
				}
			MAX-ACCESS read-write
			STATUS current
			DESCRIPTION
				"Description."
			::= { netWorkSecurity 13 }

		
--         1.3.6.1.4.1.37950.1.1.5.10.12.20.14
-- 1.3.6.1.4.1.37950.1.1.5.10.12.20.14
-- 1.3.6.1.4.1.37950.1.1.5.10.12.20.14
-- 1.3.6.1.4.1.37950.1.1.5.10.12.20.14
-- 1.3.6.1.4.1.37950.1.1.5.10.12.20.14
-- 1.3.6.1.4.1.37950.1.1.5.10.12.20.14
-- 1.3.6.1.4.1.37950.1.1.5.10.12.20.14
-- 1.3.6.1.4.1.37950.1.1.5.10.12.20.14
		-- 1.3.6.1.4.1.37950.1.1.5.10.12.20.14
		iCMPv6PingSizeCheck OBJECT-TYPE
			SYNTAX INTEGER
				{
				disable(0),
				enable(1)
				}
			MAX-ACCESS read-write
			STATUS current
			DESCRIPTION
				"Description."
			::= { netWorkSecurity 14 }

		
--         1.3.6.1.4.1.37950.1.1.5.10.12.20.15
-- 1.3.6.1.4.1.37950.1.1.5.10.12.20.15
-- 1.3.6.1.4.1.37950.1.1.5.10.12.20.15
-- 1.3.6.1.4.1.37950.1.1.5.10.12.20.15
-- 1.3.6.1.4.1.37950.1.1.5.10.12.20.15
-- 1.3.6.1.4.1.37950.1.1.5.10.12.20.15
-- 1.3.6.1.4.1.37950.1.1.5.10.12.20.15
-- 1.3.6.1.4.1.37950.1.1.5.10.12.20.15
		-- 1.3.6.1.4.1.37950.1.1.5.10.12.20.15
		iCMPv6PingSizeChecksize OBJECT-TYPE
			SYNTAX INTEGER (0..16000)
			MAX-ACCESS read-write
			STATUS current
			DESCRIPTION
				"Description."
			::= { netWorkSecurity 15 }

		
--         1.3.6.1.4.1.37950.1.1.5.10.12.20.16
-- 1.3.6.1.4.1.37950.1.1.5.10.12.20.16
-- 1.3.6.1.4.1.37950.1.1.5.10.12.20.16
-- 1.3.6.1.4.1.37950.1.1.5.10.12.20.16
-- 1.3.6.1.4.1.37950.1.1.5.10.12.20.16
-- 1.3.6.1.4.1.37950.1.1.5.10.12.20.16
-- 1.3.6.1.4.1.37950.1.1.5.10.12.20.16
-- 1.3.6.1.4.1.37950.1.1.5.10.12.20.16
		-- 1.3.6.1.4.1.37950.1.1.5.10.12.20.16
		iCMPv4PingSizeCheck OBJECT-TYPE
			SYNTAX INTEGER
				{
				disable(0),
				enable(1)
				}
			MAX-ACCESS read-write
			STATUS current
			DESCRIPTION
				"Description."
			::= { netWorkSecurity 16 }

		
--         1.3.6.1.4.1.37950.1.1.5.10.12.20.17
-- 1.3.6.1.4.1.37950.1.1.5.10.12.20.17
-- 1.3.6.1.4.1.37950.1.1.5.10.12.20.17
-- 1.3.6.1.4.1.37950.1.1.5.10.12.20.17
-- 1.3.6.1.4.1.37950.1.1.5.10.12.20.17
-- 1.3.6.1.4.1.37950.1.1.5.10.12.20.17
-- 1.3.6.1.4.1.37950.1.1.5.10.12.20.17
-- 1.3.6.1.4.1.37950.1.1.5.10.12.20.17
		-- 1.3.6.1.4.1.37950.1.1.5.10.12.20.17
		iCMPv4PingSizeChecksize OBJECT-TYPE
			SYNTAX INTEGER (0..16000)
			MAX-ACCESS read-write
			STATUS current
			DESCRIPTION
				"Description."
			::= { netWorkSecurity 17 }

		
--         1.3.6.1.4.1.37950.1.1.5.10.12.20.18
-- 1.3.6.1.4.1.37950.1.1.5.10.12.20.18
-- 1.3.6.1.4.1.37950.1.1.5.10.12.20.18
-- 1.3.6.1.4.1.37950.1.1.5.10.12.20.18
-- 1.3.6.1.4.1.37950.1.1.5.10.12.20.18
-- 1.3.6.1.4.1.37950.1.1.5.10.12.20.18
-- 1.3.6.1.4.1.37950.1.1.5.10.12.20.18
-- 1.3.6.1.4.1.37950.1.1.5.10.12.20.18
		-- 1.3.6.1.4.1.37950.1.1.5.10.12.20.18
		iCMPFragPktCheck OBJECT-TYPE
			SYNTAX INTEGER
				{
				disable(0),
				enable(1)
				}
			MAX-ACCESS read-write
			STATUS current
			DESCRIPTION
				"Description."
			::= { netWorkSecurity 18 }

		
--         1.3.6.1.4.1.37950.1.1.5.10.12.20.19
-- 1.3.6.1.4.1.37950.1.1.5.10.12.20.19
-- 1.3.6.1.4.1.37950.1.1.5.10.12.20.19
-- 1.3.6.1.4.1.37950.1.1.5.10.12.20.19
-- 1.3.6.1.4.1.37950.1.1.5.10.12.20.19
-- 1.3.6.1.4.1.37950.1.1.5.10.12.20.19
-- 1.3.6.1.4.1.37950.1.1.5.10.12.20.19
-- 1.3.6.1.4.1.37950.1.1.5.10.12.20.19
		-- 1.3.6.1.4.1.37950.1.1.5.10.12.20.19
		iPv6MinFragSizeCheck OBJECT-TYPE
			SYNTAX INTEGER
				{
				disable(0),
				enable(1)
				}
			MAX-ACCESS read-write
			STATUS current
			DESCRIPTION
				"Description."
			::= { netWorkSecurity 19 }

		
--         1.3.6.1.4.1.37950.1.1.5.10.12.20.20
-- 1.3.6.1.4.1.37950.1.1.5.10.12.20.20
-- 1.3.6.1.4.1.37950.1.1.5.10.12.20.20
-- 1.3.6.1.4.1.37950.1.1.5.10.12.20.20
-- 1.3.6.1.4.1.37950.1.1.5.10.12.20.20
-- 1.3.6.1.4.1.37950.1.1.5.10.12.20.20
-- 1.3.6.1.4.1.37950.1.1.5.10.12.20.20
-- 1.3.6.1.4.1.37950.1.1.5.10.12.20.20
		-- 1.3.6.1.4.1.37950.1.1.5.10.12.20.20
		ponDebug OBJECT-TYPE
			SYNTAX INTEGER
				{
				disable(0),
				enable(1)
				}
			MAX-ACCESS read-write
			STATUS current
			DESCRIPTION
				"Description."
			::= { netWorkSecurity 20 }

		
--         1.3.6.1.4.1.37950.1.1.5.10.12.20.21
-- 1.3.6.1.4.1.37950.1.1.5.10.12.20.21
-- 1.3.6.1.4.1.37950.1.1.5.10.12.20.21
-- 1.3.6.1.4.1.37950.1.1.5.10.12.20.21
-- 1.3.6.1.4.1.37950.1.1.5.10.12.20.21
-- 1.3.6.1.4.1.37950.1.1.5.10.12.20.21
-- 1.3.6.1.4.1.37950.1.1.5.10.12.20.21
-- 1.3.6.1.4.1.37950.1.1.5.10.12.20.21
		-- 1.3.6.1.4.1.37950.1.1.5.10.12.20.21
		kernalDebug OBJECT-TYPE
			SYNTAX INTEGER
				{
				disable(0),
				enable(1)
				}
			MAX-ACCESS read-write
			STATUS current
			DESCRIPTION
				"Description."
			::= { netWorkSecurity 21 }

		
--         1.3.6.1.4.1.37950.1.1.5.10.12.20.22
-- 1.3.6.1.4.1.37950.1.1.5.10.12.20.22
-- 1.3.6.1.4.1.37950.1.1.5.10.12.20.22
-- 1.3.6.1.4.1.37950.1.1.5.10.12.20.22
-- 1.3.6.1.4.1.37950.1.1.5.10.12.20.22
-- 1.3.6.1.4.1.37950.1.1.5.10.12.20.22
-- 1.3.6.1.4.1.37950.1.1.5.10.12.20.22
-- 1.3.6.1.4.1.37950.1.1.5.10.12.20.22
		-- 1.3.6.1.4.1.37950.1.1.5.10.12.20.22
		normal OBJECT-TYPE
			SYNTAX INTEGER
				{
				disable(0),
				enable(1)
				}
			MAX-ACCESS read-write
			STATUS current
			DESCRIPTION
				"Description."
			::= { netWorkSecurity 22 }

		
--         1.3.6.1.4.1.37950.1.1.5.10.12.20.23
-- 1.3.6.1.4.1.37950.1.1.5.10.12.20.23
-- 1.3.6.1.4.1.37950.1.1.5.10.12.20.23
-- 1.3.6.1.4.1.37950.1.1.5.10.12.20.23
-- 1.3.6.1.4.1.37950.1.1.5.10.12.20.23
-- 1.3.6.1.4.1.37950.1.1.5.10.12.20.23
-- 1.3.6.1.4.1.37950.1.1.5.10.12.20.23
-- 1.3.6.1.4.1.37950.1.1.5.10.12.20.23
		-- 1.3.6.1.4.1.37950.1.1.5.10.12.20.23
		networkaction OBJECT-TYPE
			SYNTAX INTEGER { submit(0) }
			MAX-ACCESS read-write
			STATUS current
			DESCRIPTION
				"Description."
			::= { netWorkSecurity 23 }

		
--         1.3.6.1.4.1.37950.1.1.5.10.12.20.24
-- 1.3.6.1.4.1.37950.1.1.5.10.12.20.24
-- 1.3.6.1.4.1.37950.1.1.5.10.12.20.24
-- 1.3.6.1.4.1.37950.1.1.5.10.12.20.24
-- 1.3.6.1.4.1.37950.1.1.5.10.12.20.24
-- 1.3.6.1.4.1.37950.1.1.5.10.12.20.24
-- 1.3.6.1.4.1.37950.1.1.5.10.12.20.24
-- 1.3.6.1.4.1.37950.1.1.5.10.12.20.24
		-- 1.3.6.1.4.1.37950.1.1.5.10.12.20.24
		d4lownetWorkSecurity OBJECT IDENTIFIER ::= { netWorkSecurity 24 }

		
--         1.3.6.1.4.1.37950.1.1.5.10.12.20.24.1
-- 1.3.6.1.4.1.37950.1.1.5.10.12.20.24.1
-- 1.3.6.1.4.1.37950.1.1.5.10.12.20.24.1
-- 1.3.6.1.4.1.37950.1.1.5.10.12.20.24.1
-- 1.3.6.1.4.1.37950.1.1.5.10.12.20.24.1
-- 1.3.6.1.4.1.37950.1.1.5.10.12.20.24.1
-- 1.3.6.1.4.1.37950.1.1.5.10.12.20.24.1
-- 1.3.6.1.4.1.37950.1.1.5.10.12.20.24.1
		-- 1.3.6.1.4.1.37950.1.1.5.10.12.20.24.1
		d4lowsrcMacDstMacCheck OBJECT-TYPE
			SYNTAX INTEGER
				{
				disable(0),
				enable(1)
				}
			MAX-ACCESS read-write
			STATUS current
			DESCRIPTION
				"Description."
			::= { d4lownetWorkSecurity 1 }

		
--         1.3.6.1.4.1.37950.1.1.5.10.12.20.24.2
-- 1.3.6.1.4.1.37950.1.1.5.10.12.20.24.2
-- 1.3.6.1.4.1.37950.1.1.5.10.12.20.24.2
-- 1.3.6.1.4.1.37950.1.1.5.10.12.20.24.2
-- 1.3.6.1.4.1.37950.1.1.5.10.12.20.24.2
-- 1.3.6.1.4.1.37950.1.1.5.10.12.20.24.2
-- 1.3.6.1.4.1.37950.1.1.5.10.12.20.24.2
-- 1.3.6.1.4.1.37950.1.1.5.10.12.20.24.2
		-- 1.3.6.1.4.1.37950.1.1.5.10.12.20.24.2
		d4lowsrcIpDstIpCheck OBJECT-TYPE
			SYNTAX INTEGER
				{
				disable(0),
				enable(1)
				}
			MAX-ACCESS read-write
			STATUS current
			DESCRIPTION
				"Description."
			::= { d4lownetWorkSecurity 2 }

		
--         1.3.6.1.4.1.37950.1.1.5.10.12.20.24.3
-- 1.3.6.1.4.1.37950.1.1.5.10.12.20.24.3
-- 1.3.6.1.4.1.37950.1.1.5.10.12.20.24.3
-- 1.3.6.1.4.1.37950.1.1.5.10.12.20.24.3
-- 1.3.6.1.4.1.37950.1.1.5.10.12.20.24.3
-- 1.3.6.1.4.1.37950.1.1.5.10.12.20.24.3
-- 1.3.6.1.4.1.37950.1.1.5.10.12.20.24.3
-- 1.3.6.1.4.1.37950.1.1.5.10.12.20.24.3
		-- 1.3.6.1.4.1.37950.1.1.5.10.12.20.24.3
		d4lowl4SrcportEqDstportCheck OBJECT-TYPE
			SYNTAX INTEGER
				{
				disable(0),
				enable(1)
				}
			MAX-ACCESS read-write
			STATUS current
			DESCRIPTION
				"Description."
			::= { d4lownetWorkSecurity 3 }

		
--         1.3.6.1.4.1.37950.1.1.5.10.12.20.24.4
-- 1.3.6.1.4.1.37950.1.1.5.10.12.20.24.4
-- 1.3.6.1.4.1.37950.1.1.5.10.12.20.24.4
-- 1.3.6.1.4.1.37950.1.1.5.10.12.20.24.4
-- 1.3.6.1.4.1.37950.1.1.5.10.12.20.24.4
-- 1.3.6.1.4.1.37950.1.1.5.10.12.20.24.4
-- 1.3.6.1.4.1.37950.1.1.5.10.12.20.24.4
-- 1.3.6.1.4.1.37950.1.1.5.10.12.20.24.4
		-- 1.3.6.1.4.1.37950.1.1.5.10.12.20.24.4
		d4lowtcpFlagsSynFinCheck OBJECT-TYPE
			SYNTAX INTEGER
				{
				disable(0),
				enable(1)
				}
			MAX-ACCESS read-write
			STATUS current
			DESCRIPTION
				"Description."
			::= { d4lownetWorkSecurity 4 }

		
--         1.3.6.1.4.1.37950.1.1.5.10.12.20.24.5
-- 1.3.6.1.4.1.37950.1.1.5.10.12.20.24.5
-- 1.3.6.1.4.1.37950.1.1.5.10.12.20.24.5
-- 1.3.6.1.4.1.37950.1.1.5.10.12.20.24.5
-- 1.3.6.1.4.1.37950.1.1.5.10.12.20.24.5
-- 1.3.6.1.4.1.37950.1.1.5.10.12.20.24.5
-- 1.3.6.1.4.1.37950.1.1.5.10.12.20.24.5
-- 1.3.6.1.4.1.37950.1.1.5.10.12.20.24.5
		-- 1.3.6.1.4.1.37950.1.1.5.10.12.20.24.5
		d4lowtcpFlagFinUrgPshSeq0Check OBJECT-TYPE
			SYNTAX INTEGER
				{
				disable(0),
				enable(1)
				}
			MAX-ACCESS read-write
			STATUS current
			DESCRIPTION
				"Description."
			::= { d4lownetWorkSecurity 5 }

		
--         1.3.6.1.4.1.37950.1.1.5.10.12.20.24.6
-- 1.3.6.1.4.1.37950.1.1.5.10.12.20.24.6
-- 1.3.6.1.4.1.37950.1.1.5.10.12.20.24.6
-- 1.3.6.1.4.1.37950.1.1.5.10.12.20.24.6
-- 1.3.6.1.4.1.37950.1.1.5.10.12.20.24.6
-- 1.3.6.1.4.1.37950.1.1.5.10.12.20.24.6
-- 1.3.6.1.4.1.37950.1.1.5.10.12.20.24.6
-- 1.3.6.1.4.1.37950.1.1.5.10.12.20.24.6
		-- 1.3.6.1.4.1.37950.1.1.5.10.12.20.24.6
		d4lowtcpFlagsCrtl0Seq0Check OBJECT-TYPE
			SYNTAX INTEGER
				{
				disable(0),
				enable(1)
				}
			MAX-ACCESS read-write
			STATUS current
			DESCRIPTION
				"Description."
			::= { d4lownetWorkSecurity 6 }

		
--         1.3.6.1.4.1.37950.1.1.5.10.12.20.24.7
-- 1.3.6.1.4.1.37950.1.1.5.10.12.20.24.7
-- 1.3.6.1.4.1.37950.1.1.5.10.12.20.24.7
-- 1.3.6.1.4.1.37950.1.1.5.10.12.20.24.7
-- 1.3.6.1.4.1.37950.1.1.5.10.12.20.24.7
-- 1.3.6.1.4.1.37950.1.1.5.10.12.20.24.7
-- 1.3.6.1.4.1.37950.1.1.5.10.12.20.24.7
-- 1.3.6.1.4.1.37950.1.1.5.10.12.20.24.7
		-- 1.3.6.1.4.1.37950.1.1.5.10.12.20.24.7
		d4lowtcpFlagsSynFragCheck OBJECT-TYPE
			SYNTAX INTEGER
				{
				disable(0),
				enable(1)
				}
			MAX-ACCESS read-write
			STATUS current
			DESCRIPTION
				"Description."
			::= { d4lownetWorkSecurity 7 }

		
--         1.3.6.1.4.1.37950.1.1.5.10.12.20.24.8
-- 1.3.6.1.4.1.37950.1.1.5.10.12.20.24.8
-- 1.3.6.1.4.1.37950.1.1.5.10.12.20.24.8
-- 1.3.6.1.4.1.37950.1.1.5.10.12.20.24.8
-- 1.3.6.1.4.1.37950.1.1.5.10.12.20.24.8
-- 1.3.6.1.4.1.37950.1.1.5.10.12.20.24.8
-- 1.3.6.1.4.1.37950.1.1.5.10.12.20.24.8
-- 1.3.6.1.4.1.37950.1.1.5.10.12.20.24.8
		-- 1.3.6.1.4.1.37950.1.1.5.10.12.20.24.8
		d4lowtcpHdrPartialCheck OBJECT-TYPE
			SYNTAX INTEGER
				{
				disable(0),
				enable(1)
				}
			MAX-ACCESS read-write
			STATUS current
			DESCRIPTION
				"Description."
			::= { d4lownetWorkSecurity 8 }

		
--         1.3.6.1.4.1.37950.1.1.5.10.12.20.24.9
-- 1.3.6.1.4.1.37950.1.1.5.10.12.20.24.9
-- 1.3.6.1.4.1.37950.1.1.5.10.12.20.24.9
-- 1.3.6.1.4.1.37950.1.1.5.10.12.20.24.9
-- 1.3.6.1.4.1.37950.1.1.5.10.12.20.24.9
-- 1.3.6.1.4.1.37950.1.1.5.10.12.20.24.9
-- 1.3.6.1.4.1.37950.1.1.5.10.12.20.24.9
-- 1.3.6.1.4.1.37950.1.1.5.10.12.20.24.9
		-- 1.3.6.1.4.1.37950.1.1.5.10.12.20.24.9
		d4lowtcpHdrOffsetEq1Check OBJECT-TYPE
			SYNTAX INTEGER
				{
				disable(0),
				enable(1)
				}
			MAX-ACCESS read-write
			STATUS current
			DESCRIPTION
				"Description."
			::= { d4lownetWorkSecurity 9 }

		
--         1.3.6.1.4.1.37950.1.1.5.10.12.20.24.10
-- 1.3.6.1.4.1.37950.1.1.5.10.12.20.24.10
-- 1.3.6.1.4.1.37950.1.1.5.10.12.20.24.10
-- 1.3.6.1.4.1.37950.1.1.5.10.12.20.24.10
-- 1.3.6.1.4.1.37950.1.1.5.10.12.20.24.10
-- 1.3.6.1.4.1.37950.1.1.5.10.12.20.24.10
-- 1.3.6.1.4.1.37950.1.1.5.10.12.20.24.10
-- 1.3.6.1.4.1.37950.1.1.5.10.12.20.24.10
		-- 1.3.6.1.4.1.37950.1.1.5.10.12.20.24.10
		d4lowiCMPFragPktCheck OBJECT-TYPE
			SYNTAX INTEGER
				{
				disable(0),
				enable(1)
				}
			MAX-ACCESS read-write
			STATUS current
			DESCRIPTION
				"Description."
			::= { d4lownetWorkSecurity 10 }

		
--         1.3.6.1.4.1.37950.1.1.5.10.12.20.24.11
-- 1.3.6.1.4.1.37950.1.1.5.10.12.20.24.11
-- 1.3.6.1.4.1.37950.1.1.5.10.12.20.24.11
-- 1.3.6.1.4.1.37950.1.1.5.10.12.20.24.11
-- 1.3.6.1.4.1.37950.1.1.5.10.12.20.24.11
-- 1.3.6.1.4.1.37950.1.1.5.10.12.20.24.11
-- 1.3.6.1.4.1.37950.1.1.5.10.12.20.24.11
-- 1.3.6.1.4.1.37950.1.1.5.10.12.20.24.11
		-- 1.3.6.1.4.1.37950.1.1.5.10.12.20.24.11
		d4lownetworkaction OBJECT-TYPE
			SYNTAX INTEGER { submit(1) }
			MAX-ACCESS read-write
			STATUS current
			DESCRIPTION
				"Description."
			::= { d4lownetWorkSecurity 11 }

		
--         1.3.6.1.4.1.37950.1.1.5.10.12.21
-- 1.3.6.1.4.1.37950.1.1.5.10.12.21
-- 1.3.6.1.4.1.37950.1.1.5.10.12.21
-- 1.3.6.1.4.1.37950.1.1.5.10.12.21
-- 1.3.6.1.4.1.37950.1.1.5.10.12.21
-- 1.3.6.1.4.1.37950.1.1.5.10.12.21
-- 1.3.6.1.4.1.37950.1.1.5.10.12.21
-- 1.3.6.1.4.1.37950.1.1.5.10.12.21
		-- 1.3.6.1.4.1.37950.1.1.5.10.12.21
		powerBattery OBJECT IDENTIFIER ::= { v1600dSysCfg 21 }

		
--         1.3.6.1.4.1.37950.1.1.5.10.12.21.1
-- 1.3.6.1.4.1.37950.1.1.5.10.12.21.1
-- 1.3.6.1.4.1.37950.1.1.5.10.12.21.1
-- 1.3.6.1.4.1.37950.1.1.5.10.12.21.1
-- 1.3.6.1.4.1.37950.1.1.5.10.12.21.1
-- 1.3.6.1.4.1.37950.1.1.5.10.12.21.1
-- 1.3.6.1.4.1.37950.1.1.5.10.12.21.1
-- 1.3.6.1.4.1.37950.1.1.5.10.12.21.1
		-- 1.3.6.1.4.1.37950.1.1.5.10.12.21.1
		batteryChargeMode OBJECT-TYPE
			SYNTAX INTEGER
				{
				close(0),
				open(1)
				}
			MAX-ACCESS read-write
			STATUS current
			DESCRIPTION
				"Description."
			::= { powerBattery 1 }

		
--         1.3.6.1.4.1.37950.1.1.5.10.12.21.2
-- 1.3.6.1.4.1.37950.1.1.5.10.12.21.2
-- 1.3.6.1.4.1.37950.1.1.5.10.12.21.2
-- 1.3.6.1.4.1.37950.1.1.5.10.12.21.2
-- 1.3.6.1.4.1.37950.1.1.5.10.12.21.2
-- 1.3.6.1.4.1.37950.1.1.5.10.12.21.2
-- 1.3.6.1.4.1.37950.1.1.5.10.12.21.2
-- 1.3.6.1.4.1.37950.1.1.5.10.12.21.2
		-- 1.3.6.1.4.1.37950.1.1.5.10.12.21.2
		batteryChargeStatus OBJECT-TYPE
			SYNTAX OCTET STRING
			MAX-ACCESS read-only
			STATUS current
			DESCRIPTION
				"Description."
			::= { powerBattery 2 }

		
--         1.3.6.1.4.1.37950.1.1.5.10.12.21.3
-- 1.3.6.1.4.1.37950.1.1.5.10.12.21.3
-- 1.3.6.1.4.1.37950.1.1.5.10.12.21.3
-- 1.3.6.1.4.1.37950.1.1.5.10.12.21.3
-- 1.3.6.1.4.1.37950.1.1.5.10.12.21.3
-- 1.3.6.1.4.1.37950.1.1.5.10.12.21.3
-- 1.3.6.1.4.1.37950.1.1.5.10.12.21.3
-- 1.3.6.1.4.1.37950.1.1.5.10.12.21.3
		-- 1.3.6.1.4.1.37950.1.1.5.10.12.21.3
		batteryRemainingPower OBJECT-TYPE
			SYNTAX OCTET STRING
			MAX-ACCESS read-only
			STATUS current
			DESCRIPTION
				"Description."
			::= { powerBattery 3 }

		
--         1.3.6.1.4.1.37950.1.1.5.10.12.21.4
-- 1.3.6.1.4.1.37950.1.1.5.10.12.21.4
-- 1.3.6.1.4.1.37950.1.1.5.10.12.21.4
-- 1.3.6.1.4.1.37950.1.1.5.10.12.21.4
-- 1.3.6.1.4.1.37950.1.1.5.10.12.21.4
-- 1.3.6.1.4.1.37950.1.1.5.10.12.21.4
-- 1.3.6.1.4.1.37950.1.1.5.10.12.21.4
-- 1.3.6.1.4.1.37950.1.1.5.10.12.21.4
		-- 1.3.6.1.4.1.37950.1.1.5.10.12.21.4
		powerModuleStateTable OBJECT-TYPE
			SYNTAX SEQUENCE OF PowerModuleStateEntry
			MAX-ACCESS not-accessible
			STATUS current
			DESCRIPTION
				"Description."
			::= { powerBattery 4 }

		
--         1.3.6.1.4.1.37950.1.1.5.10.12.21.4.1
-- 1.3.6.1.4.1.37950.1.1.5.10.12.21.4.1
-- 1.3.6.1.4.1.37950.1.1.5.10.12.21.4.1
-- 1.3.6.1.4.1.37950.1.1.5.10.12.21.4.1
-- 1.3.6.1.4.1.37950.1.1.5.10.12.21.4.1
-- 1.3.6.1.4.1.37950.1.1.5.10.12.21.4.1
-- 1.3.6.1.4.1.37950.1.1.5.10.12.21.4.1
-- 1.3.6.1.4.1.37950.1.1.5.10.12.21.4.1
		-- 1.3.6.1.4.1.37950.1.1.5.10.12.21.4.1
		powerModuleStateEntry OBJECT-TYPE
			SYNTAX PowerModuleStateEntry
			MAX-ACCESS not-accessible
			STATUS current
			DESCRIPTION
				"Description."
			INDEX { powerID }
			::= { powerModuleStateTable 1 }

		
		PowerModuleStateEntry ::=
			SEQUENCE { 
				powerID
					Integer32,
				powerState
					OCTET STRING
			 }

--         1.3.6.1.4.1.37950.1.1.5.10.12.21.4.1.1
-- 1.3.6.1.4.1.37950.1.1.5.10.12.21.4.1.1
-- 1.3.6.1.4.1.37950.1.1.5.10.12.21.4.1.1
-- 1.3.6.1.4.1.37950.1.1.5.10.12.21.4.1.1
-- 1.3.6.1.4.1.37950.1.1.5.10.12.21.4.1.1
-- 1.3.6.1.4.1.37950.1.1.5.10.12.21.4.1.1
-- 1.3.6.1.4.1.37950.1.1.5.10.12.21.4.1.1
-- 1.3.6.1.4.1.37950.1.1.5.10.12.21.4.1.1
		-- 1.3.6.1.4.1.37950.1.1.5.10.12.21.4.1.1
		powerID OBJECT-TYPE
			SYNTAX Integer32
			MAX-ACCESS read-only
			STATUS current
			DESCRIPTION
				"Description."
			::= { powerModuleStateEntry 1 }

		
--         1.3.6.1.4.1.37950.1.1.5.10.12.21.4.1.2
-- 1.3.6.1.4.1.37950.1.1.5.10.12.21.4.1.2
-- 1.3.6.1.4.1.37950.1.1.5.10.12.21.4.1.2
-- 1.3.6.1.4.1.37950.1.1.5.10.12.21.4.1.2
-- 1.3.6.1.4.1.37950.1.1.5.10.12.21.4.1.2
-- 1.3.6.1.4.1.37950.1.1.5.10.12.21.4.1.2
-- 1.3.6.1.4.1.37950.1.1.5.10.12.21.4.1.2
-- 1.3.6.1.4.1.37950.1.1.5.10.12.21.4.1.2
		-- 1.3.6.1.4.1.37950.1.1.5.10.12.21.4.1.2
		powerState OBJECT-TYPE
			SYNTAX OCTET STRING
			MAX-ACCESS read-only
			STATUS current
			DESCRIPTION
				"Description."
			::= { powerModuleStateEntry 2 }

		
--       1.3.6.1.4.1.37950.1.1.5.10.12.22
-- 1.3.6.1.4.1.37950.1.1.5.10.12.22
-- 1.3.6.1.4.1.37950.1.1.5.10.12.22
-- 1.3.6.1.4.1.37950.1.1.5.10.12.22
-- 1.3.6.1.4.1.37950.1.1.5.10.12.22
-- 1.3.6.1.4.1.37950.1.1.5.10.12.22
		-- 1.3.6.1.4.1.37950.1.1.5.10.12.22
		servicePort OBJECT IDENTIFIER ::= { v1600dSysCfg 22 }

		
--       1.3.6.1.4.1.37950.1.1.5.10.12.22.1
-- 1.3.6.1.4.1.37950.1.1.5.10.12.22.1
-- 1.3.6.1.4.1.37950.1.1.5.10.12.22.1
-- 1.3.6.1.4.1.37950.1.1.5.10.12.22.1
-- 1.3.6.1.4.1.37950.1.1.5.10.12.22.1
-- 1.3.6.1.4.1.37950.1.1.5.10.12.22.1
		-- 1.3.6.1.4.1.37950.1.1.5.10.12.22.1
		spWebPort OBJECT-TYPE
			SYNTAX Integer32 (1..65535)
			MAX-ACCESS read-write
			STATUS current
			DESCRIPTION
				"Description."
			::= { servicePort 1 }

		
--       1.3.6.1.4.1.37950.1.1.5.10.12.22.2
-- 1.3.6.1.4.1.37950.1.1.5.10.12.22.2
-- 1.3.6.1.4.1.37950.1.1.5.10.12.22.2
-- 1.3.6.1.4.1.37950.1.1.5.10.12.22.2
-- 1.3.6.1.4.1.37950.1.1.5.10.12.22.2
-- 1.3.6.1.4.1.37950.1.1.5.10.12.22.2
		-- 1.3.6.1.4.1.37950.1.1.5.10.12.22.2
		spTelnetPort OBJECT-TYPE
			SYNTAX Integer32 (1..65535)
			MAX-ACCESS read-write
			STATUS current
			DESCRIPTION
				"Description."
			::= { servicePort 2 }

		
--       1.3.6.1.4.1.37950.1.1.5.10.12.22.3
-- 1.3.6.1.4.1.37950.1.1.5.10.12.22.3
-- 1.3.6.1.4.1.37950.1.1.5.10.12.22.3
-- 1.3.6.1.4.1.37950.1.1.5.10.12.22.3
-- 1.3.6.1.4.1.37950.1.1.5.10.12.22.3
-- 1.3.6.1.4.1.37950.1.1.5.10.12.22.3
		-- 1.3.6.1.4.1.37950.1.1.5.10.12.22.3
		spSSHPort OBJECT-TYPE
			SYNTAX Integer32 (1..65535)
			MAX-ACCESS read-write
			STATUS current
			DESCRIPTION
				"Description."
			::= { servicePort 3 }

		
--       1.3.6.1.4.1.37950.1.1.5.10.12.22.4
-- 1.3.6.1.4.1.37950.1.1.5.10.12.22.4
-- 1.3.6.1.4.1.37950.1.1.5.10.12.22.4
-- 1.3.6.1.4.1.37950.1.1.5.10.12.22.4
-- 1.3.6.1.4.1.37950.1.1.5.10.12.22.4
-- 1.3.6.1.4.1.37950.1.1.5.10.12.22.4
		-- 1.3.6.1.4.1.37950.1.1.5.10.12.22.4
		spSNMPPort OBJECT-TYPE
			SYNTAX Integer32 (1..65535)
			MAX-ACCESS read-write
			STATUS current
			DESCRIPTION
				"Description."
			::= { servicePort 4 }

		
--       1.3.6.1.4.1.37950.1.1.5.10.12.22.5
-- 1.3.6.1.4.1.37950.1.1.5.10.12.22.5
-- 1.3.6.1.4.1.37950.1.1.5.10.12.22.5
-- 1.3.6.1.4.1.37950.1.1.5.10.12.22.5
-- 1.3.6.1.4.1.37950.1.1.5.10.12.22.5
-- 1.3.6.1.4.1.37950.1.1.5.10.12.22.5
		-- 1.3.6.1.4.1.37950.1.1.5.10.12.22.5
		spAction OBJECT-TYPE
			SYNTAX INTEGER { submit(1) }
			MAX-ACCESS read-write
			STATUS current
			DESCRIPTION
				"Description."
			::= { servicePort 5 }

		
--       1.3.6.1.4.1.37950.1.1.5.10.12.23
-- 1.3.6.1.4.1.37950.1.1.5.10.12.23
-- 1.3.6.1.4.1.37950.1.1.5.10.12.23
-- 1.3.6.1.4.1.37950.1.1.5.10.12.23
-- 1.3.6.1.4.1.37950.1.1.5.10.12.23
-- 1.3.6.1.4.1.37950.1.1.5.10.12.23
		-- 1.3.6.1.4.1.37950.1.1.5.10.12.23
		loginConfiguration OBJECT IDENTIFIER ::= { v1600dSysCfg 23 }

		
--       1.3.6.1.4.1.37950.1.1.5.10.12.23.1
-- 1.3.6.1.4.1.37950.1.1.5.10.12.23.1
-- 1.3.6.1.4.1.37950.1.1.5.10.12.23.1
-- 1.3.6.1.4.1.37950.1.1.5.10.12.23.1
-- 1.3.6.1.4.1.37950.1.1.5.10.12.23.1
-- 1.3.6.1.4.1.37950.1.1.5.10.12.23.1
		-- 1.3.6.1.4.1.37950.1.1.5.10.12.23.1
		loginCfgLoginTimeout OBJECT-TYPE
			SYNTAX Integer32 (1..180)
			MAX-ACCESS read-write
			STATUS current
			DESCRIPTION
				"Description."
			::= { loginConfiguration 1 }

		
--       1.3.6.1.4.1.37950.1.1.5.10.12.23.2
-- 1.3.6.1.4.1.37950.1.1.5.10.12.23.2
-- 1.3.6.1.4.1.37950.1.1.5.10.12.23.2
-- 1.3.6.1.4.1.37950.1.1.5.10.12.23.2
-- 1.3.6.1.4.1.37950.1.1.5.10.12.23.2
-- 1.3.6.1.4.1.37950.1.1.5.10.12.23.2
		-- 1.3.6.1.4.1.37950.1.1.5.10.12.23.2
		loginCfgVerificationCode OBJECT-TYPE
			SYNTAX INTEGER
				{
				disable(0),
				enable(1)
				}
			MAX-ACCESS read-write
			STATUS current
			DESCRIPTION
				"Description."
			::= { loginConfiguration 2 }

		
--       1.3.6.1.4.1.37950.1.1.5.10.12.23.3
-- 1.3.6.1.4.1.37950.1.1.5.10.12.23.3
-- 1.3.6.1.4.1.37950.1.1.5.10.12.23.3
-- 1.3.6.1.4.1.37950.1.1.5.10.12.23.3
-- 1.3.6.1.4.1.37950.1.1.5.10.12.23.3
-- 1.3.6.1.4.1.37950.1.1.5.10.12.23.3
		-- 1.3.6.1.4.1.37950.1.1.5.10.12.23.3
		loginCfgSessionKey OBJECT-TYPE
			SYNTAX INTEGER
				{
				disable(0),
				enable(1)
				}
			MAX-ACCESS read-write
			STATUS current
			DESCRIPTION
				"Description."
			::= { loginConfiguration 3 }

		
--     1.3.6.1.4.1.37950.1.1.5.10.12.23
-- 1.3.6.1.4.1.37950.1.1.5.10.12.24
-- 1.3.6.1.4.1.37950.1.1.5.10.12.24
-- 1.3.6.1.4.1.37950.1.1.5.10.12.24
		-- 1.3.6.1.4.1.37950.1.1.5.10.12.24
		scheduleRebootConfiguration OBJECT IDENTIFIER ::= { v1600dSysCfg 24 }

		
--     1.3.6.1.4.1.37950.1.1.5.10.12.23.1
-- 1.3.6.1.4.1.37950.1.1.5.10.12.24.1
-- 1.3.6.1.4.1.37950.1.1.5.10.12.24.1
-- 1.3.6.1.4.1.37950.1.1.5.10.12.24.1
		-- 1.3.6.1.4.1.37950.1.1.5.10.12.24.1
		scheduleRebootConfigurationType OBJECT-TYPE
			SYNTAX INTEGER
				{
				timeout(0),
				fix-time(1),
				week-day(2)
				}
			MAX-ACCESS read-write
			STATUS current
			DESCRIPTION
				"Description."
			::= { scheduleRebootConfiguration 1 }

		
--     1.3.6.1.4.1.37950.1.1.5.10.12.23.2
-- 1.3.6.1.4.1.37950.1.1.5.10.12.24.2
-- 1.3.6.1.4.1.37950.1.1.5.10.12.24.2
-- 1.3.6.1.4.1.37950.1.1.5.10.12.24.2
		-- 1.3.6.1.4.1.37950.1.1.5.10.12.24.2
		scheduleRebootConfigurationTimeoutValue OBJECT-TYPE
			SYNTAX Unsigned32 (60..2678400)
			MAX-ACCESS read-write
			STATUS current
			DESCRIPTION
				"Description."
			::= { scheduleRebootConfiguration 2 }

		
--     1.3.6.1.4.1.37950.1.1.5.10.12.23.3
-- 1.3.6.1.4.1.37950.1.1.5.10.12.24.3
-- 1.3.6.1.4.1.37950.1.1.5.10.12.24.3
-- 1.3.6.1.4.1.37950.1.1.5.10.12.24.3
		-- 1.3.6.1.4.1.37950.1.1.5.10.12.24.3
		scheduleRebootConfigurationFixTimeDay OBJECT-TYPE
			SYNTAX Integer32 (1..31)
			MAX-ACCESS read-write
			STATUS current
			DESCRIPTION
				"Description."
			::= { scheduleRebootConfiguration 3 }

		
--     1.3.6.1.4.1.37950.1.1.5.10.12.23.4
-- 1.3.6.1.4.1.37950.1.1.5.10.12.24.4
-- 1.3.6.1.4.1.37950.1.1.5.10.12.24.4
-- 1.3.6.1.4.1.37950.1.1.5.10.12.24.4
		-- 1.3.6.1.4.1.37950.1.1.5.10.12.24.4
		scheduleRebootConfigurationFixTimeHour OBJECT-TYPE
			SYNTAX Integer32 (0..23)
			MAX-ACCESS read-write
			STATUS current
			DESCRIPTION
				"Description."
			::= { scheduleRebootConfiguration 4 }

		
--     1.3.6.1.4.1.37950.1.1.5.10.12.23.5
-- 1.3.6.1.4.1.37950.1.1.5.10.12.24.5
-- 1.3.6.1.4.1.37950.1.1.5.10.12.24.5
-- 1.3.6.1.4.1.37950.1.1.5.10.12.24.5
		-- 1.3.6.1.4.1.37950.1.1.5.10.12.24.5
		scheduleRebootConfigurationFixTimeMinute OBJECT-TYPE
			SYNTAX Integer32 (0..59)
			MAX-ACCESS read-write
			STATUS current
			DESCRIPTION
				"Description."
			::= { scheduleRebootConfiguration 5 }

		
--     1.3.6.1.4.1.37950.1.1.5.10.12.23.6
-- 1.3.6.1.4.1.37950.1.1.5.10.12.24.6
-- 1.3.6.1.4.1.37950.1.1.5.10.12.24.6
-- 1.3.6.1.4.1.37950.1.1.5.10.12.24.6
		-- 1.3.6.1.4.1.37950.1.1.5.10.12.24.6
		scheduleRebootConfigurationWeekMon OBJECT-TYPE
			SYNTAX INTEGER
				{
				disable(0),
				enable(1)
				}
			MAX-ACCESS read-write
			STATUS current
			DESCRIPTION
				"Description."
			::= { scheduleRebootConfiguration 6 }

		
--     1.3.6.1.4.1.37950.1.1.5.10.12.23.7
-- 1.3.6.1.4.1.37950.1.1.5.10.12.24.7
-- 1.3.6.1.4.1.37950.1.1.5.10.12.24.7
-- 1.3.6.1.4.1.37950.1.1.5.10.12.24.7
		-- 1.3.6.1.4.1.37950.1.1.5.10.12.24.7
		scheduleRebootConfigurationWeekTues OBJECT-TYPE
			SYNTAX INTEGER
				{
				disable(0),
				enable(1)
				}
			MAX-ACCESS read-write
			STATUS current
			DESCRIPTION
				"Description."
			::= { scheduleRebootConfiguration 7 }

		
--     1.3.6.1.4.1.37950.1.1.5.10.12.23.8
-- 1.3.6.1.4.1.37950.1.1.5.10.12.24.8
-- 1.3.6.1.4.1.37950.1.1.5.10.12.24.8
-- 1.3.6.1.4.1.37950.1.1.5.10.12.24.8
		-- 1.3.6.1.4.1.37950.1.1.5.10.12.24.8
		scheduleRebootConfigurationWeekWed OBJECT-TYPE
			SYNTAX INTEGER
				{
				disable(0),
				enable(1)
				}
			MAX-ACCESS read-write
			STATUS current
			DESCRIPTION
				"Description."
			::= { scheduleRebootConfiguration 8 }

		
--     1.3.6.1.4.1.37950.1.1.5.10.12.23.9
-- 1.3.6.1.4.1.37950.1.1.5.10.12.24.9
-- 1.3.6.1.4.1.37950.1.1.5.10.12.24.9
-- 1.3.6.1.4.1.37950.1.1.5.10.12.24.9
		-- 1.3.6.1.4.1.37950.1.1.5.10.12.24.9
		scheduleRebootConfigurationWeekThur OBJECT-TYPE
			SYNTAX INTEGER
				{
				disable(0),
				enable(1)
				}
			MAX-ACCESS read-write
			STATUS current
			DESCRIPTION
				"Description."
			::= { scheduleRebootConfiguration 9 }

		
--     1.3.6.1.4.1.37950.1.1.5.10.12.23.10
-- 1.3.6.1.4.1.37950.1.1.5.10.12.24.10
-- 1.3.6.1.4.1.37950.1.1.5.10.12.24.10
-- 1.3.6.1.4.1.37950.1.1.5.10.12.24.10
		-- 1.3.6.1.4.1.37950.1.1.5.10.12.24.10
		scheduleRebootConfigurationWeekFri OBJECT-TYPE
			SYNTAX INTEGER
				{
				disable(0),
				enable(1)
				}
			MAX-ACCESS read-write
			STATUS current
			DESCRIPTION
				"Description."
			::= { scheduleRebootConfiguration 10 }

		
--     1.3.6.1.4.1.37950.1.1.5.10.12.23.11
-- 1.3.6.1.4.1.37950.1.1.5.10.12.24.11
-- 1.3.6.1.4.1.37950.1.1.5.10.12.24.11
-- 1.3.6.1.4.1.37950.1.1.5.10.12.24.11
		-- 1.3.6.1.4.1.37950.1.1.5.10.12.24.11
		scheduleRebootConfigurationWeekSat OBJECT-TYPE
			SYNTAX INTEGER
				{
				disable(0),
				enable(1)
				}
			MAX-ACCESS read-write
			STATUS current
			DESCRIPTION
				"Description."
			::= { scheduleRebootConfiguration 11 }

		
--     1.3.6.1.4.1.37950.1.1.5.10.12.23.12
-- 1.3.6.1.4.1.37950.1.1.5.10.12.24.12
-- 1.3.6.1.4.1.37950.1.1.5.10.12.24.12
-- 1.3.6.1.4.1.37950.1.1.5.10.12.24.12
		-- 1.3.6.1.4.1.37950.1.1.5.10.12.24.12
		scheduleRebootConfigurationWeekSun OBJECT-TYPE
			SYNTAX INTEGER
				{
				disable(0),
				enable(1)
				}
			MAX-ACCESS read-write
			STATUS current
			DESCRIPTION
				"Description."
			::= { scheduleRebootConfiguration 12 }

		
--     1.3.6.1.4.1.37950.1.1.5.10.12.23.13
-- 1.3.6.1.4.1.37950.1.1.5.10.12.24.13
-- 1.3.6.1.4.1.37950.1.1.5.10.12.24.13
-- 1.3.6.1.4.1.37950.1.1.5.10.12.24.13
		-- 1.3.6.1.4.1.37950.1.1.5.10.12.24.13
		scheduleRebootConfigurationWeekHour OBJECT-TYPE
			SYNTAX Integer32 (0..23)
			MAX-ACCESS read-write
			STATUS current
			DESCRIPTION
				"Description."
			::= { scheduleRebootConfiguration 13 }

		
--     1.3.6.1.4.1.37950.1.1.5.10.12.23.14
-- 1.3.6.1.4.1.37950.1.1.5.10.12.24.14
-- 1.3.6.1.4.1.37950.1.1.5.10.12.24.14
-- 1.3.6.1.4.1.37950.1.1.5.10.12.24.14
		-- 1.3.6.1.4.1.37950.1.1.5.10.12.24.14
		scheduleRebootConfigurationWeekMinute OBJECT-TYPE
			SYNTAX Integer32 (0..59)
			MAX-ACCESS read-write
			STATUS current
			DESCRIPTION
				"Description."
			::= { scheduleRebootConfiguration 14 }

		
--     1.3.6.1.4.1.37950.1.1.5.10.12.23.15
-- 1.3.6.1.4.1.37950.1.1.5.10.12.24.15
-- 1.3.6.1.4.1.37950.1.1.5.10.12.24.15
-- 1.3.6.1.4.1.37950.1.1.5.10.12.24.15
		-- 1.3.6.1.4.1.37950.1.1.5.10.12.24.15
		scheduleRebootConfigurationAction OBJECT-TYPE
			SYNTAX INTEGER
				{
				disable(0),
				enable(1)
				}
			MAX-ACCESS read-write
			STATUS current
			DESCRIPTION
				"Description."
			::= { scheduleRebootConfiguration 15 }

		
--     1.3.6.1.4.1.37950.1.1.5.10.12.24
-- 1.3.6.1.4.1.37950.1.1.5.10.12.25
-- 1.3.6.1.4.1.37950.1.1.5.10.12.25
-- 1.3.6.1.4.1.37950.1.1.5.10.12.25
		-- 1.3.6.1.4.1.37950.1.1.5.10.12.25
		scheduleRebootConfigurationTable OBJECT-TYPE
			SYNTAX SEQUENCE OF ScheduleRebootConfigurationEntry
			MAX-ACCESS not-accessible
			STATUS current
			DESCRIPTION
				"Description."
			::= { v1600dSysCfg 25 }

		
--     1.3.6.1.4.1.37950.1.1.5.10.12.24.1
-- 1.3.6.1.4.1.37950.1.1.5.10.12.25.1
-- 1.3.6.1.4.1.37950.1.1.5.10.12.25.1
-- 1.3.6.1.4.1.37950.1.1.5.10.12.25.1
		-- 1.3.6.1.4.1.37950.1.1.5.10.12.25.1
		scheduleRebootConfigurationEntry OBJECT-TYPE
			SYNTAX ScheduleRebootConfigurationEntry
			MAX-ACCESS not-accessible
			STATUS current
			DESCRIPTION
				"Description."
			INDEX { scheduleRebootTableEnable }
			::= { scheduleRebootConfigurationTable 1 }

		
		ScheduleRebootConfigurationEntry ::=
			SEQUENCE { 
				scheduleRebootTableEnable
					INTEGER,
				scheduleRebootTableTypeS
					INTEGER,
				scheduleRebootTableTimeoutValueS
					Unsigned32,
				scheduleRebootTableFixTimeDayS
					Integer32,
				scheduleRebootTableFixTimeHourS
					Integer32,
				scheduleRebootTableFixTimeMinuteS
					Integer32,
				scheduleRebootTableWeekMonS
					INTEGER,
				scheduleRebootTableWeekTuesS
					INTEGER,
				scheduleRebootTableWeekWedS
					INTEGER,
				scheduleRebootTableWeekThurS
					INTEGER,
				scheduleRebootTableWeekFriS
					INTEGER,
				scheduleRebootTableWeekSatS
					INTEGER,
				scheduleRebootTableWeekSunS
					INTEGER,
				scheduleRebootTableWeekHourS
					Integer32,
				scheduleRebootTableWeekMinuteS
					Integer32
			 }

--     1.3.6.1.4.1.37950.1.1.5.10.12.24.1.1
-- 1.3.6.1.4.1.37950.1.1.5.10.12.25.1.1
-- 1.3.6.1.4.1.37950.1.1.5.10.12.25.1.1
-- 1.3.6.1.4.1.37950.1.1.5.10.12.25.1.1
		-- 1.3.6.1.4.1.37950.1.1.5.10.12.25.1.1
		scheduleRebootTableEnable OBJECT-TYPE
			SYNTAX INTEGER
				{
				disable(0),
				enable(1)
				}
			MAX-ACCESS read-write
			STATUS current
			DESCRIPTION
				"Description."
			::= { scheduleRebootConfigurationEntry 1 }

		
--     1.3.6.1.4.1.37950.1.1.5.10.12.24.1.2
-- 1.3.6.1.4.1.37950.1.1.5.10.12.25.1.2
-- 1.3.6.1.4.1.37950.1.1.5.10.12.25.1.2
-- 1.3.6.1.4.1.37950.1.1.5.10.12.25.1.2
		-- 1.3.6.1.4.1.37950.1.1.5.10.12.25.1.2
		scheduleRebootTableTypeS OBJECT-TYPE
			SYNTAX INTEGER
				{
				timeout(0),
				fix-time(1),
				week-day(2)
				}
			MAX-ACCESS read-write
			STATUS current
			DESCRIPTION
				"Description."
			::= { scheduleRebootConfigurationEntry 2 }

		
--     1.3.6.1.4.1.37950.1.1.5.10.12.24.1.3
-- 1.3.6.1.4.1.37950.1.1.5.10.12.25.1.3
-- 1.3.6.1.4.1.37950.1.1.5.10.12.25.1.3
-- 1.3.6.1.4.1.37950.1.1.5.10.12.25.1.3
		-- 1.3.6.1.4.1.37950.1.1.5.10.12.25.1.3
		scheduleRebootTableTimeoutValueS OBJECT-TYPE
			SYNTAX Unsigned32 (60..2678400)
			MAX-ACCESS read-write
			STATUS current
			DESCRIPTION
				"Description."
			::= { scheduleRebootConfigurationEntry 3 }

		
--     1.3.6.1.4.1.37950.1.1.5.10.12.24.1.4
-- 1.3.6.1.4.1.37950.1.1.5.10.12.25.1.4
-- 1.3.6.1.4.1.37950.1.1.5.10.12.25.1.4
-- 1.3.6.1.4.1.37950.1.1.5.10.12.25.1.4
		-- 1.3.6.1.4.1.37950.1.1.5.10.12.25.1.4
		scheduleRebootTableFixTimeDayS OBJECT-TYPE
			SYNTAX Integer32 (1..31)
			MAX-ACCESS read-write
			STATUS current
			DESCRIPTION
				"Description."
			::= { scheduleRebootConfigurationEntry 4 }

		
--     1.3.6.1.4.1.37950.1.1.5.10.12.24.1.5
-- 1.3.6.1.4.1.37950.1.1.5.10.12.25.1.5
-- 1.3.6.1.4.1.37950.1.1.5.10.12.25.1.5
-- 1.3.6.1.4.1.37950.1.1.5.10.12.25.1.5
		-- 1.3.6.1.4.1.37950.1.1.5.10.12.25.1.5
		scheduleRebootTableFixTimeHourS OBJECT-TYPE
			SYNTAX Integer32 (0..23)
			MAX-ACCESS read-write
			STATUS current
			DESCRIPTION
				"Description."
			::= { scheduleRebootConfigurationEntry 5 }

		
--     1.3.6.1.4.1.37950.1.1.5.10.12.24.1.6
-- 1.3.6.1.4.1.37950.1.1.5.10.12.25.1.6
-- 1.3.6.1.4.1.37950.1.1.5.10.12.25.1.6
-- 1.3.6.1.4.1.37950.1.1.5.10.12.25.1.6
		-- 1.3.6.1.4.1.37950.1.1.5.10.12.25.1.6
		scheduleRebootTableFixTimeMinuteS OBJECT-TYPE
			SYNTAX Integer32 (0..59)
			MAX-ACCESS read-write
			STATUS current
			DESCRIPTION
				"Description."
			::= { scheduleRebootConfigurationEntry 6 }

		
--     1.3.6.1.4.1.37950.1.1.5.10.12.24.1.7
-- 1.3.6.1.4.1.37950.1.1.5.10.12.25.1.7
-- 1.3.6.1.4.1.37950.1.1.5.10.12.25.1.7
-- 1.3.6.1.4.1.37950.1.1.5.10.12.25.1.7
		-- 1.3.6.1.4.1.37950.1.1.5.10.12.25.1.7
		scheduleRebootTableWeekMonS OBJECT-TYPE
			SYNTAX INTEGER
				{
				disable(0),
				enable(1)
				}
			MAX-ACCESS read-write
			STATUS current
			DESCRIPTION
				"Description."
			::= { scheduleRebootConfigurationEntry 7 }

		
--     1.3.6.1.4.1.37950.1.1.5.10.12.24.1.8
-- 1.3.6.1.4.1.37950.1.1.5.10.12.25.1.8
-- 1.3.6.1.4.1.37950.1.1.5.10.12.25.1.8
-- 1.3.6.1.4.1.37950.1.1.5.10.12.25.1.8
		-- 1.3.6.1.4.1.37950.1.1.5.10.12.25.1.8
		scheduleRebootTableWeekTuesS OBJECT-TYPE
			SYNTAX INTEGER
				{
				disable(0),
				enable(1)
				}
			MAX-ACCESS read-write
			STATUS current
			DESCRIPTION
				"Description."
			::= { scheduleRebootConfigurationEntry 8 }

		
--     1.3.6.1.4.1.37950.1.1.5.10.12.24.1.9
-- 1.3.6.1.4.1.37950.1.1.5.10.12.25.1.9
-- 1.3.6.1.4.1.37950.1.1.5.10.12.25.1.9
-- 1.3.6.1.4.1.37950.1.1.5.10.12.25.1.9
		-- 1.3.6.1.4.1.37950.1.1.5.10.12.25.1.9
		scheduleRebootTableWeekWedS OBJECT-TYPE
			SYNTAX INTEGER
				{
				disable(0),
				enable(1)
				}
			MAX-ACCESS read-write
			STATUS current
			DESCRIPTION
				"Description."
			::= { scheduleRebootConfigurationEntry 9 }

		
--     1.3.6.1.4.1.37950.1.1.5.10.12.24.1.10
-- 1.3.6.1.4.1.37950.1.1.5.10.12.25.1.10
-- 1.3.6.1.4.1.37950.1.1.5.10.12.25.1.10
-- 1.3.6.1.4.1.37950.1.1.5.10.12.25.1.10
		-- 1.3.6.1.4.1.37950.1.1.5.10.12.25.1.10
		scheduleRebootTableWeekThurS OBJECT-TYPE
			SYNTAX INTEGER
				{
				disable(0),
				enable(1)
				}
			MAX-ACCESS read-write
			STATUS current
			DESCRIPTION
				"Description."
			::= { scheduleRebootConfigurationEntry 10 }

		
--     1.3.6.1.4.1.37950.1.1.5.10.12.24.1.11
-- 1.3.6.1.4.1.37950.1.1.5.10.12.25.1.11
-- 1.3.6.1.4.1.37950.1.1.5.10.12.25.1.11
-- 1.3.6.1.4.1.37950.1.1.5.10.12.25.1.11
		-- 1.3.6.1.4.1.37950.1.1.5.10.12.25.1.11
		scheduleRebootTableWeekFriS OBJECT-TYPE
			SYNTAX INTEGER
				{
				disable(0),
				enable(1)
				}
			MAX-ACCESS read-write
			STATUS current
			DESCRIPTION
				"Description."
			::= { scheduleRebootConfigurationEntry 11 }

		
--     1.3.6.1.4.1.37950.1.1.5.10.12.24.1.12
-- 1.3.6.1.4.1.37950.1.1.5.10.12.25.1.12
-- 1.3.6.1.4.1.37950.1.1.5.10.12.25.1.12
-- 1.3.6.1.4.1.37950.1.1.5.10.12.25.1.12
		-- 1.3.6.1.4.1.37950.1.1.5.10.12.25.1.12
		scheduleRebootTableWeekSatS OBJECT-TYPE
			SYNTAX INTEGER
				{
				disable(0),
				enable(1)
				}
			MAX-ACCESS read-write
			STATUS current
			DESCRIPTION
				"Description."
			::= { scheduleRebootConfigurationEntry 12 }

		
--     1.3.6.1.4.1.37950.1.1.5.10.12.24.1.13
-- 1.3.6.1.4.1.37950.1.1.5.10.12.25.1.13
-- 1.3.6.1.4.1.37950.1.1.5.10.12.25.1.13
-- 1.3.6.1.4.1.37950.1.1.5.10.12.25.1.13
		-- 1.3.6.1.4.1.37950.1.1.5.10.12.25.1.13
		scheduleRebootTableWeekSunS OBJECT-TYPE
			SYNTAX INTEGER
				{
				disable(0),
				enable(1)
				}
			MAX-ACCESS read-write
			STATUS current
			DESCRIPTION
				"Description."
			::= { scheduleRebootConfigurationEntry 13 }

		
--     1.3.6.1.4.1.37950.1.1.5.10.12.24.1.14
-- 1.3.6.1.4.1.37950.1.1.5.10.12.25.1.14
-- 1.3.6.1.4.1.37950.1.1.5.10.12.25.1.14
-- 1.3.6.1.4.1.37950.1.1.5.10.12.25.1.14
		-- 1.3.6.1.4.1.37950.1.1.5.10.12.25.1.14
		scheduleRebootTableWeekHourS OBJECT-TYPE
			SYNTAX Integer32 (0..23)
			MAX-ACCESS read-write
			STATUS current
			DESCRIPTION
				"Description."
			::= { scheduleRebootConfigurationEntry 14 }

		
--     1.3.6.1.4.1.37950.1.1.5.10.12.24.1.15
-- 1.3.6.1.4.1.37950.1.1.5.10.12.25.1.15
-- 1.3.6.1.4.1.37950.1.1.5.10.12.25.1.15
-- 1.3.6.1.4.1.37950.1.1.5.10.12.25.1.15
		-- 1.3.6.1.4.1.37950.1.1.5.10.12.25.1.15
		scheduleRebootTableWeekMinuteS OBJECT-TYPE
			SYNTAX Integer32 (0..59)
			MAX-ACCESS read-write
			STATUS current
			DESCRIPTION
				"Description."
			::= { scheduleRebootConfigurationEntry 15 }

		
--          1.3.6.1.4.1.37950.1.1.5.10.13
-- 1.3.6.1.4.1.37950.1.1.5.10.13
-- 1.3.6.1.4.1.37950.1.1.5.10.13
-- 1.3.6.1.4.1.37950.1.1.5.10.13
-- 1.3.6.1.4.1.37950.1.1.5.10.13
-- 1.3.6.1.4.1.37950.1.1.5.10.13
-- 1.3.6.1.4.1.37950.1.1.5.10.13
-- 1.3.6.1.4.1.37950.1.1.5.10.13
-- 1.3.6.1.4.1.37950.1.1.5.10.13
		-- 1.3.6.1.4.1.37950.1.1.5.10.13
		v1600dAlarm OBJECT IDENTIFIER ::= { v1600dSwitch 13 }

		
--          1.3.6.1.4.1.37950.1.1.5.10.13.1
-- 1.3.6.1.4.1.37950.1.1.5.10.13.1
-- 1.3.6.1.4.1.37950.1.1.5.10.13.1
-- 1.3.6.1.4.1.37950.1.1.5.10.13.1
-- 1.3.6.1.4.1.37950.1.1.5.10.13.1
-- 1.3.6.1.4.1.37950.1.1.5.10.13.1
-- 1.3.6.1.4.1.37950.1.1.5.10.13.1
-- 1.3.6.1.4.1.37950.1.1.5.10.13.1
-- 1.3.6.1.4.1.37950.1.1.5.10.13.1
		-- 1.3.6.1.4.1.37950.1.1.5.10.13.1
		ponTransceiverTable OBJECT-TYPE
			SYNTAX SEQUENCE OF PonTransceiverEntry
			MAX-ACCESS not-accessible
			STATUS current
			DESCRIPTION
				"Description."
			::= { v1600dAlarm 1 }

		
--          1.3.6.1.4.1.37950.1.1.5.10.13.1.1
-- 1.3.6.1.4.1.37950.1.1.5.10.13.1.1
-- 1.3.6.1.4.1.37950.1.1.5.10.13.1.1
-- 1.3.6.1.4.1.37950.1.1.5.10.13.1.1
-- 1.3.6.1.4.1.37950.1.1.5.10.13.1.1
-- 1.3.6.1.4.1.37950.1.1.5.10.13.1.1
-- 1.3.6.1.4.1.37950.1.1.5.10.13.1.1
-- 1.3.6.1.4.1.37950.1.1.5.10.13.1.1
-- 1.3.6.1.4.1.37950.1.1.5.10.13.1.1
		-- 1.3.6.1.4.1.37950.1.1.5.10.13.1.1
		ponTransceiverEntry OBJECT-TYPE
			SYNTAX PonTransceiverEntry
			MAX-ACCESS not-accessible
			STATUS current
			DESCRIPTION
				"Description."
			INDEX { transceiverPonIndex }
			::= { ponTransceiverTable 1 }

		
		PonTransceiverEntry ::=
			SEQUENCE { 
				transceiverPonIndex
					INTEGER,
				tempperature
					OCTET STRING,
				voltage
					OCTET STRING,
				biasCurrent
					OCTET STRING,
				transmitPower
					OCTET STRING
			 }

--          1.3.6.1.4.1.37950.1.1.5.10.13.1.1.1
-- 1.3.6.1.4.1.37950.1.1.5.10.13.1.1.1
-- 1.3.6.1.4.1.37950.1.1.5.10.13.1.1.1
-- 1.3.6.1.4.1.37950.1.1.5.10.13.1.1.1
-- 1.3.6.1.4.1.37950.1.1.5.10.13.1.1.1
-- 1.3.6.1.4.1.37950.1.1.5.10.13.1.1.1
-- 1.3.6.1.4.1.37950.1.1.5.10.13.1.1.1
-- 1.3.6.1.4.1.37950.1.1.5.10.13.1.1.1
-- 1.3.6.1.4.1.37950.1.1.5.10.13.1.1.1
		-- 1.3.6.1.4.1.37950.1.1.5.10.13.1.1.1
		transceiverPonIndex OBJECT-TYPE
			SYNTAX INTEGER (1..16)
			MAX-ACCESS read-only
			STATUS current
			DESCRIPTION
				"Description."
			::= { ponTransceiverEntry 1 }

		
--          1.3.6.1.4.1.37950.1.1.5.10.13.1.1.2
-- 1.3.6.1.4.1.37950.1.1.5.10.13.1.1.2
-- 1.3.6.1.4.1.37950.1.1.5.10.13.1.1.2
-- 1.3.6.1.4.1.37950.1.1.5.10.13.1.1.2
-- 1.3.6.1.4.1.37950.1.1.5.10.13.1.1.2
-- 1.3.6.1.4.1.37950.1.1.5.10.13.1.1.2
-- 1.3.6.1.4.1.37950.1.1.5.10.13.1.1.2
-- 1.3.6.1.4.1.37950.1.1.5.10.13.1.1.2
-- 1.3.6.1.4.1.37950.1.1.5.10.13.1.1.2
		-- 1.3.6.1.4.1.37950.1.1.5.10.13.1.1.2
		tempperature OBJECT-TYPE
			SYNTAX OCTET STRING
			MAX-ACCESS read-only
			STATUS current
			DESCRIPTION
				"Description."
			::= { ponTransceiverEntry 2 }

		
--          1.3.6.1.4.1.37950.1.1.5.10.13.1.1.3
-- 1.3.6.1.4.1.37950.1.1.5.10.13.1.1.3
-- 1.3.6.1.4.1.37950.1.1.5.10.13.1.1.3
-- 1.3.6.1.4.1.37950.1.1.5.10.13.1.1.3
-- 1.3.6.1.4.1.37950.1.1.5.10.13.1.1.3
-- 1.3.6.1.4.1.37950.1.1.5.10.13.1.1.3
-- 1.3.6.1.4.1.37950.1.1.5.10.13.1.1.3
-- 1.3.6.1.4.1.37950.1.1.5.10.13.1.1.3
-- 1.3.6.1.4.1.37950.1.1.5.10.13.1.1.3
		-- 1.3.6.1.4.1.37950.1.1.5.10.13.1.1.3
		voltage OBJECT-TYPE
			SYNTAX OCTET STRING
			MAX-ACCESS read-only
			STATUS current
			DESCRIPTION
				"Description."
			::= { ponTransceiverEntry 3 }

		
--          1.3.6.1.4.1.37950.1.1.5.10.13.1.1.4
-- 1.3.6.1.4.1.37950.1.1.5.10.13.1.1.4
-- 1.3.6.1.4.1.37950.1.1.5.10.13.1.1.4
-- 1.3.6.1.4.1.37950.1.1.5.10.13.1.1.4
-- 1.3.6.1.4.1.37950.1.1.5.10.13.1.1.4
-- 1.3.6.1.4.1.37950.1.1.5.10.13.1.1.4
-- 1.3.6.1.4.1.37950.1.1.5.10.13.1.1.4
-- 1.3.6.1.4.1.37950.1.1.5.10.13.1.1.4
-- 1.3.6.1.4.1.37950.1.1.5.10.13.1.1.4
		-- 1.3.6.1.4.1.37950.1.1.5.10.13.1.1.4
		biasCurrent OBJECT-TYPE
			SYNTAX OCTET STRING
			MAX-ACCESS read-only
			STATUS current
			DESCRIPTION
				"Description."
			::= { ponTransceiverEntry 4 }

		
--          1.3.6.1.4.1.37950.1.1.5.10.13.1.1.5
-- 1.3.6.1.4.1.37950.1.1.5.10.13.1.1.5
-- 1.3.6.1.4.1.37950.1.1.5.10.13.1.1.5
-- 1.3.6.1.4.1.37950.1.1.5.10.13.1.1.5
-- 1.3.6.1.4.1.37950.1.1.5.10.13.1.1.5
-- 1.3.6.1.4.1.37950.1.1.5.10.13.1.1.5
-- 1.3.6.1.4.1.37950.1.1.5.10.13.1.1.5
-- 1.3.6.1.4.1.37950.1.1.5.10.13.1.1.5
-- 1.3.6.1.4.1.37950.1.1.5.10.13.1.1.5
		-- 1.3.6.1.4.1.37950.1.1.5.10.13.1.1.5
		transmitPower OBJECT-TYPE
			SYNTAX OCTET STRING
			MAX-ACCESS read-only
			STATUS current
			DESCRIPTION
				"Description."
			::= { ponTransceiverEntry 5 }

		
--          1.3.6.1.4.1.37950.1.1.5.10.13.2
-- 1.3.6.1.4.1.37950.1.1.5.10.13.2
-- 1.3.6.1.4.1.37950.1.1.5.10.13.2
-- 1.3.6.1.4.1.37950.1.1.5.10.13.2
-- 1.3.6.1.4.1.37950.1.1.5.10.13.2
-- 1.3.6.1.4.1.37950.1.1.5.10.13.2
-- 1.3.6.1.4.1.37950.1.1.5.10.13.2
-- 1.3.6.1.4.1.37950.1.1.5.10.13.2
-- 1.3.6.1.4.1.37950.1.1.5.10.13.2
		-- 1.3.6.1.4.1.37950.1.1.5.10.13.2
		alarmMsg OBJECT IDENTIFIER ::= { v1600dAlarm 2 }

		
--          1.3.6.1.4.1.37950.1.1.5.10.13.2.1
-- 1.3.6.1.4.1.37950.1.1.5.10.13.2.1
-- 1.3.6.1.4.1.37950.1.1.5.10.13.2.1
-- 1.3.6.1.4.1.37950.1.1.5.10.13.2.1
-- 1.3.6.1.4.1.37950.1.1.5.10.13.2.1
-- 1.3.6.1.4.1.37950.1.1.5.10.13.2.1
-- 1.3.6.1.4.1.37950.1.1.5.10.13.2.1
-- 1.3.6.1.4.1.37950.1.1.5.10.13.2.1
-- 1.3.6.1.4.1.37950.1.1.5.10.13.2.1
		-- 1.3.6.1.4.1.37950.1.1.5.10.13.2.1
		dataUpLinkPort OBJECT-TYPE
			SYNTAX OCTET STRING
			MAX-ACCESS read-write
			STATUS current
			DESCRIPTION
				"Description."
			::= { alarmMsg 1 }

		
--          1.3.6.1.4.1.37950.1.1.5.10.13.2.2
-- 1.3.6.1.4.1.37950.1.1.5.10.13.2.2
-- 1.3.6.1.4.1.37950.1.1.5.10.13.2.2
-- 1.3.6.1.4.1.37950.1.1.5.10.13.2.2
-- 1.3.6.1.4.1.37950.1.1.5.10.13.2.2
-- 1.3.6.1.4.1.37950.1.1.5.10.13.2.2
-- 1.3.6.1.4.1.37950.1.1.5.10.13.2.2
-- 1.3.6.1.4.1.37950.1.1.5.10.13.2.2
-- 1.3.6.1.4.1.37950.1.1.5.10.13.2.2
		-- 1.3.6.1.4.1.37950.1.1.5.10.13.2.2
		dataPon OBJECT-TYPE
			SYNTAX OCTET STRING
			MAX-ACCESS read-write
			STATUS current
			DESCRIPTION
				"Description."
			::= { alarmMsg 2 }

		
--          1.3.6.1.4.1.37950.1.1.5.10.13.2.3
-- 1.3.6.1.4.1.37950.1.1.5.10.13.2.3
-- 1.3.6.1.4.1.37950.1.1.5.10.13.2.3
-- 1.3.6.1.4.1.37950.1.1.5.10.13.2.3
-- 1.3.6.1.4.1.37950.1.1.5.10.13.2.3
-- 1.3.6.1.4.1.37950.1.1.5.10.13.2.3
-- 1.3.6.1.4.1.37950.1.1.5.10.13.2.3
-- 1.3.6.1.4.1.37950.1.1.5.10.13.2.3
-- 1.3.6.1.4.1.37950.1.1.5.10.13.2.3
		-- 1.3.6.1.4.1.37950.1.1.5.10.13.2.3
		dataOnu OBJECT-TYPE
			SYNTAX OCTET STRING
			MAX-ACCESS read-write
			STATUS current
			DESCRIPTION
				"Description."
			::= { alarmMsg 3 }

		
--          1.3.6.1.4.1.37950.1.1.5.10.13.2.4
-- 1.3.6.1.4.1.37950.1.1.5.10.13.2.4
-- 1.3.6.1.4.1.37950.1.1.5.10.13.2.4
-- 1.3.6.1.4.1.37950.1.1.5.10.13.2.4
-- 1.3.6.1.4.1.37950.1.1.5.10.13.2.4
-- 1.3.6.1.4.1.37950.1.1.5.10.13.2.4
-- 1.3.6.1.4.1.37950.1.1.5.10.13.2.4
-- 1.3.6.1.4.1.37950.1.1.5.10.13.2.4
-- 1.3.6.1.4.1.37950.1.1.5.10.13.2.4
		-- 1.3.6.1.4.1.37950.1.1.5.10.13.2.4
		dataOnuPort OBJECT-TYPE
			SYNTAX OCTET STRING
			MAX-ACCESS read-write
			STATUS current
			DESCRIPTION
				"Description."
			::= { alarmMsg 4 }

		
--          1.3.6.1.4.1.37950.1.1.5.10.13.2.5
-- 1.3.6.1.4.1.37950.1.1.5.10.13.2.5
-- 1.3.6.1.4.1.37950.1.1.5.10.13.2.5
-- 1.3.6.1.4.1.37950.1.1.5.10.13.2.5
-- 1.3.6.1.4.1.37950.1.1.5.10.13.2.5
-- 1.3.6.1.4.1.37950.1.1.5.10.13.2.5
-- 1.3.6.1.4.1.37950.1.1.5.10.13.2.5
-- 1.3.6.1.4.1.37950.1.1.5.10.13.2.5
-- 1.3.6.1.4.1.37950.1.1.5.10.13.2.5
		-- 1.3.6.1.4.1.37950.1.1.5.10.13.2.5
		dataTrapOID OBJECT-TYPE
			SYNTAX OBJECT IDENTIFIER
			MAX-ACCESS read-write
			STATUS current
			DESCRIPTION
				"Description."
			::= { alarmMsg 5 }

		
--          1.3.6.1.4.1.37950.1.1.5.10.13.2.6
-- 1.3.6.1.4.1.37950.1.1.5.10.13.2.6
-- 1.3.6.1.4.1.37950.1.1.5.10.13.2.6
-- 1.3.6.1.4.1.37950.1.1.5.10.13.2.6
-- 1.3.6.1.4.1.37950.1.1.5.10.13.2.6
-- 1.3.6.1.4.1.37950.1.1.5.10.13.2.6
-- 1.3.6.1.4.1.37950.1.1.5.10.13.2.6
-- 1.3.6.1.4.1.37950.1.1.5.10.13.2.6
-- 1.3.6.1.4.1.37950.1.1.5.10.13.2.6
		-- 1.3.6.1.4.1.37950.1.1.5.10.13.2.6
		dataTrapClass OBJECT-TYPE
			SYNTAX INTEGER
				{
				clear-alarm(0),
				raised-alarm(1),
				no-clear-alarm(2)
				}
			MAX-ACCESS read-write
			STATUS current
			DESCRIPTION
				"Description."
			::= { alarmMsg 6 }

		
--          1.3.6.1.4.1.37950.1.1.5.10.13.2.7
-- 1.3.6.1.4.1.37950.1.1.5.10.13.2.7
-- 1.3.6.1.4.1.37950.1.1.5.10.13.2.7
-- 1.3.6.1.4.1.37950.1.1.5.10.13.2.7
-- 1.3.6.1.4.1.37950.1.1.5.10.13.2.7
-- 1.3.6.1.4.1.37950.1.1.5.10.13.2.7
-- 1.3.6.1.4.1.37950.1.1.5.10.13.2.7
-- 1.3.6.1.4.1.37950.1.1.5.10.13.2.7
-- 1.3.6.1.4.1.37950.1.1.5.10.13.2.7
		-- 1.3.6.1.4.1.37950.1.1.5.10.13.2.7
		dataMac OBJECT-TYPE
			SYNTAX OCTET STRING
			MAX-ACCESS read-only
			STATUS current
			DESCRIPTION
				"Description."
			::= { alarmMsg 7 }

		
--          1.3.6.1.4.1.37950.1.1.5.10.13.2.8
-- 1.3.6.1.4.1.37950.1.1.5.10.13.2.8
-- 1.3.6.1.4.1.37950.1.1.5.10.13.2.8
-- 1.3.6.1.4.1.37950.1.1.5.10.13.2.8
-- 1.3.6.1.4.1.37950.1.1.5.10.13.2.8
-- 1.3.6.1.4.1.37950.1.1.5.10.13.2.8
-- 1.3.6.1.4.1.37950.1.1.5.10.13.2.8
-- 1.3.6.1.4.1.37950.1.1.5.10.13.2.8
-- 1.3.6.1.4.1.37950.1.1.5.10.13.2.8
		-- 1.3.6.1.4.1.37950.1.1.5.10.13.2.8
		dataTime OBJECT-TYPE
			SYNTAX OCTET STRING
			MAX-ACCESS read-write
			STATUS current
			DESCRIPTION
				"Description."
			::= { alarmMsg 8 }

		
--          1.3.6.1.4.1.37950.1.1.5.10.13.2.9
-- 1.3.6.1.4.1.37950.1.1.5.10.13.2.9
-- 1.3.6.1.4.1.37950.1.1.5.10.13.2.9
-- 1.3.6.1.4.1.37950.1.1.5.10.13.2.9
-- 1.3.6.1.4.1.37950.1.1.5.10.13.2.9
-- 1.3.6.1.4.1.37950.1.1.5.10.13.2.9
-- 1.3.6.1.4.1.37950.1.1.5.10.13.2.9
-- 1.3.6.1.4.1.37950.1.1.5.10.13.2.9
-- 1.3.6.1.4.1.37950.1.1.5.10.13.2.9
		-- 1.3.6.1.4.1.37950.1.1.5.10.13.2.9
		dateAlarmLevel OBJECT-TYPE
			SYNTAX INTEGER
				{
				debug(0),
				info(1),
				notice(2),
				warning(3),
				major(4),
				criterr(5),
				alert(6),
				emerg(7)
				}
			MAX-ACCESS read-write
			STATUS current
			DESCRIPTION
				"Description."
			::= { alarmMsg 9 }

		
--          1.3.6.1.4.1.37950.1.1.5.10.13.2.10
-- 1.3.6.1.4.1.37950.1.1.5.10.13.2.10
-- 1.3.6.1.4.1.37950.1.1.5.10.13.2.10
-- 1.3.6.1.4.1.37950.1.1.5.10.13.2.10
-- 1.3.6.1.4.1.37950.1.1.5.10.13.2.10
-- 1.3.6.1.4.1.37950.1.1.5.10.13.2.10
-- 1.3.6.1.4.1.37950.1.1.5.10.13.2.10
-- 1.3.6.1.4.1.37950.1.1.5.10.13.2.10
-- 1.3.6.1.4.1.37950.1.1.5.10.13.2.10
		-- 1.3.6.1.4.1.37950.1.1.5.10.13.2.10
		dataValue OBJECT-TYPE
			SYNTAX OCTET STRING
			MAX-ACCESS read-write
			STATUS current
			DESCRIPTION
				"Description."
			::= { alarmMsg 10 }

		
--          1.3.6.1.4.1.37950.1.1.5.10.13.2.11
-- 1.3.6.1.4.1.37950.1.1.5.10.13.2.11
-- 1.3.6.1.4.1.37950.1.1.5.10.13.2.11
-- 1.3.6.1.4.1.37950.1.1.5.10.13.2.11
-- 1.3.6.1.4.1.37950.1.1.5.10.13.2.11
-- 1.3.6.1.4.1.37950.1.1.5.10.13.2.11
-- 1.3.6.1.4.1.37950.1.1.5.10.13.2.11
-- 1.3.6.1.4.1.37950.1.1.5.10.13.2.11
-- 1.3.6.1.4.1.37950.1.1.5.10.13.2.11
		-- 1.3.6.1.4.1.37950.1.1.5.10.13.2.11
		dataAlarmType OBJECT-TYPE
			SYNTAX INTEGER
				{
				equipment(0),
				process(1),
				communit(2)
				}
			MAX-ACCESS read-write
			STATUS current
			DESCRIPTION
				"Description."
			::= { alarmMsg 11 }

		
--          1.3.6.1.4.1.37950.1.1.5.10.13.2.12
-- 1.3.6.1.4.1.37950.1.1.5.10.13.2.12
-- 1.3.6.1.4.1.37950.1.1.5.10.13.2.12
-- 1.3.6.1.4.1.37950.1.1.5.10.13.2.12
-- 1.3.6.1.4.1.37950.1.1.5.10.13.2.12
-- 1.3.6.1.4.1.37950.1.1.5.10.13.2.12
-- 1.3.6.1.4.1.37950.1.1.5.10.13.2.12
-- 1.3.6.1.4.1.37950.1.1.5.10.13.2.12
-- 1.3.6.1.4.1.37950.1.1.5.10.13.2.12
		-- 1.3.6.1.4.1.37950.1.1.5.10.13.2.12
		dataSynOID OBJECT-TYPE
			SYNTAX OCTET STRING
			MAX-ACCESS read-write
			STATUS current
			DESCRIPTION
				"Description."
			::= { alarmMsg 12 }

		
--          1.3.6.1.4.1.37950.1.1.5.10.13.3
-- 1.3.6.1.4.1.37950.1.1.5.10.13.3
-- 1.3.6.1.4.1.37950.1.1.5.10.13.3
-- 1.3.6.1.4.1.37950.1.1.5.10.13.3
-- 1.3.6.1.4.1.37950.1.1.5.10.13.3
-- 1.3.6.1.4.1.37950.1.1.5.10.13.3
-- 1.3.6.1.4.1.37950.1.1.5.10.13.3
-- 1.3.6.1.4.1.37950.1.1.5.10.13.3
-- 1.3.6.1.4.1.37950.1.1.5.10.13.3
		-- 1.3.6.1.4.1.37950.1.1.5.10.13.3
		ponOpticalAlarmControl OBJECT IDENTIFIER ::= { v1600dAlarm 3 }

		
--          1.3.6.1.4.1.37950.1.1.5.10.13.3.1
-- 1.3.6.1.4.1.37950.1.1.5.10.13.3.1
-- 1.3.6.1.4.1.37950.1.1.5.10.13.3.1
-- 1.3.6.1.4.1.37950.1.1.5.10.13.3.1
-- 1.3.6.1.4.1.37950.1.1.5.10.13.3.1
-- 1.3.6.1.4.1.37950.1.1.5.10.13.3.1
-- 1.3.6.1.4.1.37950.1.1.5.10.13.3.1
-- 1.3.6.1.4.1.37950.1.1.5.10.13.3.1
-- 1.3.6.1.4.1.37950.1.1.5.10.13.3.1
		-- 1.3.6.1.4.1.37950.1.1.5.10.13.3.1
		ponOpticalAlarmDisCfg OBJECT IDENTIFIER ::= { ponOpticalAlarmControl 1 }

		
--          1.3.6.1.4.1.37950.1.1.5.10.13.3.1.1
-- 1.3.6.1.4.1.37950.1.1.5.10.13.3.1.1
-- 1.3.6.1.4.1.37950.1.1.5.10.13.3.1.1
-- 1.3.6.1.4.1.37950.1.1.5.10.13.3.1.1
-- 1.3.6.1.4.1.37950.1.1.5.10.13.3.1.1
-- 1.3.6.1.4.1.37950.1.1.5.10.13.3.1.1
-- 1.3.6.1.4.1.37950.1.1.5.10.13.3.1.1
-- 1.3.6.1.4.1.37950.1.1.5.10.13.3.1.1
-- 1.3.6.1.4.1.37950.1.1.5.10.13.3.1.1
		-- 1.3.6.1.4.1.37950.1.1.5.10.13.3.1.1
		ponAlarmPonNo OBJECT-TYPE
			SYNTAX INTEGER (1..16)
			MAX-ACCESS read-write
			STATUS current
			DESCRIPTION
				"Description."
			::= { ponOpticalAlarmDisCfg 1 }

		
--          1.3.6.1.4.1.37950.1.1.5.10.13.3.1.2
-- 1.3.6.1.4.1.37950.1.1.5.10.13.3.1.2
-- 1.3.6.1.4.1.37950.1.1.5.10.13.3.1.2
-- 1.3.6.1.4.1.37950.1.1.5.10.13.3.1.2
-- 1.3.6.1.4.1.37950.1.1.5.10.13.3.1.2
-- 1.3.6.1.4.1.37950.1.1.5.10.13.3.1.2
-- 1.3.6.1.4.1.37950.1.1.5.10.13.3.1.2
-- 1.3.6.1.4.1.37950.1.1.5.10.13.3.1.2
-- 1.3.6.1.4.1.37950.1.1.5.10.13.3.1.2
		-- 1.3.6.1.4.1.37950.1.1.5.10.13.3.1.2
		ponOpticalType OBJECT-TYPE
			SYNTAX INTEGER
				{
				txPowerHighAlarm(1),
				txPowerLowAlarm(2),
				txBiasHighAlarm(3),
				txBiasLowAlarm(4),
				vccHighAlarm(5),
				vccLowAlarm(6),
				tempHighAlarm(7),
				tempLowAlarm(8)
				}
			MAX-ACCESS read-write
			STATUS current
			DESCRIPTION
				"Description."
			::= { ponOpticalAlarmDisCfg 2 }

		
--          1.3.6.1.4.1.37950.1.1.5.10.13.3.1.3
-- 1.3.6.1.4.1.37950.1.1.5.10.13.3.1.3
-- 1.3.6.1.4.1.37950.1.1.5.10.13.3.1.3
-- 1.3.6.1.4.1.37950.1.1.5.10.13.3.1.3
-- 1.3.6.1.4.1.37950.1.1.5.10.13.3.1.3
-- 1.3.6.1.4.1.37950.1.1.5.10.13.3.1.3
-- 1.3.6.1.4.1.37950.1.1.5.10.13.3.1.3
-- 1.3.6.1.4.1.37950.1.1.5.10.13.3.1.3
-- 1.3.6.1.4.1.37950.1.1.5.10.13.3.1.3
		-- 1.3.6.1.4.1.37950.1.1.5.10.13.3.1.3
		ponOpticalAlarmDis OBJECT-TYPE
			SYNTAX INTEGER { disable(0) }
			MAX-ACCESS read-write
			STATUS current
			DESCRIPTION
				"Description."
			::= { ponOpticalAlarmDisCfg 3 }

		
--          1.3.6.1.4.1.37950.1.1.5.10.13.3.1.4
-- 1.3.6.1.4.1.37950.1.1.5.10.13.3.1.4
-- 1.3.6.1.4.1.37950.1.1.5.10.13.3.1.4
-- 1.3.6.1.4.1.37950.1.1.5.10.13.3.1.4
-- 1.3.6.1.4.1.37950.1.1.5.10.13.3.1.4
-- 1.3.6.1.4.1.37950.1.1.5.10.13.3.1.4
-- 1.3.6.1.4.1.37950.1.1.5.10.13.3.1.4
-- 1.3.6.1.4.1.37950.1.1.5.10.13.3.1.4
-- 1.3.6.1.4.1.37950.1.1.5.10.13.3.1.4
		-- 1.3.6.1.4.1.37950.1.1.5.10.13.3.1.4
		ponOpticalDisAction OBJECT-TYPE
			SYNTAX INTEGER { commit(1) }
			MAX-ACCESS read-write
			STATUS current
			DESCRIPTION
				"Description."
			::= { ponOpticalAlarmDisCfg 4 }

		
--          1.3.6.1.4.1.37950.1.1.5.10.13.3.2
-- 1.3.6.1.4.1.37950.1.1.5.10.13.3.2
-- 1.3.6.1.4.1.37950.1.1.5.10.13.3.2
-- 1.3.6.1.4.1.37950.1.1.5.10.13.3.2
-- 1.3.6.1.4.1.37950.1.1.5.10.13.3.2
-- 1.3.6.1.4.1.37950.1.1.5.10.13.3.2
-- 1.3.6.1.4.1.37950.1.1.5.10.13.3.2
-- 1.3.6.1.4.1.37950.1.1.5.10.13.3.2
-- 1.3.6.1.4.1.37950.1.1.5.10.13.3.2
		-- 1.3.6.1.4.1.37950.1.1.5.10.13.3.2
		ponOpticalAlarmEnCfg OBJECT IDENTIFIER ::= { ponOpticalAlarmControl 2 }

		
--          1.3.6.1.4.1.37950.1.1.5.10.13.3.2.1
-- 1.3.6.1.4.1.37950.1.1.5.10.13.3.2.1
-- 1.3.6.1.4.1.37950.1.1.5.10.13.3.2.1
-- 1.3.6.1.4.1.37950.1.1.5.10.13.3.2.1
-- 1.3.6.1.4.1.37950.1.1.5.10.13.3.2.1
-- 1.3.6.1.4.1.37950.1.1.5.10.13.3.2.1
-- 1.3.6.1.4.1.37950.1.1.5.10.13.3.2.1
-- 1.3.6.1.4.1.37950.1.1.5.10.13.3.2.1
-- 1.3.6.1.4.1.37950.1.1.5.10.13.3.2.1
		-- 1.3.6.1.4.1.37950.1.1.5.10.13.3.2.1
		ponOpticalAlarmPonNo OBJECT-TYPE
			SYNTAX INTEGER (1..16)
			MAX-ACCESS read-write
			STATUS current
			DESCRIPTION
				"Description."
			::= { ponOpticalAlarmEnCfg 1 }

		
--          1.3.6.1.4.1.37950.1.1.5.10.13.3.2.2
-- 1.3.6.1.4.1.37950.1.1.5.10.13.3.2.2
-- 1.3.6.1.4.1.37950.1.1.5.10.13.3.2.2
-- 1.3.6.1.4.1.37950.1.1.5.10.13.3.2.2
-- 1.3.6.1.4.1.37950.1.1.5.10.13.3.2.2
-- 1.3.6.1.4.1.37950.1.1.5.10.13.3.2.2
-- 1.3.6.1.4.1.37950.1.1.5.10.13.3.2.2
-- 1.3.6.1.4.1.37950.1.1.5.10.13.3.2.2
-- 1.3.6.1.4.1.37950.1.1.5.10.13.3.2.2
		-- 1.3.6.1.4.1.37950.1.1.5.10.13.3.2.2
		ponOpticalAlarmType OBJECT-TYPE
			SYNTAX INTEGER
				{
				txPowerHighAlarm(1),
				txPowerLowAlarm(2),
				txBiasHighAlarm(3),
				txBiasLowAlarm(4),
				vccHighAlarm(5),
				vccLowAlarm(6),
				tempHighAlarm(7),
				tempLowAlarm(8)
				}
			MAX-ACCESS read-write
			STATUS current
			DESCRIPTION
				"Description."
			::= { ponOpticalAlarmEnCfg 2 }

		
--          1.3.6.1.4.1.37950.1.1.5.10.13.3.2.3
-- 1.3.6.1.4.1.37950.1.1.5.10.13.3.2.3
-- 1.3.6.1.4.1.37950.1.1.5.10.13.3.2.3
-- 1.3.6.1.4.1.37950.1.1.5.10.13.3.2.3
-- 1.3.6.1.4.1.37950.1.1.5.10.13.3.2.3
-- 1.3.6.1.4.1.37950.1.1.5.10.13.3.2.3
-- 1.3.6.1.4.1.37950.1.1.5.10.13.3.2.3
-- 1.3.6.1.4.1.37950.1.1.5.10.13.3.2.3
-- 1.3.6.1.4.1.37950.1.1.5.10.13.3.2.3
		-- 1.3.6.1.4.1.37950.1.1.5.10.13.3.2.3
		ponOpticalAlarmEn OBJECT-TYPE
			SYNTAX INTEGER { enable(1) }
			MAX-ACCESS read-write
			STATUS current
			DESCRIPTION
				"Description."
			::= { ponOpticalAlarmEnCfg 3 }

		
--          1.3.6.1.4.1.37950.1.1.5.10.13.3.2.4
-- 1.3.6.1.4.1.37950.1.1.5.10.13.3.2.4
-- 1.3.6.1.4.1.37950.1.1.5.10.13.3.2.4
-- 1.3.6.1.4.1.37950.1.1.5.10.13.3.2.4
-- 1.3.6.1.4.1.37950.1.1.5.10.13.3.2.4
-- 1.3.6.1.4.1.37950.1.1.5.10.13.3.2.4
-- 1.3.6.1.4.1.37950.1.1.5.10.13.3.2.4
-- 1.3.6.1.4.1.37950.1.1.5.10.13.3.2.4
-- 1.3.6.1.4.1.37950.1.1.5.10.13.3.2.4
		-- 1.3.6.1.4.1.37950.1.1.5.10.13.3.2.4
		ponOpticalAlarmThld OBJECT-TYPE
			SYNTAX OCTET STRING
			MAX-ACCESS read-write
			STATUS current
			DESCRIPTION
				"Description."
			::= { ponOpticalAlarmEnCfg 4 }

		
--          1.3.6.1.4.1.37950.1.1.5.10.13.3.2.5
-- 1.3.6.1.4.1.37950.1.1.5.10.13.3.2.5
-- 1.3.6.1.4.1.37950.1.1.5.10.13.3.2.5
-- 1.3.6.1.4.1.37950.1.1.5.10.13.3.2.5
-- 1.3.6.1.4.1.37950.1.1.5.10.13.3.2.5
-- 1.3.6.1.4.1.37950.1.1.5.10.13.3.2.5
-- 1.3.6.1.4.1.37950.1.1.5.10.13.3.2.5
-- 1.3.6.1.4.1.37950.1.1.5.10.13.3.2.5
-- 1.3.6.1.4.1.37950.1.1.5.10.13.3.2.5
		-- 1.3.6.1.4.1.37950.1.1.5.10.13.3.2.5
		ponOpticalClearThld OBJECT-TYPE
			SYNTAX OCTET STRING
			MAX-ACCESS read-write
			STATUS current
			DESCRIPTION
				"Description."
			::= { ponOpticalAlarmEnCfg 5 }

		
--          1.3.6.1.4.1.37950.1.1.5.10.13.3.2.6
-- 1.3.6.1.4.1.37950.1.1.5.10.13.3.2.6
-- 1.3.6.1.4.1.37950.1.1.5.10.13.3.2.6
-- 1.3.6.1.4.1.37950.1.1.5.10.13.3.2.6
-- 1.3.6.1.4.1.37950.1.1.5.10.13.3.2.6
-- 1.3.6.1.4.1.37950.1.1.5.10.13.3.2.6
-- 1.3.6.1.4.1.37950.1.1.5.10.13.3.2.6
-- 1.3.6.1.4.1.37950.1.1.5.10.13.3.2.6
-- 1.3.6.1.4.1.37950.1.1.5.10.13.3.2.6
		-- 1.3.6.1.4.1.37950.1.1.5.10.13.3.2.6
		ponOpticalAlarmEnAction OBJECT-TYPE
			SYNTAX INTEGER { commit(1) }
			MAX-ACCESS read-write
			STATUS current
			DESCRIPTION
				"Description."
			::= { ponOpticalAlarmEnCfg 6 }

		
--          1.3.6.1.4.1.37950.1.1.5.10.13.3.3
-- 1.3.6.1.4.1.37950.1.1.5.10.13.3.3
-- 1.3.6.1.4.1.37950.1.1.5.10.13.3.3
-- 1.3.6.1.4.1.37950.1.1.5.10.13.3.3
-- 1.3.6.1.4.1.37950.1.1.5.10.13.3.3
-- 1.3.6.1.4.1.37950.1.1.5.10.13.3.3
-- 1.3.6.1.4.1.37950.1.1.5.10.13.3.3
-- 1.3.6.1.4.1.37950.1.1.5.10.13.3.3
-- 1.3.6.1.4.1.37950.1.1.5.10.13.3.3
		-- 1.3.6.1.4.1.37950.1.1.5.10.13.3.3
		ponOpticalAlarmTable OBJECT-TYPE
			SYNTAX SEQUENCE OF PonOpticalAlarmEntry
			MAX-ACCESS not-accessible
			STATUS current
			DESCRIPTION
				"Description."
			::= { ponOpticalAlarmControl 3 }

		
--          1.3.6.1.4.1.37950.1.1.5.10.13.3.3.1
-- 1.3.6.1.4.1.37950.1.1.5.10.13.3.3.1
-- 1.3.6.1.4.1.37950.1.1.5.10.13.3.3.1
-- 1.3.6.1.4.1.37950.1.1.5.10.13.3.3.1
-- 1.3.6.1.4.1.37950.1.1.5.10.13.3.3.1
-- 1.3.6.1.4.1.37950.1.1.5.10.13.3.3.1
-- 1.3.6.1.4.1.37950.1.1.5.10.13.3.3.1
-- 1.3.6.1.4.1.37950.1.1.5.10.13.3.3.1
-- 1.3.6.1.4.1.37950.1.1.5.10.13.3.3.1
		-- 1.3.6.1.4.1.37950.1.1.5.10.13.3.3.1
		ponOpticalAlarmEntry OBJECT-TYPE
			SYNTAX PonOpticalAlarmEntry
			MAX-ACCESS not-accessible
			STATUS current
			DESCRIPTION
				"Description."
			INDEX { ponAlarmPonIndex, ponAlarmType }
			::= { ponOpticalAlarmTable 1 }

		
		PonOpticalAlarmEntry ::=
			SEQUENCE { 
				ponAlarmPonIndex
					Integer32,
				ponAlarmType
					INTEGER,
				ponOpticalAlarmStatus
					INTEGER,
				ponOpticalAlarmThldVal
					OCTET STRING,
				ponOpticalClearThldVal
					OCTET STRING
			 }

--          1.3.6.1.4.1.37950.1.1.5.10.13.3.3.1.1
-- 1.3.6.1.4.1.37950.1.1.5.10.13.3.3.1.1
-- 1.3.6.1.4.1.37950.1.1.5.10.13.3.3.1.1
-- 1.3.6.1.4.1.37950.1.1.5.10.13.3.3.1.1
-- 1.3.6.1.4.1.37950.1.1.5.10.13.3.3.1.1
-- 1.3.6.1.4.1.37950.1.1.5.10.13.3.3.1.1
-- 1.3.6.1.4.1.37950.1.1.5.10.13.3.3.1.1
-- 1.3.6.1.4.1.37950.1.1.5.10.13.3.3.1.1
-- 1.3.6.1.4.1.37950.1.1.5.10.13.3.3.1.1
		-- 1.3.6.1.4.1.37950.1.1.5.10.13.3.3.1.1
		ponAlarmPonIndex OBJECT-TYPE
			SYNTAX Integer32 (1..16)
			MAX-ACCESS read-only
			STATUS current
			DESCRIPTION
				"Description."
			::= { ponOpticalAlarmEntry 1 }

		
--          1.3.6.1.4.1.37950.1.1.5.10.13.3.3.1.2
-- 1.3.6.1.4.1.37950.1.1.5.10.13.3.3.1.2
-- 1.3.6.1.4.1.37950.1.1.5.10.13.3.3.1.2
-- 1.3.6.1.4.1.37950.1.1.5.10.13.3.3.1.2
-- 1.3.6.1.4.1.37950.1.1.5.10.13.3.3.1.2
-- 1.3.6.1.4.1.37950.1.1.5.10.13.3.3.1.2
-- 1.3.6.1.4.1.37950.1.1.5.10.13.3.3.1.2
-- 1.3.6.1.4.1.37950.1.1.5.10.13.3.3.1.2
-- 1.3.6.1.4.1.37950.1.1.5.10.13.3.3.1.2
		-- 1.3.6.1.4.1.37950.1.1.5.10.13.3.3.1.2
		ponAlarmType OBJECT-TYPE
			SYNTAX INTEGER
				{
				txPowerHighAlarm(1),
				txPowerLowAlarm(2),
				txBiasHighAlarm(3),
				txBiasLowAlarm(4),
				vccHighAlarm(5),
				vccLowAlarm(6),
				tempHighAlarm(7),
				tempLowAlarm(8)
				}
			MAX-ACCESS read-only
			STATUS current
			DESCRIPTION
				"Description."
			::= { ponOpticalAlarmEntry 2 }

		
--          1.3.6.1.4.1.37950.1.1.5.10.13.3.3.1.3
-- 1.3.6.1.4.1.37950.1.1.5.10.13.3.3.1.3
-- 1.3.6.1.4.1.37950.1.1.5.10.13.3.3.1.3
-- 1.3.6.1.4.1.37950.1.1.5.10.13.3.3.1.3
-- 1.3.6.1.4.1.37950.1.1.5.10.13.3.3.1.3
-- 1.3.6.1.4.1.37950.1.1.5.10.13.3.3.1.3
-- 1.3.6.1.4.1.37950.1.1.5.10.13.3.3.1.3
-- 1.3.6.1.4.1.37950.1.1.5.10.13.3.3.1.3
-- 1.3.6.1.4.1.37950.1.1.5.10.13.3.3.1.3
		-- 1.3.6.1.4.1.37950.1.1.5.10.13.3.3.1.3
		ponOpticalAlarmStatus OBJECT-TYPE
			SYNTAX INTEGER
				{
				disable(0),
				enable(1)
				}
			MAX-ACCESS read-only
			STATUS current
			DESCRIPTION
				"Description."
			::= { ponOpticalAlarmEntry 3 }

		
--          1.3.6.1.4.1.37950.1.1.5.10.13.3.3.1.4
-- 1.3.6.1.4.1.37950.1.1.5.10.13.3.3.1.4
-- 1.3.6.1.4.1.37950.1.1.5.10.13.3.3.1.4
-- 1.3.6.1.4.1.37950.1.1.5.10.13.3.3.1.4
-- 1.3.6.1.4.1.37950.1.1.5.10.13.3.3.1.4
-- 1.3.6.1.4.1.37950.1.1.5.10.13.3.3.1.4
-- 1.3.6.1.4.1.37950.1.1.5.10.13.3.3.1.4
-- 1.3.6.1.4.1.37950.1.1.5.10.13.3.3.1.4
-- 1.3.6.1.4.1.37950.1.1.5.10.13.3.3.1.4
		-- 1.3.6.1.4.1.37950.1.1.5.10.13.3.3.1.4
		ponOpticalAlarmThldVal OBJECT-TYPE
			SYNTAX OCTET STRING
			MAX-ACCESS read-only
			STATUS current
			DESCRIPTION
				"Description."
			::= { ponOpticalAlarmEntry 4 }

		
--          1.3.6.1.4.1.37950.1.1.5.10.13.3.3.1.5
-- 1.3.6.1.4.1.37950.1.1.5.10.13.3.3.1.5
-- 1.3.6.1.4.1.37950.1.1.5.10.13.3.3.1.5
-- 1.3.6.1.4.1.37950.1.1.5.10.13.3.3.1.5
-- 1.3.6.1.4.1.37950.1.1.5.10.13.3.3.1.5
-- 1.3.6.1.4.1.37950.1.1.5.10.13.3.3.1.5
-- 1.3.6.1.4.1.37950.1.1.5.10.13.3.3.1.5
-- 1.3.6.1.4.1.37950.1.1.5.10.13.3.3.1.5
-- 1.3.6.1.4.1.37950.1.1.5.10.13.3.3.1.5
		-- 1.3.6.1.4.1.37950.1.1.5.10.13.3.3.1.5
		ponOpticalClearThldVal OBJECT-TYPE
			SYNTAX OCTET STRING
			MAX-ACCESS read-only
			STATUS current
			DESCRIPTION
				"Description."
			::= { ponOpticalAlarmEntry 5 }

		
--          1.3.6.1.4.1.37950.1.1.5.10.13.4
-- 1.3.6.1.4.1.37950.1.1.5.10.13.4
-- 1.3.6.1.4.1.37950.1.1.5.10.13.4
-- 1.3.6.1.4.1.37950.1.1.5.10.13.4
-- 1.3.6.1.4.1.37950.1.1.5.10.13.4
-- 1.3.6.1.4.1.37950.1.1.5.10.13.4
-- 1.3.6.1.4.1.37950.1.1.5.10.13.4
-- 1.3.6.1.4.1.37950.1.1.5.10.13.4
-- 1.3.6.1.4.1.37950.1.1.5.10.13.4
		-- 1.3.6.1.4.1.37950.1.1.5.10.13.4
		alarmCtrl OBJECT IDENTIFIER ::= { v1600dAlarm 4 }

		
--          1.3.6.1.4.1.37950.1.1.5.10.13.4.1
-- 1.3.6.1.4.1.37950.1.1.5.10.13.4.1
-- 1.3.6.1.4.1.37950.1.1.5.10.13.4.1
-- 1.3.6.1.4.1.37950.1.1.5.10.13.4.1
-- 1.3.6.1.4.1.37950.1.1.5.10.13.4.1
-- 1.3.6.1.4.1.37950.1.1.5.10.13.4.1
-- 1.3.6.1.4.1.37950.1.1.5.10.13.4.1
-- 1.3.6.1.4.1.37950.1.1.5.10.13.4.1
-- 1.3.6.1.4.1.37950.1.1.5.10.13.4.1
		-- 1.3.6.1.4.1.37950.1.1.5.10.13.4.1
		alarmControlCfg OBJECT IDENTIFIER ::= { alarmCtrl 1 }

		
--          1.3.6.1.4.1.37950.1.1.5.10.13.4.1.1
-- 1.3.6.1.4.1.37950.1.1.5.10.13.4.1.1
-- 1.3.6.1.4.1.37950.1.1.5.10.13.4.1.1
-- 1.3.6.1.4.1.37950.1.1.5.10.13.4.1.1
-- 1.3.6.1.4.1.37950.1.1.5.10.13.4.1.1
-- 1.3.6.1.4.1.37950.1.1.5.10.13.4.1.1
-- 1.3.6.1.4.1.37950.1.1.5.10.13.4.1.1
-- 1.3.6.1.4.1.37950.1.1.5.10.13.4.1.1
-- 1.3.6.1.4.1.37950.1.1.5.10.13.4.1.1
		-- 1.3.6.1.4.1.37950.1.1.5.10.13.4.1.1
		alarmControlType OBJECT-TYPE
			SYNTAX INTEGER
				{
				fan(1),
				download-file-failed(2),
				upload-file-failed(3),
				upgrade-file-failed(4),
				port-updown(5),
				port-loopback(6),
				pon-deregister(7),
				pon-register-failed(8),
				pon-disable(9),
				pon-txpower-high(10),
				pon-txpower-low(11),
				pon-txbias-high(12),
				pon-txbias-low(13),
				pon-vcc-high(14),
				pon-vcc-low(15),
				pon-temp-high(16),
				pon-temp-low(17),
				pon-los(18),
				onu-deregister(19),
				onu-link-lost(20),
				onu-illegal-register(21),
				onu-auth-failed(22),
				onu-mac-conflict(23),
				onu-loid-conflict(24),
				onu-critical-event(25),
				onu-dying-gasp(26),
				onu-link-fault(27),
				onu-link-event(28),
				onu-event-notific(29),
				reset(30),
				config-save(31),
				config-erase(32),
				download-file-success(33),
				upload-file-success(34),
				upgrade-file-success(35),
				pon-register(36),
				pon-enable(37),
				pon-los-recovery(38),
				onu-register(39),
				onu-link-discover(40),
				onu-auth-success(41),
				onu-deauth-success(42),
				onu-pon-rxpower-high(43),
				onu-pon-rxpower-low(44),
				onu-pon-txpower-high(45),
				onu-pon-txpower-low(46),
				onu-pon-txbias-high(47),
				onu-pon-txbias-low(48),
				onu-pon-vcc-high(49),
				onu-pon-vcc-low(50),
				onu-pon-temp-high(51),
				onu-pon-temp-low(52),
				onu-port-autoneg-failure(53),
				onu-port-los(54),
				onu-port-failure(55),
				onu-port-loopback(56),
				onu-pots-failure(57),
				user-login(58),
				user-logout(59)
				}
			MAX-ACCESS read-write
			STATUS current
			DESCRIPTION
				"Description."
			::= { alarmControlCfg 1 }

		
--          1.3.6.1.4.1.37950.1.1.5.10.13.4.1.2
-- 1.3.6.1.4.1.37950.1.1.5.10.13.4.1.2
-- 1.3.6.1.4.1.37950.1.1.5.10.13.4.1.2
-- 1.3.6.1.4.1.37950.1.1.5.10.13.4.1.2
-- 1.3.6.1.4.1.37950.1.1.5.10.13.4.1.2
-- 1.3.6.1.4.1.37950.1.1.5.10.13.4.1.2
-- 1.3.6.1.4.1.37950.1.1.5.10.13.4.1.2
-- 1.3.6.1.4.1.37950.1.1.5.10.13.4.1.2
-- 1.3.6.1.4.1.37950.1.1.5.10.13.4.1.2
		-- 1.3.6.1.4.1.37950.1.1.5.10.13.4.1.2
		alarmOutputType OBJECT-TYPE
			SYNTAX INTEGER
				{
				print(0),
				record(1),
				trap(2),
				remote(3),
				all(4)
				}
			MAX-ACCESS read-write
			STATUS current
			DESCRIPTION
				"Description."
			::= { alarmControlCfg 2 }

		
--          1.3.6.1.4.1.37950.1.1.5.10.13.4.1.3
-- 1.3.6.1.4.1.37950.1.1.5.10.13.4.1.3
-- 1.3.6.1.4.1.37950.1.1.5.10.13.4.1.3
-- 1.3.6.1.4.1.37950.1.1.5.10.13.4.1.3
-- 1.3.6.1.4.1.37950.1.1.5.10.13.4.1.3
-- 1.3.6.1.4.1.37950.1.1.5.10.13.4.1.3
-- 1.3.6.1.4.1.37950.1.1.5.10.13.4.1.3
-- 1.3.6.1.4.1.37950.1.1.5.10.13.4.1.3
-- 1.3.6.1.4.1.37950.1.1.5.10.13.4.1.3
		-- 1.3.6.1.4.1.37950.1.1.5.10.13.4.1.3
		alarmControlEnable OBJECT-TYPE
			SYNTAX INTEGER
				{
				disable(0),
				enable(1)
				}
			MAX-ACCESS read-write
			STATUS current
			DESCRIPTION
				"Description."
			::= { alarmControlCfg 3 }

		
--          1.3.6.1.4.1.37950.1.1.5.10.13.4.1.4
-- 1.3.6.1.4.1.37950.1.1.5.10.13.4.1.4
-- 1.3.6.1.4.1.37950.1.1.5.10.13.4.1.4
-- 1.3.6.1.4.1.37950.1.1.5.10.13.4.1.4
-- 1.3.6.1.4.1.37950.1.1.5.10.13.4.1.4
-- 1.3.6.1.4.1.37950.1.1.5.10.13.4.1.4
-- 1.3.6.1.4.1.37950.1.1.5.10.13.4.1.4
-- 1.3.6.1.4.1.37950.1.1.5.10.13.4.1.4
-- 1.3.6.1.4.1.37950.1.1.5.10.13.4.1.4
		-- 1.3.6.1.4.1.37950.1.1.5.10.13.4.1.4
		alarmControlAction OBJECT-TYPE
			SYNTAX INTEGER { commit(1) }
			MAX-ACCESS read-write
			STATUS current
			DESCRIPTION
				"Description."
			::= { alarmControlCfg 4 }

		
--          1.3.6.1.4.1.37950.1.1.5.10.13.4.2
-- 1.3.6.1.4.1.37950.1.1.5.10.13.4.2
-- 1.3.6.1.4.1.37950.1.1.5.10.13.4.2
-- 1.3.6.1.4.1.37950.1.1.5.10.13.4.2
-- 1.3.6.1.4.1.37950.1.1.5.10.13.4.2
-- 1.3.6.1.4.1.37950.1.1.5.10.13.4.2
-- 1.3.6.1.4.1.37950.1.1.5.10.13.4.2
-- 1.3.6.1.4.1.37950.1.1.5.10.13.4.2
-- 1.3.6.1.4.1.37950.1.1.5.10.13.4.2
		-- 1.3.6.1.4.1.37950.1.1.5.10.13.4.2
		alarmControlTable OBJECT-TYPE
			SYNTAX SEQUENCE OF AlarmControlEntry
			MAX-ACCESS not-accessible
			STATUS current
			DESCRIPTION
				"Description."
			::= { alarmCtrl 2 }

		
--          1.3.6.1.4.1.37950.1.1.5.10.13.4.2.1
-- 1.3.6.1.4.1.37950.1.1.5.10.13.4.2.1
-- 1.3.6.1.4.1.37950.1.1.5.10.13.4.2.1
-- 1.3.6.1.4.1.37950.1.1.5.10.13.4.2.1
-- 1.3.6.1.4.1.37950.1.1.5.10.13.4.2.1
-- 1.3.6.1.4.1.37950.1.1.5.10.13.4.2.1
-- 1.3.6.1.4.1.37950.1.1.5.10.13.4.2.1
-- 1.3.6.1.4.1.37950.1.1.5.10.13.4.2.1
-- 1.3.6.1.4.1.37950.1.1.5.10.13.4.2.1
		-- 1.3.6.1.4.1.37950.1.1.5.10.13.4.2.1
		alarmControlEntry OBJECT-TYPE
			SYNTAX AlarmControlEntry
			MAX-ACCESS not-accessible
			STATUS current
			DESCRIPTION
				"Description."
			INDEX { alarmControlId }
			::= { alarmControlTable 1 }

		
		AlarmControlEntry ::=
			SEQUENCE { 
				alarmControlId
					Integer32,
				alarmControlTypeS
					OCTET STRING,
				alarmPrintStatus
					INTEGER,
				alarmRecordStatus
					INTEGER,
				alarmTrapStatus
					INTEGER,
				alarmRemoteStatus
					INTEGER
			 }

--          1.3.6.1.4.1.37950.1.1.5.10.13.4.2.1.1
-- 1.3.6.1.4.1.37950.1.1.5.10.13.4.2.1.1
-- 1.3.6.1.4.1.37950.1.1.5.10.13.4.2.1.1
-- 1.3.6.1.4.1.37950.1.1.5.10.13.4.2.1.1
-- 1.3.6.1.4.1.37950.1.1.5.10.13.4.2.1.1
-- 1.3.6.1.4.1.37950.1.1.5.10.13.4.2.1.1
-- 1.3.6.1.4.1.37950.1.1.5.10.13.4.2.1.1
-- 1.3.6.1.4.1.37950.1.1.5.10.13.4.2.1.1
-- 1.3.6.1.4.1.37950.1.1.5.10.13.4.2.1.1
		-- 1.3.6.1.4.1.37950.1.1.5.10.13.4.2.1.1
		alarmControlId OBJECT-TYPE
			SYNTAX Integer32
			MAX-ACCESS read-only
			STATUS current
			DESCRIPTION
				"Description."
			::= { alarmControlEntry 1 }

		
--          1.3.6.1.4.1.37950.1.1.5.10.13.4.2.1.2
-- 1.3.6.1.4.1.37950.1.1.5.10.13.4.2.1.2
-- 1.3.6.1.4.1.37950.1.1.5.10.13.4.2.1.2
-- 1.3.6.1.4.1.37950.1.1.5.10.13.4.2.1.2
-- 1.3.6.1.4.1.37950.1.1.5.10.13.4.2.1.2
-- 1.3.6.1.4.1.37950.1.1.5.10.13.4.2.1.2
-- 1.3.6.1.4.1.37950.1.1.5.10.13.4.2.1.2
-- 1.3.6.1.4.1.37950.1.1.5.10.13.4.2.1.2
-- 1.3.6.1.4.1.37950.1.1.5.10.13.4.2.1.2
		-- 1.3.6.1.4.1.37950.1.1.5.10.13.4.2.1.2
		alarmControlTypeS OBJECT-TYPE
			SYNTAX OCTET STRING
			MAX-ACCESS read-only
			STATUS current
			DESCRIPTION
				"Description."
			::= { alarmControlEntry 2 }

		
--          1.3.6.1.4.1.37950.1.1.5.10.13.4.2.1.3
-- 1.3.6.1.4.1.37950.1.1.5.10.13.4.2.1.3
-- 1.3.6.1.4.1.37950.1.1.5.10.13.4.2.1.3
-- 1.3.6.1.4.1.37950.1.1.5.10.13.4.2.1.3
-- 1.3.6.1.4.1.37950.1.1.5.10.13.4.2.1.3
-- 1.3.6.1.4.1.37950.1.1.5.10.13.4.2.1.3
-- 1.3.6.1.4.1.37950.1.1.5.10.13.4.2.1.3
-- 1.3.6.1.4.1.37950.1.1.5.10.13.4.2.1.3
-- 1.3.6.1.4.1.37950.1.1.5.10.13.4.2.1.3
		-- 1.3.6.1.4.1.37950.1.1.5.10.13.4.2.1.3
		alarmPrintStatus OBJECT-TYPE
			SYNTAX INTEGER
				{
				disable(0),
				enable(1)
				}
			MAX-ACCESS read-write
			STATUS current
			DESCRIPTION
				"Description."
			::= { alarmControlEntry 3 }

		
--          1.3.6.1.4.1.37950.1.1.5.10.13.4.2.1.4
-- 1.3.6.1.4.1.37950.1.1.5.10.13.4.2.1.4
-- 1.3.6.1.4.1.37950.1.1.5.10.13.4.2.1.4
-- 1.3.6.1.4.1.37950.1.1.5.10.13.4.2.1.4
-- 1.3.6.1.4.1.37950.1.1.5.10.13.4.2.1.4
-- 1.3.6.1.4.1.37950.1.1.5.10.13.4.2.1.4
-- 1.3.6.1.4.1.37950.1.1.5.10.13.4.2.1.4
-- 1.3.6.1.4.1.37950.1.1.5.10.13.4.2.1.4
-- 1.3.6.1.4.1.37950.1.1.5.10.13.4.2.1.4
		-- 1.3.6.1.4.1.37950.1.1.5.10.13.4.2.1.4
		alarmRecordStatus OBJECT-TYPE
			SYNTAX INTEGER
				{
				disable(0),
				enable(1)
				}
			MAX-ACCESS read-write
			STATUS current
			DESCRIPTION
				"Description."
			::= { alarmControlEntry 4 }

		
--          1.3.6.1.4.1.37950.1.1.5.10.13.4.2.1.5
-- 1.3.6.1.4.1.37950.1.1.5.10.13.4.2.1.5
-- 1.3.6.1.4.1.37950.1.1.5.10.13.4.2.1.5
-- 1.3.6.1.4.1.37950.1.1.5.10.13.4.2.1.5
-- 1.3.6.1.4.1.37950.1.1.5.10.13.4.2.1.5
-- 1.3.6.1.4.1.37950.1.1.5.10.13.4.2.1.5
-- 1.3.6.1.4.1.37950.1.1.5.10.13.4.2.1.5
-- 1.3.6.1.4.1.37950.1.1.5.10.13.4.2.1.5
-- 1.3.6.1.4.1.37950.1.1.5.10.13.4.2.1.5
		-- 1.3.6.1.4.1.37950.1.1.5.10.13.4.2.1.5
		alarmTrapStatus OBJECT-TYPE
			SYNTAX INTEGER
				{
				disable(0),
				enable(1)
				}
			MAX-ACCESS read-write
			STATUS current
			DESCRIPTION
				"Description."
			::= { alarmControlEntry 5 }

		
--          1.3.6.1.4.1.37950.1.1.5.10.13.4.2.1.6
-- 1.3.6.1.4.1.37950.1.1.5.10.13.4.2.1.6
-- 1.3.6.1.4.1.37950.1.1.5.10.13.4.2.1.6
-- 1.3.6.1.4.1.37950.1.1.5.10.13.4.2.1.6
-- 1.3.6.1.4.1.37950.1.1.5.10.13.4.2.1.6
-- 1.3.6.1.4.1.37950.1.1.5.10.13.4.2.1.6
-- 1.3.6.1.4.1.37950.1.1.5.10.13.4.2.1.6
-- 1.3.6.1.4.1.37950.1.1.5.10.13.4.2.1.6
-- 1.3.6.1.4.1.37950.1.1.5.10.13.4.2.1.6
		-- 1.3.6.1.4.1.37950.1.1.5.10.13.4.2.1.6
		alarmRemoteStatus OBJECT-TYPE
			SYNTAX INTEGER
				{
				disable(0),
				enable(1)
				}
			MAX-ACCESS read-only
			STATUS current
			DESCRIPTION
				"Description."
			::= { alarmControlEntry 6 }

		
--          1.3.6.1.4.1.37950.1.1.5.10.13.4.3
-- 1.3.6.1.4.1.37950.1.1.5.10.13.4.3
-- 1.3.6.1.4.1.37950.1.1.5.10.13.4.3
-- 1.3.6.1.4.1.37950.1.1.5.10.13.4.3
-- 1.3.6.1.4.1.37950.1.1.5.10.13.4.3
-- 1.3.6.1.4.1.37950.1.1.5.10.13.4.3
-- 1.3.6.1.4.1.37950.1.1.5.10.13.4.3
-- 1.3.6.1.4.1.37950.1.1.5.10.13.4.3
-- 1.3.6.1.4.1.37950.1.1.5.10.13.4.3
		-- 1.3.6.1.4.1.37950.1.1.5.10.13.4.3
		alarmControlThldCfg OBJECT IDENTIFIER ::= { alarmCtrl 3 }

		
--          1.3.6.1.4.1.37950.1.1.5.10.13.4.3.1
-- 1.3.6.1.4.1.37950.1.1.5.10.13.4.3.1
-- 1.3.6.1.4.1.37950.1.1.5.10.13.4.3.1
-- 1.3.6.1.4.1.37950.1.1.5.10.13.4.3.1
-- 1.3.6.1.4.1.37950.1.1.5.10.13.4.3.1
-- 1.3.6.1.4.1.37950.1.1.5.10.13.4.3.1
-- 1.3.6.1.4.1.37950.1.1.5.10.13.4.3.1
-- 1.3.6.1.4.1.37950.1.1.5.10.13.4.3.1
-- 1.3.6.1.4.1.37950.1.1.5.10.13.4.3.1
		-- 1.3.6.1.4.1.37950.1.1.5.10.13.4.3.1
		alarmControlThldType OBJECT-TYPE
			SYNTAX INTEGER
				{
				temp-high(1),
				temp-low(2),
				cpu-usage-high(3),
				mem-usage-high(4)
				}
			MAX-ACCESS read-write
			STATUS current
			DESCRIPTION
				"Description."
			::= { alarmControlThldCfg 1 }

		
--          1.3.6.1.4.1.37950.1.1.5.10.13.4.3.2
-- 1.3.6.1.4.1.37950.1.1.5.10.13.4.3.2
-- 1.3.6.1.4.1.37950.1.1.5.10.13.4.3.2
-- 1.3.6.1.4.1.37950.1.1.5.10.13.4.3.2
-- 1.3.6.1.4.1.37950.1.1.5.10.13.4.3.2
-- 1.3.6.1.4.1.37950.1.1.5.10.13.4.3.2
-- 1.3.6.1.4.1.37950.1.1.5.10.13.4.3.2
-- 1.3.6.1.4.1.37950.1.1.5.10.13.4.3.2
-- 1.3.6.1.4.1.37950.1.1.5.10.13.4.3.2
		-- 1.3.6.1.4.1.37950.1.1.5.10.13.4.3.2
		alarmOutputThldType OBJECT-TYPE
			SYNTAX INTEGER
				{
				print(0),
				record(1),
				trap(2),
				remote(3),
				all(4)
				}
			MAX-ACCESS read-write
			STATUS current
			DESCRIPTION
				"Description."
			::= { alarmControlThldCfg 2 }

		
--          1.3.6.1.4.1.37950.1.1.5.10.13.4.3.3
-- 1.3.6.1.4.1.37950.1.1.5.10.13.4.3.3
-- 1.3.6.1.4.1.37950.1.1.5.10.13.4.3.3
-- 1.3.6.1.4.1.37950.1.1.5.10.13.4.3.3
-- 1.3.6.1.4.1.37950.1.1.5.10.13.4.3.3
-- 1.3.6.1.4.1.37950.1.1.5.10.13.4.3.3
-- 1.3.6.1.4.1.37950.1.1.5.10.13.4.3.3
-- 1.3.6.1.4.1.37950.1.1.5.10.13.4.3.3
-- 1.3.6.1.4.1.37950.1.1.5.10.13.4.3.3
		-- 1.3.6.1.4.1.37950.1.1.5.10.13.4.3.3
		alarmControlThldEnable OBJECT-TYPE
			SYNTAX INTEGER
				{
				disable(0),
				enablel(1)
				}
			MAX-ACCESS read-write
			STATUS current
			DESCRIPTION
				"Description."
			::= { alarmControlThldCfg 3 }

		
--          1.3.6.1.4.1.37950.1.1.5.10.13.4.3.4
-- 1.3.6.1.4.1.37950.1.1.5.10.13.4.3.4
-- 1.3.6.1.4.1.37950.1.1.5.10.13.4.3.4
-- 1.3.6.1.4.1.37950.1.1.5.10.13.4.3.4
-- 1.3.6.1.4.1.37950.1.1.5.10.13.4.3.4
-- 1.3.6.1.4.1.37950.1.1.5.10.13.4.3.4
-- 1.3.6.1.4.1.37950.1.1.5.10.13.4.3.4
-- 1.3.6.1.4.1.37950.1.1.5.10.13.4.3.4
-- 1.3.6.1.4.1.37950.1.1.5.10.13.4.3.4
		-- 1.3.6.1.4.1.37950.1.1.5.10.13.4.3.4
		alarmControlThldAlarm OBJECT-TYPE
			SYNTAX OCTET STRING
			MAX-ACCESS read-write
			STATUS current
			DESCRIPTION
				"Description."
			::= { alarmControlThldCfg 4 }

		
--          1.3.6.1.4.1.37950.1.1.5.10.13.4.3.5
-- 1.3.6.1.4.1.37950.1.1.5.10.13.4.3.5
-- 1.3.6.1.4.1.37950.1.1.5.10.13.4.3.5
-- 1.3.6.1.4.1.37950.1.1.5.10.13.4.3.5
-- 1.3.6.1.4.1.37950.1.1.5.10.13.4.3.5
-- 1.3.6.1.4.1.37950.1.1.5.10.13.4.3.5
-- 1.3.6.1.4.1.37950.1.1.5.10.13.4.3.5
-- 1.3.6.1.4.1.37950.1.1.5.10.13.4.3.5
-- 1.3.6.1.4.1.37950.1.1.5.10.13.4.3.5
		-- 1.3.6.1.4.1.37950.1.1.5.10.13.4.3.5
		alarmControlThldClear OBJECT-TYPE
			SYNTAX OCTET STRING
			MAX-ACCESS read-write
			STATUS current
			DESCRIPTION
				"Description."
			::= { alarmControlThldCfg 5 }

		
--         1.3.6.1.4.1.37950.1.1.5.10.13.4.3.6
-- 1.3.6.1.4.1.37950.1.1.5.10.13.4.3.6
-- 1.3.6.1.4.1.37950.1.1.5.10.13.4.3.6
-- 1.3.6.1.4.1.37950.1.1.5.10.13.4.3.6
-- 1.3.6.1.4.1.37950.1.1.5.10.13.4.3.6
-- 1.3.6.1.4.1.37950.1.1.5.10.13.4.3.6
-- 1.3.6.1.4.1.37950.1.1.5.10.13.4.3.6
-- 1.3.6.1.4.1.37950.1.1.5.10.13.4.3.6
		-- 1.3.6.1.4.1.37950.1.1.5.10.13.4.3.6
		alarmControlThldAction OBJECT-TYPE
			SYNTAX INTEGER { commit(1) }
			MAX-ACCESS read-write
			STATUS current
			DESCRIPTION
				"Description."
			::= { alarmControlThldCfg 6 }

		
--          1.3.6.1.4.1.37950.1.1.5.10.13.4.4
-- 1.3.6.1.4.1.37950.1.1.5.10.13.4.4
-- 1.3.6.1.4.1.37950.1.1.5.10.13.4.4
-- 1.3.6.1.4.1.37950.1.1.5.10.13.4.4
-- 1.3.6.1.4.1.37950.1.1.5.10.13.4.4
-- 1.3.6.1.4.1.37950.1.1.5.10.13.4.4
-- 1.3.6.1.4.1.37950.1.1.5.10.13.4.4
-- 1.3.6.1.4.1.37950.1.1.5.10.13.4.4
-- 1.3.6.1.4.1.37950.1.1.5.10.13.4.4
		-- 1.3.6.1.4.1.37950.1.1.5.10.13.4.4
		alarmControlThldTable OBJECT-TYPE
			SYNTAX SEQUENCE OF AlarmControlThldEntry
			MAX-ACCESS not-accessible
			STATUS current
			DESCRIPTION
				"Description."
			::= { alarmCtrl 4 }

		
--          1.3.6.1.4.1.37950.1.1.5.10.13.4.4.1
-- 1.3.6.1.4.1.37950.1.1.5.10.13.4.4.1
-- 1.3.6.1.4.1.37950.1.1.5.10.13.4.4.1
-- 1.3.6.1.4.1.37950.1.1.5.10.13.4.4.1
-- 1.3.6.1.4.1.37950.1.1.5.10.13.4.4.1
-- 1.3.6.1.4.1.37950.1.1.5.10.13.4.4.1
-- 1.3.6.1.4.1.37950.1.1.5.10.13.4.4.1
-- 1.3.6.1.4.1.37950.1.1.5.10.13.4.4.1
-- 1.3.6.1.4.1.37950.1.1.5.10.13.4.4.1
		-- 1.3.6.1.4.1.37950.1.1.5.10.13.4.4.1
		alarmControlThldEntry OBJECT-TYPE
			SYNTAX AlarmControlThldEntry
			MAX-ACCESS not-accessible
			STATUS current
			DESCRIPTION
				"Description."
			INDEX { alarmCtrlThldId }
			::= { alarmControlThldTable 1 }

		
		AlarmControlThldEntry ::=
			SEQUENCE { 
				alarmCtrlThldId
					Integer32,
				alarmCtrlThldType
					INTEGER,
				alarmPrintThldStatus
					INTEGER,
				alarmRecordThldStatus
					INTEGER,
				alarmTrapThldStatus
					INTEGER,
				alarmRemoteThldStatus
					INTEGER,
				alarmCtrlThldAlarm
					OCTET STRING,
				alarmCtrlThldClear
					OCTET STRING
			 }

--          1.3.6.1.4.1.37950.1.1.5.10.13.4.4.1.1
-- 1.3.6.1.4.1.37950.1.1.5.10.13.4.4.1.1
-- 1.3.6.1.4.1.37950.1.1.5.10.13.4.4.1.1
-- 1.3.6.1.4.1.37950.1.1.5.10.13.4.4.1.1
-- 1.3.6.1.4.1.37950.1.1.5.10.13.4.4.1.1
-- 1.3.6.1.4.1.37950.1.1.5.10.13.4.4.1.1
-- 1.3.6.1.4.1.37950.1.1.5.10.13.4.4.1.1
-- 1.3.6.1.4.1.37950.1.1.5.10.13.4.4.1.1
-- 1.3.6.1.4.1.37950.1.1.5.10.13.4.4.1.1
		-- 1.3.6.1.4.1.37950.1.1.5.10.13.4.4.1.1
		alarmCtrlThldId OBJECT-TYPE
			SYNTAX Integer32
			MAX-ACCESS read-only
			STATUS current
			DESCRIPTION
				"Description."
			::= { alarmControlThldEntry 1 }

		
--          1.3.6.1.4.1.37950.1.1.5.10.13.4.4.1.2
-- 1.3.6.1.4.1.37950.1.1.5.10.13.4.4.1.2
-- 1.3.6.1.4.1.37950.1.1.5.10.13.4.4.1.2
-- 1.3.6.1.4.1.37950.1.1.5.10.13.4.4.1.2
-- 1.3.6.1.4.1.37950.1.1.5.10.13.4.4.1.2
-- 1.3.6.1.4.1.37950.1.1.5.10.13.4.4.1.2
-- 1.3.6.1.4.1.37950.1.1.5.10.13.4.4.1.2
-- 1.3.6.1.4.1.37950.1.1.5.10.13.4.4.1.2
-- 1.3.6.1.4.1.37950.1.1.5.10.13.4.4.1.2
		-- 1.3.6.1.4.1.37950.1.1.5.10.13.4.4.1.2
		alarmCtrlThldType OBJECT-TYPE
			SYNTAX INTEGER
				{
				temp-high(1),
				temp-low(2),
				cpu-usage-high(3),
				mem-usage-high(4)
				}
			MAX-ACCESS read-only
			STATUS current
			DESCRIPTION
				"Description."
			::= { alarmControlThldEntry 2 }

		
--          1.3.6.1.4.1.37950.1.1.5.10.13.4.4.1.3
-- 1.3.6.1.4.1.37950.1.1.5.10.13.4.4.1.3
-- 1.3.6.1.4.1.37950.1.1.5.10.13.4.4.1.3
-- 1.3.6.1.4.1.37950.1.1.5.10.13.4.4.1.3
-- 1.3.6.1.4.1.37950.1.1.5.10.13.4.4.1.3
-- 1.3.6.1.4.1.37950.1.1.5.10.13.4.4.1.3
-- 1.3.6.1.4.1.37950.1.1.5.10.13.4.4.1.3
-- 1.3.6.1.4.1.37950.1.1.5.10.13.4.4.1.3
-- 1.3.6.1.4.1.37950.1.1.5.10.13.4.4.1.3
		-- 1.3.6.1.4.1.37950.1.1.5.10.13.4.4.1.3
		alarmPrintThldStatus OBJECT-TYPE
			SYNTAX INTEGER
				{
				disable(0),
				enable(1)
				}
			MAX-ACCESS read-write
			STATUS current
			DESCRIPTION
				"Description."
			::= { alarmControlThldEntry 3 }

		
--          1.3.6.1.4.1.37950.1.1.5.10.13.4.4.1.4
-- 1.3.6.1.4.1.37950.1.1.5.10.13.4.4.1.4
-- 1.3.6.1.4.1.37950.1.1.5.10.13.4.4.1.4
-- 1.3.6.1.4.1.37950.1.1.5.10.13.4.4.1.4
-- 1.3.6.1.4.1.37950.1.1.5.10.13.4.4.1.4
-- 1.3.6.1.4.1.37950.1.1.5.10.13.4.4.1.4
-- 1.3.6.1.4.1.37950.1.1.5.10.13.4.4.1.4
-- 1.3.6.1.4.1.37950.1.1.5.10.13.4.4.1.4
-- 1.3.6.1.4.1.37950.1.1.5.10.13.4.4.1.4
		-- 1.3.6.1.4.1.37950.1.1.5.10.13.4.4.1.4
		alarmRecordThldStatus OBJECT-TYPE
			SYNTAX INTEGER
				{
				disable(0),
				enable(1)
				}
			MAX-ACCESS read-write
			STATUS current
			DESCRIPTION
				"Description."
			::= { alarmControlThldEntry 4 }

		
--          1.3.6.1.4.1.37950.1.1.5.10.13.4.4.1.5
-- 1.3.6.1.4.1.37950.1.1.5.10.13.4.4.1.5
-- 1.3.6.1.4.1.37950.1.1.5.10.13.4.4.1.5
-- 1.3.6.1.4.1.37950.1.1.5.10.13.4.4.1.5
-- 1.3.6.1.4.1.37950.1.1.5.10.13.4.4.1.5
-- 1.3.6.1.4.1.37950.1.1.5.10.13.4.4.1.5
-- 1.3.6.1.4.1.37950.1.1.5.10.13.4.4.1.5
-- 1.3.6.1.4.1.37950.1.1.5.10.13.4.4.1.5
-- 1.3.6.1.4.1.37950.1.1.5.10.13.4.4.1.5
		-- 1.3.6.1.4.1.37950.1.1.5.10.13.4.4.1.5
		alarmTrapThldStatus OBJECT-TYPE
			SYNTAX INTEGER
				{
				disable(0),
				enable(1)
				}
			MAX-ACCESS read-write
			STATUS current
			DESCRIPTION
				"Description."
			::= { alarmControlThldEntry 5 }

		
--          1.3.6.1.4.1.37950.1.1.5.10.13.4.4.1.6
-- 1.3.6.1.4.1.37950.1.1.5.10.13.4.4.1.6
-- 1.3.6.1.4.1.37950.1.1.5.10.13.4.4.1.6
-- 1.3.6.1.4.1.37950.1.1.5.10.13.4.4.1.6
-- 1.3.6.1.4.1.37950.1.1.5.10.13.4.4.1.6
-- 1.3.6.1.4.1.37950.1.1.5.10.13.4.4.1.6
-- 1.3.6.1.4.1.37950.1.1.5.10.13.4.4.1.6
-- 1.3.6.1.4.1.37950.1.1.5.10.13.4.4.1.6
-- 1.3.6.1.4.1.37950.1.1.5.10.13.4.4.1.6
		-- 1.3.6.1.4.1.37950.1.1.5.10.13.4.4.1.6
		alarmRemoteThldStatus OBJECT-TYPE
			SYNTAX INTEGER
				{
				disable(0),
				enable(1)
				}
			MAX-ACCESS read-only
			STATUS current
			DESCRIPTION
				"Description."
			::= { alarmControlThldEntry 6 }

		
--          1.3.6.1.4.1.37950.1.1.5.10.13.4.4.1.7
-- 1.3.6.1.4.1.37950.1.1.5.10.13.4.4.1.7
-- 1.3.6.1.4.1.37950.1.1.5.10.13.4.4.1.7
-- 1.3.6.1.4.1.37950.1.1.5.10.13.4.4.1.7
-- 1.3.6.1.4.1.37950.1.1.5.10.13.4.4.1.7
-- 1.3.6.1.4.1.37950.1.1.5.10.13.4.4.1.7
-- 1.3.6.1.4.1.37950.1.1.5.10.13.4.4.1.7
-- 1.3.6.1.4.1.37950.1.1.5.10.13.4.4.1.7
-- 1.3.6.1.4.1.37950.1.1.5.10.13.4.4.1.7
		-- 1.3.6.1.4.1.37950.1.1.5.10.13.4.4.1.7
		alarmCtrlThldAlarm OBJECT-TYPE
			SYNTAX OCTET STRING
			MAX-ACCESS read-only
			STATUS current
			DESCRIPTION
				"Description."
			::= { alarmControlThldEntry 7 }

		
--          1.3.6.1.4.1.37950.1.1.5.10.13.4.4.1.8
-- 1.3.6.1.4.1.37950.1.1.5.10.13.4.4.1.8
-- 1.3.6.1.4.1.37950.1.1.5.10.13.4.4.1.8
-- 1.3.6.1.4.1.37950.1.1.5.10.13.4.4.1.8
-- 1.3.6.1.4.1.37950.1.1.5.10.13.4.4.1.8
-- 1.3.6.1.4.1.37950.1.1.5.10.13.4.4.1.8
-- 1.3.6.1.4.1.37950.1.1.5.10.13.4.4.1.8
-- 1.3.6.1.4.1.37950.1.1.5.10.13.4.4.1.8
-- 1.3.6.1.4.1.37950.1.1.5.10.13.4.4.1.8
		-- 1.3.6.1.4.1.37950.1.1.5.10.13.4.4.1.8
		alarmCtrlThldClear OBJECT-TYPE
			SYNTAX OCTET STRING
			MAX-ACCESS read-only
			STATUS current
			DESCRIPTION
				"Description."
			::= { alarmControlThldEntry 8 }

		
--          1.3.6.1.4.1.37950.1.1.5.10.13.5
-- 1.3.6.1.4.1.37950.1.1.5.10.13.5
-- 1.3.6.1.4.1.37950.1.1.5.10.13.5
-- 1.3.6.1.4.1.37950.1.1.5.10.13.5
-- 1.3.6.1.4.1.37950.1.1.5.10.13.5
-- 1.3.6.1.4.1.37950.1.1.5.10.13.5
-- 1.3.6.1.4.1.37950.1.1.5.10.13.5
-- 1.3.6.1.4.1.37950.1.1.5.10.13.5
-- 1.3.6.1.4.1.37950.1.1.5.10.13.5
		-- 1.3.6.1.4.1.37950.1.1.5.10.13.5
		alarmOID OBJECT IDENTIFIER ::= { v1600dAlarm 5 }

		
--          1.3.6.1.4.1.37950.1.1.5.10.13.5.1
-- 1.3.6.1.4.1.37950.1.1.5.10.13.5.1
-- 1.3.6.1.4.1.37950.1.1.5.10.13.5.1
-- 1.3.6.1.4.1.37950.1.1.5.10.13.5.1
-- 1.3.6.1.4.1.37950.1.1.5.10.13.5.1
-- 1.3.6.1.4.1.37950.1.1.5.10.13.5.1
-- 1.3.6.1.4.1.37950.1.1.5.10.13.5.1
-- 1.3.6.1.4.1.37950.1.1.5.10.13.5.1
-- 1.3.6.1.4.1.37950.1.1.5.10.13.5.1
		-- 1.3.6.1.4.1.37950.1.1.5.10.13.5.1
		tempHigh OBJECT-TYPE
			SYNTAX Integer32
			MAX-ACCESS read-write
			STATUS current
			DESCRIPTION
				"Description."
			::= { alarmOID 1 }

		
--          1.3.6.1.4.1.37950.1.1.5.10.13.5.2
-- 1.3.6.1.4.1.37950.1.1.5.10.13.5.2
-- 1.3.6.1.4.1.37950.1.1.5.10.13.5.2
-- 1.3.6.1.4.1.37950.1.1.5.10.13.5.2
-- 1.3.6.1.4.1.37950.1.1.5.10.13.5.2
-- 1.3.6.1.4.1.37950.1.1.5.10.13.5.2
-- 1.3.6.1.4.1.37950.1.1.5.10.13.5.2
-- 1.3.6.1.4.1.37950.1.1.5.10.13.5.2
-- 1.3.6.1.4.1.37950.1.1.5.10.13.5.2
		-- 1.3.6.1.4.1.37950.1.1.5.10.13.5.2
		tempLow OBJECT-TYPE
			SYNTAX Integer32
			MAX-ACCESS read-write
			STATUS current
			DESCRIPTION
				"Description."
			::= { alarmOID 2 }

		
--          1.3.6.1.4.1.37950.1.1.5.10.13.5.3
-- 1.3.6.1.4.1.37950.1.1.5.10.13.5.3
-- 1.3.6.1.4.1.37950.1.1.5.10.13.5.3
-- 1.3.6.1.4.1.37950.1.1.5.10.13.5.3
-- 1.3.6.1.4.1.37950.1.1.5.10.13.5.3
-- 1.3.6.1.4.1.37950.1.1.5.10.13.5.3
-- 1.3.6.1.4.1.37950.1.1.5.10.13.5.3
-- 1.3.6.1.4.1.37950.1.1.5.10.13.5.3
-- 1.3.6.1.4.1.37950.1.1.5.10.13.5.3
		-- 1.3.6.1.4.1.37950.1.1.5.10.13.5.3
		cpuUsageHigh OBJECT-TYPE
			SYNTAX Integer32
			MAX-ACCESS read-write
			STATUS current
			DESCRIPTION
				"Description."
			::= { alarmOID 3 }

		
--          1.3.6.1.4.1.37950.1.1.5.10.13.5.4
-- 1.3.6.1.4.1.37950.1.1.5.10.13.5.4
-- 1.3.6.1.4.1.37950.1.1.5.10.13.5.4
-- 1.3.6.1.4.1.37950.1.1.5.10.13.5.4
-- 1.3.6.1.4.1.37950.1.1.5.10.13.5.4
-- 1.3.6.1.4.1.37950.1.1.5.10.13.5.4
-- 1.3.6.1.4.1.37950.1.1.5.10.13.5.4
-- 1.3.6.1.4.1.37950.1.1.5.10.13.5.4
-- 1.3.6.1.4.1.37950.1.1.5.10.13.5.4
		-- 1.3.6.1.4.1.37950.1.1.5.10.13.5.4
		memUsageHigh OBJECT-TYPE
			SYNTAX Integer32
			MAX-ACCESS read-write
			STATUS current
			DESCRIPTION
				"Description."
			::= { alarmOID 4 }

		
--          1.3.6.1.4.1.37950.1.1.5.10.13.5.5
-- 1.3.6.1.4.1.37950.1.1.5.10.13.5.5
-- 1.3.6.1.4.1.37950.1.1.5.10.13.5.5
-- 1.3.6.1.4.1.37950.1.1.5.10.13.5.5
-- 1.3.6.1.4.1.37950.1.1.5.10.13.5.5
-- 1.3.6.1.4.1.37950.1.1.5.10.13.5.5
-- 1.3.6.1.4.1.37950.1.1.5.10.13.5.5
-- 1.3.6.1.4.1.37950.1.1.5.10.13.5.5
-- 1.3.6.1.4.1.37950.1.1.5.10.13.5.5
		-- 1.3.6.1.4.1.37950.1.1.5.10.13.5.5
		fan OBJECT-TYPE
			SYNTAX Integer32
			MAX-ACCESS read-write
			STATUS current
			DESCRIPTION
				"Description."
			::= { alarmOID 5 }

		
--          1.3.6.1.4.1.37950.1.1.5.10.13.5.6
-- 1.3.6.1.4.1.37950.1.1.5.10.13.5.6
-- 1.3.6.1.4.1.37950.1.1.5.10.13.5.6
-- 1.3.6.1.4.1.37950.1.1.5.10.13.5.6
-- 1.3.6.1.4.1.37950.1.1.5.10.13.5.6
-- 1.3.6.1.4.1.37950.1.1.5.10.13.5.6
-- 1.3.6.1.4.1.37950.1.1.5.10.13.5.6
-- 1.3.6.1.4.1.37950.1.1.5.10.13.5.6
-- 1.3.6.1.4.1.37950.1.1.5.10.13.5.6
		-- 1.3.6.1.4.1.37950.1.1.5.10.13.5.6
		downloadFileFailed OBJECT-TYPE
			SYNTAX Integer32
			MAX-ACCESS read-write
			STATUS current
			DESCRIPTION
				"Description."
			::= { alarmOID 6 }

		
--          1.3.6.1.4.1.37950.1.1.5.10.13.5.7
-- 1.3.6.1.4.1.37950.1.1.5.10.13.5.7
-- 1.3.6.1.4.1.37950.1.1.5.10.13.5.7
-- 1.3.6.1.4.1.37950.1.1.5.10.13.5.7
-- 1.3.6.1.4.1.37950.1.1.5.10.13.5.7
-- 1.3.6.1.4.1.37950.1.1.5.10.13.5.7
-- 1.3.6.1.4.1.37950.1.1.5.10.13.5.7
-- 1.3.6.1.4.1.37950.1.1.5.10.13.5.7
-- 1.3.6.1.4.1.37950.1.1.5.10.13.5.7
		-- 1.3.6.1.4.1.37950.1.1.5.10.13.5.7
		uploadFileFailed OBJECT-TYPE
			SYNTAX Integer32
			MAX-ACCESS read-write
			STATUS current
			DESCRIPTION
				"Description."
			::= { alarmOID 7 }

		
--          1.3.6.1.4.1.37950.1.1.5.10.13.5.8
-- 1.3.6.1.4.1.37950.1.1.5.10.13.5.8
-- 1.3.6.1.4.1.37950.1.1.5.10.13.5.8
-- 1.3.6.1.4.1.37950.1.1.5.10.13.5.8
-- 1.3.6.1.4.1.37950.1.1.5.10.13.5.8
-- 1.3.6.1.4.1.37950.1.1.5.10.13.5.8
-- 1.3.6.1.4.1.37950.1.1.5.10.13.5.8
-- 1.3.6.1.4.1.37950.1.1.5.10.13.5.8
-- 1.3.6.1.4.1.37950.1.1.5.10.13.5.8
		-- 1.3.6.1.4.1.37950.1.1.5.10.13.5.8
		upgradeFileFailled OBJECT-TYPE
			SYNTAX Integer32
			MAX-ACCESS read-write
			STATUS current
			DESCRIPTION
				"Description."
			::= { alarmOID 8 }

		
--          1.3.6.1.4.1.37950.1.1.5.10.13.5.9
-- 1.3.6.1.4.1.37950.1.1.5.10.13.5.9
-- 1.3.6.1.4.1.37950.1.1.5.10.13.5.9
-- 1.3.6.1.4.1.37950.1.1.5.10.13.5.9
-- 1.3.6.1.4.1.37950.1.1.5.10.13.5.9
-- 1.3.6.1.4.1.37950.1.1.5.10.13.5.9
-- 1.3.6.1.4.1.37950.1.1.5.10.13.5.9
-- 1.3.6.1.4.1.37950.1.1.5.10.13.5.9
-- 1.3.6.1.4.1.37950.1.1.5.10.13.5.9
		-- 1.3.6.1.4.1.37950.1.1.5.10.13.5.9
		portUpdown OBJECT-TYPE
			SYNTAX Integer32
			MAX-ACCESS read-write
			STATUS current
			DESCRIPTION
				"Description."
			::= { alarmOID 9 }

		
--          1.3.6.1.4.1.37950.1.1.5.10.13.5.10
-- 1.3.6.1.4.1.37950.1.1.5.10.13.5.10
-- 1.3.6.1.4.1.37950.1.1.5.10.13.5.10
-- 1.3.6.1.4.1.37950.1.1.5.10.13.5.10
-- 1.3.6.1.4.1.37950.1.1.5.10.13.5.10
-- 1.3.6.1.4.1.37950.1.1.5.10.13.5.10
-- 1.3.6.1.4.1.37950.1.1.5.10.13.5.10
-- 1.3.6.1.4.1.37950.1.1.5.10.13.5.10
-- 1.3.6.1.4.1.37950.1.1.5.10.13.5.10
		-- 1.3.6.1.4.1.37950.1.1.5.10.13.5.10
		portLoopback OBJECT-TYPE
			SYNTAX Integer32
			MAX-ACCESS read-write
			STATUS current
			DESCRIPTION
				"Description."
			::= { alarmOID 10 }

		
--          1.3.6.1.4.1.37950.1.1.5.10.13.5.11
-- 1.3.6.1.4.1.37950.1.1.5.10.13.5.11
-- 1.3.6.1.4.1.37950.1.1.5.10.13.5.11
-- 1.3.6.1.4.1.37950.1.1.5.10.13.5.11
-- 1.3.6.1.4.1.37950.1.1.5.10.13.5.11
-- 1.3.6.1.4.1.37950.1.1.5.10.13.5.11
-- 1.3.6.1.4.1.37950.1.1.5.10.13.5.11
-- 1.3.6.1.4.1.37950.1.1.5.10.13.5.11
-- 1.3.6.1.4.1.37950.1.1.5.10.13.5.11
		-- 1.3.6.1.4.1.37950.1.1.5.10.13.5.11
		ponDeregister OBJECT-TYPE
			SYNTAX Integer32
			MAX-ACCESS read-write
			STATUS current
			DESCRIPTION
				"Description."
			::= { alarmOID 11 }

		
--          1.3.6.1.4.1.37950.1.1.5.10.13.5.12
-- 1.3.6.1.4.1.37950.1.1.5.10.13.5.12
-- 1.3.6.1.4.1.37950.1.1.5.10.13.5.12
-- 1.3.6.1.4.1.37950.1.1.5.10.13.5.12
-- 1.3.6.1.4.1.37950.1.1.5.10.13.5.12
-- 1.3.6.1.4.1.37950.1.1.5.10.13.5.12
-- 1.3.6.1.4.1.37950.1.1.5.10.13.5.12
-- 1.3.6.1.4.1.37950.1.1.5.10.13.5.12
-- 1.3.6.1.4.1.37950.1.1.5.10.13.5.12
		-- 1.3.6.1.4.1.37950.1.1.5.10.13.5.12
		ponRegisterFailed OBJECT-TYPE
			SYNTAX Integer32
			MAX-ACCESS read-write
			STATUS current
			DESCRIPTION
				"Description."
			::= { alarmOID 12 }

		
--          1.3.6.1.4.1.37950.1.1.5.10.13.5.13
-- 1.3.6.1.4.1.37950.1.1.5.10.13.5.13
-- 1.3.6.1.4.1.37950.1.1.5.10.13.5.13
-- 1.3.6.1.4.1.37950.1.1.5.10.13.5.13
-- 1.3.6.1.4.1.37950.1.1.5.10.13.5.13
-- 1.3.6.1.4.1.37950.1.1.5.10.13.5.13
-- 1.3.6.1.4.1.37950.1.1.5.10.13.5.13
-- 1.3.6.1.4.1.37950.1.1.5.10.13.5.13
-- 1.3.6.1.4.1.37950.1.1.5.10.13.5.13
		-- 1.3.6.1.4.1.37950.1.1.5.10.13.5.13
		ponDisable OBJECT-TYPE
			SYNTAX Integer32
			MAX-ACCESS read-write
			STATUS current
			DESCRIPTION
				"Description."
			::= { alarmOID 13 }

		
--          1.3.6.1.4.1.37950.1.1.5.10.13.5.14
-- 1.3.6.1.4.1.37950.1.1.5.10.13.5.14
-- 1.3.6.1.4.1.37950.1.1.5.10.13.5.14
-- 1.3.6.1.4.1.37950.1.1.5.10.13.5.14
-- 1.3.6.1.4.1.37950.1.1.5.10.13.5.14
-- 1.3.6.1.4.1.37950.1.1.5.10.13.5.14
-- 1.3.6.1.4.1.37950.1.1.5.10.13.5.14
-- 1.3.6.1.4.1.37950.1.1.5.10.13.5.14
-- 1.3.6.1.4.1.37950.1.1.5.10.13.5.14
		-- 1.3.6.1.4.1.37950.1.1.5.10.13.5.14
		ponTxPowerHigh OBJECT-TYPE
			SYNTAX Integer32
			MAX-ACCESS read-write
			STATUS current
			DESCRIPTION
				"Description."
			::= { alarmOID 14 }

		
--          1.3.6.1.4.1.37950.1.1.5.10.13.5.15
-- 1.3.6.1.4.1.37950.1.1.5.10.13.5.15
-- 1.3.6.1.4.1.37950.1.1.5.10.13.5.15
-- 1.3.6.1.4.1.37950.1.1.5.10.13.5.15
-- 1.3.6.1.4.1.37950.1.1.5.10.13.5.15
-- 1.3.6.1.4.1.37950.1.1.5.10.13.5.15
-- 1.3.6.1.4.1.37950.1.1.5.10.13.5.15
-- 1.3.6.1.4.1.37950.1.1.5.10.13.5.15
-- 1.3.6.1.4.1.37950.1.1.5.10.13.5.15
		-- 1.3.6.1.4.1.37950.1.1.5.10.13.5.15
		ponTxPowerLow OBJECT-TYPE
			SYNTAX Integer32
			MAX-ACCESS read-write
			STATUS current
			DESCRIPTION
				"Description."
			::= { alarmOID 15 }

		
--          1.3.6.1.4.1.37950.1.1.5.10.13.5.16
-- 1.3.6.1.4.1.37950.1.1.5.10.13.5.16
-- 1.3.6.1.4.1.37950.1.1.5.10.13.5.16
-- 1.3.6.1.4.1.37950.1.1.5.10.13.5.16
-- 1.3.6.1.4.1.37950.1.1.5.10.13.5.16
-- 1.3.6.1.4.1.37950.1.1.5.10.13.5.16
-- 1.3.6.1.4.1.37950.1.1.5.10.13.5.16
-- 1.3.6.1.4.1.37950.1.1.5.10.13.5.16
-- 1.3.6.1.4.1.37950.1.1.5.10.13.5.16
		-- 1.3.6.1.4.1.37950.1.1.5.10.13.5.16
		ponTxBisaHigh OBJECT-TYPE
			SYNTAX Integer32
			MAX-ACCESS read-write
			STATUS current
			DESCRIPTION
				"Description."
			::= { alarmOID 16 }

		
--          1.3.6.1.4.1.37950.1.1.5.10.13.5.17
-- 1.3.6.1.4.1.37950.1.1.5.10.13.5.17
-- 1.3.6.1.4.1.37950.1.1.5.10.13.5.17
-- 1.3.6.1.4.1.37950.1.1.5.10.13.5.17
-- 1.3.6.1.4.1.37950.1.1.5.10.13.5.17
-- 1.3.6.1.4.1.37950.1.1.5.10.13.5.17
-- 1.3.6.1.4.1.37950.1.1.5.10.13.5.17
-- 1.3.6.1.4.1.37950.1.1.5.10.13.5.17
-- 1.3.6.1.4.1.37950.1.1.5.10.13.5.17
		-- 1.3.6.1.4.1.37950.1.1.5.10.13.5.17
		ponTxbiasLow OBJECT-TYPE
			SYNTAX Integer32
			MAX-ACCESS read-write
			STATUS current
			DESCRIPTION
				"Description."
			::= { alarmOID 17 }

		
--          1.3.6.1.4.1.37950.1.1.5.10.13.5.18
-- 1.3.6.1.4.1.37950.1.1.5.10.13.5.18
-- 1.3.6.1.4.1.37950.1.1.5.10.13.5.18
-- 1.3.6.1.4.1.37950.1.1.5.10.13.5.18
-- 1.3.6.1.4.1.37950.1.1.5.10.13.5.18
-- 1.3.6.1.4.1.37950.1.1.5.10.13.5.18
-- 1.3.6.1.4.1.37950.1.1.5.10.13.5.18
-- 1.3.6.1.4.1.37950.1.1.5.10.13.5.18
-- 1.3.6.1.4.1.37950.1.1.5.10.13.5.18
		-- 1.3.6.1.4.1.37950.1.1.5.10.13.5.18
		ponVccHigh OBJECT-TYPE
			SYNTAX Integer32
			MAX-ACCESS read-write
			STATUS current
			DESCRIPTION
				"Description."
			::= { alarmOID 18 }

		
--          1.3.6.1.4.1.37950.1.1.5.10.13.5.19
-- 1.3.6.1.4.1.37950.1.1.5.10.13.5.19
-- 1.3.6.1.4.1.37950.1.1.5.10.13.5.19
-- 1.3.6.1.4.1.37950.1.1.5.10.13.5.19
-- 1.3.6.1.4.1.37950.1.1.5.10.13.5.19
-- 1.3.6.1.4.1.37950.1.1.5.10.13.5.19
-- 1.3.6.1.4.1.37950.1.1.5.10.13.5.19
-- 1.3.6.1.4.1.37950.1.1.5.10.13.5.19
-- 1.3.6.1.4.1.37950.1.1.5.10.13.5.19
		-- 1.3.6.1.4.1.37950.1.1.5.10.13.5.19
		ponVccLow OBJECT-TYPE
			SYNTAX Integer32
			MAX-ACCESS read-write
			STATUS current
			DESCRIPTION
				"Description."
			::= { alarmOID 19 }

		
--          1.3.6.1.4.1.37950.1.1.5.10.13.5.20
-- 1.3.6.1.4.1.37950.1.1.5.10.13.5.20
-- 1.3.6.1.4.1.37950.1.1.5.10.13.5.20
-- 1.3.6.1.4.1.37950.1.1.5.10.13.5.20
-- 1.3.6.1.4.1.37950.1.1.5.10.13.5.20
-- 1.3.6.1.4.1.37950.1.1.5.10.13.5.20
-- 1.3.6.1.4.1.37950.1.1.5.10.13.5.20
-- 1.3.6.1.4.1.37950.1.1.5.10.13.5.20
-- 1.3.6.1.4.1.37950.1.1.5.10.13.5.20
		-- 1.3.6.1.4.1.37950.1.1.5.10.13.5.20
		ponTempHigh OBJECT-TYPE
			SYNTAX Integer32
			MAX-ACCESS read-write
			STATUS current
			DESCRIPTION
				"Description."
			::= { alarmOID 20 }

		
--          1.3.6.1.4.1.37950.1.1.5.10.13.5.21
-- 1.3.6.1.4.1.37950.1.1.5.10.13.5.21
-- 1.3.6.1.4.1.37950.1.1.5.10.13.5.21
-- 1.3.6.1.4.1.37950.1.1.5.10.13.5.21
-- 1.3.6.1.4.1.37950.1.1.5.10.13.5.21
-- 1.3.6.1.4.1.37950.1.1.5.10.13.5.21
-- 1.3.6.1.4.1.37950.1.1.5.10.13.5.21
-- 1.3.6.1.4.1.37950.1.1.5.10.13.5.21
-- 1.3.6.1.4.1.37950.1.1.5.10.13.5.21
		-- 1.3.6.1.4.1.37950.1.1.5.10.13.5.21
		ponTempLow OBJECT-TYPE
			SYNTAX Integer32
			MAX-ACCESS read-write
			STATUS current
			DESCRIPTION
				"Description."
			::= { alarmOID 21 }

		
--          1.3.6.1.4.1.37950.1.1.5.10.13.5.22
-- 1.3.6.1.4.1.37950.1.1.5.10.13.5.22
-- 1.3.6.1.4.1.37950.1.1.5.10.13.5.22
-- 1.3.6.1.4.1.37950.1.1.5.10.13.5.22
-- 1.3.6.1.4.1.37950.1.1.5.10.13.5.22
-- 1.3.6.1.4.1.37950.1.1.5.10.13.5.22
-- 1.3.6.1.4.1.37950.1.1.5.10.13.5.22
-- 1.3.6.1.4.1.37950.1.1.5.10.13.5.22
-- 1.3.6.1.4.1.37950.1.1.5.10.13.5.22
		-- 1.3.6.1.4.1.37950.1.1.5.10.13.5.22
		ponLos OBJECT-TYPE
			SYNTAX Integer32
			MAX-ACCESS read-write
			STATUS current
			DESCRIPTION
				"Description."
			::= { alarmOID 22 }

		
--          1.3.6.1.4.1.37950.1.1.5.10.13.5.23
-- 1.3.6.1.4.1.37950.1.1.5.10.13.5.23
-- 1.3.6.1.4.1.37950.1.1.5.10.13.5.23
-- 1.3.6.1.4.1.37950.1.1.5.10.13.5.23
-- 1.3.6.1.4.1.37950.1.1.5.10.13.5.23
-- 1.3.6.1.4.1.37950.1.1.5.10.13.5.23
-- 1.3.6.1.4.1.37950.1.1.5.10.13.5.23
-- 1.3.6.1.4.1.37950.1.1.5.10.13.5.23
-- 1.3.6.1.4.1.37950.1.1.5.10.13.5.23
		-- 1.3.6.1.4.1.37950.1.1.5.10.13.5.23
		onuDeregister OBJECT-TYPE
			SYNTAX Integer32
			MAX-ACCESS read-write
			STATUS current
			DESCRIPTION
				"Description."
			::= { alarmOID 23 }

		
--          1.3.6.1.4.1.37950.1.1.5.10.13.5.24
-- 1.3.6.1.4.1.37950.1.1.5.10.13.5.24
-- 1.3.6.1.4.1.37950.1.1.5.10.13.5.24
-- 1.3.6.1.4.1.37950.1.1.5.10.13.5.24
-- 1.3.6.1.4.1.37950.1.1.5.10.13.5.24
-- 1.3.6.1.4.1.37950.1.1.5.10.13.5.24
-- 1.3.6.1.4.1.37950.1.1.5.10.13.5.24
-- 1.3.6.1.4.1.37950.1.1.5.10.13.5.24
-- 1.3.6.1.4.1.37950.1.1.5.10.13.5.24
		-- 1.3.6.1.4.1.37950.1.1.5.10.13.5.24
		onuLinkLost OBJECT-TYPE
			SYNTAX Integer32
			MAX-ACCESS read-write
			STATUS current
			DESCRIPTION
				"Description."
			::= { alarmOID 24 }

		
--          1.3.6.1.4.1.37950.1.1.5.10.13.5.25
-- 1.3.6.1.4.1.37950.1.1.5.10.13.5.25
-- 1.3.6.1.4.1.37950.1.1.5.10.13.5.25
-- 1.3.6.1.4.1.37950.1.1.5.10.13.5.25
-- 1.3.6.1.4.1.37950.1.1.5.10.13.5.25
-- 1.3.6.1.4.1.37950.1.1.5.10.13.5.25
-- 1.3.6.1.4.1.37950.1.1.5.10.13.5.25
-- 1.3.6.1.4.1.37950.1.1.5.10.13.5.25
-- 1.3.6.1.4.1.37950.1.1.5.10.13.5.25
		-- 1.3.6.1.4.1.37950.1.1.5.10.13.5.25
		onuIllegalRegister OBJECT-TYPE
			SYNTAX Integer32
			MAX-ACCESS read-write
			STATUS current
			DESCRIPTION
				"Description."
			::= { alarmOID 25 }

		
--          1.3.6.1.4.1.37950.1.1.5.10.13.5.26
-- 1.3.6.1.4.1.37950.1.1.5.10.13.5.26
-- 1.3.6.1.4.1.37950.1.1.5.10.13.5.26
-- 1.3.6.1.4.1.37950.1.1.5.10.13.5.26
-- 1.3.6.1.4.1.37950.1.1.5.10.13.5.26
-- 1.3.6.1.4.1.37950.1.1.5.10.13.5.26
-- 1.3.6.1.4.1.37950.1.1.5.10.13.5.26
-- 1.3.6.1.4.1.37950.1.1.5.10.13.5.26
-- 1.3.6.1.4.1.37950.1.1.5.10.13.5.26
		-- 1.3.6.1.4.1.37950.1.1.5.10.13.5.26
		onuAuthFailed OBJECT-TYPE
			SYNTAX Integer32
			MAX-ACCESS read-write
			STATUS current
			DESCRIPTION
				"Description."
			::= { alarmOID 26 }

		
--          1.3.6.1.4.1.37950.1.1.5.10.13.5.27
-- 1.3.6.1.4.1.37950.1.1.5.10.13.5.27
-- 1.3.6.1.4.1.37950.1.1.5.10.13.5.27
-- 1.3.6.1.4.1.37950.1.1.5.10.13.5.27
-- 1.3.6.1.4.1.37950.1.1.5.10.13.5.27
-- 1.3.6.1.4.1.37950.1.1.5.10.13.5.27
-- 1.3.6.1.4.1.37950.1.1.5.10.13.5.27
-- 1.3.6.1.4.1.37950.1.1.5.10.13.5.27
-- 1.3.6.1.4.1.37950.1.1.5.10.13.5.27
		-- 1.3.6.1.4.1.37950.1.1.5.10.13.5.27
		onuMacConflict OBJECT-TYPE
			SYNTAX Integer32
			MAX-ACCESS read-write
			STATUS current
			DESCRIPTION
				"Description."
			::= { alarmOID 27 }

		
--          1.3.6.1.4.1.37950.1.1.5.10.13.5.28
-- 1.3.6.1.4.1.37950.1.1.5.10.13.5.28
-- 1.3.6.1.4.1.37950.1.1.5.10.13.5.28
-- 1.3.6.1.4.1.37950.1.1.5.10.13.5.28
-- 1.3.6.1.4.1.37950.1.1.5.10.13.5.28
-- 1.3.6.1.4.1.37950.1.1.5.10.13.5.28
-- 1.3.6.1.4.1.37950.1.1.5.10.13.5.28
-- 1.3.6.1.4.1.37950.1.1.5.10.13.5.28
-- 1.3.6.1.4.1.37950.1.1.5.10.13.5.28
		-- 1.3.6.1.4.1.37950.1.1.5.10.13.5.28
		onuLoidConflict OBJECT-TYPE
			SYNTAX Integer32
			MAX-ACCESS read-write
			STATUS current
			DESCRIPTION
				"Description."
			::= { alarmOID 28 }

		
--          1.3.6.1.4.1.37950.1.1.5.10.13.5.29
-- 1.3.6.1.4.1.37950.1.1.5.10.13.5.29
-- 1.3.6.1.4.1.37950.1.1.5.10.13.5.29
-- 1.3.6.1.4.1.37950.1.1.5.10.13.5.29
-- 1.3.6.1.4.1.37950.1.1.5.10.13.5.29
-- 1.3.6.1.4.1.37950.1.1.5.10.13.5.29
-- 1.3.6.1.4.1.37950.1.1.5.10.13.5.29
-- 1.3.6.1.4.1.37950.1.1.5.10.13.5.29
-- 1.3.6.1.4.1.37950.1.1.5.10.13.5.29
		-- 1.3.6.1.4.1.37950.1.1.5.10.13.5.29
		onuCriticalEvent OBJECT-TYPE
			SYNTAX Integer32
			MAX-ACCESS read-write
			STATUS current
			DESCRIPTION
				"Description."
			::= { alarmOID 29 }

		
--          1.3.6.1.4.1.37950.1.1.5.10.13.5.30
-- 1.3.6.1.4.1.37950.1.1.5.10.13.5.30
-- 1.3.6.1.4.1.37950.1.1.5.10.13.5.30
-- 1.3.6.1.4.1.37950.1.1.5.10.13.5.30
-- 1.3.6.1.4.1.37950.1.1.5.10.13.5.30
-- 1.3.6.1.4.1.37950.1.1.5.10.13.5.30
-- 1.3.6.1.4.1.37950.1.1.5.10.13.5.30
-- 1.3.6.1.4.1.37950.1.1.5.10.13.5.30
-- 1.3.6.1.4.1.37950.1.1.5.10.13.5.30
		-- 1.3.6.1.4.1.37950.1.1.5.10.13.5.30
		onuDyingGasp OBJECT-TYPE
			SYNTAX Integer32
			MAX-ACCESS read-write
			STATUS current
			DESCRIPTION
				"Description."
			::= { alarmOID 30 }

		
--          1.3.6.1.4.1.37950.1.1.5.10.13.5.31
-- 1.3.6.1.4.1.37950.1.1.5.10.13.5.31
-- 1.3.6.1.4.1.37950.1.1.5.10.13.5.31
-- 1.3.6.1.4.1.37950.1.1.5.10.13.5.31
-- 1.3.6.1.4.1.37950.1.1.5.10.13.5.31
-- 1.3.6.1.4.1.37950.1.1.5.10.13.5.31
-- 1.3.6.1.4.1.37950.1.1.5.10.13.5.31
-- 1.3.6.1.4.1.37950.1.1.5.10.13.5.31
-- 1.3.6.1.4.1.37950.1.1.5.10.13.5.31
		-- 1.3.6.1.4.1.37950.1.1.5.10.13.5.31
		onuLinkFault OBJECT-TYPE
			SYNTAX Integer32
			MAX-ACCESS read-write
			STATUS current
			DESCRIPTION
				"Description."
			::= { alarmOID 31 }

		
--          1.3.6.1.4.1.37950.1.1.5.10.13.5.32
-- 1.3.6.1.4.1.37950.1.1.5.10.13.5.32
-- 1.3.6.1.4.1.37950.1.1.5.10.13.5.32
-- 1.3.6.1.4.1.37950.1.1.5.10.13.5.32
-- 1.3.6.1.4.1.37950.1.1.5.10.13.5.32
-- 1.3.6.1.4.1.37950.1.1.5.10.13.5.32
-- 1.3.6.1.4.1.37950.1.1.5.10.13.5.32
-- 1.3.6.1.4.1.37950.1.1.5.10.13.5.32
-- 1.3.6.1.4.1.37950.1.1.5.10.13.5.32
		-- 1.3.6.1.4.1.37950.1.1.5.10.13.5.32
		onuLinkEvent OBJECT-TYPE
			SYNTAX Integer32
			MAX-ACCESS read-write
			STATUS current
			DESCRIPTION
				"Description."
			::= { alarmOID 32 }

		
--          1.3.6.1.4.1.37950.1.1.5.10.13.5.33
-- 1.3.6.1.4.1.37950.1.1.5.10.13.5.33
-- 1.3.6.1.4.1.37950.1.1.5.10.13.5.33
-- 1.3.6.1.4.1.37950.1.1.5.10.13.5.33
-- 1.3.6.1.4.1.37950.1.1.5.10.13.5.33
-- 1.3.6.1.4.1.37950.1.1.5.10.13.5.33
-- 1.3.6.1.4.1.37950.1.1.5.10.13.5.33
-- 1.3.6.1.4.1.37950.1.1.5.10.13.5.33
-- 1.3.6.1.4.1.37950.1.1.5.10.13.5.33
		-- 1.3.6.1.4.1.37950.1.1.5.10.13.5.33
		onuEventNotific OBJECT-TYPE
			SYNTAX Integer32
			MAX-ACCESS read-write
			STATUS current
			DESCRIPTION
				"Description."
			::= { alarmOID 33 }

		
--          1.3.6.1.4.1.37950.1.1.5.10.13.5.34
-- 1.3.6.1.4.1.37950.1.1.5.10.13.5.34
-- 1.3.6.1.4.1.37950.1.1.5.10.13.5.34
-- 1.3.6.1.4.1.37950.1.1.5.10.13.5.34
-- 1.3.6.1.4.1.37950.1.1.5.10.13.5.34
-- 1.3.6.1.4.1.37950.1.1.5.10.13.5.34
-- 1.3.6.1.4.1.37950.1.1.5.10.13.5.34
-- 1.3.6.1.4.1.37950.1.1.5.10.13.5.34
-- 1.3.6.1.4.1.37950.1.1.5.10.13.5.34
		-- 1.3.6.1.4.1.37950.1.1.5.10.13.5.34
		onuOmLaoDetect OBJECT-TYPE
			SYNTAX Integer32
			MAX-ACCESS read-write
			STATUS current
			DESCRIPTION
				"Description."
			::= { alarmOID 34 }

		
--          1.3.6.1.4.1.37950.1.1.5.10.13.5.35
-- 1.3.6.1.4.1.37950.1.1.5.10.13.5.35
-- 1.3.6.1.4.1.37950.1.1.5.10.13.5.35
-- 1.3.6.1.4.1.37950.1.1.5.10.13.5.35
-- 1.3.6.1.4.1.37950.1.1.5.10.13.5.35
-- 1.3.6.1.4.1.37950.1.1.5.10.13.5.35
-- 1.3.6.1.4.1.37950.1.1.5.10.13.5.35
-- 1.3.6.1.4.1.37950.1.1.5.10.13.5.35
-- 1.3.6.1.4.1.37950.1.1.5.10.13.5.35
		-- 1.3.6.1.4.1.37950.1.1.5.10.13.5.35
		onuOmLolDetect OBJECT-TYPE
			SYNTAX Integer32
			MAX-ACCESS read-write
			STATUS current
			DESCRIPTION
				"Description."
			::= { alarmOID 35 }

		
--          1.3.6.1.4.1.37950.1.1.5.10.13.5.36
-- 1.3.6.1.4.1.37950.1.1.5.10.13.5.36
-- 1.3.6.1.4.1.37950.1.1.5.10.13.5.36
-- 1.3.6.1.4.1.37950.1.1.5.10.13.5.36
-- 1.3.6.1.4.1.37950.1.1.5.10.13.5.36
-- 1.3.6.1.4.1.37950.1.1.5.10.13.5.36
-- 1.3.6.1.4.1.37950.1.1.5.10.13.5.36
-- 1.3.6.1.4.1.37950.1.1.5.10.13.5.36
-- 1.3.6.1.4.1.37950.1.1.5.10.13.5.36
		-- 1.3.6.1.4.1.37950.1.1.5.10.13.5.36
		alarmMax OBJECT-TYPE
			SYNTAX Integer32
			MAX-ACCESS read-write
			STATUS current
			DESCRIPTION
				"Description."
			::= { alarmOID 36 }

		
--          1.3.6.1.4.1.37950.1.1.5.10.13.5.37
-- 1.3.6.1.4.1.37950.1.1.5.10.13.5.37
-- 1.3.6.1.4.1.37950.1.1.5.10.13.5.37
-- 1.3.6.1.4.1.37950.1.1.5.10.13.5.37
-- 1.3.6.1.4.1.37950.1.1.5.10.13.5.37
-- 1.3.6.1.4.1.37950.1.1.5.10.13.5.37
-- 1.3.6.1.4.1.37950.1.1.5.10.13.5.37
-- 1.3.6.1.4.1.37950.1.1.5.10.13.5.37
-- 1.3.6.1.4.1.37950.1.1.5.10.13.5.37
		-- 1.3.6.1.4.1.37950.1.1.5.10.13.5.37
		reset OBJECT-TYPE
			SYNTAX Integer32
			MAX-ACCESS read-write
			STATUS current
			DESCRIPTION
				"Description."
			::= { alarmOID 37 }

		
--          1.3.6.1.4.1.37950.1.1.5.10.13.5.38
-- 1.3.6.1.4.1.37950.1.1.5.10.13.5.38
-- 1.3.6.1.4.1.37950.1.1.5.10.13.5.38
-- 1.3.6.1.4.1.37950.1.1.5.10.13.5.38
-- 1.3.6.1.4.1.37950.1.1.5.10.13.5.38
-- 1.3.6.1.4.1.37950.1.1.5.10.13.5.38
-- 1.3.6.1.4.1.37950.1.1.5.10.13.5.38
-- 1.3.6.1.4.1.37950.1.1.5.10.13.5.38
-- 1.3.6.1.4.1.37950.1.1.5.10.13.5.38
		-- 1.3.6.1.4.1.37950.1.1.5.10.13.5.38
		configSave OBJECT-TYPE
			SYNTAX Integer32
			MAX-ACCESS read-write
			STATUS current
			DESCRIPTION
				"Description."
			::= { alarmOID 38 }

		
--          1.3.6.1.4.1.37950.1.1.5.10.13.5.39
-- 1.3.6.1.4.1.37950.1.1.5.10.13.5.39
-- 1.3.6.1.4.1.37950.1.1.5.10.13.5.39
-- 1.3.6.1.4.1.37950.1.1.5.10.13.5.39
-- 1.3.6.1.4.1.37950.1.1.5.10.13.5.39
-- 1.3.6.1.4.1.37950.1.1.5.10.13.5.39
-- 1.3.6.1.4.1.37950.1.1.5.10.13.5.39
-- 1.3.6.1.4.1.37950.1.1.5.10.13.5.39
-- 1.3.6.1.4.1.37950.1.1.5.10.13.5.39
		-- 1.3.6.1.4.1.37950.1.1.5.10.13.5.39
		configErase OBJECT-TYPE
			SYNTAX Integer32
			MAX-ACCESS read-write
			STATUS current
			DESCRIPTION
				"Description."
			::= { alarmOID 39 }

		
--          1.3.6.1.4.1.37950.1.1.5.10.13.5.40
-- 1.3.6.1.4.1.37950.1.1.5.10.13.5.40
-- 1.3.6.1.4.1.37950.1.1.5.10.13.5.40
-- 1.3.6.1.4.1.37950.1.1.5.10.13.5.40
-- 1.3.6.1.4.1.37950.1.1.5.10.13.5.40
-- 1.3.6.1.4.1.37950.1.1.5.10.13.5.40
-- 1.3.6.1.4.1.37950.1.1.5.10.13.5.40
-- 1.3.6.1.4.1.37950.1.1.5.10.13.5.40
-- 1.3.6.1.4.1.37950.1.1.5.10.13.5.40
		-- 1.3.6.1.4.1.37950.1.1.5.10.13.5.40
		dnLoadFileSuccess OBJECT-TYPE
			SYNTAX Integer32
			MAX-ACCESS read-write
			STATUS current
			DESCRIPTION
				"Description."
			::= { alarmOID 40 }

		
--          1.3.6.1.4.1.37950.1.1.5.10.13.5.41
-- 1.3.6.1.4.1.37950.1.1.5.10.13.5.41
-- 1.3.6.1.4.1.37950.1.1.5.10.13.5.41
-- 1.3.6.1.4.1.37950.1.1.5.10.13.5.41
-- 1.3.6.1.4.1.37950.1.1.5.10.13.5.41
-- 1.3.6.1.4.1.37950.1.1.5.10.13.5.41
-- 1.3.6.1.4.1.37950.1.1.5.10.13.5.41
-- 1.3.6.1.4.1.37950.1.1.5.10.13.5.41
-- 1.3.6.1.4.1.37950.1.1.5.10.13.5.41
		-- 1.3.6.1.4.1.37950.1.1.5.10.13.5.41
		uploadFileSuccess OBJECT-TYPE
			SYNTAX Integer32
			MAX-ACCESS read-write
			STATUS current
			DESCRIPTION
				"Description."
			::= { alarmOID 41 }

		
--          1.3.6.1.4.1.37950.1.1.5.10.13.5.42
-- 1.3.6.1.4.1.37950.1.1.5.10.13.5.42
-- 1.3.6.1.4.1.37950.1.1.5.10.13.5.42
-- 1.3.6.1.4.1.37950.1.1.5.10.13.5.42
-- 1.3.6.1.4.1.37950.1.1.5.10.13.5.42
-- 1.3.6.1.4.1.37950.1.1.5.10.13.5.42
-- 1.3.6.1.4.1.37950.1.1.5.10.13.5.42
-- 1.3.6.1.4.1.37950.1.1.5.10.13.5.42
-- 1.3.6.1.4.1.37950.1.1.5.10.13.5.42
		-- 1.3.6.1.4.1.37950.1.1.5.10.13.5.42
		upgradeFileSuccess OBJECT-TYPE
			SYNTAX Integer32
			MAX-ACCESS read-write
			STATUS current
			DESCRIPTION
				"Description."
			::= { alarmOID 42 }

		
--          1.3.6.1.4.1.37950.1.1.5.10.13.5.43
-- 1.3.6.1.4.1.37950.1.1.5.10.13.5.43
-- 1.3.6.1.4.1.37950.1.1.5.10.13.5.43
-- 1.3.6.1.4.1.37950.1.1.5.10.13.5.43
-- 1.3.6.1.4.1.37950.1.1.5.10.13.5.43
-- 1.3.6.1.4.1.37950.1.1.5.10.13.5.43
-- 1.3.6.1.4.1.37950.1.1.5.10.13.5.43
-- 1.3.6.1.4.1.37950.1.1.5.10.13.5.43
-- 1.3.6.1.4.1.37950.1.1.5.10.13.5.43
		-- 1.3.6.1.4.1.37950.1.1.5.10.13.5.43
		ponRegister OBJECT-TYPE
			SYNTAX Integer32
			MAX-ACCESS read-write
			STATUS current
			DESCRIPTION
				"Description."
			::= { alarmOID 43 }

		
--          1.3.6.1.4.1.37950.1.1.5.10.13.5.44
-- 1.3.6.1.4.1.37950.1.1.5.10.13.5.44
-- 1.3.6.1.4.1.37950.1.1.5.10.13.5.44
-- 1.3.6.1.4.1.37950.1.1.5.10.13.5.44
-- 1.3.6.1.4.1.37950.1.1.5.10.13.5.44
-- 1.3.6.1.4.1.37950.1.1.5.10.13.5.44
-- 1.3.6.1.4.1.37950.1.1.5.10.13.5.44
-- 1.3.6.1.4.1.37950.1.1.5.10.13.5.44
-- 1.3.6.1.4.1.37950.1.1.5.10.13.5.44
		-- 1.3.6.1.4.1.37950.1.1.5.10.13.5.44
		ponEnable OBJECT-TYPE
			SYNTAX Integer32
			MAX-ACCESS read-write
			STATUS current
			DESCRIPTION
				"Description."
			::= { alarmOID 44 }

		
--          1.3.6.1.4.1.37950.1.1.5.10.13.5.45
-- 1.3.6.1.4.1.37950.1.1.5.10.13.5.45
-- 1.3.6.1.4.1.37950.1.1.5.10.13.5.45
-- 1.3.6.1.4.1.37950.1.1.5.10.13.5.45
-- 1.3.6.1.4.1.37950.1.1.5.10.13.5.45
-- 1.3.6.1.4.1.37950.1.1.5.10.13.5.45
-- 1.3.6.1.4.1.37950.1.1.5.10.13.5.45
-- 1.3.6.1.4.1.37950.1.1.5.10.13.5.45
-- 1.3.6.1.4.1.37950.1.1.5.10.13.5.45
		-- 1.3.6.1.4.1.37950.1.1.5.10.13.5.45
		ponLosRecovery OBJECT-TYPE
			SYNTAX Integer32
			MAX-ACCESS read-write
			STATUS current
			DESCRIPTION
				"Description."
			::= { alarmOID 45 }

		
--          1.3.6.1.4.1.37950.1.1.5.10.13.5.46
-- 1.3.6.1.4.1.37950.1.1.5.10.13.5.46
-- 1.3.6.1.4.1.37950.1.1.5.10.13.5.46
-- 1.3.6.1.4.1.37950.1.1.5.10.13.5.46
-- 1.3.6.1.4.1.37950.1.1.5.10.13.5.46
-- 1.3.6.1.4.1.37950.1.1.5.10.13.5.46
-- 1.3.6.1.4.1.37950.1.1.5.10.13.5.46
-- 1.3.6.1.4.1.37950.1.1.5.10.13.5.46
-- 1.3.6.1.4.1.37950.1.1.5.10.13.5.46
		-- 1.3.6.1.4.1.37950.1.1.5.10.13.5.46
		onuRegister OBJECT-TYPE
			SYNTAX Integer32
			MAX-ACCESS read-write
			STATUS current
			DESCRIPTION
				"Description."
			::= { alarmOID 46 }

		
--          1.3.6.1.4.1.37950.1.1.5.10.13.5.47
-- 1.3.6.1.4.1.37950.1.1.5.10.13.5.47
-- 1.3.6.1.4.1.37950.1.1.5.10.13.5.47
-- 1.3.6.1.4.1.37950.1.1.5.10.13.5.47
-- 1.3.6.1.4.1.37950.1.1.5.10.13.5.47
-- 1.3.6.1.4.1.37950.1.1.5.10.13.5.47
-- 1.3.6.1.4.1.37950.1.1.5.10.13.5.47
-- 1.3.6.1.4.1.37950.1.1.5.10.13.5.47
-- 1.3.6.1.4.1.37950.1.1.5.10.13.5.47
		-- 1.3.6.1.4.1.37950.1.1.5.10.13.5.47
		onuLinkDiscover OBJECT-TYPE
			SYNTAX Integer32
			MAX-ACCESS read-write
			STATUS current
			DESCRIPTION
				"Description."
			::= { alarmOID 47 }

		
--          1.3.6.1.4.1.37950.1.1.5.10.13.5.48
-- 1.3.6.1.4.1.37950.1.1.5.10.13.5.48
-- 1.3.6.1.4.1.37950.1.1.5.10.13.5.48
-- 1.3.6.1.4.1.37950.1.1.5.10.13.5.48
-- 1.3.6.1.4.1.37950.1.1.5.10.13.5.48
-- 1.3.6.1.4.1.37950.1.1.5.10.13.5.48
-- 1.3.6.1.4.1.37950.1.1.5.10.13.5.48
-- 1.3.6.1.4.1.37950.1.1.5.10.13.5.48
-- 1.3.6.1.4.1.37950.1.1.5.10.13.5.48
		-- 1.3.6.1.4.1.37950.1.1.5.10.13.5.48
		onuAuthSuccess OBJECT-TYPE
			SYNTAX Integer32
			MAX-ACCESS read-write
			STATUS current
			DESCRIPTION
				"Description."
			::= { alarmOID 48 }

		
--          1.3.6.1.4.1.37950.1.1.5.10.13.5.49
-- 1.3.6.1.4.1.37950.1.1.5.10.13.5.49
-- 1.3.6.1.4.1.37950.1.1.5.10.13.5.49
-- 1.3.6.1.4.1.37950.1.1.5.10.13.5.49
-- 1.3.6.1.4.1.37950.1.1.5.10.13.5.49
-- 1.3.6.1.4.1.37950.1.1.5.10.13.5.49
-- 1.3.6.1.4.1.37950.1.1.5.10.13.5.49
-- 1.3.6.1.4.1.37950.1.1.5.10.13.5.49
-- 1.3.6.1.4.1.37950.1.1.5.10.13.5.49
		-- 1.3.6.1.4.1.37950.1.1.5.10.13.5.49
		onuDeauthSuccess OBJECT-TYPE
			SYNTAX Integer32
			MAX-ACCESS read-write
			STATUS current
			DESCRIPTION
				"Description."
			::= { alarmOID 49 }

		
--          1.3.6.1.4.1.37950.1.1.5.10.13.5.50
-- 1.3.6.1.4.1.37950.1.1.5.10.13.5.50
-- 1.3.6.1.4.1.37950.1.1.5.10.13.5.50
-- 1.3.6.1.4.1.37950.1.1.5.10.13.5.50
-- 1.3.6.1.4.1.37950.1.1.5.10.13.5.50
-- 1.3.6.1.4.1.37950.1.1.5.10.13.5.50
-- 1.3.6.1.4.1.37950.1.1.5.10.13.5.50
-- 1.3.6.1.4.1.37950.1.1.5.10.13.5.50
-- 1.3.6.1.4.1.37950.1.1.5.10.13.5.50
		-- 1.3.6.1.4.1.37950.1.1.5.10.13.5.50
		onuUpgradeOver OBJECT-TYPE
			SYNTAX Integer32
			MAX-ACCESS read-write
			STATUS current
			DESCRIPTION
				"Description."
			::= { alarmOID 50 }

		
--          1.3.6.1.4.1.37950.1.1.5.10.13.5.51
-- 1.3.6.1.4.1.37950.1.1.5.10.13.5.51
-- 1.3.6.1.4.1.37950.1.1.5.10.13.5.51
-- 1.3.6.1.4.1.37950.1.1.5.10.13.5.51
-- 1.3.6.1.4.1.37950.1.1.5.10.13.5.51
-- 1.3.6.1.4.1.37950.1.1.5.10.13.5.51
-- 1.3.6.1.4.1.37950.1.1.5.10.13.5.51
-- 1.3.6.1.4.1.37950.1.1.5.10.13.5.51
-- 1.3.6.1.4.1.37950.1.1.5.10.13.5.51
		-- 1.3.6.1.4.1.37950.1.1.5.10.13.5.51
		onuFinish OBJECT-TYPE
			SYNTAX Integer32
			MAX-ACCESS read-write
			STATUS current
			DESCRIPTION
				"Description."
			::= { alarmOID 51 }

		
--          1.3.6.1.4.1.37950.1.1.5.10.13.5.52
-- 1.3.6.1.4.1.37950.1.1.5.10.13.5.52
-- 1.3.6.1.4.1.37950.1.1.5.10.13.5.52
-- 1.3.6.1.4.1.37950.1.1.5.10.13.5.52
-- 1.3.6.1.4.1.37950.1.1.5.10.13.5.52
-- 1.3.6.1.4.1.37950.1.1.5.10.13.5.52
-- 1.3.6.1.4.1.37950.1.1.5.10.13.5.52
-- 1.3.6.1.4.1.37950.1.1.5.10.13.5.52
-- 1.3.6.1.4.1.37950.1.1.5.10.13.5.52
		-- 1.3.6.1.4.1.37950.1.1.5.10.13.5.52
		onuPonRxPowerHigh OBJECT-TYPE
			SYNTAX Integer32
			MAX-ACCESS read-write
			STATUS current
			DESCRIPTION
				"Description."
			::= { alarmOID 52 }

		
--          1.3.6.1.4.1.37950.1.1.5.10.13.5.53
-- 1.3.6.1.4.1.37950.1.1.5.10.13.5.53
-- 1.3.6.1.4.1.37950.1.1.5.10.13.5.53
-- 1.3.6.1.4.1.37950.1.1.5.10.13.5.53
-- 1.3.6.1.4.1.37950.1.1.5.10.13.5.53
-- 1.3.6.1.4.1.37950.1.1.5.10.13.5.53
-- 1.3.6.1.4.1.37950.1.1.5.10.13.5.53
-- 1.3.6.1.4.1.37950.1.1.5.10.13.5.53
-- 1.3.6.1.4.1.37950.1.1.5.10.13.5.53
		-- 1.3.6.1.4.1.37950.1.1.5.10.13.5.53
		onuPonRxPowerLow OBJECT-TYPE
			SYNTAX Integer32
			MAX-ACCESS read-write
			STATUS current
			DESCRIPTION
				"Description."
			::= { alarmOID 53 }

		
--          1.3.6.1.4.1.37950.1.1.5.10.13.5.54
-- 1.3.6.1.4.1.37950.1.1.5.10.13.5.54
-- 1.3.6.1.4.1.37950.1.1.5.10.13.5.54
-- 1.3.6.1.4.1.37950.1.1.5.10.13.5.54
-- 1.3.6.1.4.1.37950.1.1.5.10.13.5.54
-- 1.3.6.1.4.1.37950.1.1.5.10.13.5.54
-- 1.3.6.1.4.1.37950.1.1.5.10.13.5.54
-- 1.3.6.1.4.1.37950.1.1.5.10.13.5.54
-- 1.3.6.1.4.1.37950.1.1.5.10.13.5.54
		-- 1.3.6.1.4.1.37950.1.1.5.10.13.5.54
		onuPonTxPowerHigh OBJECT-TYPE
			SYNTAX Integer32
			MAX-ACCESS read-write
			STATUS current
			DESCRIPTION
				"Description."
			::= { alarmOID 54 }

		
--          1.3.6.1.4.1.37950.1.1.5.10.13.5.55
-- 1.3.6.1.4.1.37950.1.1.5.10.13.5.55
-- 1.3.6.1.4.1.37950.1.1.5.10.13.5.55
-- 1.3.6.1.4.1.37950.1.1.5.10.13.5.55
-- 1.3.6.1.4.1.37950.1.1.5.10.13.5.55
-- 1.3.6.1.4.1.37950.1.1.5.10.13.5.55
-- 1.3.6.1.4.1.37950.1.1.5.10.13.5.55
-- 1.3.6.1.4.1.37950.1.1.5.10.13.5.55
-- 1.3.6.1.4.1.37950.1.1.5.10.13.5.55
		-- 1.3.6.1.4.1.37950.1.1.5.10.13.5.55
		onuPonTxPowerLow OBJECT-TYPE
			SYNTAX Integer32
			MAX-ACCESS read-write
			STATUS current
			DESCRIPTION
				"Description."
			::= { alarmOID 55 }

		
--          1.3.6.1.4.1.37950.1.1.5.10.13.5.56
-- 1.3.6.1.4.1.37950.1.1.5.10.13.5.56
-- 1.3.6.1.4.1.37950.1.1.5.10.13.5.56
-- 1.3.6.1.4.1.37950.1.1.5.10.13.5.56
-- 1.3.6.1.4.1.37950.1.1.5.10.13.5.56
-- 1.3.6.1.4.1.37950.1.1.5.10.13.5.56
-- 1.3.6.1.4.1.37950.1.1.5.10.13.5.56
-- 1.3.6.1.4.1.37950.1.1.5.10.13.5.56
-- 1.3.6.1.4.1.37950.1.1.5.10.13.5.56
		-- 1.3.6.1.4.1.37950.1.1.5.10.13.5.56
		onuPonTxBiasHigh OBJECT-TYPE
			SYNTAX Integer32
			MAX-ACCESS read-write
			STATUS current
			DESCRIPTION
				"Description."
			::= { alarmOID 56 }

		
--          1.3.6.1.4.1.37950.1.1.5.10.13.5.57
-- 1.3.6.1.4.1.37950.1.1.5.10.13.5.57
-- 1.3.6.1.4.1.37950.1.1.5.10.13.5.57
-- 1.3.6.1.4.1.37950.1.1.5.10.13.5.57
-- 1.3.6.1.4.1.37950.1.1.5.10.13.5.57
-- 1.3.6.1.4.1.37950.1.1.5.10.13.5.57
-- 1.3.6.1.4.1.37950.1.1.5.10.13.5.57
-- 1.3.6.1.4.1.37950.1.1.5.10.13.5.57
-- 1.3.6.1.4.1.37950.1.1.5.10.13.5.57
		-- 1.3.6.1.4.1.37950.1.1.5.10.13.5.57
		onuPonTxBiasLow OBJECT-TYPE
			SYNTAX Integer32
			MAX-ACCESS read-write
			STATUS current
			DESCRIPTION
				"Description."
			::= { alarmOID 57 }

		
--          1.3.6.1.4.1.37950.1.1.5.10.13.5.58
-- 1.3.6.1.4.1.37950.1.1.5.10.13.5.58
-- 1.3.6.1.4.1.37950.1.1.5.10.13.5.58
-- 1.3.6.1.4.1.37950.1.1.5.10.13.5.58
-- 1.3.6.1.4.1.37950.1.1.5.10.13.5.58
-- 1.3.6.1.4.1.37950.1.1.5.10.13.5.58
-- 1.3.6.1.4.1.37950.1.1.5.10.13.5.58
-- 1.3.6.1.4.1.37950.1.1.5.10.13.5.58
-- 1.3.6.1.4.1.37950.1.1.5.10.13.5.58
		-- 1.3.6.1.4.1.37950.1.1.5.10.13.5.58
		onuPonVccHigh OBJECT-TYPE
			SYNTAX Integer32
			MAX-ACCESS read-write
			STATUS current
			DESCRIPTION
				"Description."
			::= { alarmOID 58 }

		
--          1.3.6.1.4.1.37950.1.1.5.10.13.5.59
-- 1.3.6.1.4.1.37950.1.1.5.10.13.5.59
-- 1.3.6.1.4.1.37950.1.1.5.10.13.5.59
-- 1.3.6.1.4.1.37950.1.1.5.10.13.5.59
-- 1.3.6.1.4.1.37950.1.1.5.10.13.5.59
-- 1.3.6.1.4.1.37950.1.1.5.10.13.5.59
-- 1.3.6.1.4.1.37950.1.1.5.10.13.5.59
-- 1.3.6.1.4.1.37950.1.1.5.10.13.5.59
-- 1.3.6.1.4.1.37950.1.1.5.10.13.5.59
		-- 1.3.6.1.4.1.37950.1.1.5.10.13.5.59
		onuPonVccLow OBJECT-TYPE
			SYNTAX Integer32
			MAX-ACCESS read-write
			STATUS current
			DESCRIPTION
				"Description."
			::= { alarmOID 59 }

		
--          1.3.6.1.4.1.37950.1.1.5.10.13.5.60
-- 1.3.6.1.4.1.37950.1.1.5.10.13.5.60
-- 1.3.6.1.4.1.37950.1.1.5.10.13.5.60
-- 1.3.6.1.4.1.37950.1.1.5.10.13.5.60
-- 1.3.6.1.4.1.37950.1.1.5.10.13.5.60
-- 1.3.6.1.4.1.37950.1.1.5.10.13.5.60
-- 1.3.6.1.4.1.37950.1.1.5.10.13.5.60
-- 1.3.6.1.4.1.37950.1.1.5.10.13.5.60
-- 1.3.6.1.4.1.37950.1.1.5.10.13.5.60
		-- 1.3.6.1.4.1.37950.1.1.5.10.13.5.60
		onuPonTempHigh OBJECT-TYPE
			SYNTAX Integer32
			MAX-ACCESS read-write
			STATUS current
			DESCRIPTION
				"Description."
			::= { alarmOID 60 }

		
--          1.3.6.1.4.1.37950.1.1.5.10.13.5.61
-- 1.3.6.1.4.1.37950.1.1.5.10.13.5.61
-- 1.3.6.1.4.1.37950.1.1.5.10.13.5.61
-- 1.3.6.1.4.1.37950.1.1.5.10.13.5.61
-- 1.3.6.1.4.1.37950.1.1.5.10.13.5.61
-- 1.3.6.1.4.1.37950.1.1.5.10.13.5.61
-- 1.3.6.1.4.1.37950.1.1.5.10.13.5.61
-- 1.3.6.1.4.1.37950.1.1.5.10.13.5.61
-- 1.3.6.1.4.1.37950.1.1.5.10.13.5.61
		-- 1.3.6.1.4.1.37950.1.1.5.10.13.5.61
		onuPonTempLow OBJECT-TYPE
			SYNTAX Integer32
			MAX-ACCESS read-write
			STATUS current
			DESCRIPTION
				"Description."
			::= { alarmOID 61 }

		
--          1.3.6.1.4.1.37950.1.1.5.10.13.5.62
-- 1.3.6.1.4.1.37950.1.1.5.10.13.5.62
-- 1.3.6.1.4.1.37950.1.1.5.10.13.5.62
-- 1.3.6.1.4.1.37950.1.1.5.10.13.5.62
-- 1.3.6.1.4.1.37950.1.1.5.10.13.5.62
-- 1.3.6.1.4.1.37950.1.1.5.10.13.5.62
-- 1.3.6.1.4.1.37950.1.1.5.10.13.5.62
-- 1.3.6.1.4.1.37950.1.1.5.10.13.5.62
-- 1.3.6.1.4.1.37950.1.1.5.10.13.5.62
		-- 1.3.6.1.4.1.37950.1.1.5.10.13.5.62
		onuPortAutoNegFailure OBJECT-TYPE
			SYNTAX Integer32
			MAX-ACCESS read-write
			STATUS current
			DESCRIPTION
				"Description."
			::= { alarmOID 62 }

		
--          1.3.6.1.4.1.37950.1.1.5.10.13.5.63
-- 1.3.6.1.4.1.37950.1.1.5.10.13.5.63
-- 1.3.6.1.4.1.37950.1.1.5.10.13.5.63
-- 1.3.6.1.4.1.37950.1.1.5.10.13.5.63
-- 1.3.6.1.4.1.37950.1.1.5.10.13.5.63
-- 1.3.6.1.4.1.37950.1.1.5.10.13.5.63
-- 1.3.6.1.4.1.37950.1.1.5.10.13.5.63
-- 1.3.6.1.4.1.37950.1.1.5.10.13.5.63
-- 1.3.6.1.4.1.37950.1.1.5.10.13.5.63
		-- 1.3.6.1.4.1.37950.1.1.5.10.13.5.63
		onuPortLos OBJECT-TYPE
			SYNTAX Integer32
			MAX-ACCESS read-write
			STATUS current
			DESCRIPTION
				"Description."
			::= { alarmOID 63 }

		
--          1.3.6.1.4.1.37950.1.1.5.10.13.5.64
-- 1.3.6.1.4.1.37950.1.1.5.10.13.5.64
-- 1.3.6.1.4.1.37950.1.1.5.10.13.5.64
-- 1.3.6.1.4.1.37950.1.1.5.10.13.5.64
-- 1.3.6.1.4.1.37950.1.1.5.10.13.5.64
-- 1.3.6.1.4.1.37950.1.1.5.10.13.5.64
-- 1.3.6.1.4.1.37950.1.1.5.10.13.5.64
-- 1.3.6.1.4.1.37950.1.1.5.10.13.5.64
-- 1.3.6.1.4.1.37950.1.1.5.10.13.5.64
		-- 1.3.6.1.4.1.37950.1.1.5.10.13.5.64
		onuPortFailure OBJECT-TYPE
			SYNTAX Integer32
			MAX-ACCESS read-write
			STATUS current
			DESCRIPTION
				"Description."
			::= { alarmOID 64 }

		
--          1.3.6.1.4.1.37950.1.1.5.10.13.5.65
-- 1.3.6.1.4.1.37950.1.1.5.10.13.5.65
-- 1.3.6.1.4.1.37950.1.1.5.10.13.5.65
-- 1.3.6.1.4.1.37950.1.1.5.10.13.5.65
-- 1.3.6.1.4.1.37950.1.1.5.10.13.5.65
-- 1.3.6.1.4.1.37950.1.1.5.10.13.5.65
-- 1.3.6.1.4.1.37950.1.1.5.10.13.5.65
-- 1.3.6.1.4.1.37950.1.1.5.10.13.5.65
-- 1.3.6.1.4.1.37950.1.1.5.10.13.5.65
		-- 1.3.6.1.4.1.37950.1.1.5.10.13.5.65
		onuPortLoopback OBJECT-TYPE
			SYNTAX Integer32
			MAX-ACCESS read-write
			STATUS current
			DESCRIPTION
				"Description."
			::= { alarmOID 65 }

		
--          1.3.6.1.4.1.37950.1.1.5.10.13.5.66
-- 1.3.6.1.4.1.37950.1.1.5.10.13.5.66
-- 1.3.6.1.4.1.37950.1.1.5.10.13.5.66
-- 1.3.6.1.4.1.37950.1.1.5.10.13.5.66
-- 1.3.6.1.4.1.37950.1.1.5.10.13.5.66
-- 1.3.6.1.4.1.37950.1.1.5.10.13.5.66
-- 1.3.6.1.4.1.37950.1.1.5.10.13.5.66
-- 1.3.6.1.4.1.37950.1.1.5.10.13.5.66
-- 1.3.6.1.4.1.37950.1.1.5.10.13.5.66
		-- 1.3.6.1.4.1.37950.1.1.5.10.13.5.66
		onuPotsFailure OBJECT-TYPE
			SYNTAX Integer32
			MAX-ACCESS read-write
			STATUS current
			DESCRIPTION
				"Description."
			::= { alarmOID 66 }

		
--         1.3.6.1.4.1.37950.1.1.5.10.13.5.67
-- 1.3.6.1.4.1.37950.1.1.5.10.13.5.67
-- 1.3.6.1.4.1.37950.1.1.5.10.13.5.67
-- 1.3.6.1.4.1.37950.1.1.5.10.13.5.67
-- 1.3.6.1.4.1.37950.1.1.5.10.13.5.67
-- 1.3.6.1.4.1.37950.1.1.5.10.13.5.67
-- 1.3.6.1.4.1.37950.1.1.5.10.13.5.67
-- 1.3.6.1.4.1.37950.1.1.5.10.13.5.67
		-- 1.3.6.1.4.1.37950.1.1.5.10.13.5.67
		ospfAdjacencyChange OBJECT-TYPE
			SYNTAX Integer32
			MAX-ACCESS read-write
			STATUS current
			DESCRIPTION
				"Description."
			::= { alarmOID 67 }

		
--         1.3.6.1.4.1.37950.1.1.5.10.13.5.68
-- 1.3.6.1.4.1.37950.1.1.5.10.13.5.68
-- 1.3.6.1.4.1.37950.1.1.5.10.13.5.68
-- 1.3.6.1.4.1.37950.1.1.5.10.13.5.68
-- 1.3.6.1.4.1.37950.1.1.5.10.13.5.68
-- 1.3.6.1.4.1.37950.1.1.5.10.13.5.68
-- 1.3.6.1.4.1.37950.1.1.5.10.13.5.68
-- 1.3.6.1.4.1.37950.1.1.5.10.13.5.68
		-- 1.3.6.1.4.1.37950.1.1.5.10.13.5.68
		illegalDhcpServer OBJECT-TYPE
			SYNTAX Integer32
			MAX-ACCESS read-write
			STATUS current
			DESCRIPTION
				"Description."
			::= { alarmOID 68 }

		
--         1.3.6.1.4.1.37950.1.1.5.10.13.5.69
-- 1.3.6.1.4.1.37950.1.1.5.10.13.5.69
-- 1.3.6.1.4.1.37950.1.1.5.10.13.5.69
-- 1.3.6.1.4.1.37950.1.1.5.10.13.5.69
-- 1.3.6.1.4.1.37950.1.1.5.10.13.5.69
-- 1.3.6.1.4.1.37950.1.1.5.10.13.5.69
-- 1.3.6.1.4.1.37950.1.1.5.10.13.5.69
-- 1.3.6.1.4.1.37950.1.1.5.10.13.5.69
		-- 1.3.6.1.4.1.37950.1.1.5.10.13.5.69
		overDhcpRateLimit OBJECT-TYPE
			SYNTAX Integer32
			MAX-ACCESS read-write
			STATUS current
			DESCRIPTION
				"Description."
			::= { alarmOID 69 }

		
--         1.3.6.1.4.1.37950.1.1.5.10.13.5.70
-- 1.3.6.1.4.1.37950.1.1.5.10.13.5.70
-- 1.3.6.1.4.1.37950.1.1.5.10.13.5.70
-- 1.3.6.1.4.1.37950.1.1.5.10.13.5.70
-- 1.3.6.1.4.1.37950.1.1.5.10.13.5.70
-- 1.3.6.1.4.1.37950.1.1.5.10.13.5.70
-- 1.3.6.1.4.1.37950.1.1.5.10.13.5.70
-- 1.3.6.1.4.1.37950.1.1.5.10.13.5.70
		-- 1.3.6.1.4.1.37950.1.1.5.10.13.5.70
		ripAdjacencyChange OBJECT-TYPE
			SYNTAX Integer32
			MAX-ACCESS read-write
			STATUS current
			DESCRIPTION
				"Description."
			::= { alarmOID 70 }

		
--         1.3.6.1.4.1.37950.1.1.5.10.13.5.71
-- 1.3.6.1.4.1.37950.1.1.5.10.13.5.71
-- 1.3.6.1.4.1.37950.1.1.5.10.13.5.71
-- 1.3.6.1.4.1.37950.1.1.5.10.13.5.71
-- 1.3.6.1.4.1.37950.1.1.5.10.13.5.71
-- 1.3.6.1.4.1.37950.1.1.5.10.13.5.71
-- 1.3.6.1.4.1.37950.1.1.5.10.13.5.71
-- 1.3.6.1.4.1.37950.1.1.5.10.13.5.71
		-- 1.3.6.1.4.1.37950.1.1.5.10.13.5.71
		onuVlanPool OBJECT-TYPE
			SYNTAX Integer32
			MAX-ACCESS read-write
			STATUS current
			DESCRIPTION
				"Description."
			::= { alarmOID 71 }

		
--         1.3.6.1.4.1.37950.1.1.5.10.13.5.72
-- 1.3.6.1.4.1.37950.1.1.5.10.13.5.72
-- 1.3.6.1.4.1.37950.1.1.5.10.13.5.72
-- 1.3.6.1.4.1.37950.1.1.5.10.13.5.72
-- 1.3.6.1.4.1.37950.1.1.5.10.13.5.72
-- 1.3.6.1.4.1.37950.1.1.5.10.13.5.72
-- 1.3.6.1.4.1.37950.1.1.5.10.13.5.72
-- 1.3.6.1.4.1.37950.1.1.5.10.13.5.72
		-- 1.3.6.1.4.1.37950.1.1.5.10.13.5.72
		onuNumLimit OBJECT-TYPE
			SYNTAX Integer32
			MAX-ACCESS read-write
			STATUS current
			DESCRIPTION
				"Description."
			::= { alarmOID 72 }

		
--         1.3.6.1.4.1.37950.1.1.5.10.13.5.73
-- 1.3.6.1.4.1.37950.1.1.5.10.13.5.73
-- 1.3.6.1.4.1.37950.1.1.5.10.13.5.73
-- 1.3.6.1.4.1.37950.1.1.5.10.13.5.73
-- 1.3.6.1.4.1.37950.1.1.5.10.13.5.73
-- 1.3.6.1.4.1.37950.1.1.5.10.13.5.73
-- 1.3.6.1.4.1.37950.1.1.5.10.13.5.73
-- 1.3.6.1.4.1.37950.1.1.5.10.13.5.73
		-- 1.3.6.1.4.1.37950.1.1.5.10.13.5.73
		onuTimeLimit OBJECT-TYPE
			SYNTAX Integer32
			MAX-ACCESS read-write
			STATUS current
			DESCRIPTION
				"Description."
			::= { alarmOID 73 }

		
--         1.3.6.1.4.1.37950.1.1.5.10.13.5.74
-- 1.3.6.1.4.1.37950.1.1.5.10.13.5.74
-- 1.3.6.1.4.1.37950.1.1.5.10.13.5.74
-- 1.3.6.1.4.1.37950.1.1.5.10.13.5.74
-- 1.3.6.1.4.1.37950.1.1.5.10.13.5.74
-- 1.3.6.1.4.1.37950.1.1.5.10.13.5.74
-- 1.3.6.1.4.1.37950.1.1.5.10.13.5.74
-- 1.3.6.1.4.1.37950.1.1.5.10.13.5.74
		-- 1.3.6.1.4.1.37950.1.1.5.10.13.5.74
		timeChange OBJECT-TYPE
			SYNTAX Integer32
			MAX-ACCESS read-write
			STATUS current
			DESCRIPTION
				"Description."
			::= { alarmOID 74 }

		
--         1.3.6.1.4.1.37950.1.1.5.10.13.5.75
-- 1.3.6.1.4.1.37950.1.1.5.10.13.5.75
-- 1.3.6.1.4.1.37950.1.1.5.10.13.5.75
-- 1.3.6.1.4.1.37950.1.1.5.10.13.5.75
-- 1.3.6.1.4.1.37950.1.1.5.10.13.5.75
-- 1.3.6.1.4.1.37950.1.1.5.10.13.5.75
-- 1.3.6.1.4.1.37950.1.1.5.10.13.5.75
-- 1.3.6.1.4.1.37950.1.1.5.10.13.5.75
		-- 1.3.6.1.4.1.37950.1.1.5.10.13.5.75
		ponImageDnload OBJECT-TYPE
			SYNTAX Integer32
			MAX-ACCESS read-write
			STATUS current
			DESCRIPTION
				"Description."
			::= { alarmOID 75 }

		
--         1.3.6.1.4.1.37950.1.1.5.10.13.5.76
-- 1.3.6.1.4.1.37950.1.1.5.10.13.5.76
-- 1.3.6.1.4.1.37950.1.1.5.10.13.5.76
-- 1.3.6.1.4.1.37950.1.1.5.10.13.5.76
-- 1.3.6.1.4.1.37950.1.1.5.10.13.5.76
-- 1.3.6.1.4.1.37950.1.1.5.10.13.5.76
-- 1.3.6.1.4.1.37950.1.1.5.10.13.5.76
-- 1.3.6.1.4.1.37950.1.1.5.10.13.5.76
		-- 1.3.6.1.4.1.37950.1.1.5.10.13.5.76
		macFlapping OBJECT-TYPE
			SYNTAX Integer32
			MAX-ACCESS read-write
			STATUS current
			DESCRIPTION
				"Description."
			::= { alarmOID 76 }

		
--         1.3.6.1.4.1.37950.1.1.5.10.13.5.77
-- 1.3.6.1.4.1.37950.1.1.5.10.13.5.77
-- 1.3.6.1.4.1.37950.1.1.5.10.13.5.77
-- 1.3.6.1.4.1.37950.1.1.5.10.13.5.77
-- 1.3.6.1.4.1.37950.1.1.5.10.13.5.77
-- 1.3.6.1.4.1.37950.1.1.5.10.13.5.77
-- 1.3.6.1.4.1.37950.1.1.5.10.13.5.77
-- 1.3.6.1.4.1.37950.1.1.5.10.13.5.77
		-- 1.3.6.1.4.1.37950.1.1.5.10.13.5.77
		portLinkFlap OBJECT-TYPE
			SYNTAX Integer32
			MAX-ACCESS read-write
			STATUS current
			DESCRIPTION
				"Description."
			::= { alarmOID 77 }

		
--         1.3.6.1.4.1.37950.1.1.5.10.13.5.78
-- 1.3.6.1.4.1.37950.1.1.5.10.13.5.78
-- 1.3.6.1.4.1.37950.1.1.5.10.13.5.78
-- 1.3.6.1.4.1.37950.1.1.5.10.13.5.78
-- 1.3.6.1.4.1.37950.1.1.5.10.13.5.78
-- 1.3.6.1.4.1.37950.1.1.5.10.13.5.78
-- 1.3.6.1.4.1.37950.1.1.5.10.13.5.78
-- 1.3.6.1.4.1.37950.1.1.5.10.13.5.78
		-- 1.3.6.1.4.1.37950.1.1.5.10.13.5.78
		ospf6AdjacencyChange OBJECT-TYPE
			SYNTAX Integer32
			MAX-ACCESS read-write
			STATUS current
			DESCRIPTION
				"Description."
			::= { alarmOID 78 }

		
--         1.3.6.1.4.1.37950.1.1.5.10.13.5.79
-- 1.3.6.1.4.1.37950.1.1.5.10.13.5.79
-- 1.3.6.1.4.1.37950.1.1.5.10.13.5.79
-- 1.3.6.1.4.1.37950.1.1.5.10.13.5.79
-- 1.3.6.1.4.1.37950.1.1.5.10.13.5.79
-- 1.3.6.1.4.1.37950.1.1.5.10.13.5.79
-- 1.3.6.1.4.1.37950.1.1.5.10.13.5.79
-- 1.3.6.1.4.1.37950.1.1.5.10.13.5.79
		-- 1.3.6.1.4.1.37950.1.1.5.10.13.5.79
		ripngAdjacencyChange OBJECT-TYPE
			SYNTAX Integer32
			MAX-ACCESS read-write
			STATUS current
			DESCRIPTION
				"Description."
			::= { alarmOID 79 }

		
--         1.3.6.1.4.1.37950.1.1.5.10.13.5.80
-- 1.3.6.1.4.1.37950.1.1.5.10.13.5.80
-- 1.3.6.1.4.1.37950.1.1.5.10.13.5.80
-- 1.3.6.1.4.1.37950.1.1.5.10.13.5.80
-- 1.3.6.1.4.1.37950.1.1.5.10.13.5.80
-- 1.3.6.1.4.1.37950.1.1.5.10.13.5.80
-- 1.3.6.1.4.1.37950.1.1.5.10.13.5.80
-- 1.3.6.1.4.1.37950.1.1.5.10.13.5.80
		-- 1.3.6.1.4.1.37950.1.1.5.10.13.5.80
		ponPsg OBJECT-TYPE
			SYNTAX Integer32
			MAX-ACCESS read-write
			STATUS current
			DESCRIPTION
				"Description."
			::= { alarmOID 80 }

		
--         1.3.6.1.4.1.37950.1.1.5.10.13.5.81
-- 1.3.6.1.4.1.37950.1.1.5.10.13.5.81
-- 1.3.6.1.4.1.37950.1.1.5.10.13.5.81
-- 1.3.6.1.4.1.37950.1.1.5.10.13.5.81
-- 1.3.6.1.4.1.37950.1.1.5.10.13.5.81
-- 1.3.6.1.4.1.37950.1.1.5.10.13.5.81
-- 1.3.6.1.4.1.37950.1.1.5.10.13.5.81
-- 1.3.6.1.4.1.37950.1.1.5.10.13.5.81
		-- 1.3.6.1.4.1.37950.1.1.5.10.13.5.81
		userLogin OBJECT-TYPE
			SYNTAX Integer32
			MAX-ACCESS read-write
			STATUS current
			DESCRIPTION
				"Description."
			::= { alarmOID 81 }

		
--         1.3.6.1.4.1.37950.1.1.5.10.13.5.82
-- 1.3.6.1.4.1.37950.1.1.5.10.13.5.82
-- 1.3.6.1.4.1.37950.1.1.5.10.13.5.82
-- 1.3.6.1.4.1.37950.1.1.5.10.13.5.82
-- 1.3.6.1.4.1.37950.1.1.5.10.13.5.82
-- 1.3.6.1.4.1.37950.1.1.5.10.13.5.82
-- 1.3.6.1.4.1.37950.1.1.5.10.13.5.82
-- 1.3.6.1.4.1.37950.1.1.5.10.13.5.82
		-- 1.3.6.1.4.1.37950.1.1.5.10.13.5.82
		userLogout OBJECT-TYPE
			SYNTAX Integer32
			MAX-ACCESS read-write
			STATUS current
			DESCRIPTION
				"Description."
			::= { alarmOID 82 }

		
--         1.3.6.1.4.1.37950.1.1.5.10.13.6
-- 1.3.6.1.4.1.37950.1.1.5.10.13.6
-- 1.3.6.1.4.1.37950.1.1.5.10.13.6
-- 1.3.6.1.4.1.37950.1.1.5.10.13.6
-- 1.3.6.1.4.1.37950.1.1.5.10.13.6
-- 1.3.6.1.4.1.37950.1.1.5.10.13.6
-- 1.3.6.1.4.1.37950.1.1.5.10.13.6
-- 1.3.6.1.4.1.37950.1.1.5.10.13.6
		-- 1.3.6.1.4.1.37950.1.1.5.10.13.6
		alarmTrap OBJECT IDENTIFIER ::= { v1600dAlarm 6 }

		
--          1.3.6.1.4.1.37950.1.1.5.10.13.6.1
-- 1.3.6.1.4.1.37950.1.1.5.10.13.6.1
-- 1.3.6.1.4.1.37950.1.1.5.10.13.6.1
-- 1.3.6.1.4.1.37950.1.1.5.10.13.6.1
-- 1.3.6.1.4.1.37950.1.1.5.10.13.6.1
-- 1.3.6.1.4.1.37950.1.1.5.10.13.6.1
-- 1.3.6.1.4.1.37950.1.1.5.10.13.6.1
-- 1.3.6.1.4.1.37950.1.1.5.10.13.6.1
-- 1.3.6.1.4.1.37950.1.1.5.10.13.6.1
		-- 1.3.6.1.4.1.37950.1.1.5.10.13.6.1
		dataAlarmTrap NOTIFICATION-TYPE
			OBJECTS { dataUpLinkPort, dataPon, dataOnu, dataOnuPort, dataTrapOID, 
				dataTrapClass, dataMac, dataTime, dateAlarmLevel, dataValue, 
				dataAlarmType, dataSynOID }
			STATUS current
			DESCRIPTION 
				"Description."
			::= { alarmTrap 1 }

		
--          1.3.6.1.4.1.37950.1.1.5.10.14
-- 1.3.6.1.4.1.37950.1.1.5.10.14
-- 1.3.6.1.4.1.37950.1.1.5.10.14
-- 1.3.6.1.4.1.37950.1.1.5.10.14
-- 1.3.6.1.4.1.37950.1.1.5.10.14
-- 1.3.6.1.4.1.37950.1.1.5.10.14
-- 1.3.6.1.4.1.37950.1.1.5.10.14
-- 1.3.6.1.4.1.37950.1.1.5.10.14
-- 1.3.6.1.4.1.37950.1.1.5.10.14
		-- 1.3.6.1.4.1.37950.1.1.5.10.14
		v1600dOltType OBJECT IDENTIFIER ::= { v1600dSwitch 14 }

		
--          1.3.6.1.4.1.37950.1.1.5.10.14.1
-- 1.3.6.1.4.1.37950.1.1.5.10.14.1
-- 1.3.6.1.4.1.37950.1.1.5.10.14.1
-- 1.3.6.1.4.1.37950.1.1.5.10.14.1
-- 1.3.6.1.4.1.37950.1.1.5.10.14.1
-- 1.3.6.1.4.1.37950.1.1.5.10.14.1
-- 1.3.6.1.4.1.37950.1.1.5.10.14.1
-- 1.3.6.1.4.1.37950.1.1.5.10.14.1
-- 1.3.6.1.4.1.37950.1.1.5.10.14.1
		-- 1.3.6.1.4.1.37950.1.1.5.10.14.1
		oltType OBJECT-TYPE
			SYNTAX OCTET STRING
			MAX-ACCESS read-write
			STATUS current
			DESCRIPTION
				"Description."
			::= { v1600dOltType 1 }

		
--         1.3.6.1.4.1.37950.1.1.5.10.14.2
-- 1.3.6.1.4.1.37950.1.1.5.10.14.2
-- 1.3.6.1.4.1.37950.1.1.5.10.14.2
-- 1.3.6.1.4.1.37950.1.1.5.10.14.2
-- 1.3.6.1.4.1.37950.1.1.5.10.14.2
-- 1.3.6.1.4.1.37950.1.1.5.10.14.2
-- 1.3.6.1.4.1.37950.1.1.5.10.14.2
-- 1.3.6.1.4.1.37950.1.1.5.10.14.2
		-- 1.3.6.1.4.1.37950.1.1.5.10.14.2
		routeEnable OBJECT-TYPE
			SYNTAX INTEGER
				{
				disable(0),
				enable(1)
				}
			MAX-ACCESS read-write
			STATUS current
			DESCRIPTION
				"Description."
			::= { v1600dOltType 2 }

		
--         1.3.6.1.4.1.37950.1.1.5.10.14.3
-- 1.3.6.1.4.1.37950.1.1.5.10.14.3
-- 1.3.6.1.4.1.37950.1.1.5.10.14.3
-- 1.3.6.1.4.1.37950.1.1.5.10.14.3
-- 1.3.6.1.4.1.37950.1.1.5.10.14.3
-- 1.3.6.1.4.1.37950.1.1.5.10.14.3
-- 1.3.6.1.4.1.37950.1.1.5.10.14.3
-- 1.3.6.1.4.1.37950.1.1.5.10.14.3
		-- 1.3.6.1.4.1.37950.1.1.5.10.14.3
		protocolSupport OBJECT-TYPE
			SYNTAX Unsigned32
			MAX-ACCESS read-write
			STATUS current
			DESCRIPTION
				"Description."
			::= { v1600dOltType 3 }

		
--         1.3.6.1.4.1.37950.1.1.5.10.14.4
-- 1.3.6.1.4.1.37950.1.1.5.10.14.4
-- 1.3.6.1.4.1.37950.1.1.5.10.14.4
-- 1.3.6.1.4.1.37950.1.1.5.10.14.4
-- 1.3.6.1.4.1.37950.1.1.5.10.14.4
-- 1.3.6.1.4.1.37950.1.1.5.10.14.4
-- 1.3.6.1.4.1.37950.1.1.5.10.14.4
-- 1.3.6.1.4.1.37950.1.1.5.10.14.4
		-- 1.3.6.1.4.1.37950.1.1.5.10.14.4
		ipv6Enable OBJECT-TYPE
			SYNTAX INTEGER
				{
				disable(0),
				enable(1)
				}
			MAX-ACCESS read-write
			STATUS current
			DESCRIPTION
				"Description."
			::= { v1600dOltType 4 }

		
--         1.3.6.1.4.1.37950.1.1.5.10.14.5
-- 1.3.6.1.4.1.37950.1.1.5.10.14.5
-- 1.3.6.1.4.1.37950.1.1.5.10.14.5
-- 1.3.6.1.4.1.37950.1.1.5.10.14.5
-- 1.3.6.1.4.1.37950.1.1.5.10.14.5
-- 1.3.6.1.4.1.37950.1.1.5.10.14.5
-- 1.3.6.1.4.1.37950.1.1.5.10.14.5
-- 1.3.6.1.4.1.37950.1.1.5.10.14.5
		-- 1.3.6.1.4.1.37950.1.1.5.10.14.5
		oltTypeVersion OBJECT-TYPE
			SYNTAX OCTET STRING
			MAX-ACCESS read-write
			STATUS current
			DESCRIPTION
				"Description."
			::= { v1600dOltType 5 }

		
--         1.3.6.1.4.1.37950.1.1.5.10.15
-- 1.3.6.1.4.1.37950.1.1.5.10.15
-- 1.3.6.1.4.1.37950.1.1.5.10.15
-- 1.3.6.1.4.1.37950.1.1.5.10.15
-- 1.3.6.1.4.1.37950.1.1.5.10.15
-- 1.3.6.1.4.1.37950.1.1.5.10.15
-- 1.3.6.1.4.1.37950.1.1.5.10.15
-- 1.3.6.1.4.1.37950.1.1.5.10.15
		-- 1.3.6.1.4.1.37950.1.1.5.10.15
		v1600dLoopback OBJECT IDENTIFIER ::= { v1600dSwitch 15 }

		
--         1.3.6.1.4.1.37950.1.1.5.10.15.1
-- 1.3.6.1.4.1.37950.1.1.5.10.15.1
-- 1.3.6.1.4.1.37950.1.1.5.10.15.1
-- 1.3.6.1.4.1.37950.1.1.5.10.15.1
-- 1.3.6.1.4.1.37950.1.1.5.10.15.1
-- 1.3.6.1.4.1.37950.1.1.5.10.15.1
-- 1.3.6.1.4.1.37950.1.1.5.10.15.1
-- 1.3.6.1.4.1.37950.1.1.5.10.15.1
		-- 1.3.6.1.4.1.37950.1.1.5.10.15.1
		loopbackEn OBJECT-TYPE
			SYNTAX INTEGER
				{
				disable(0),
				enable(1)
				}
			MAX-ACCESS read-write
			STATUS current
			DESCRIPTION
				"Description."
			::= { v1600dLoopback 1 }

		
--         1.3.6.1.4.1.37950.1.1.5.10.15.2
-- 1.3.6.1.4.1.37950.1.1.5.10.15.2
-- 1.3.6.1.4.1.37950.1.1.5.10.15.2
-- 1.3.6.1.4.1.37950.1.1.5.10.15.2
-- 1.3.6.1.4.1.37950.1.1.5.10.15.2
-- 1.3.6.1.4.1.37950.1.1.5.10.15.2
-- 1.3.6.1.4.1.37950.1.1.5.10.15.2
-- 1.3.6.1.4.1.37950.1.1.5.10.15.2
		-- 1.3.6.1.4.1.37950.1.1.5.10.15.2
		loopbackCfg OBJECT IDENTIFIER ::= { v1600dLoopback 2 }

		
--         1.3.6.1.4.1.37950.1.1.5.10.15.2.1
-- 1.3.6.1.4.1.37950.1.1.5.10.15.2.1
-- 1.3.6.1.4.1.37950.1.1.5.10.15.2.1
-- 1.3.6.1.4.1.37950.1.1.5.10.15.2.1
-- 1.3.6.1.4.1.37950.1.1.5.10.15.2.1
-- 1.3.6.1.4.1.37950.1.1.5.10.15.2.1
-- 1.3.6.1.4.1.37950.1.1.5.10.15.2.1
-- 1.3.6.1.4.1.37950.1.1.5.10.15.2.1
		-- 1.3.6.1.4.1.37950.1.1.5.10.15.2.1
		mode OBJECT-TYPE
			SYNTAX INTEGER
				{
				onlyAlarm(1),
				manualRecovery(2),
				autoRecovery(3)
				}
			MAX-ACCESS read-write
			STATUS current
			DESCRIPTION
				"Description."
			::= { loopbackCfg 1 }

		
--         1.3.6.1.4.1.37950.1.1.5.10.15.2.2
-- 1.3.6.1.4.1.37950.1.1.5.10.15.2.2
-- 1.3.6.1.4.1.37950.1.1.5.10.15.2.2
-- 1.3.6.1.4.1.37950.1.1.5.10.15.2.2
-- 1.3.6.1.4.1.37950.1.1.5.10.15.2.2
-- 1.3.6.1.4.1.37950.1.1.5.10.15.2.2
-- 1.3.6.1.4.1.37950.1.1.5.10.15.2.2
-- 1.3.6.1.4.1.37950.1.1.5.10.15.2.2
		-- 1.3.6.1.4.1.37950.1.1.5.10.15.2.2
		agingTime OBJECT-TYPE
			SYNTAX Integer32 (10..3600)
			MAX-ACCESS read-write
			STATUS current
			DESCRIPTION
				"Description."
			::= { loopbackCfg 2 }

		
--         1.3.6.1.4.1.37950.1.1.5.10.15.2.3
-- 1.3.6.1.4.1.37950.1.1.5.10.15.2.3
-- 1.3.6.1.4.1.37950.1.1.5.10.15.2.3
-- 1.3.6.1.4.1.37950.1.1.5.10.15.2.3
-- 1.3.6.1.4.1.37950.1.1.5.10.15.2.3
-- 1.3.6.1.4.1.37950.1.1.5.10.15.2.3
-- 1.3.6.1.4.1.37950.1.1.5.10.15.2.3
-- 1.3.6.1.4.1.37950.1.1.5.10.15.2.3
		-- 1.3.6.1.4.1.37950.1.1.5.10.15.2.3
		range OBJECT-TYPE
			SYNTAX INTEGER
				{
				uplink(0),
				pon(1),
				all(2)
				}
			MAX-ACCESS read-write
			STATUS current
			DESCRIPTION
				"Description."
			::= { loopbackCfg 3 }

		
--       1.3.6.1.4.1.37950.1.1.5.10.15.2.4
-- 1.3.6.1.4.1.37950.1.1.5.10.15.2.4
-- 1.3.6.1.4.1.37950.1.1.5.10.15.2.4
-- 1.3.6.1.4.1.37950.1.1.5.10.15.2.4
-- 1.3.6.1.4.1.37950.1.1.5.10.15.2.4
-- 1.3.6.1.4.1.37950.1.1.5.10.15.2.4
		-- 1.3.6.1.4.1.37950.1.1.5.10.15.2.4
		effect OBJECT-TYPE
			SYNTAX INTEGER
				{
				pon(0),
				onu(1)
				}
			MAX-ACCESS read-write
			STATUS current
			DESCRIPTION
				"Description."
			::= { loopbackCfg 4 }

		
--       1.3.6.1.4.1.37950.1.1.5.10.15.2.5
-- 1.3.6.1.4.1.37950.1.1.5.10.15.2.5
-- 1.3.6.1.4.1.37950.1.1.5.10.15.2.5
-- 1.3.6.1.4.1.37950.1.1.5.10.15.2.5
-- 1.3.6.1.4.1.37950.1.1.5.10.15.2.5
-- 1.3.6.1.4.1.37950.1.1.5.10.15.2.5
		-- 1.3.6.1.4.1.37950.1.1.5.10.15.2.5
		packetSendWay OBJECT-TYPE
			SYNTAX INTEGER
				{
				port-base(0),
				vlan-base(1)
				}
			MAX-ACCESS read-write
			STATUS current
			DESCRIPTION
				"Description."
			::= { loopbackCfg 5 }

		
--       1.3.6.1.4.1.37950.1.1.5.10.15.2.6
-- 1.3.6.1.4.1.37950.1.1.5.10.15.2.6
-- 1.3.6.1.4.1.37950.1.1.5.10.15.2.6
-- 1.3.6.1.4.1.37950.1.1.5.10.15.2.6
-- 1.3.6.1.4.1.37950.1.1.5.10.15.2.6
-- 1.3.6.1.4.1.37950.1.1.5.10.15.2.6
		-- 1.3.6.1.4.1.37950.1.1.5.10.15.2.6
		packetSendTime OBJECT-TYPE
			SYNTAX Integer32 (1..720)
			MAX-ACCESS read-write
			STATUS current
			DESCRIPTION
				"Description."
			::= { loopbackCfg 6 }

		
--         1.3.6.1.4.1.37950.1.1.5.10.15.3
-- 1.3.6.1.4.1.37950.1.1.5.10.15.3
-- 1.3.6.1.4.1.37950.1.1.5.10.15.3
-- 1.3.6.1.4.1.37950.1.1.5.10.15.3
-- 1.3.6.1.4.1.37950.1.1.5.10.15.3
-- 1.3.6.1.4.1.37950.1.1.5.10.15.3
-- 1.3.6.1.4.1.37950.1.1.5.10.15.3
-- 1.3.6.1.4.1.37950.1.1.5.10.15.3
		-- 1.3.6.1.4.1.37950.1.1.5.10.15.3
		loopbackTable OBJECT-TYPE
			SYNTAX SEQUENCE OF LoopbackEntry
			MAX-ACCESS not-accessible
			STATUS current
			DESCRIPTION
				"Description."
			::= { v1600dLoopback 3 }

		
--         1.3.6.1.4.1.37950.1.1.5.10.15.3.1
-- 1.3.6.1.4.1.37950.1.1.5.10.15.3.1
-- 1.3.6.1.4.1.37950.1.1.5.10.15.3.1
-- 1.3.6.1.4.1.37950.1.1.5.10.15.3.1
-- 1.3.6.1.4.1.37950.1.1.5.10.15.3.1
-- 1.3.6.1.4.1.37950.1.1.5.10.15.3.1
-- 1.3.6.1.4.1.37950.1.1.5.10.15.3.1
-- 1.3.6.1.4.1.37950.1.1.5.10.15.3.1
		-- 1.3.6.1.4.1.37950.1.1.5.10.15.3.1
		loopbackEntry OBJECT-TYPE
			SYNTAX LoopbackEntry
			MAX-ACCESS not-accessible
			STATUS current
			DESCRIPTION
				"Description."
			INDEX { interfaceS }
			::= { loopbackTable 1 }

		
		LoopbackEntry ::=
			SEQUENCE { 
				interfaceS
					OCTET STRING,
				modeS
					INTEGER,
				timeS
					Integer32,
				srcInterface
					OCTET STRING
			 }

--         1.3.6.1.4.1.37950.1.1.5.10.15.3.1.1
-- 1.3.6.1.4.1.37950.1.1.5.10.15.3.1.1
-- 1.3.6.1.4.1.37950.1.1.5.10.15.3.1.1
-- 1.3.6.1.4.1.37950.1.1.5.10.15.3.1.1
-- 1.3.6.1.4.1.37950.1.1.5.10.15.3.1.1
-- 1.3.6.1.4.1.37950.1.1.5.10.15.3.1.1
-- 1.3.6.1.4.1.37950.1.1.5.10.15.3.1.1
-- 1.3.6.1.4.1.37950.1.1.5.10.15.3.1.1
		-- 1.3.6.1.4.1.37950.1.1.5.10.15.3.1.1
		interfaceS OBJECT-TYPE
			SYNTAX OCTET STRING
			MAX-ACCESS read-only
			STATUS current
			DESCRIPTION
				"Description."
			::= { loopbackEntry 1 }

		
--         1.3.6.1.4.1.37950.1.1.5.10.15.3.1.2
-- 1.3.6.1.4.1.37950.1.1.5.10.15.3.1.2
-- 1.3.6.1.4.1.37950.1.1.5.10.15.3.1.2
-- 1.3.6.1.4.1.37950.1.1.5.10.15.3.1.2
-- 1.3.6.1.4.1.37950.1.1.5.10.15.3.1.2
-- 1.3.6.1.4.1.37950.1.1.5.10.15.3.1.2
-- 1.3.6.1.4.1.37950.1.1.5.10.15.3.1.2
-- 1.3.6.1.4.1.37950.1.1.5.10.15.3.1.2
		-- 1.3.6.1.4.1.37950.1.1.5.10.15.3.1.2
		modeS OBJECT-TYPE
			SYNTAX INTEGER
				{
				noShutdown(0),
				shutdown(1)
				}
			MAX-ACCESS read-write
			STATUS current
			DESCRIPTION
				"Description."
			::= { loopbackEntry 2 }

		
--         1.3.6.1.4.1.37950.1.1.5.10.15.3.1.3
-- 1.3.6.1.4.1.37950.1.1.5.10.15.3.1.3
-- 1.3.6.1.4.1.37950.1.1.5.10.15.3.1.3
-- 1.3.6.1.4.1.37950.1.1.5.10.15.3.1.3
-- 1.3.6.1.4.1.37950.1.1.5.10.15.3.1.3
-- 1.3.6.1.4.1.37950.1.1.5.10.15.3.1.3
-- 1.3.6.1.4.1.37950.1.1.5.10.15.3.1.3
-- 1.3.6.1.4.1.37950.1.1.5.10.15.3.1.3
		-- 1.3.6.1.4.1.37950.1.1.5.10.15.3.1.3
		timeS OBJECT-TYPE
			SYNTAX Integer32
			MAX-ACCESS read-write
			STATUS current
			DESCRIPTION
				"Description."
			::= { loopbackEntry 3 }

		
--         1.3.6.1.4.1.37950.1.1.5.10.15.3.1.4
-- 1.3.6.1.4.1.37950.1.1.5.10.15.3.1.4
-- 1.3.6.1.4.1.37950.1.1.5.10.15.3.1.4
-- 1.3.6.1.4.1.37950.1.1.5.10.15.3.1.4
-- 1.3.6.1.4.1.37950.1.1.5.10.15.3.1.4
-- 1.3.6.1.4.1.37950.1.1.5.10.15.3.1.4
-- 1.3.6.1.4.1.37950.1.1.5.10.15.3.1.4
-- 1.3.6.1.4.1.37950.1.1.5.10.15.3.1.4
		-- 1.3.6.1.4.1.37950.1.1.5.10.15.3.1.4
		srcInterface OBJECT-TYPE
			SYNTAX OCTET STRING
			MAX-ACCESS read-write
			STATUS current
			DESCRIPTION
				"Description."
			::= { loopbackEntry 4 }

		
--         1.3.6.1.4.1.37950.1.1.5.10.15.4
-- 1.3.6.1.4.1.37950.1.1.5.10.15.4
-- 1.3.6.1.4.1.37950.1.1.5.10.15.4
-- 1.3.6.1.4.1.37950.1.1.5.10.15.4
-- 1.3.6.1.4.1.37950.1.1.5.10.15.4
-- 1.3.6.1.4.1.37950.1.1.5.10.15.4
-- 1.3.6.1.4.1.37950.1.1.5.10.15.4
-- 1.3.6.1.4.1.37950.1.1.5.10.15.4
		-- 1.3.6.1.4.1.37950.1.1.5.10.15.4
		loopbackPortCfgTable OBJECT-TYPE
			SYNTAX SEQUENCE OF LoopbackPortCfgEntry
			MAX-ACCESS not-accessible
			STATUS current
			DESCRIPTION
				"Description."
			::= { v1600dLoopback 4 }

		
--         1.3.6.1.4.1.37950.1.1.5.10.15.4.1
-- 1.3.6.1.4.1.37950.1.1.5.10.15.4.1
-- 1.3.6.1.4.1.37950.1.1.5.10.15.4.1
-- 1.3.6.1.4.1.37950.1.1.5.10.15.4.1
-- 1.3.6.1.4.1.37950.1.1.5.10.15.4.1
-- 1.3.6.1.4.1.37950.1.1.5.10.15.4.1
-- 1.3.6.1.4.1.37950.1.1.5.10.15.4.1
-- 1.3.6.1.4.1.37950.1.1.5.10.15.4.1
		-- 1.3.6.1.4.1.37950.1.1.5.10.15.4.1
		loopbackPortCfgEntry OBJECT-TYPE
			SYNTAX LoopbackPortCfgEntry
			MAX-ACCESS not-accessible
			STATUS current
			DESCRIPTION
				"Description."
			INDEX { loopbackPort }
			::= { loopbackPortCfgTable 1 }

		
		LoopbackPortCfgEntry ::=
			SEQUENCE { 
				loopbackPort
					Integer32,
				loopbackStatus
					INTEGER
			 }

--         1.3.6.1.4.1.37950.1.1.5.10.15.4.1.1
-- 1.3.6.1.4.1.37950.1.1.5.10.15.4.1.1
-- 1.3.6.1.4.1.37950.1.1.5.10.15.4.1.1
-- 1.3.6.1.4.1.37950.1.1.5.10.15.4.1.1
-- 1.3.6.1.4.1.37950.1.1.5.10.15.4.1.1
-- 1.3.6.1.4.1.37950.1.1.5.10.15.4.1.1
-- 1.3.6.1.4.1.37950.1.1.5.10.15.4.1.1
-- 1.3.6.1.4.1.37950.1.1.5.10.15.4.1.1
		-- 1.3.6.1.4.1.37950.1.1.5.10.15.4.1.1
		loopbackPort OBJECT-TYPE
			SYNTAX Integer32
			MAX-ACCESS read-only
			STATUS current
			DESCRIPTION
				"Description."
			::= { loopbackPortCfgEntry 1 }

		
--         1.3.6.1.4.1.37950.1.1.5.10.15.4.1.2
-- 1.3.6.1.4.1.37950.1.1.5.10.15.4.1.2
-- 1.3.6.1.4.1.37950.1.1.5.10.15.4.1.2
-- 1.3.6.1.4.1.37950.1.1.5.10.15.4.1.2
-- 1.3.6.1.4.1.37950.1.1.5.10.15.4.1.2
-- 1.3.6.1.4.1.37950.1.1.5.10.15.4.1.2
-- 1.3.6.1.4.1.37950.1.1.5.10.15.4.1.2
-- 1.3.6.1.4.1.37950.1.1.5.10.15.4.1.2
		-- 1.3.6.1.4.1.37950.1.1.5.10.15.4.1.2
		loopbackStatus OBJECT-TYPE
			SYNTAX INTEGER
				{
				disable(0),
				enable(1)
				}
			MAX-ACCESS read-write
			STATUS current
			DESCRIPTION
				"Description."
			::= { loopbackPortCfgEntry 2 }

		
--         1.3.6.1.4.1.37950.1.1.5.10.16
-- 1.3.6.1.4.1.37950.1.1.5.10.16
-- 1.3.6.1.4.1.37950.1.1.5.10.16
-- 1.3.6.1.4.1.37950.1.1.5.10.16
-- 1.3.6.1.4.1.37950.1.1.5.10.16
-- 1.3.6.1.4.1.37950.1.1.5.10.16
-- 1.3.6.1.4.1.37950.1.1.5.10.16
-- 1.3.6.1.4.1.37950.1.1.5.10.16
		-- 1.3.6.1.4.1.37950.1.1.5.10.16
		v1600dRip OBJECT IDENTIFIER ::= { v1600dSwitch 16 }

		
--         1.3.6.1.4.1.37950.1.1.5.10.16.1
-- 1.3.6.1.4.1.37950.1.1.5.10.16.1
-- 1.3.6.1.4.1.37950.1.1.5.10.16.1
-- 1.3.6.1.4.1.37950.1.1.5.10.16.1
-- 1.3.6.1.4.1.37950.1.1.5.10.16.1
-- 1.3.6.1.4.1.37950.1.1.5.10.16.1
-- 1.3.6.1.4.1.37950.1.1.5.10.16.1
-- 1.3.6.1.4.1.37950.1.1.5.10.16.1
		-- 1.3.6.1.4.1.37950.1.1.5.10.16.1
		ripGlobalCfg OBJECT IDENTIFIER ::= { v1600dRip 1 }

		
--         1.3.6.1.4.1.37950.1.1.5.10.16.1.1
-- 1.3.6.1.4.1.37950.1.1.5.10.16.1.1
-- 1.3.6.1.4.1.37950.1.1.5.10.16.1.1
-- 1.3.6.1.4.1.37950.1.1.5.10.16.1.1
-- 1.3.6.1.4.1.37950.1.1.5.10.16.1.1
-- 1.3.6.1.4.1.37950.1.1.5.10.16.1.1
-- 1.3.6.1.4.1.37950.1.1.5.10.16.1.1
-- 1.3.6.1.4.1.37950.1.1.5.10.16.1.1
		-- 1.3.6.1.4.1.37950.1.1.5.10.16.1.1
		ripRouteEn OBJECT-TYPE
			SYNTAX INTEGER
				{
				disable(0),
				enable(1)
				}
			MAX-ACCESS read-write
			STATUS current
			DESCRIPTION
				"Description."
			::= { ripGlobalCfg 1 }

		
--         1.3.6.1.4.1.37950.1.1.5.10.16.1.2
-- 1.3.6.1.4.1.37950.1.1.5.10.16.1.2
-- 1.3.6.1.4.1.37950.1.1.5.10.16.1.2
-- 1.3.6.1.4.1.37950.1.1.5.10.16.1.2
-- 1.3.6.1.4.1.37950.1.1.5.10.16.1.2
-- 1.3.6.1.4.1.37950.1.1.5.10.16.1.2
-- 1.3.6.1.4.1.37950.1.1.5.10.16.1.2
-- 1.3.6.1.4.1.37950.1.1.5.10.16.1.2
		-- 1.3.6.1.4.1.37950.1.1.5.10.16.1.2
		updateTimer OBJECT-TYPE
			SYNTAX Integer32 (5..2147483647)
			MAX-ACCESS read-write
			STATUS current
			DESCRIPTION
				"Description."
			::= { ripGlobalCfg 2 }

		
--         1.3.6.1.4.1.37950.1.1.5.10.16.1.3
-- 1.3.6.1.4.1.37950.1.1.5.10.16.1.3
-- 1.3.6.1.4.1.37950.1.1.5.10.16.1.3
-- 1.3.6.1.4.1.37950.1.1.5.10.16.1.3
-- 1.3.6.1.4.1.37950.1.1.5.10.16.1.3
-- 1.3.6.1.4.1.37950.1.1.5.10.16.1.3
-- 1.3.6.1.4.1.37950.1.1.5.10.16.1.3
-- 1.3.6.1.4.1.37950.1.1.5.10.16.1.3
		-- 1.3.6.1.4.1.37950.1.1.5.10.16.1.3
		timeoutTimer OBJECT-TYPE
			SYNTAX Integer32 (5..2147483647)
			MAX-ACCESS read-write
			STATUS current
			DESCRIPTION
				"Description."
			::= { ripGlobalCfg 3 }

		
--         1.3.6.1.4.1.37950.1.1.5.10.16.1.4
-- 1.3.6.1.4.1.37950.1.1.5.10.16.1.4
-- 1.3.6.1.4.1.37950.1.1.5.10.16.1.4
-- 1.3.6.1.4.1.37950.1.1.5.10.16.1.4
-- 1.3.6.1.4.1.37950.1.1.5.10.16.1.4
-- 1.3.6.1.4.1.37950.1.1.5.10.16.1.4
-- 1.3.6.1.4.1.37950.1.1.5.10.16.1.4
-- 1.3.6.1.4.1.37950.1.1.5.10.16.1.4
		-- 1.3.6.1.4.1.37950.1.1.5.10.16.1.4
		garbageTimer OBJECT-TYPE
			SYNTAX Integer32 (5..2147483647)
			MAX-ACCESS read-write
			STATUS current
			DESCRIPTION
				"Description."
			::= { ripGlobalCfg 4 }

		
--         1.3.6.1.4.1.37950.1.1.5.10.16.1.5
-- 1.3.6.1.4.1.37950.1.1.5.10.16.1.5
-- 1.3.6.1.4.1.37950.1.1.5.10.16.1.5
-- 1.3.6.1.4.1.37950.1.1.5.10.16.1.5
-- 1.3.6.1.4.1.37950.1.1.5.10.16.1.5
-- 1.3.6.1.4.1.37950.1.1.5.10.16.1.5
-- 1.3.6.1.4.1.37950.1.1.5.10.16.1.5
-- 1.3.6.1.4.1.37950.1.1.5.10.16.1.5
		-- 1.3.6.1.4.1.37950.1.1.5.10.16.1.5
		defMetric OBJECT-TYPE
			SYNTAX Integer32 (1..16)
			MAX-ACCESS read-write
			STATUS current
			DESCRIPTION
				"Description."
			::= { ripGlobalCfg 5 }

		
--         1.3.6.1.4.1.37950.1.1.5.10.16.1.6
-- 1.3.6.1.4.1.37950.1.1.5.10.16.1.6
-- 1.3.6.1.4.1.37950.1.1.5.10.16.1.6
-- 1.3.6.1.4.1.37950.1.1.5.10.16.1.6
-- 1.3.6.1.4.1.37950.1.1.5.10.16.1.6
-- 1.3.6.1.4.1.37950.1.1.5.10.16.1.6
-- 1.3.6.1.4.1.37950.1.1.5.10.16.1.6
-- 1.3.6.1.4.1.37950.1.1.5.10.16.1.6
		-- 1.3.6.1.4.1.37950.1.1.5.10.16.1.6
		distance OBJECT-TYPE
			SYNTAX Integer32 (1..255)
			MAX-ACCESS read-write
			STATUS current
			DESCRIPTION
				"Description."
			::= { ripGlobalCfg 6 }

		
--         1.3.6.1.4.1.37950.1.1.5.10.16.1.7
-- 1.3.6.1.4.1.37950.1.1.5.10.16.1.7
-- 1.3.6.1.4.1.37950.1.1.5.10.16.1.7
-- 1.3.6.1.4.1.37950.1.1.5.10.16.1.7
-- 1.3.6.1.4.1.37950.1.1.5.10.16.1.7
-- 1.3.6.1.4.1.37950.1.1.5.10.16.1.7
-- 1.3.6.1.4.1.37950.1.1.5.10.16.1.7
-- 1.3.6.1.4.1.37950.1.1.5.10.16.1.7
		-- 1.3.6.1.4.1.37950.1.1.5.10.16.1.7
		version OBJECT-TYPE
			SYNTAX Integer32 (1..2)
			MAX-ACCESS read-write
			STATUS current
			DESCRIPTION
				"Description."
			::= { ripGlobalCfg 7 }

		
--         1.3.6.1.4.1.37950.1.1.5.10.16.1.8
-- 1.3.6.1.4.1.37950.1.1.5.10.16.1.8
-- 1.3.6.1.4.1.37950.1.1.5.10.16.1.8
-- 1.3.6.1.4.1.37950.1.1.5.10.16.1.8
-- 1.3.6.1.4.1.37950.1.1.5.10.16.1.8
-- 1.3.6.1.4.1.37950.1.1.5.10.16.1.8
-- 1.3.6.1.4.1.37950.1.1.5.10.16.1.8
-- 1.3.6.1.4.1.37950.1.1.5.10.16.1.8
		-- 1.3.6.1.4.1.37950.1.1.5.10.16.1.8
		keyChainCfg OBJECT IDENTIFIER ::= { ripGlobalCfg 8 }

		
--         1.3.6.1.4.1.37950.1.1.5.10.16.1.8.1
-- 1.3.6.1.4.1.37950.1.1.5.10.16.1.8.1
-- 1.3.6.1.4.1.37950.1.1.5.10.16.1.8.1
-- 1.3.6.1.4.1.37950.1.1.5.10.16.1.8.1
-- 1.3.6.1.4.1.37950.1.1.5.10.16.1.8.1
-- 1.3.6.1.4.1.37950.1.1.5.10.16.1.8.1
-- 1.3.6.1.4.1.37950.1.1.5.10.16.1.8.1
-- 1.3.6.1.4.1.37950.1.1.5.10.16.1.8.1
		-- 1.3.6.1.4.1.37950.1.1.5.10.16.1.8.1
		keyName OBJECT-TYPE
			SYNTAX OCTET STRING
			MAX-ACCESS read-write
			STATUS current
			DESCRIPTION
				"Description."
			::= { keyChainCfg 1 }

		
--         1.3.6.1.4.1.37950.1.1.5.10.16.1.8.2
-- 1.3.6.1.4.1.37950.1.1.5.10.16.1.8.2
-- 1.3.6.1.4.1.37950.1.1.5.10.16.1.8.2
-- 1.3.6.1.4.1.37950.1.1.5.10.16.1.8.2
-- 1.3.6.1.4.1.37950.1.1.5.10.16.1.8.2
-- 1.3.6.1.4.1.37950.1.1.5.10.16.1.8.2
-- 1.3.6.1.4.1.37950.1.1.5.10.16.1.8.2
-- 1.3.6.1.4.1.37950.1.1.5.10.16.1.8.2
		-- 1.3.6.1.4.1.37950.1.1.5.10.16.1.8.2
		keyId OBJECT-TYPE
			SYNTAX Integer32 (0..2147483647)
			MAX-ACCESS read-write
			STATUS current
			DESCRIPTION
				"Description."
			::= { keyChainCfg 2 }

		
--         1.3.6.1.4.1.37950.1.1.5.10.16.1.8.3
-- 1.3.6.1.4.1.37950.1.1.5.10.16.1.8.3
-- 1.3.6.1.4.1.37950.1.1.5.10.16.1.8.3
-- 1.3.6.1.4.1.37950.1.1.5.10.16.1.8.3
-- 1.3.6.1.4.1.37950.1.1.5.10.16.1.8.3
-- 1.3.6.1.4.1.37950.1.1.5.10.16.1.8.3
-- 1.3.6.1.4.1.37950.1.1.5.10.16.1.8.3
-- 1.3.6.1.4.1.37950.1.1.5.10.16.1.8.3
		-- 1.3.6.1.4.1.37950.1.1.5.10.16.1.8.3
		keyChainString OBJECT-TYPE
			SYNTAX OCTET STRING
			MAX-ACCESS read-write
			STATUS current
			DESCRIPTION
				"Description."
			::= { keyChainCfg 3 }

		
--         1.3.6.1.4.1.37950.1.1.5.10.16.1.8.4
-- 1.3.6.1.4.1.37950.1.1.5.10.16.1.8.4
-- 1.3.6.1.4.1.37950.1.1.5.10.16.1.8.4
-- 1.3.6.1.4.1.37950.1.1.5.10.16.1.8.4
-- 1.3.6.1.4.1.37950.1.1.5.10.16.1.8.4
-- 1.3.6.1.4.1.37950.1.1.5.10.16.1.8.4
-- 1.3.6.1.4.1.37950.1.1.5.10.16.1.8.4
-- 1.3.6.1.4.1.37950.1.1.5.10.16.1.8.4
		-- 1.3.6.1.4.1.37950.1.1.5.10.16.1.8.4
		keyAction OBJECT-TYPE
			SYNTAX INTEGER
				{
				add(1),
				del(2)
				}
			MAX-ACCESS read-write
			STATUS current
			DESCRIPTION
				"Description."
			::= { keyChainCfg 4 }

		
--         1.3.6.1.4.1.37950.1.1.5.10.16.1.9
-- 1.3.6.1.4.1.37950.1.1.5.10.16.1.9
-- 1.3.6.1.4.1.37950.1.1.5.10.16.1.9
-- 1.3.6.1.4.1.37950.1.1.5.10.16.1.9
-- 1.3.6.1.4.1.37950.1.1.5.10.16.1.9
-- 1.3.6.1.4.1.37950.1.1.5.10.16.1.9
-- 1.3.6.1.4.1.37950.1.1.5.10.16.1.9
-- 1.3.6.1.4.1.37950.1.1.5.10.16.1.9
		-- 1.3.6.1.4.1.37950.1.1.5.10.16.1.9
		keyChainTable OBJECT-TYPE
			SYNTAX SEQUENCE OF KeyChainEntry
			MAX-ACCESS not-accessible
			STATUS current
			DESCRIPTION
				"Description."
			::= { ripGlobalCfg 9 }

		
--         1.3.6.1.4.1.37950.1.1.5.10.16.1.9.1
-- 1.3.6.1.4.1.37950.1.1.5.10.16.1.9.1
-- 1.3.6.1.4.1.37950.1.1.5.10.16.1.9.1
-- 1.3.6.1.4.1.37950.1.1.5.10.16.1.9.1
-- 1.3.6.1.4.1.37950.1.1.5.10.16.1.9.1
-- 1.3.6.1.4.1.37950.1.1.5.10.16.1.9.1
-- 1.3.6.1.4.1.37950.1.1.5.10.16.1.9.1
-- 1.3.6.1.4.1.37950.1.1.5.10.16.1.9.1
		-- 1.3.6.1.4.1.37950.1.1.5.10.16.1.9.1
		keyChainEntry OBJECT-TYPE
			SYNTAX KeyChainEntry
			MAX-ACCESS not-accessible
			STATUS current
			DESCRIPTION
				"Description."
			INDEX { keyChainName, keyChainId }
			::= { keyChainTable 1 }

		
		KeyChainEntry ::=
			SEQUENCE { 
				keyChainName
					OCTET STRING,
				keyChainId
					Integer32,
				keyChainStr
					OCTET STRING
			 }

--         1.3.6.1.4.1.37950.1.1.5.10.16.1.9.1.1
-- 1.3.6.1.4.1.37950.1.1.5.10.16.1.9.1.1
-- 1.3.6.1.4.1.37950.1.1.5.10.16.1.9.1.1
-- 1.3.6.1.4.1.37950.1.1.5.10.16.1.9.1.1
-- 1.3.6.1.4.1.37950.1.1.5.10.16.1.9.1.1
-- 1.3.6.1.4.1.37950.1.1.5.10.16.1.9.1.1
-- 1.3.6.1.4.1.37950.1.1.5.10.16.1.9.1.1
-- 1.3.6.1.4.1.37950.1.1.5.10.16.1.9.1.1
		-- 1.3.6.1.4.1.37950.1.1.5.10.16.1.9.1.1
		keyChainName OBJECT-TYPE
			SYNTAX OCTET STRING
			MAX-ACCESS read-only
			STATUS current
			DESCRIPTION
				"Description."
			::= { keyChainEntry 1 }

		
--         1.3.6.1.4.1.37950.1.1.5.10.16.1.9.1.2
-- 1.3.6.1.4.1.37950.1.1.5.10.16.1.9.1.2
-- 1.3.6.1.4.1.37950.1.1.5.10.16.1.9.1.2
-- 1.3.6.1.4.1.37950.1.1.5.10.16.1.9.1.2
-- 1.3.6.1.4.1.37950.1.1.5.10.16.1.9.1.2
-- 1.3.6.1.4.1.37950.1.1.5.10.16.1.9.1.2
-- 1.3.6.1.4.1.37950.1.1.5.10.16.1.9.1.2
-- 1.3.6.1.4.1.37950.1.1.5.10.16.1.9.1.2
		-- 1.3.6.1.4.1.37950.1.1.5.10.16.1.9.1.2
		keyChainId OBJECT-TYPE
			SYNTAX Integer32
			MAX-ACCESS read-only
			STATUS current
			DESCRIPTION
				"Description."
			::= { keyChainEntry 2 }

		
--         1.3.6.1.4.1.37950.1.1.5.10.16.1.9.1.3
-- 1.3.6.1.4.1.37950.1.1.5.10.16.1.9.1.3
-- 1.3.6.1.4.1.37950.1.1.5.10.16.1.9.1.3
-- 1.3.6.1.4.1.37950.1.1.5.10.16.1.9.1.3
-- 1.3.6.1.4.1.37950.1.1.5.10.16.1.9.1.3
-- 1.3.6.1.4.1.37950.1.1.5.10.16.1.9.1.3
-- 1.3.6.1.4.1.37950.1.1.5.10.16.1.9.1.3
-- 1.3.6.1.4.1.37950.1.1.5.10.16.1.9.1.3
		-- 1.3.6.1.4.1.37950.1.1.5.10.16.1.9.1.3
		keyChainStr OBJECT-TYPE
			SYNTAX OCTET STRING
			MAX-ACCESS read-only
			STATUS current
			DESCRIPTION
				"Description."
			::= { keyChainEntry 3 }

		
--         1.3.6.1.4.1.37950.1.1.5.10.16.1.10
-- 1.3.6.1.4.1.37950.1.1.5.10.16.1.10
-- 1.3.6.1.4.1.37950.1.1.5.10.16.1.10
-- 1.3.6.1.4.1.37950.1.1.5.10.16.1.10
-- 1.3.6.1.4.1.37950.1.1.5.10.16.1.10
-- 1.3.6.1.4.1.37950.1.1.5.10.16.1.10
-- 1.3.6.1.4.1.37950.1.1.5.10.16.1.10
-- 1.3.6.1.4.1.37950.1.1.5.10.16.1.10
		-- 1.3.6.1.4.1.37950.1.1.5.10.16.1.10
		offsetListCfg OBJECT IDENTIFIER ::= { ripGlobalCfg 10 }

		
--         1.3.6.1.4.1.37950.1.1.5.10.16.1.10.1
-- 1.3.6.1.4.1.37950.1.1.5.10.16.1.10.1
-- 1.3.6.1.4.1.37950.1.1.5.10.16.1.10.1
-- 1.3.6.1.4.1.37950.1.1.5.10.16.1.10.1
-- 1.3.6.1.4.1.37950.1.1.5.10.16.1.10.1
-- 1.3.6.1.4.1.37950.1.1.5.10.16.1.10.1
-- 1.3.6.1.4.1.37950.1.1.5.10.16.1.10.1
-- 1.3.6.1.4.1.37950.1.1.5.10.16.1.10.1
		-- 1.3.6.1.4.1.37950.1.1.5.10.16.1.10.1
		offsetListId OBJECT-TYPE
			SYNTAX Integer32 (1..99 | 100..199 | 1300..1999 | 2000..2699)
			MAX-ACCESS read-write
			STATUS current
			DESCRIPTION
				"Description."
			::= { offsetListCfg 1 }

		
--         1.3.6.1.4.1.37950.1.1.5.10.16.1.10.2
-- 1.3.6.1.4.1.37950.1.1.5.10.16.1.10.2
-- 1.3.6.1.4.1.37950.1.1.5.10.16.1.10.2
-- 1.3.6.1.4.1.37950.1.1.5.10.16.1.10.2
-- 1.3.6.1.4.1.37950.1.1.5.10.16.1.10.2
-- 1.3.6.1.4.1.37950.1.1.5.10.16.1.10.2
-- 1.3.6.1.4.1.37950.1.1.5.10.16.1.10.2
-- 1.3.6.1.4.1.37950.1.1.5.10.16.1.10.2
		-- 1.3.6.1.4.1.37950.1.1.5.10.16.1.10.2
		offsetType OBJECT-TYPE
			SYNTAX INTEGER
				{
				incoming(1),
				outgoing(2)
				}
			MAX-ACCESS read-write
			STATUS current
			DESCRIPTION
				"Description."
			::= { offsetListCfg 2 }

		
--         1.3.6.1.4.1.37950.1.1.5.10.16.1.10.3
-- 1.3.6.1.4.1.37950.1.1.5.10.16.1.10.3
-- 1.3.6.1.4.1.37950.1.1.5.10.16.1.10.3
-- 1.3.6.1.4.1.37950.1.1.5.10.16.1.10.3
-- 1.3.6.1.4.1.37950.1.1.5.10.16.1.10.3
-- 1.3.6.1.4.1.37950.1.1.5.10.16.1.10.3
-- 1.3.6.1.4.1.37950.1.1.5.10.16.1.10.3
-- 1.3.6.1.4.1.37950.1.1.5.10.16.1.10.3
		-- 1.3.6.1.4.1.37950.1.1.5.10.16.1.10.3
		metricVal OBJECT-TYPE
			SYNTAX Integer32 (0..16)
			MAX-ACCESS read-write
			STATUS current
			DESCRIPTION
				"Description."
			::= { offsetListCfg 3 }

		
--         1.3.6.1.4.1.37950.1.1.5.10.16.1.10.4
-- 1.3.6.1.4.1.37950.1.1.5.10.16.1.10.4
-- 1.3.6.1.4.1.37950.1.1.5.10.16.1.10.4
-- 1.3.6.1.4.1.37950.1.1.5.10.16.1.10.4
-- 1.3.6.1.4.1.37950.1.1.5.10.16.1.10.4
-- 1.3.6.1.4.1.37950.1.1.5.10.16.1.10.4
-- 1.3.6.1.4.1.37950.1.1.5.10.16.1.10.4
-- 1.3.6.1.4.1.37950.1.1.5.10.16.1.10.4
		-- 1.3.6.1.4.1.37950.1.1.5.10.16.1.10.4
		vlanIfNum OBJECT-TYPE
			SYNTAX OCTET STRING
			MAX-ACCESS read-write
			STATUS current
			DESCRIPTION
				"Description."
			::= { offsetListCfg 4 }

		
--         1.3.6.1.4.1.37950.1.1.5.10.16.1.10.5
-- 1.3.6.1.4.1.37950.1.1.5.10.16.1.10.5
-- 1.3.6.1.4.1.37950.1.1.5.10.16.1.10.5
-- 1.3.6.1.4.1.37950.1.1.5.10.16.1.10.5
-- 1.3.6.1.4.1.37950.1.1.5.10.16.1.10.5
-- 1.3.6.1.4.1.37950.1.1.5.10.16.1.10.5
-- 1.3.6.1.4.1.37950.1.1.5.10.16.1.10.5
-- 1.3.6.1.4.1.37950.1.1.5.10.16.1.10.5
		-- 1.3.6.1.4.1.37950.1.1.5.10.16.1.10.5
		offsetListAction OBJECT-TYPE
			SYNTAX INTEGER
				{
				add(1),
				del(2)
				}
			MAX-ACCESS read-write
			STATUS current
			DESCRIPTION
				"Description."
			::= { offsetListCfg 5 }

		
--         1.3.6.1.4.1.37950.1.1.5.10.16.1.11
-- 1.3.6.1.4.1.37950.1.1.5.10.16.1.11
-- 1.3.6.1.4.1.37950.1.1.5.10.16.1.11
-- 1.3.6.1.4.1.37950.1.1.5.10.16.1.11
-- 1.3.6.1.4.1.37950.1.1.5.10.16.1.11
-- 1.3.6.1.4.1.37950.1.1.5.10.16.1.11
-- 1.3.6.1.4.1.37950.1.1.5.10.16.1.11
-- 1.3.6.1.4.1.37950.1.1.5.10.16.1.11
		-- 1.3.6.1.4.1.37950.1.1.5.10.16.1.11
		offsetTable OBJECT-TYPE
			SYNTAX SEQUENCE OF OffsetEntry
			MAX-ACCESS not-accessible
			STATUS current
			DESCRIPTION
				"Description."
			::= { ripGlobalCfg 11 }

		
--         1.3.6.1.4.1.37950.1.1.5.10.16.1.11.1
-- 1.3.6.1.4.1.37950.1.1.5.10.16.1.11.1
-- 1.3.6.1.4.1.37950.1.1.5.10.16.1.11.1
-- 1.3.6.1.4.1.37950.1.1.5.10.16.1.11.1
-- 1.3.6.1.4.1.37950.1.1.5.10.16.1.11.1
-- 1.3.6.1.4.1.37950.1.1.5.10.16.1.11.1
-- 1.3.6.1.4.1.37950.1.1.5.10.16.1.11.1
-- 1.3.6.1.4.1.37950.1.1.5.10.16.1.11.1
		-- 1.3.6.1.4.1.37950.1.1.5.10.16.1.11.1
		offsetEntry OBJECT-TYPE
			SYNTAX OffsetEntry
			MAX-ACCESS not-accessible
			STATUS current
			DESCRIPTION
				"Description."
			INDEX { id, type, metric, vlan }
			::= { offsetTable 1 }

		
		OffsetEntry ::=
			SEQUENCE { 
				id
					Integer32,
				type
					INTEGER,
				metric
					Integer32,
				vlan
					OCTET STRING
			 }

--         1.3.6.1.4.1.37950.1.1.5.10.16.1.11.1.1
-- 1.3.6.1.4.1.37950.1.1.5.10.16.1.11.1.1
-- 1.3.6.1.4.1.37950.1.1.5.10.16.1.11.1.1
-- 1.3.6.1.4.1.37950.1.1.5.10.16.1.11.1.1
-- 1.3.6.1.4.1.37950.1.1.5.10.16.1.11.1.1
-- 1.3.6.1.4.1.37950.1.1.5.10.16.1.11.1.1
-- 1.3.6.1.4.1.37950.1.1.5.10.16.1.11.1.1
-- 1.3.6.1.4.1.37950.1.1.5.10.16.1.11.1.1
		-- 1.3.6.1.4.1.37950.1.1.5.10.16.1.11.1.1
		id OBJECT-TYPE
			SYNTAX Integer32
			MAX-ACCESS read-only
			STATUS current
			DESCRIPTION
				"Description."
			::= { offsetEntry 1 }

		
--         1.3.6.1.4.1.37950.1.1.5.10.16.1.11.1.2
-- 1.3.6.1.4.1.37950.1.1.5.10.16.1.11.1.2
-- 1.3.6.1.4.1.37950.1.1.5.10.16.1.11.1.2
-- 1.3.6.1.4.1.37950.1.1.5.10.16.1.11.1.2
-- 1.3.6.1.4.1.37950.1.1.5.10.16.1.11.1.2
-- 1.3.6.1.4.1.37950.1.1.5.10.16.1.11.1.2
-- 1.3.6.1.4.1.37950.1.1.5.10.16.1.11.1.2
-- 1.3.6.1.4.1.37950.1.1.5.10.16.1.11.1.2
		-- 1.3.6.1.4.1.37950.1.1.5.10.16.1.11.1.2
		type OBJECT-TYPE
			SYNTAX INTEGER
				{
				incoming(1),
				outgoing(2)
				}
			MAX-ACCESS read-only
			STATUS current
			DESCRIPTION
				"Description."
			::= { offsetEntry 2 }

		
--         1.3.6.1.4.1.37950.1.1.5.10.16.1.11.1.3
-- 1.3.6.1.4.1.37950.1.1.5.10.16.1.11.1.3
-- 1.3.6.1.4.1.37950.1.1.5.10.16.1.11.1.3
-- 1.3.6.1.4.1.37950.1.1.5.10.16.1.11.1.3
-- 1.3.6.1.4.1.37950.1.1.5.10.16.1.11.1.3
-- 1.3.6.1.4.1.37950.1.1.5.10.16.1.11.1.3
-- 1.3.6.1.4.1.37950.1.1.5.10.16.1.11.1.3
-- 1.3.6.1.4.1.37950.1.1.5.10.16.1.11.1.3
		-- 1.3.6.1.4.1.37950.1.1.5.10.16.1.11.1.3
		metric OBJECT-TYPE
			SYNTAX Integer32
			MAX-ACCESS read-only
			STATUS current
			DESCRIPTION
				"Description."
			::= { offsetEntry 3 }

		
--         1.3.6.1.4.1.37950.1.1.5.10.16.1.11.1.4
-- 1.3.6.1.4.1.37950.1.1.5.10.16.1.11.1.4
-- 1.3.6.1.4.1.37950.1.1.5.10.16.1.11.1.4
-- 1.3.6.1.4.1.37950.1.1.5.10.16.1.11.1.4
-- 1.3.6.1.4.1.37950.1.1.5.10.16.1.11.1.4
-- 1.3.6.1.4.1.37950.1.1.5.10.16.1.11.1.4
-- 1.3.6.1.4.1.37950.1.1.5.10.16.1.11.1.4
-- 1.3.6.1.4.1.37950.1.1.5.10.16.1.11.1.4
		-- 1.3.6.1.4.1.37950.1.1.5.10.16.1.11.1.4
		vlan OBJECT-TYPE
			SYNTAX OCTET STRING
			MAX-ACCESS read-only
			STATUS current
			DESCRIPTION
				"Description."
			::= { offsetEntry 4 }

		
--         1.3.6.1.4.1.37950.1.1.5.10.16.1.12
-- 1.3.6.1.4.1.37950.1.1.5.10.16.1.12
-- 1.3.6.1.4.1.37950.1.1.5.10.16.1.12
-- 1.3.6.1.4.1.37950.1.1.5.10.16.1.12
-- 1.3.6.1.4.1.37950.1.1.5.10.16.1.12
-- 1.3.6.1.4.1.37950.1.1.5.10.16.1.12
-- 1.3.6.1.4.1.37950.1.1.5.10.16.1.12
-- 1.3.6.1.4.1.37950.1.1.5.10.16.1.12
		-- 1.3.6.1.4.1.37950.1.1.5.10.16.1.12
		ripRedistribute OBJECT IDENTIFIER ::= { ripGlobalCfg 12 }

		
--         1.3.6.1.4.1.37950.1.1.5.10.16.1.12.1
-- 1.3.6.1.4.1.37950.1.1.5.10.16.1.12.1
-- 1.3.6.1.4.1.37950.1.1.5.10.16.1.12.1
-- 1.3.6.1.4.1.37950.1.1.5.10.16.1.12.1
-- 1.3.6.1.4.1.37950.1.1.5.10.16.1.12.1
-- 1.3.6.1.4.1.37950.1.1.5.10.16.1.12.1
-- 1.3.6.1.4.1.37950.1.1.5.10.16.1.12.1
-- 1.3.6.1.4.1.37950.1.1.5.10.16.1.12.1
		-- 1.3.6.1.4.1.37950.1.1.5.10.16.1.12.1
		ripRedis OBJECT-TYPE
			SYNTAX INTEGER
				{
				kernel(1),
				connected(2),
				static(3),
				ospf(4)
				}
			MAX-ACCESS read-write
			STATUS current
			DESCRIPTION
				"Description."
			::= { ripRedistribute 1 }

		
--         1.3.6.1.4.1.37950.1.1.5.10.16.1.12.2
-- 1.3.6.1.4.1.37950.1.1.5.10.16.1.12.2
-- 1.3.6.1.4.1.37950.1.1.5.10.16.1.12.2
-- 1.3.6.1.4.1.37950.1.1.5.10.16.1.12.2
-- 1.3.6.1.4.1.37950.1.1.5.10.16.1.12.2
-- 1.3.6.1.4.1.37950.1.1.5.10.16.1.12.2
-- 1.3.6.1.4.1.37950.1.1.5.10.16.1.12.2
-- 1.3.6.1.4.1.37950.1.1.5.10.16.1.12.2
		-- 1.3.6.1.4.1.37950.1.1.5.10.16.1.12.2
		ripRedisMetric OBJECT-TYPE
			SYNTAX Integer32 (-1..16)
			MAX-ACCESS read-write
			STATUS current
			DESCRIPTION
				"Description."
			::= { ripRedistribute 2 }

		
--         1.3.6.1.4.1.37950.1.1.5.10.16.1.12.3
-- 1.3.6.1.4.1.37950.1.1.5.10.16.1.12.3
-- 1.3.6.1.4.1.37950.1.1.5.10.16.1.12.3
-- 1.3.6.1.4.1.37950.1.1.5.10.16.1.12.3
-- 1.3.6.1.4.1.37950.1.1.5.10.16.1.12.3
-- 1.3.6.1.4.1.37950.1.1.5.10.16.1.12.3
-- 1.3.6.1.4.1.37950.1.1.5.10.16.1.12.3
-- 1.3.6.1.4.1.37950.1.1.5.10.16.1.12.3
		-- 1.3.6.1.4.1.37950.1.1.5.10.16.1.12.3
		ripRedisAction OBJECT-TYPE
			SYNTAX INTEGER
				{
				add(1),
				del(2)
				}
			MAX-ACCESS read-write
			STATUS current
			DESCRIPTION
				"Description."
			::= { ripRedistribute 3 }

		
--         1.3.6.1.4.1.37950.1.1.5.10.16.1.13
-- 1.3.6.1.4.1.37950.1.1.5.10.16.1.13
-- 1.3.6.1.4.1.37950.1.1.5.10.16.1.13
-- 1.3.6.1.4.1.37950.1.1.5.10.16.1.13
-- 1.3.6.1.4.1.37950.1.1.5.10.16.1.13
-- 1.3.6.1.4.1.37950.1.1.5.10.16.1.13
-- 1.3.6.1.4.1.37950.1.1.5.10.16.1.13
-- 1.3.6.1.4.1.37950.1.1.5.10.16.1.13
		-- 1.3.6.1.4.1.37950.1.1.5.10.16.1.13
		ripRedistributeTable OBJECT-TYPE
			SYNTAX SEQUENCE OF RipRedistributeEntry
			MAX-ACCESS not-accessible
			STATUS current
			DESCRIPTION
				"Description."
			::= { ripGlobalCfg 13 }

		
--         1.3.6.1.4.1.37950.1.1.5.10.16.1.13.1
-- 1.3.6.1.4.1.37950.1.1.5.10.16.1.13.1
-- 1.3.6.1.4.1.37950.1.1.5.10.16.1.13.1
-- 1.3.6.1.4.1.37950.1.1.5.10.16.1.13.1
-- 1.3.6.1.4.1.37950.1.1.5.10.16.1.13.1
-- 1.3.6.1.4.1.37950.1.1.5.10.16.1.13.1
-- 1.3.6.1.4.1.37950.1.1.5.10.16.1.13.1
-- 1.3.6.1.4.1.37950.1.1.5.10.16.1.13.1
		-- 1.3.6.1.4.1.37950.1.1.5.10.16.1.13.1
		ripRedistributeEntry OBJECT-TYPE
			SYNTAX RipRedistributeEntry
			MAX-ACCESS not-accessible
			STATUS current
			DESCRIPTION
				"Description."
			INDEX { ripRedistributeType }
			::= { ripRedistributeTable 1 }

		
		RipRedistributeEntry ::=
			SEQUENCE { 
				ripRedistributeType
					INTEGER,
				ripRedistributeMetric
					Integer32
			 }

--         1.3.6.1.4.1.37950.1.1.5.10.16.1.13.1.1
-- 1.3.6.1.4.1.37950.1.1.5.10.16.1.13.1.1
-- 1.3.6.1.4.1.37950.1.1.5.10.16.1.13.1.1
-- 1.3.6.1.4.1.37950.1.1.5.10.16.1.13.1.1
-- 1.3.6.1.4.1.37950.1.1.5.10.16.1.13.1.1
-- 1.3.6.1.4.1.37950.1.1.5.10.16.1.13.1.1
-- 1.3.6.1.4.1.37950.1.1.5.10.16.1.13.1.1
-- 1.3.6.1.4.1.37950.1.1.5.10.16.1.13.1.1
		-- 1.3.6.1.4.1.37950.1.1.5.10.16.1.13.1.1
		ripRedistributeType OBJECT-TYPE
			SYNTAX INTEGER
				{
				kernel(1),
				connected(2),
				static(3),
				ospf(4)
				}
			MAX-ACCESS read-only
			STATUS current
			DESCRIPTION
				"Description."
			::= { ripRedistributeEntry 1 }

		
--         1.3.6.1.4.1.37950.1.1.5.10.16.1.13.1.2
-- 1.3.6.1.4.1.37950.1.1.5.10.16.1.13.1.2
-- 1.3.6.1.4.1.37950.1.1.5.10.16.1.13.1.2
-- 1.3.6.1.4.1.37950.1.1.5.10.16.1.13.1.2
-- 1.3.6.1.4.1.37950.1.1.5.10.16.1.13.1.2
-- 1.3.6.1.4.1.37950.1.1.5.10.16.1.13.1.2
-- 1.3.6.1.4.1.37950.1.1.5.10.16.1.13.1.2
-- 1.3.6.1.4.1.37950.1.1.5.10.16.1.13.1.2
		-- 1.3.6.1.4.1.37950.1.1.5.10.16.1.13.1.2
		ripRedistributeMetric OBJECT-TYPE
			SYNTAX Integer32
			MAX-ACCESS read-only
			STATUS current
			DESCRIPTION
				"Description."
			::= { ripRedistributeEntry 2 }

		
--         1.3.6.1.4.1.37950.1.1.5.10.16.1.14
-- 1.3.6.1.4.1.37950.1.1.5.10.16.1.14
-- 1.3.6.1.4.1.37950.1.1.5.10.16.1.14
-- 1.3.6.1.4.1.37950.1.1.5.10.16.1.14
-- 1.3.6.1.4.1.37950.1.1.5.10.16.1.14
-- 1.3.6.1.4.1.37950.1.1.5.10.16.1.14
-- 1.3.6.1.4.1.37950.1.1.5.10.16.1.14
-- 1.3.6.1.4.1.37950.1.1.5.10.16.1.14
		-- 1.3.6.1.4.1.37950.1.1.5.10.16.1.14
		ripDefaultRedistribute OBJECT IDENTIFIER ::= { ripGlobalCfg 14 }

		
--         1.3.6.1.4.1.37950.1.1.5.10.16.1.14.1
-- 1.3.6.1.4.1.37950.1.1.5.10.16.1.14.1
-- 1.3.6.1.4.1.37950.1.1.5.10.16.1.14.1
-- 1.3.6.1.4.1.37950.1.1.5.10.16.1.14.1
-- 1.3.6.1.4.1.37950.1.1.5.10.16.1.14.1
-- 1.3.6.1.4.1.37950.1.1.5.10.16.1.14.1
-- 1.3.6.1.4.1.37950.1.1.5.10.16.1.14.1
-- 1.3.6.1.4.1.37950.1.1.5.10.16.1.14.1
		-- 1.3.6.1.4.1.37950.1.1.5.10.16.1.14.1
		ripDefRedis OBJECT-TYPE
			SYNTAX INTEGER
				{
				disable(0),
				enable(1)
				}
			MAX-ACCESS read-write
			STATUS current
			DESCRIPTION
				"Description."
			::= { ripDefaultRedistribute 1 }

		
--         1.3.6.1.4.1.37950.1.1.5.10.16.2
-- 1.3.6.1.4.1.37950.1.1.5.10.16.2
-- 1.3.6.1.4.1.37950.1.1.5.10.16.2
-- 1.3.6.1.4.1.37950.1.1.5.10.16.2
-- 1.3.6.1.4.1.37950.1.1.5.10.16.2
-- 1.3.6.1.4.1.37950.1.1.5.10.16.2
-- 1.3.6.1.4.1.37950.1.1.5.10.16.2
-- 1.3.6.1.4.1.37950.1.1.5.10.16.2
		-- 1.3.6.1.4.1.37950.1.1.5.10.16.2
		ripVlanTable OBJECT-TYPE
			SYNTAX SEQUENCE OF RipVlanEntry
			MAX-ACCESS not-accessible
			STATUS current
			DESCRIPTION
				"Description."
			::= { v1600dRip 2 }

		
--         1.3.6.1.4.1.37950.1.1.5.10.16.2.1
-- 1.3.6.1.4.1.37950.1.1.5.10.16.2.1
-- 1.3.6.1.4.1.37950.1.1.5.10.16.2.1
-- 1.3.6.1.4.1.37950.1.1.5.10.16.2.1
-- 1.3.6.1.4.1.37950.1.1.5.10.16.2.1
-- 1.3.6.1.4.1.37950.1.1.5.10.16.2.1
-- 1.3.6.1.4.1.37950.1.1.5.10.16.2.1
-- 1.3.6.1.4.1.37950.1.1.5.10.16.2.1
		-- 1.3.6.1.4.1.37950.1.1.5.10.16.2.1
		ripVlanEntry OBJECT-TYPE
			SYNTAX RipVlanEntry
			MAX-ACCESS not-accessible
			STATUS current
			DESCRIPTION
				"Description."
			INDEX { ripVlanAddress }
			::= { ripVlanTable 1 }

		
		RipVlanEntry ::=
			SEQUENCE { 
				ripVlanAddress
					IpAddress,
				ripAuthType
					INTEGER,
				ripAuthStr
					OCTET STRING,
				authKeyChain
					OCTET STRING,
				sendVer
					INTEGER,
				recvVer
					INTEGER,
				ripVlanstatus
					RowStatus
			 }

--         1.3.6.1.4.1.37950.1.1.5.10.16.2.1.1
-- 1.3.6.1.4.1.37950.1.1.5.10.16.2.1.1
-- 1.3.6.1.4.1.37950.1.1.5.10.16.2.1.1
-- 1.3.6.1.4.1.37950.1.1.5.10.16.2.1.1
-- 1.3.6.1.4.1.37950.1.1.5.10.16.2.1.1
-- 1.3.6.1.4.1.37950.1.1.5.10.16.2.1.1
-- 1.3.6.1.4.1.37950.1.1.5.10.16.2.1.1
-- 1.3.6.1.4.1.37950.1.1.5.10.16.2.1.1
		-- 1.3.6.1.4.1.37950.1.1.5.10.16.2.1.1
		ripVlanAddress OBJECT-TYPE
			SYNTAX IpAddress
			MAX-ACCESS read-only
			STATUS current
			DESCRIPTION
				"Description."
			::= { ripVlanEntry 1 }

		
--         1.3.6.1.4.1.37950.1.1.5.10.16.2.1.2
-- 1.3.6.1.4.1.37950.1.1.5.10.16.2.1.2
-- 1.3.6.1.4.1.37950.1.1.5.10.16.2.1.2
-- 1.3.6.1.4.1.37950.1.1.5.10.16.2.1.2
-- 1.3.6.1.4.1.37950.1.1.5.10.16.2.1.2
-- 1.3.6.1.4.1.37950.1.1.5.10.16.2.1.2
-- 1.3.6.1.4.1.37950.1.1.5.10.16.2.1.2
-- 1.3.6.1.4.1.37950.1.1.5.10.16.2.1.2
		-- 1.3.6.1.4.1.37950.1.1.5.10.16.2.1.2
		ripAuthType OBJECT-TYPE
			SYNTAX INTEGER
				{
				noAuthentication(1),
				simplePassword(2),
				md5(3)
				}
			MAX-ACCESS read-write
			STATUS current
			DESCRIPTION
				"Description."
			::= { ripVlanEntry 2 }

		
--         1.3.6.1.4.1.37950.1.1.5.10.16.2.1.3
-- 1.3.6.1.4.1.37950.1.1.5.10.16.2.1.3
-- 1.3.6.1.4.1.37950.1.1.5.10.16.2.1.3
-- 1.3.6.1.4.1.37950.1.1.5.10.16.2.1.3
-- 1.3.6.1.4.1.37950.1.1.5.10.16.2.1.3
-- 1.3.6.1.4.1.37950.1.1.5.10.16.2.1.3
-- 1.3.6.1.4.1.37950.1.1.5.10.16.2.1.3
-- 1.3.6.1.4.1.37950.1.1.5.10.16.2.1.3
		-- 1.3.6.1.4.1.37950.1.1.5.10.16.2.1.3
		ripAuthStr OBJECT-TYPE
			SYNTAX OCTET STRING
			MAX-ACCESS read-write
			STATUS current
			DESCRIPTION
				"Description."
			::= { ripVlanEntry 3 }

		
--         1.3.6.1.4.1.37950.1.1.5.10.16.2.1.4
-- 1.3.6.1.4.1.37950.1.1.5.10.16.2.1.4
-- 1.3.6.1.4.1.37950.1.1.5.10.16.2.1.4
-- 1.3.6.1.4.1.37950.1.1.5.10.16.2.1.4
-- 1.3.6.1.4.1.37950.1.1.5.10.16.2.1.4
-- 1.3.6.1.4.1.37950.1.1.5.10.16.2.1.4
-- 1.3.6.1.4.1.37950.1.1.5.10.16.2.1.4
-- 1.3.6.1.4.1.37950.1.1.5.10.16.2.1.4
		-- 1.3.6.1.4.1.37950.1.1.5.10.16.2.1.4
		authKeyChain OBJECT-TYPE
			SYNTAX OCTET STRING
			MAX-ACCESS read-write
			STATUS current
			DESCRIPTION
				"Description."
			::= { ripVlanEntry 4 }

		
--         1.3.6.1.4.1.37950.1.1.5.10.16.2.1.5
-- 1.3.6.1.4.1.37950.1.1.5.10.16.2.1.5
-- 1.3.6.1.4.1.37950.1.1.5.10.16.2.1.5
-- 1.3.6.1.4.1.37950.1.1.5.10.16.2.1.5
-- 1.3.6.1.4.1.37950.1.1.5.10.16.2.1.5
-- 1.3.6.1.4.1.37950.1.1.5.10.16.2.1.5
-- 1.3.6.1.4.1.37950.1.1.5.10.16.2.1.5
-- 1.3.6.1.4.1.37950.1.1.5.10.16.2.1.5
		-- 1.3.6.1.4.1.37950.1.1.5.10.16.2.1.5
		sendVer OBJECT-TYPE
			SYNTAX INTEGER
				{
				version1(1),
				version2(2),
				version1and2(3)
				}
			MAX-ACCESS read-write
			STATUS current
			DESCRIPTION
				"Description."
			::= { ripVlanEntry 5 }

		
--         1.3.6.1.4.1.37950.1.1.5.10.16.2.1.6
-- 1.3.6.1.4.1.37950.1.1.5.10.16.2.1.6
-- 1.3.6.1.4.1.37950.1.1.5.10.16.2.1.6
-- 1.3.6.1.4.1.37950.1.1.5.10.16.2.1.6
-- 1.3.6.1.4.1.37950.1.1.5.10.16.2.1.6
-- 1.3.6.1.4.1.37950.1.1.5.10.16.2.1.6
-- 1.3.6.1.4.1.37950.1.1.5.10.16.2.1.6
-- 1.3.6.1.4.1.37950.1.1.5.10.16.2.1.6
		-- 1.3.6.1.4.1.37950.1.1.5.10.16.2.1.6
		recvVer OBJECT-TYPE
			SYNTAX INTEGER
				{
				version1(1),
				version2(2),
				version1and2(3)
				}
			MAX-ACCESS read-write
			STATUS current
			DESCRIPTION
				"Description."
			::= { ripVlanEntry 6 }

		
--         1.3.6.1.4.1.37950.1.1.5.10.16.2.1.7
-- 1.3.6.1.4.1.37950.1.1.5.10.16.2.1.7
-- 1.3.6.1.4.1.37950.1.1.5.10.16.2.1.7
-- 1.3.6.1.4.1.37950.1.1.5.10.16.2.1.7
-- 1.3.6.1.4.1.37950.1.1.5.10.16.2.1.7
-- 1.3.6.1.4.1.37950.1.1.5.10.16.2.1.7
-- 1.3.6.1.4.1.37950.1.1.5.10.16.2.1.7
-- 1.3.6.1.4.1.37950.1.1.5.10.16.2.1.7
		-- 1.3.6.1.4.1.37950.1.1.5.10.16.2.1.7
		ripVlanstatus OBJECT-TYPE
			SYNTAX RowStatus
			MAX-ACCESS read-create
			STATUS current
			DESCRIPTION
				"Description."
			::= { ripVlanEntry 7 }

		
--         1.3.6.1.4.1.37950.1.1.5.10.16.3
-- 1.3.6.1.4.1.37950.1.1.5.10.16.3
-- 1.3.6.1.4.1.37950.1.1.5.10.16.3
-- 1.3.6.1.4.1.37950.1.1.5.10.16.3
-- 1.3.6.1.4.1.37950.1.1.5.10.16.3
-- 1.3.6.1.4.1.37950.1.1.5.10.16.3
-- 1.3.6.1.4.1.37950.1.1.5.10.16.3
-- 1.3.6.1.4.1.37950.1.1.5.10.16.3
		-- 1.3.6.1.4.1.37950.1.1.5.10.16.3
		ripTable OBJECT-TYPE
			SYNTAX SEQUENCE OF RipEntry
			MAX-ACCESS not-accessible
			STATUS current
			DESCRIPTION
				"Description."
			::= { v1600dRip 3 }

		
--         1.3.6.1.4.1.37950.1.1.5.10.16.3.1
-- 1.3.6.1.4.1.37950.1.1.5.10.16.3.1
-- 1.3.6.1.4.1.37950.1.1.5.10.16.3.1
-- 1.3.6.1.4.1.37950.1.1.5.10.16.3.1
-- 1.3.6.1.4.1.37950.1.1.5.10.16.3.1
-- 1.3.6.1.4.1.37950.1.1.5.10.16.3.1
-- 1.3.6.1.4.1.37950.1.1.5.10.16.3.1
-- 1.3.6.1.4.1.37950.1.1.5.10.16.3.1
		-- 1.3.6.1.4.1.37950.1.1.5.10.16.3.1
		ripEntry OBJECT-TYPE
			SYNTAX RipEntry
			MAX-ACCESS not-accessible
			STATUS current
			DESCRIPTION
				"Description."
			INDEX { ripNetwork }
			::= { ripTable 1 }

		
		RipEntry ::=
			SEQUENCE { 
				ripNetworkType
					OCTET STRING,
				ripNetwork
					OCTET STRING,
				ripNextHop
					IpAddress,
				ripMetric
					Integer32,
				ripFrom
					OCTET STRING,
				ripTag
					Integer32,
				ripTime
					OCTET STRING
			 }

--         1.3.6.1.4.1.37950.1.1.5.10.16.3.1.1
-- 1.3.6.1.4.1.37950.1.1.5.10.16.3.1.1
-- 1.3.6.1.4.1.37950.1.1.5.10.16.3.1.1
-- 1.3.6.1.4.1.37950.1.1.5.10.16.3.1.1
-- 1.3.6.1.4.1.37950.1.1.5.10.16.3.1.1
-- 1.3.6.1.4.1.37950.1.1.5.10.16.3.1.1
-- 1.3.6.1.4.1.37950.1.1.5.10.16.3.1.1
-- 1.3.6.1.4.1.37950.1.1.5.10.16.3.1.1
		-- 1.3.6.1.4.1.37950.1.1.5.10.16.3.1.1
		ripNetworkType OBJECT-TYPE
			SYNTAX OCTET STRING
			MAX-ACCESS read-only
			STATUS current
			DESCRIPTION
				"Description."
			::= { ripEntry 1 }

		
--         1.3.6.1.4.1.37950.1.1.5.10.16.3.1.2
-- 1.3.6.1.4.1.37950.1.1.5.10.16.3.1.2
-- 1.3.6.1.4.1.37950.1.1.5.10.16.3.1.2
-- 1.3.6.1.4.1.37950.1.1.5.10.16.3.1.2
-- 1.3.6.1.4.1.37950.1.1.5.10.16.3.1.2
-- 1.3.6.1.4.1.37950.1.1.5.10.16.3.1.2
-- 1.3.6.1.4.1.37950.1.1.5.10.16.3.1.2
-- 1.3.6.1.4.1.37950.1.1.5.10.16.3.1.2
		-- 1.3.6.1.4.1.37950.1.1.5.10.16.3.1.2
		ripNetwork OBJECT-TYPE
			SYNTAX OCTET STRING
			MAX-ACCESS read-only
			STATUS current
			DESCRIPTION
				"Description."
			::= { ripEntry 2 }

		
--         1.3.6.1.4.1.37950.1.1.5.10.16.3.1.3
-- 1.3.6.1.4.1.37950.1.1.5.10.16.3.1.3
-- 1.3.6.1.4.1.37950.1.1.5.10.16.3.1.3
-- 1.3.6.1.4.1.37950.1.1.5.10.16.3.1.3
-- 1.3.6.1.4.1.37950.1.1.5.10.16.3.1.3
-- 1.3.6.1.4.1.37950.1.1.5.10.16.3.1.3
-- 1.3.6.1.4.1.37950.1.1.5.10.16.3.1.3
-- 1.3.6.1.4.1.37950.1.1.5.10.16.3.1.3
		-- 1.3.6.1.4.1.37950.1.1.5.10.16.3.1.3
		ripNextHop OBJECT-TYPE
			SYNTAX IpAddress
			MAX-ACCESS read-only
			STATUS current
			DESCRIPTION
				"Description."
			::= { ripEntry 3 }

		
--         1.3.6.1.4.1.37950.1.1.5.10.16.3.1.4
-- 1.3.6.1.4.1.37950.1.1.5.10.16.3.1.4
-- 1.3.6.1.4.1.37950.1.1.5.10.16.3.1.4
-- 1.3.6.1.4.1.37950.1.1.5.10.16.3.1.4
-- 1.3.6.1.4.1.37950.1.1.5.10.16.3.1.4
-- 1.3.6.1.4.1.37950.1.1.5.10.16.3.1.4
-- 1.3.6.1.4.1.37950.1.1.5.10.16.3.1.4
-- 1.3.6.1.4.1.37950.1.1.5.10.16.3.1.4
		-- 1.3.6.1.4.1.37950.1.1.5.10.16.3.1.4
		ripMetric OBJECT-TYPE
			SYNTAX Integer32
			MAX-ACCESS read-only
			STATUS current
			DESCRIPTION
				"Description."
			::= { ripEntry 4 }

		
--         1.3.6.1.4.1.37950.1.1.5.10.16.3.1.5
-- 1.3.6.1.4.1.37950.1.1.5.10.16.3.1.5
-- 1.3.6.1.4.1.37950.1.1.5.10.16.3.1.5
-- 1.3.6.1.4.1.37950.1.1.5.10.16.3.1.5
-- 1.3.6.1.4.1.37950.1.1.5.10.16.3.1.5
-- 1.3.6.1.4.1.37950.1.1.5.10.16.3.1.5
-- 1.3.6.1.4.1.37950.1.1.5.10.16.3.1.5
-- 1.3.6.1.4.1.37950.1.1.5.10.16.3.1.5
		-- 1.3.6.1.4.1.37950.1.1.5.10.16.3.1.5
		ripFrom OBJECT-TYPE
			SYNTAX OCTET STRING
			MAX-ACCESS read-only
			STATUS current
			DESCRIPTION
				"Description."
			::= { ripEntry 5 }

		
--         1.3.6.1.4.1.37950.1.1.5.10.16.3.1.6
-- 1.3.6.1.4.1.37950.1.1.5.10.16.3.1.6
-- 1.3.6.1.4.1.37950.1.1.5.10.16.3.1.6
-- 1.3.6.1.4.1.37950.1.1.5.10.16.3.1.6
-- 1.3.6.1.4.1.37950.1.1.5.10.16.3.1.6
-- 1.3.6.1.4.1.37950.1.1.5.10.16.3.1.6
-- 1.3.6.1.4.1.37950.1.1.5.10.16.3.1.6
-- 1.3.6.1.4.1.37950.1.1.5.10.16.3.1.6
		-- 1.3.6.1.4.1.37950.1.1.5.10.16.3.1.6
		ripTag OBJECT-TYPE
			SYNTAX Integer32
			MAX-ACCESS read-only
			STATUS current
			DESCRIPTION
				"Description."
			::= { ripEntry 6 }

		
--         1.3.6.1.4.1.37950.1.1.5.10.16.3.1.7
-- 1.3.6.1.4.1.37950.1.1.5.10.16.3.1.7
-- 1.3.6.1.4.1.37950.1.1.5.10.16.3.1.7
-- 1.3.6.1.4.1.37950.1.1.5.10.16.3.1.7
-- 1.3.6.1.4.1.37950.1.1.5.10.16.3.1.7
-- 1.3.6.1.4.1.37950.1.1.5.10.16.3.1.7
-- 1.3.6.1.4.1.37950.1.1.5.10.16.3.1.7
-- 1.3.6.1.4.1.37950.1.1.5.10.16.3.1.7
		-- 1.3.6.1.4.1.37950.1.1.5.10.16.3.1.7
		ripTime OBJECT-TYPE
			SYNTAX OCTET STRING
			MAX-ACCESS read-only
			STATUS current
			DESCRIPTION
				"Description."
			::= { ripEntry 7 }

		
--         1.3.6.1.4.1.37950.1.1.5.10.16.4
-- 1.3.6.1.4.1.37950.1.1.5.10.16.4
-- 1.3.6.1.4.1.37950.1.1.5.10.16.4
-- 1.3.6.1.4.1.37950.1.1.5.10.16.4
-- 1.3.6.1.4.1.37950.1.1.5.10.16.4
-- 1.3.6.1.4.1.37950.1.1.5.10.16.4
-- 1.3.6.1.4.1.37950.1.1.5.10.16.4
-- 1.3.6.1.4.1.37950.1.1.5.10.16.4
		-- 1.3.6.1.4.1.37950.1.1.5.10.16.4
		ripPeerTable OBJECT-TYPE
			SYNTAX SEQUENCE OF RipPeerEntry
			MAX-ACCESS not-accessible
			STATUS current
			DESCRIPTION
				"Description."
			::= { v1600dRip 4 }

		
--         1.3.6.1.4.1.37950.1.1.5.10.16.4.1
-- 1.3.6.1.4.1.37950.1.1.5.10.16.4.1
-- 1.3.6.1.4.1.37950.1.1.5.10.16.4.1
-- 1.3.6.1.4.1.37950.1.1.5.10.16.4.1
-- 1.3.6.1.4.1.37950.1.1.5.10.16.4.1
-- 1.3.6.1.4.1.37950.1.1.5.10.16.4.1
-- 1.3.6.1.4.1.37950.1.1.5.10.16.4.1
-- 1.3.6.1.4.1.37950.1.1.5.10.16.4.1
		-- 1.3.6.1.4.1.37950.1.1.5.10.16.4.1
		ripPeerEntry OBJECT-TYPE
			SYNTAX RipPeerEntry
			MAX-ACCESS not-accessible
			STATUS current
			DESCRIPTION
				"Description."
			INDEX { ripPeerAddress }
			::= { ripPeerTable 1 }

		
		RipPeerEntry ::=
			SEQUENCE { 
				ripPeerAddress
					IpAddress,
				ripPeerVersion
					Integer32,
				ripPeerDistance
					Integer32,
				ripPeerRcvBadPackets
					Counter32,
				ripPeerRcvBadRoutes
					Counter32,
				ripPeerLastUpdate
					TimeTicks
			 }

--         1.3.6.1.4.1.37950.1.1.5.10.16.4.1.1
-- 1.3.6.1.4.1.37950.1.1.5.10.16.4.1.1
-- 1.3.6.1.4.1.37950.1.1.5.10.16.4.1.1
-- 1.3.6.1.4.1.37950.1.1.5.10.16.4.1.1
-- 1.3.6.1.4.1.37950.1.1.5.10.16.4.1.1
-- 1.3.6.1.4.1.37950.1.1.5.10.16.4.1.1
-- 1.3.6.1.4.1.37950.1.1.5.10.16.4.1.1
-- 1.3.6.1.4.1.37950.1.1.5.10.16.4.1.1
		-- 1.3.6.1.4.1.37950.1.1.5.10.16.4.1.1
		ripPeerAddress OBJECT-TYPE
			SYNTAX IpAddress
			MAX-ACCESS read-only
			STATUS current
			DESCRIPTION
				"Description."
			::= { ripPeerEntry 1 }

		
--         1.3.6.1.4.1.37950.1.1.5.10.16.4.1.2
-- 1.3.6.1.4.1.37950.1.1.5.10.16.4.1.2
-- 1.3.6.1.4.1.37950.1.1.5.10.16.4.1.2
-- 1.3.6.1.4.1.37950.1.1.5.10.16.4.1.2
-- 1.3.6.1.4.1.37950.1.1.5.10.16.4.1.2
-- 1.3.6.1.4.1.37950.1.1.5.10.16.4.1.2
-- 1.3.6.1.4.1.37950.1.1.5.10.16.4.1.2
-- 1.3.6.1.4.1.37950.1.1.5.10.16.4.1.2
		-- 1.3.6.1.4.1.37950.1.1.5.10.16.4.1.2
		ripPeerVersion OBJECT-TYPE
			SYNTAX Integer32
			MAX-ACCESS read-only
			STATUS current
			DESCRIPTION
				"Description."
			::= { ripPeerEntry 2 }

		
--         1.3.6.1.4.1.37950.1.1.5.10.16.4.1.3
-- 1.3.6.1.4.1.37950.1.1.5.10.16.4.1.3
-- 1.3.6.1.4.1.37950.1.1.5.10.16.4.1.3
-- 1.3.6.1.4.1.37950.1.1.5.10.16.4.1.3
-- 1.3.6.1.4.1.37950.1.1.5.10.16.4.1.3
-- 1.3.6.1.4.1.37950.1.1.5.10.16.4.1.3
-- 1.3.6.1.4.1.37950.1.1.5.10.16.4.1.3
-- 1.3.6.1.4.1.37950.1.1.5.10.16.4.1.3
		-- 1.3.6.1.4.1.37950.1.1.5.10.16.4.1.3
		ripPeerDistance OBJECT-TYPE
			SYNTAX Integer32
			MAX-ACCESS read-only
			STATUS current
			DESCRIPTION
				"Description."
			::= { ripPeerEntry 3 }

		
--         1.3.6.1.4.1.37950.1.1.5.10.16.4.1.4
-- 1.3.6.1.4.1.37950.1.1.5.10.16.4.1.4
-- 1.3.6.1.4.1.37950.1.1.5.10.16.4.1.4
-- 1.3.6.1.4.1.37950.1.1.5.10.16.4.1.4
-- 1.3.6.1.4.1.37950.1.1.5.10.16.4.1.4
-- 1.3.6.1.4.1.37950.1.1.5.10.16.4.1.4
-- 1.3.6.1.4.1.37950.1.1.5.10.16.4.1.4
-- 1.3.6.1.4.1.37950.1.1.5.10.16.4.1.4
		-- 1.3.6.1.4.1.37950.1.1.5.10.16.4.1.4
		ripPeerRcvBadPackets OBJECT-TYPE
			SYNTAX Counter32
			MAX-ACCESS read-only
			STATUS current
			DESCRIPTION
				"Description."
			::= { ripPeerEntry 4 }

		
--         1.3.6.1.4.1.37950.1.1.5.10.16.4.1.5
-- 1.3.6.1.4.1.37950.1.1.5.10.16.4.1.5
-- 1.3.6.1.4.1.37950.1.1.5.10.16.4.1.5
-- 1.3.6.1.4.1.37950.1.1.5.10.16.4.1.5
-- 1.3.6.1.4.1.37950.1.1.5.10.16.4.1.5
-- 1.3.6.1.4.1.37950.1.1.5.10.16.4.1.5
-- 1.3.6.1.4.1.37950.1.1.5.10.16.4.1.5
-- 1.3.6.1.4.1.37950.1.1.5.10.16.4.1.5
		-- 1.3.6.1.4.1.37950.1.1.5.10.16.4.1.5
		ripPeerRcvBadRoutes OBJECT-TYPE
			SYNTAX Counter32
			MAX-ACCESS read-only
			STATUS current
			DESCRIPTION
				"Description."
			::= { ripPeerEntry 5 }

		
--         1.3.6.1.4.1.37950.1.1.5.10.16.4.1.6
-- 1.3.6.1.4.1.37950.1.1.5.10.16.4.1.6
-- 1.3.6.1.4.1.37950.1.1.5.10.16.4.1.6
-- 1.3.6.1.4.1.37950.1.1.5.10.16.4.1.6
-- 1.3.6.1.4.1.37950.1.1.5.10.16.4.1.6
-- 1.3.6.1.4.1.37950.1.1.5.10.16.4.1.6
-- 1.3.6.1.4.1.37950.1.1.5.10.16.4.1.6
-- 1.3.6.1.4.1.37950.1.1.5.10.16.4.1.6
		-- 1.3.6.1.4.1.37950.1.1.5.10.16.4.1.6
		ripPeerLastUpdate OBJECT-TYPE
			SYNTAX TimeTicks
			MAX-ACCESS read-only
			STATUS current
			DESCRIPTION
				"Description."
			::= { ripPeerEntry 6 }

		
--         1.3.6.1.4.1.37950.1.1.5.10.17
-- 1.3.6.1.4.1.37950.1.1.5.10.17
-- 1.3.6.1.4.1.37950.1.1.5.10.17
-- 1.3.6.1.4.1.37950.1.1.5.10.17
-- 1.3.6.1.4.1.37950.1.1.5.10.17
-- 1.3.6.1.4.1.37950.1.1.5.10.17
-- 1.3.6.1.4.1.37950.1.1.5.10.17
-- 1.3.6.1.4.1.37950.1.1.5.10.17
		-- 1.3.6.1.4.1.37950.1.1.5.10.17
		v1600dOspf OBJECT IDENTIFIER ::= { v1600dSwitch 17 }

		
--         1.3.6.1.4.1.37950.1.1.5.10.17.1
-- 1.3.6.1.4.1.37950.1.1.5.10.17.1
-- 1.3.6.1.4.1.37950.1.1.5.10.17.1
-- 1.3.6.1.4.1.37950.1.1.5.10.17.1
-- 1.3.6.1.4.1.37950.1.1.5.10.17.1
-- 1.3.6.1.4.1.37950.1.1.5.10.17.1
-- 1.3.6.1.4.1.37950.1.1.5.10.17.1
-- 1.3.6.1.4.1.37950.1.1.5.10.17.1
		-- 1.3.6.1.4.1.37950.1.1.5.10.17.1
		ospfGlobal OBJECT IDENTIFIER ::= { v1600dOspf 1 }

		
--         1.3.6.1.4.1.37950.1.1.5.10.17.1.1
-- 1.3.6.1.4.1.37950.1.1.5.10.17.1.1
-- 1.3.6.1.4.1.37950.1.1.5.10.17.1.1
-- 1.3.6.1.4.1.37950.1.1.5.10.17.1.1
-- 1.3.6.1.4.1.37950.1.1.5.10.17.1.1
-- 1.3.6.1.4.1.37950.1.1.5.10.17.1.1
-- 1.3.6.1.4.1.37950.1.1.5.10.17.1.1
-- 1.3.6.1.4.1.37950.1.1.5.10.17.1.1
		-- 1.3.6.1.4.1.37950.1.1.5.10.17.1.1
		ospfRouteEn OBJECT-TYPE
			SYNTAX INTEGER
				{
				enable(1),
				disable(2)
				}
			MAX-ACCESS read-write
			STATUS current
			DESCRIPTION
				"Description."
			::= { ospfGlobal 1 }

		
--         1.3.6.1.4.1.37950.1.1.5.10.17.1.2
-- 1.3.6.1.4.1.37950.1.1.5.10.17.1.2
-- 1.3.6.1.4.1.37950.1.1.5.10.17.1.2
-- 1.3.6.1.4.1.37950.1.1.5.10.17.1.2
-- 1.3.6.1.4.1.37950.1.1.5.10.17.1.2
-- 1.3.6.1.4.1.37950.1.1.5.10.17.1.2
-- 1.3.6.1.4.1.37950.1.1.5.10.17.1.2
-- 1.3.6.1.4.1.37950.1.1.5.10.17.1.2
		-- 1.3.6.1.4.1.37950.1.1.5.10.17.1.2
		ospfGlobalRouterId OBJECT-TYPE
			SYNTAX IpAddress
			MAX-ACCESS read-write
			STATUS current
			DESCRIPTION
				"Description."
			::= { ospfGlobal 2 }

		
--         1.3.6.1.4.1.37950.1.1.5.10.17.1.3
-- 1.3.6.1.4.1.37950.1.1.5.10.17.1.3
-- 1.3.6.1.4.1.37950.1.1.5.10.17.1.3
-- 1.3.6.1.4.1.37950.1.1.5.10.17.1.3
-- 1.3.6.1.4.1.37950.1.1.5.10.17.1.3
-- 1.3.6.1.4.1.37950.1.1.5.10.17.1.3
-- 1.3.6.1.4.1.37950.1.1.5.10.17.1.3
-- 1.3.6.1.4.1.37950.1.1.5.10.17.1.3
		-- 1.3.6.1.4.1.37950.1.1.5.10.17.1.3
		ospfRedistribute OBJECT IDENTIFIER ::= { ospfGlobal 3 }

		
--         1.3.6.1.4.1.37950.1.1.5.10.17.1.3.1
-- 1.3.6.1.4.1.37950.1.1.5.10.17.1.3.1
-- 1.3.6.1.4.1.37950.1.1.5.10.17.1.3.1
-- 1.3.6.1.4.1.37950.1.1.5.10.17.1.3.1
-- 1.3.6.1.4.1.37950.1.1.5.10.17.1.3.1
-- 1.3.6.1.4.1.37950.1.1.5.10.17.1.3.1
-- 1.3.6.1.4.1.37950.1.1.5.10.17.1.3.1
-- 1.3.6.1.4.1.37950.1.1.5.10.17.1.3.1
		-- 1.3.6.1.4.1.37950.1.1.5.10.17.1.3.1
		redistribute OBJECT-TYPE
			SYNTAX INTEGER
				{
				kernel(1),
				connected(2),
				static(3),
				rip(4)
				}
			MAX-ACCESS read-write
			STATUS current
			DESCRIPTION
				"Description."
			::= { ospfRedistribute 1 }

		
--         1.3.6.1.4.1.37950.1.1.5.10.17.1.3.2
-- 1.3.6.1.4.1.37950.1.1.5.10.17.1.3.2
-- 1.3.6.1.4.1.37950.1.1.5.10.17.1.3.2
-- 1.3.6.1.4.1.37950.1.1.5.10.17.1.3.2
-- 1.3.6.1.4.1.37950.1.1.5.10.17.1.3.2
-- 1.3.6.1.4.1.37950.1.1.5.10.17.1.3.2
-- 1.3.6.1.4.1.37950.1.1.5.10.17.1.3.2
-- 1.3.6.1.4.1.37950.1.1.5.10.17.1.3.2
		-- 1.3.6.1.4.1.37950.1.1.5.10.17.1.3.2
		redisMetric OBJECT-TYPE
			SYNTAX Integer32 (-1..16777214)
			MAX-ACCESS read-write
			STATUS current
			DESCRIPTION
				"Description."
			::= { ospfRedistribute 2 }

		
--         1.3.6.1.4.1.37950.1.1.5.10.17.1.3.3
-- 1.3.6.1.4.1.37950.1.1.5.10.17.1.3.3
-- 1.3.6.1.4.1.37950.1.1.5.10.17.1.3.3
-- 1.3.6.1.4.1.37950.1.1.5.10.17.1.3.3
-- 1.3.6.1.4.1.37950.1.1.5.10.17.1.3.3
-- 1.3.6.1.4.1.37950.1.1.5.10.17.1.3.3
-- 1.3.6.1.4.1.37950.1.1.5.10.17.1.3.3
-- 1.3.6.1.4.1.37950.1.1.5.10.17.1.3.3
		-- 1.3.6.1.4.1.37950.1.1.5.10.17.1.3.3
		redisMetricType OBJECT-TYPE
			SYNTAX Integer32 (-1 | 1..2)
			MAX-ACCESS read-write
			STATUS current
			DESCRIPTION
				"Description."
			::= { ospfRedistribute 3 }

		
--         1.3.6.1.4.1.37950.1.1.5.10.17.1.3.4
-- 1.3.6.1.4.1.37950.1.1.5.10.17.1.3.4
-- 1.3.6.1.4.1.37950.1.1.5.10.17.1.3.4
-- 1.3.6.1.4.1.37950.1.1.5.10.17.1.3.4
-- 1.3.6.1.4.1.37950.1.1.5.10.17.1.3.4
-- 1.3.6.1.4.1.37950.1.1.5.10.17.1.3.4
-- 1.3.6.1.4.1.37950.1.1.5.10.17.1.3.4
-- 1.3.6.1.4.1.37950.1.1.5.10.17.1.3.4
		-- 1.3.6.1.4.1.37950.1.1.5.10.17.1.3.4
		redisRouteMap OBJECT-TYPE
			SYNTAX OCTET STRING
			MAX-ACCESS read-write
			STATUS current
			DESCRIPTION
				"Description."
			::= { ospfRedistribute 4 }

		
--         1.3.6.1.4.1.37950.1.1.5.10.17.1.3.5
-- 1.3.6.1.4.1.37950.1.1.5.10.17.1.3.5
-- 1.3.6.1.4.1.37950.1.1.5.10.17.1.3.5
-- 1.3.6.1.4.1.37950.1.1.5.10.17.1.3.5
-- 1.3.6.1.4.1.37950.1.1.5.10.17.1.3.5
-- 1.3.6.1.4.1.37950.1.1.5.10.17.1.3.5
-- 1.3.6.1.4.1.37950.1.1.5.10.17.1.3.5
-- 1.3.6.1.4.1.37950.1.1.5.10.17.1.3.5
		-- 1.3.6.1.4.1.37950.1.1.5.10.17.1.3.5
		redisAction OBJECT-TYPE
			SYNTAX INTEGER
				{
				add(1),
				del(2)
				}
			MAX-ACCESS read-write
			STATUS current
			DESCRIPTION
				"Description."
			::= { ospfRedistribute 5 }

		
--         1.3.6.1.4.1.37950.1.1.5.10.17.1.4
-- 1.3.6.1.4.1.37950.1.1.5.10.17.1.4
-- 1.3.6.1.4.1.37950.1.1.5.10.17.1.4
-- 1.3.6.1.4.1.37950.1.1.5.10.17.1.4
-- 1.3.6.1.4.1.37950.1.1.5.10.17.1.4
-- 1.3.6.1.4.1.37950.1.1.5.10.17.1.4
-- 1.3.6.1.4.1.37950.1.1.5.10.17.1.4
-- 1.3.6.1.4.1.37950.1.1.5.10.17.1.4
		-- 1.3.6.1.4.1.37950.1.1.5.10.17.1.4
		ospfRedistributeTable OBJECT-TYPE
			SYNTAX SEQUENCE OF OspfRedistributeEntry
			MAX-ACCESS not-accessible
			STATUS current
			DESCRIPTION
				"Description."
			::= { ospfGlobal 4 }

		
--         1.3.6.1.4.1.37950.1.1.5.10.17.1.4.1
-- 1.3.6.1.4.1.37950.1.1.5.10.17.1.4.1
-- 1.3.6.1.4.1.37950.1.1.5.10.17.1.4.1
-- 1.3.6.1.4.1.37950.1.1.5.10.17.1.4.1
-- 1.3.6.1.4.1.37950.1.1.5.10.17.1.4.1
-- 1.3.6.1.4.1.37950.1.1.5.10.17.1.4.1
-- 1.3.6.1.4.1.37950.1.1.5.10.17.1.4.1
-- 1.3.6.1.4.1.37950.1.1.5.10.17.1.4.1
		-- 1.3.6.1.4.1.37950.1.1.5.10.17.1.4.1
		ospfRedistributeEntry OBJECT-TYPE
			SYNTAX OspfRedistributeEntry
			MAX-ACCESS not-accessible
			STATUS current
			DESCRIPTION
				"Description."
			INDEX { redistributeType }
			::= { ospfRedistributeTable 1 }

		
		OspfRedistributeEntry ::=
			SEQUENCE { 
				redistributeType
					INTEGER,
				redistributeMetric
					Integer32,
				metricType
					Integer32,
				redistributeRouteMap
					OCTET STRING
			 }

--         1.3.6.1.4.1.37950.1.1.5.10.17.1.4.1.1
-- 1.3.6.1.4.1.37950.1.1.5.10.17.1.4.1.1
-- 1.3.6.1.4.1.37950.1.1.5.10.17.1.4.1.1
-- 1.3.6.1.4.1.37950.1.1.5.10.17.1.4.1.1
-- 1.3.6.1.4.1.37950.1.1.5.10.17.1.4.1.1
-- 1.3.6.1.4.1.37950.1.1.5.10.17.1.4.1.1
-- 1.3.6.1.4.1.37950.1.1.5.10.17.1.4.1.1
-- 1.3.6.1.4.1.37950.1.1.5.10.17.1.4.1.1
		-- 1.3.6.1.4.1.37950.1.1.5.10.17.1.4.1.1
		redistributeType OBJECT-TYPE
			SYNTAX INTEGER
				{
				kernel(1),
				connected(2),
				static(3),
				rip(4)
				}
			MAX-ACCESS read-only
			STATUS current
			DESCRIPTION
				"Description."
			::= { ospfRedistributeEntry 1 }

		
--         1.3.6.1.4.1.37950.1.1.5.10.17.1.4.1.2
-- 1.3.6.1.4.1.37950.1.1.5.10.17.1.4.1.2
-- 1.3.6.1.4.1.37950.1.1.5.10.17.1.4.1.2
-- 1.3.6.1.4.1.37950.1.1.5.10.17.1.4.1.2
-- 1.3.6.1.4.1.37950.1.1.5.10.17.1.4.1.2
-- 1.3.6.1.4.1.37950.1.1.5.10.17.1.4.1.2
-- 1.3.6.1.4.1.37950.1.1.5.10.17.1.4.1.2
-- 1.3.6.1.4.1.37950.1.1.5.10.17.1.4.1.2
		-- 1.3.6.1.4.1.37950.1.1.5.10.17.1.4.1.2
		redistributeMetric OBJECT-TYPE
			SYNTAX Integer32
			MAX-ACCESS read-only
			STATUS current
			DESCRIPTION
				"Description."
			::= { ospfRedistributeEntry 2 }

		
--         1.3.6.1.4.1.37950.1.1.5.10.17.1.4.1.3
-- 1.3.6.1.4.1.37950.1.1.5.10.17.1.4.1.3
-- 1.3.6.1.4.1.37950.1.1.5.10.17.1.4.1.3
-- 1.3.6.1.4.1.37950.1.1.5.10.17.1.4.1.3
-- 1.3.6.1.4.1.37950.1.1.5.10.17.1.4.1.3
-- 1.3.6.1.4.1.37950.1.1.5.10.17.1.4.1.3
-- 1.3.6.1.4.1.37950.1.1.5.10.17.1.4.1.3
-- 1.3.6.1.4.1.37950.1.1.5.10.17.1.4.1.3
		-- 1.3.6.1.4.1.37950.1.1.5.10.17.1.4.1.3
		metricType OBJECT-TYPE
			SYNTAX Integer32
			MAX-ACCESS read-only
			STATUS current
			DESCRIPTION
				"Description."
			::= { ospfRedistributeEntry 3 }

		
--         1.3.6.1.4.1.37950.1.1.5.10.17.1.4.1.4
-- 1.3.6.1.4.1.37950.1.1.5.10.17.1.4.1.4
-- 1.3.6.1.4.1.37950.1.1.5.10.17.1.4.1.4
-- 1.3.6.1.4.1.37950.1.1.5.10.17.1.4.1.4
-- 1.3.6.1.4.1.37950.1.1.5.10.17.1.4.1.4
-- 1.3.6.1.4.1.37950.1.1.5.10.17.1.4.1.4
-- 1.3.6.1.4.1.37950.1.1.5.10.17.1.4.1.4
-- 1.3.6.1.4.1.37950.1.1.5.10.17.1.4.1.4
		-- 1.3.6.1.4.1.37950.1.1.5.10.17.1.4.1.4
		redistributeRouteMap OBJECT-TYPE
			SYNTAX OCTET STRING
			MAX-ACCESS read-only
			STATUS current
			DESCRIPTION
				"Description."
			::= { ospfRedistributeEntry 4 }

		
--         1.3.6.1.4.1.37950.1.1.5.10.17.1.5
-- 1.3.6.1.4.1.37950.1.1.5.10.17.1.5
-- 1.3.6.1.4.1.37950.1.1.5.10.17.1.5
-- 1.3.6.1.4.1.37950.1.1.5.10.17.1.5
-- 1.3.6.1.4.1.37950.1.1.5.10.17.1.5
-- 1.3.6.1.4.1.37950.1.1.5.10.17.1.5
-- 1.3.6.1.4.1.37950.1.1.5.10.17.1.5
-- 1.3.6.1.4.1.37950.1.1.5.10.17.1.5
		-- 1.3.6.1.4.1.37950.1.1.5.10.17.1.5
		ospfDefaultRedistribute OBJECT IDENTIFIER ::= { ospfGlobal 5 }

		
--         1.3.6.1.4.1.37950.1.1.5.10.17.1.5.1
-- 1.3.6.1.4.1.37950.1.1.5.10.17.1.5.1
-- 1.3.6.1.4.1.37950.1.1.5.10.17.1.5.1
-- 1.3.6.1.4.1.37950.1.1.5.10.17.1.5.1
-- 1.3.6.1.4.1.37950.1.1.5.10.17.1.5.1
-- 1.3.6.1.4.1.37950.1.1.5.10.17.1.5.1
-- 1.3.6.1.4.1.37950.1.1.5.10.17.1.5.1
-- 1.3.6.1.4.1.37950.1.1.5.10.17.1.5.1
		-- 1.3.6.1.4.1.37950.1.1.5.10.17.1.5.1
		ospfDefRedis OBJECT-TYPE
			SYNTAX INTEGER
				{
				disable(0),
				enable(1)
				}
			MAX-ACCESS read-write
			STATUS current
			DESCRIPTION
				"Description."
			::= { ospfDefaultRedistribute 1 }

		
--         1.3.6.1.4.1.37950.1.1.5.10.17.1.5.2
-- 1.3.6.1.4.1.37950.1.1.5.10.17.1.5.2
-- 1.3.6.1.4.1.37950.1.1.5.10.17.1.5.2
-- 1.3.6.1.4.1.37950.1.1.5.10.17.1.5.2
-- 1.3.6.1.4.1.37950.1.1.5.10.17.1.5.2
-- 1.3.6.1.4.1.37950.1.1.5.10.17.1.5.2
-- 1.3.6.1.4.1.37950.1.1.5.10.17.1.5.2
-- 1.3.6.1.4.1.37950.1.1.5.10.17.1.5.2
		-- 1.3.6.1.4.1.37950.1.1.5.10.17.1.5.2
		always OBJECT-TYPE
			SYNTAX INTEGER
				{
				disable(0),
				enable(1)
				}
			MAX-ACCESS read-write
			STATUS current
			DESCRIPTION
				"Description."
			::= { ospfDefaultRedistribute 2 }

		
--         1.3.6.1.4.1.37950.1.1.5.10.17.1.5.3
-- 1.3.6.1.4.1.37950.1.1.5.10.17.1.5.3
-- 1.3.6.1.4.1.37950.1.1.5.10.17.1.5.3
-- 1.3.6.1.4.1.37950.1.1.5.10.17.1.5.3
-- 1.3.6.1.4.1.37950.1.1.5.10.17.1.5.3
-- 1.3.6.1.4.1.37950.1.1.5.10.17.1.5.3
-- 1.3.6.1.4.1.37950.1.1.5.10.17.1.5.3
-- 1.3.6.1.4.1.37950.1.1.5.10.17.1.5.3
		-- 1.3.6.1.4.1.37950.1.1.5.10.17.1.5.3
		defRedisMetric OBJECT-TYPE
			SYNTAX Integer32 (-1 | 1..16777214)
			MAX-ACCESS read-write
			STATUS current
			DESCRIPTION
				"Description."
			::= { ospfDefaultRedistribute 3 }

		
--         1.3.6.1.4.1.37950.1.1.5.10.17.1.5.4
-- 1.3.6.1.4.1.37950.1.1.5.10.17.1.5.4
-- 1.3.6.1.4.1.37950.1.1.5.10.17.1.5.4
-- 1.3.6.1.4.1.37950.1.1.5.10.17.1.5.4
-- 1.3.6.1.4.1.37950.1.1.5.10.17.1.5.4
-- 1.3.6.1.4.1.37950.1.1.5.10.17.1.5.4
-- 1.3.6.1.4.1.37950.1.1.5.10.17.1.5.4
-- 1.3.6.1.4.1.37950.1.1.5.10.17.1.5.4
		-- 1.3.6.1.4.1.37950.1.1.5.10.17.1.5.4
		defRedisMetricType OBJECT-TYPE
			SYNTAX Integer32 (-1 | 1..2)
			MAX-ACCESS read-write
			STATUS current
			DESCRIPTION
				"Description."
			::= { ospfDefaultRedistribute 4 }

		
--         1.3.6.1.4.1.37950.1.1.5.10.17.1.5.5
-- 1.3.6.1.4.1.37950.1.1.5.10.17.1.5.5
-- 1.3.6.1.4.1.37950.1.1.5.10.17.1.5.5
-- 1.3.6.1.4.1.37950.1.1.5.10.17.1.5.5
-- 1.3.6.1.4.1.37950.1.1.5.10.17.1.5.5
-- 1.3.6.1.4.1.37950.1.1.5.10.17.1.5.5
-- 1.3.6.1.4.1.37950.1.1.5.10.17.1.5.5
-- 1.3.6.1.4.1.37950.1.1.5.10.17.1.5.5
		-- 1.3.6.1.4.1.37950.1.1.5.10.17.1.5.5
		defRedisAction OBJECT-TYPE
			SYNTAX INTEGER { commit(1) }
			MAX-ACCESS read-write
			STATUS current
			DESCRIPTION
				"Description."
			::= { ospfDefaultRedistribute 5 }

		
--         1.3.6.1.4.1.37950.1.1.5.10.17.2
-- 1.3.6.1.4.1.37950.1.1.5.10.17.2
-- 1.3.6.1.4.1.37950.1.1.5.10.17.2
-- 1.3.6.1.4.1.37950.1.1.5.10.17.2
-- 1.3.6.1.4.1.37950.1.1.5.10.17.2
-- 1.3.6.1.4.1.37950.1.1.5.10.17.2
-- 1.3.6.1.4.1.37950.1.1.5.10.17.2
-- 1.3.6.1.4.1.37950.1.1.5.10.17.2
		-- 1.3.6.1.4.1.37950.1.1.5.10.17.2
		ospfArea OBJECT IDENTIFIER ::= { v1600dOspf 2 }

		
--         1.3.6.1.4.1.37950.1.1.5.10.17.2.1
-- 1.3.6.1.4.1.37950.1.1.5.10.17.2.1
-- 1.3.6.1.4.1.37950.1.1.5.10.17.2.1
-- 1.3.6.1.4.1.37950.1.1.5.10.17.2.1
-- 1.3.6.1.4.1.37950.1.1.5.10.17.2.1
-- 1.3.6.1.4.1.37950.1.1.5.10.17.2.1
-- 1.3.6.1.4.1.37950.1.1.5.10.17.2.1
-- 1.3.6.1.4.1.37950.1.1.5.10.17.2.1
		-- 1.3.6.1.4.1.37950.1.1.5.10.17.2.1
		ospfRouteNetworking OBJECT IDENTIFIER ::= { ospfArea 1 }

		
--         1.3.6.1.4.1.37950.1.1.5.10.17.2.1.1
-- 1.3.6.1.4.1.37950.1.1.5.10.17.2.1.1
-- 1.3.6.1.4.1.37950.1.1.5.10.17.2.1.1
-- 1.3.6.1.4.1.37950.1.1.5.10.17.2.1.1
-- 1.3.6.1.4.1.37950.1.1.5.10.17.2.1.1
-- 1.3.6.1.4.1.37950.1.1.5.10.17.2.1.1
-- 1.3.6.1.4.1.37950.1.1.5.10.17.2.1.1
-- 1.3.6.1.4.1.37950.1.1.5.10.17.2.1.1
		-- 1.3.6.1.4.1.37950.1.1.5.10.17.2.1.1
		network OBJECT-TYPE
			SYNTAX OCTET STRING
			MAX-ACCESS read-write
			STATUS current
			DESCRIPTION
				"Description."
			::= { ospfRouteNetworking 1 }

		
--         1.3.6.1.4.1.37950.1.1.5.10.17.2.1.2
-- 1.3.6.1.4.1.37950.1.1.5.10.17.2.1.2
-- 1.3.6.1.4.1.37950.1.1.5.10.17.2.1.2
-- 1.3.6.1.4.1.37950.1.1.5.10.17.2.1.2
-- 1.3.6.1.4.1.37950.1.1.5.10.17.2.1.2
-- 1.3.6.1.4.1.37950.1.1.5.10.17.2.1.2
-- 1.3.6.1.4.1.37950.1.1.5.10.17.2.1.2
-- 1.3.6.1.4.1.37950.1.1.5.10.17.2.1.2
		-- 1.3.6.1.4.1.37950.1.1.5.10.17.2.1.2
		area OBJECT-TYPE
			SYNTAX OCTET STRING
			MAX-ACCESS read-write
			STATUS current
			DESCRIPTION
				"Description."
			::= { ospfRouteNetworking 2 }

		
--         1.3.6.1.4.1.37950.1.1.5.10.17.2.1.3
-- 1.3.6.1.4.1.37950.1.1.5.10.17.2.1.3
-- 1.3.6.1.4.1.37950.1.1.5.10.17.2.1.3
-- 1.3.6.1.4.1.37950.1.1.5.10.17.2.1.3
-- 1.3.6.1.4.1.37950.1.1.5.10.17.2.1.3
-- 1.3.6.1.4.1.37950.1.1.5.10.17.2.1.3
-- 1.3.6.1.4.1.37950.1.1.5.10.17.2.1.3
-- 1.3.6.1.4.1.37950.1.1.5.10.17.2.1.3
		-- 1.3.6.1.4.1.37950.1.1.5.10.17.2.1.3
		ospfNetworkAction OBJECT-TYPE
			SYNTAX INTEGER
				{
				add(1),
				del(2)
				}
			MAX-ACCESS read-write
			STATUS current
			DESCRIPTION
				"Description."
			::= { ospfRouteNetworking 3 }

		
--         1.3.6.1.4.1.37950.1.1.5.10.17.2.2
-- 1.3.6.1.4.1.37950.1.1.5.10.17.2.2
-- 1.3.6.1.4.1.37950.1.1.5.10.17.2.2
-- 1.3.6.1.4.1.37950.1.1.5.10.17.2.2
-- 1.3.6.1.4.1.37950.1.1.5.10.17.2.2
-- 1.3.6.1.4.1.37950.1.1.5.10.17.2.2
-- 1.3.6.1.4.1.37950.1.1.5.10.17.2.2
-- 1.3.6.1.4.1.37950.1.1.5.10.17.2.2
		-- 1.3.6.1.4.1.37950.1.1.5.10.17.2.2
		ospfRouteNetworkingTable OBJECT-TYPE
			SYNTAX SEQUENCE OF OspfRouteNetworkingEntry
			MAX-ACCESS not-accessible
			STATUS current
			DESCRIPTION
				"Description."
			::= { ospfArea 2 }

		
--         1.3.6.1.4.1.37950.1.1.5.10.17.2.2.1
-- 1.3.6.1.4.1.37950.1.1.5.10.17.2.2.1
-- 1.3.6.1.4.1.37950.1.1.5.10.17.2.2.1
-- 1.3.6.1.4.1.37950.1.1.5.10.17.2.2.1
-- 1.3.6.1.4.1.37950.1.1.5.10.17.2.2.1
-- 1.3.6.1.4.1.37950.1.1.5.10.17.2.2.1
-- 1.3.6.1.4.1.37950.1.1.5.10.17.2.2.1
-- 1.3.6.1.4.1.37950.1.1.5.10.17.2.2.1
		-- 1.3.6.1.4.1.37950.1.1.5.10.17.2.2.1
		ospfRouteNetworkingEntry OBJECT-TYPE
			SYNTAX OspfRouteNetworkingEntry
			MAX-ACCESS not-accessible
			STATUS current
			DESCRIPTION
				"Description."
			INDEX { ospfNetwork }
			::= { ospfRouteNetworkingTable 1 }

		
		OspfRouteNetworkingEntry ::=
			SEQUENCE { 
				routerId
					IpAddress,
				ospfNetwork
					OCTET STRING,
				areaId
					IpAddress
			 }

--         1.3.6.1.4.1.37950.1.1.5.10.17.2.2.1.1
-- 1.3.6.1.4.1.37950.1.1.5.10.17.2.2.1.1
-- 1.3.6.1.4.1.37950.1.1.5.10.17.2.2.1.1
-- 1.3.6.1.4.1.37950.1.1.5.10.17.2.2.1.1
-- 1.3.6.1.4.1.37950.1.1.5.10.17.2.2.1.1
-- 1.3.6.1.4.1.37950.1.1.5.10.17.2.2.1.1
-- 1.3.6.1.4.1.37950.1.1.5.10.17.2.2.1.1
-- 1.3.6.1.4.1.37950.1.1.5.10.17.2.2.1.1
		-- 1.3.6.1.4.1.37950.1.1.5.10.17.2.2.1.1
		routerId OBJECT-TYPE
			SYNTAX IpAddress
			MAX-ACCESS read-only
			STATUS current
			DESCRIPTION
				"Description."
			::= { ospfRouteNetworkingEntry 1 }

		
--         1.3.6.1.4.1.37950.1.1.5.10.17.2.2.1.2
-- 1.3.6.1.4.1.37950.1.1.5.10.17.2.2.1.2
-- 1.3.6.1.4.1.37950.1.1.5.10.17.2.2.1.2
-- 1.3.6.1.4.1.37950.1.1.5.10.17.2.2.1.2
-- 1.3.6.1.4.1.37950.1.1.5.10.17.2.2.1.2
-- 1.3.6.1.4.1.37950.1.1.5.10.17.2.2.1.2
-- 1.3.6.1.4.1.37950.1.1.5.10.17.2.2.1.2
-- 1.3.6.1.4.1.37950.1.1.5.10.17.2.2.1.2
		-- 1.3.6.1.4.1.37950.1.1.5.10.17.2.2.1.2
		ospfNetwork OBJECT-TYPE
			SYNTAX OCTET STRING
			MAX-ACCESS read-only
			STATUS current
			DESCRIPTION
				"Description."
			::= { ospfRouteNetworkingEntry 2 }

		
--         1.3.6.1.4.1.37950.1.1.5.10.17.2.2.1.3
-- 1.3.6.1.4.1.37950.1.1.5.10.17.2.2.1.3
-- 1.3.6.1.4.1.37950.1.1.5.10.17.2.2.1.3
-- 1.3.6.1.4.1.37950.1.1.5.10.17.2.2.1.3
-- 1.3.6.1.4.1.37950.1.1.5.10.17.2.2.1.3
-- 1.3.6.1.4.1.37950.1.1.5.10.17.2.2.1.3
-- 1.3.6.1.4.1.37950.1.1.5.10.17.2.2.1.3
-- 1.3.6.1.4.1.37950.1.1.5.10.17.2.2.1.3
		-- 1.3.6.1.4.1.37950.1.1.5.10.17.2.2.1.3
		areaId OBJECT-TYPE
			SYNTAX IpAddress
			MAX-ACCESS read-only
			STATUS current
			DESCRIPTION
				"Description."
			::= { ospfRouteNetworkingEntry 3 }

		
--         1.3.6.1.4.1.37950.1.1.5.10.17.2.3
-- 1.3.6.1.4.1.37950.1.1.5.10.17.2.3
-- 1.3.6.1.4.1.37950.1.1.5.10.17.2.3
-- 1.3.6.1.4.1.37950.1.1.5.10.17.2.3
-- 1.3.6.1.4.1.37950.1.1.5.10.17.2.3
-- 1.3.6.1.4.1.37950.1.1.5.10.17.2.3
-- 1.3.6.1.4.1.37950.1.1.5.10.17.2.3
-- 1.3.6.1.4.1.37950.1.1.5.10.17.2.3
		-- 1.3.6.1.4.1.37950.1.1.5.10.17.2.3
		ospfAreaTypeCfg OBJECT IDENTIFIER ::= { ospfArea 3 }

		
--         1.3.6.1.4.1.37950.1.1.5.10.17.2.3.1
-- 1.3.6.1.4.1.37950.1.1.5.10.17.2.3.1
-- 1.3.6.1.4.1.37950.1.1.5.10.17.2.3.1
-- 1.3.6.1.4.1.37950.1.1.5.10.17.2.3.1
-- 1.3.6.1.4.1.37950.1.1.5.10.17.2.3.1
-- 1.3.6.1.4.1.37950.1.1.5.10.17.2.3.1
-- 1.3.6.1.4.1.37950.1.1.5.10.17.2.3.1
-- 1.3.6.1.4.1.37950.1.1.5.10.17.2.3.1
		-- 1.3.6.1.4.1.37950.1.1.5.10.17.2.3.1
		ospfAreaCfg OBJECT-TYPE
			SYNTAX IpAddress
			MAX-ACCESS read-write
			STATUS current
			DESCRIPTION
				"Description."
			::= { ospfAreaTypeCfg 1 }

		
--         1.3.6.1.4.1.37950.1.1.5.10.17.2.3.2
-- 1.3.6.1.4.1.37950.1.1.5.10.17.2.3.2
-- 1.3.6.1.4.1.37950.1.1.5.10.17.2.3.2
-- 1.3.6.1.4.1.37950.1.1.5.10.17.2.3.2
-- 1.3.6.1.4.1.37950.1.1.5.10.17.2.3.2
-- 1.3.6.1.4.1.37950.1.1.5.10.17.2.3.2
-- 1.3.6.1.4.1.37950.1.1.5.10.17.2.3.2
-- 1.3.6.1.4.1.37950.1.1.5.10.17.2.3.2
		-- 1.3.6.1.4.1.37950.1.1.5.10.17.2.3.2
		areaTypeCfg OBJECT-TYPE
			SYNTAX INTEGER
				{
				disable(0),
				stub(1),
				nssa(2)
				}
			MAX-ACCESS read-write
			STATUS current
			DESCRIPTION
				"Description."
			::= { ospfAreaTypeCfg 2 }

		
--         1.3.6.1.4.1.37950.1.1.5.10.17.2.3.3
-- 1.3.6.1.4.1.37950.1.1.5.10.17.2.3.3
-- 1.3.6.1.4.1.37950.1.1.5.10.17.2.3.3
-- 1.3.6.1.4.1.37950.1.1.5.10.17.2.3.3
-- 1.3.6.1.4.1.37950.1.1.5.10.17.2.3.3
-- 1.3.6.1.4.1.37950.1.1.5.10.17.2.3.3
-- 1.3.6.1.4.1.37950.1.1.5.10.17.2.3.3
-- 1.3.6.1.4.1.37950.1.1.5.10.17.2.3.3
		-- 1.3.6.1.4.1.37950.1.1.5.10.17.2.3.3
		noSummaryCfg OBJECT-TYPE
			SYNTAX INTEGER
				{
				disable(0),
				enable(1)
				}
			MAX-ACCESS read-write
			STATUS current
			DESCRIPTION
				"Description."
			::= { ospfAreaTypeCfg 3 }

		
--         1.3.6.1.4.1.37950.1.1.5.10.17.2.3.4
-- 1.3.6.1.4.1.37950.1.1.5.10.17.2.3.4
-- 1.3.6.1.4.1.37950.1.1.5.10.17.2.3.4
-- 1.3.6.1.4.1.37950.1.1.5.10.17.2.3.4
-- 1.3.6.1.4.1.37950.1.1.5.10.17.2.3.4
-- 1.3.6.1.4.1.37950.1.1.5.10.17.2.3.4
-- 1.3.6.1.4.1.37950.1.1.5.10.17.2.3.4
-- 1.3.6.1.4.1.37950.1.1.5.10.17.2.3.4
		-- 1.3.6.1.4.1.37950.1.1.5.10.17.2.3.4
		areaActionCfg OBJECT-TYPE
			SYNTAX INTEGER
				{
				add(1),
				del(2)
				}
			MAX-ACCESS read-write
			STATUS current
			DESCRIPTION
				"Description."
			::= { ospfAreaTypeCfg 4 }

		
--         1.3.6.1.4.1.37950.1.1.5.10.17.2.4
-- 1.3.6.1.4.1.37950.1.1.5.10.17.2.4
-- 1.3.6.1.4.1.37950.1.1.5.10.17.2.4
-- 1.3.6.1.4.1.37950.1.1.5.10.17.2.4
-- 1.3.6.1.4.1.37950.1.1.5.10.17.2.4
-- 1.3.6.1.4.1.37950.1.1.5.10.17.2.4
-- 1.3.6.1.4.1.37950.1.1.5.10.17.2.4
-- 1.3.6.1.4.1.37950.1.1.5.10.17.2.4
		-- 1.3.6.1.4.1.37950.1.1.5.10.17.2.4
		ospfAreaTypeTable OBJECT-TYPE
			SYNTAX SEQUENCE OF OspfAreaTypeEntry
			MAX-ACCESS not-accessible
			STATUS current
			DESCRIPTION
				"Description."
			::= { ospfArea 4 }

		
--         1.3.6.1.4.1.37950.1.1.5.10.17.2.4.1
-- 1.3.6.1.4.1.37950.1.1.5.10.17.2.4.1
-- 1.3.6.1.4.1.37950.1.1.5.10.17.2.4.1
-- 1.3.6.1.4.1.37950.1.1.5.10.17.2.4.1
-- 1.3.6.1.4.1.37950.1.1.5.10.17.2.4.1
-- 1.3.6.1.4.1.37950.1.1.5.10.17.2.4.1
-- 1.3.6.1.4.1.37950.1.1.5.10.17.2.4.1
-- 1.3.6.1.4.1.37950.1.1.5.10.17.2.4.1
		-- 1.3.6.1.4.1.37950.1.1.5.10.17.2.4.1
		ospfAreaTypeEntry OBJECT-TYPE
			SYNTAX OspfAreaTypeEntry
			MAX-ACCESS not-accessible
			STATUS current
			DESCRIPTION
				"Description."
			INDEX { getArea }
			::= { ospfAreaTypeTable 1 }

		
		OspfAreaTypeEntry ::=
			SEQUENCE { 
				getArea
					IpAddress,
				areaType
					INTEGER,
				noSummary
					INTEGER
			 }

--         1.3.6.1.4.1.37950.1.1.5.10.17.2.4.1.1
-- 1.3.6.1.4.1.37950.1.1.5.10.17.2.4.1.1
-- 1.3.6.1.4.1.37950.1.1.5.10.17.2.4.1.1
-- 1.3.6.1.4.1.37950.1.1.5.10.17.2.4.1.1
-- 1.3.6.1.4.1.37950.1.1.5.10.17.2.4.1.1
-- 1.3.6.1.4.1.37950.1.1.5.10.17.2.4.1.1
-- 1.3.6.1.4.1.37950.1.1.5.10.17.2.4.1.1
-- 1.3.6.1.4.1.37950.1.1.5.10.17.2.4.1.1
		-- 1.3.6.1.4.1.37950.1.1.5.10.17.2.4.1.1
		getArea OBJECT-TYPE
			SYNTAX IpAddress
			MAX-ACCESS read-write
			STATUS current
			DESCRIPTION
				"Description."
			::= { ospfAreaTypeEntry 1 }

		
--         1.3.6.1.4.1.37950.1.1.5.10.17.2.4.1.2
-- 1.3.6.1.4.1.37950.1.1.5.10.17.2.4.1.2
-- 1.3.6.1.4.1.37950.1.1.5.10.17.2.4.1.2
-- 1.3.6.1.4.1.37950.1.1.5.10.17.2.4.1.2
-- 1.3.6.1.4.1.37950.1.1.5.10.17.2.4.1.2
-- 1.3.6.1.4.1.37950.1.1.5.10.17.2.4.1.2
-- 1.3.6.1.4.1.37950.1.1.5.10.17.2.4.1.2
-- 1.3.6.1.4.1.37950.1.1.5.10.17.2.4.1.2
		-- 1.3.6.1.4.1.37950.1.1.5.10.17.2.4.1.2
		areaType OBJECT-TYPE
			SYNTAX INTEGER
				{
				stub(1),
				nssa(2)
				}
			MAX-ACCESS read-write
			STATUS current
			DESCRIPTION
				"Description."
			::= { ospfAreaTypeEntry 2 }

		
--         1.3.6.1.4.1.37950.1.1.5.10.17.2.4.1.3
-- 1.3.6.1.4.1.37950.1.1.5.10.17.2.4.1.3
-- 1.3.6.1.4.1.37950.1.1.5.10.17.2.4.1.3
-- 1.3.6.1.4.1.37950.1.1.5.10.17.2.4.1.3
-- 1.3.6.1.4.1.37950.1.1.5.10.17.2.4.1.3
-- 1.3.6.1.4.1.37950.1.1.5.10.17.2.4.1.3
-- 1.3.6.1.4.1.37950.1.1.5.10.17.2.4.1.3
-- 1.3.6.1.4.1.37950.1.1.5.10.17.2.4.1.3
		-- 1.3.6.1.4.1.37950.1.1.5.10.17.2.4.1.3
		noSummary OBJECT-TYPE
			SYNTAX INTEGER
				{
				disable(0),
				enable(1)
				}
			MAX-ACCESS read-write
			STATUS current
			DESCRIPTION
				"Description."
			::= { ospfAreaTypeEntry 3 }

		
--         1.3.6.1.4.1.37950.1.1.5.10.17.2.5
-- 1.3.6.1.4.1.37950.1.1.5.10.17.2.5
-- 1.3.6.1.4.1.37950.1.1.5.10.17.2.5
-- 1.3.6.1.4.1.37950.1.1.5.10.17.2.5
-- 1.3.6.1.4.1.37950.1.1.5.10.17.2.5
-- 1.3.6.1.4.1.37950.1.1.5.10.17.2.5
-- 1.3.6.1.4.1.37950.1.1.5.10.17.2.5
-- 1.3.6.1.4.1.37950.1.1.5.10.17.2.5
		-- 1.3.6.1.4.1.37950.1.1.5.10.17.2.5
		ospfAreaSummaryCfg OBJECT IDENTIFIER ::= { ospfArea 5 }

		
--         1.3.6.1.4.1.37950.1.1.5.10.17.2.5.1
-- 1.3.6.1.4.1.37950.1.1.5.10.17.2.5.1
-- 1.3.6.1.4.1.37950.1.1.5.10.17.2.5.1
-- 1.3.6.1.4.1.37950.1.1.5.10.17.2.5.1
-- 1.3.6.1.4.1.37950.1.1.5.10.17.2.5.1
-- 1.3.6.1.4.1.37950.1.1.5.10.17.2.5.1
-- 1.3.6.1.4.1.37950.1.1.5.10.17.2.5.1
-- 1.3.6.1.4.1.37950.1.1.5.10.17.2.5.1
		-- 1.3.6.1.4.1.37950.1.1.5.10.17.2.5.1
		ospfSummaryArea OBJECT-TYPE
			SYNTAX IpAddress
			MAX-ACCESS read-write
			STATUS current
			DESCRIPTION
				"Description."
			::= { ospfAreaSummaryCfg 1 }

		
--         1.3.6.1.4.1.37950.1.1.5.10.17.2.5.2
-- 1.3.6.1.4.1.37950.1.1.5.10.17.2.5.2
-- 1.3.6.1.4.1.37950.1.1.5.10.17.2.5.2
-- 1.3.6.1.4.1.37950.1.1.5.10.17.2.5.2
-- 1.3.6.1.4.1.37950.1.1.5.10.17.2.5.2
-- 1.3.6.1.4.1.37950.1.1.5.10.17.2.5.2
-- 1.3.6.1.4.1.37950.1.1.5.10.17.2.5.2
-- 1.3.6.1.4.1.37950.1.1.5.10.17.2.5.2
		-- 1.3.6.1.4.1.37950.1.1.5.10.17.2.5.2
		ipAddress OBJECT-TYPE
			SYNTAX IpAddress
			MAX-ACCESS read-write
			STATUS current
			DESCRIPTION
				"Description."
			::= { ospfAreaSummaryCfg 2 }

		
--         1.3.6.1.4.1.37950.1.1.5.10.17.2.5.3
-- 1.3.6.1.4.1.37950.1.1.5.10.17.2.5.3
-- 1.3.6.1.4.1.37950.1.1.5.10.17.2.5.3
-- 1.3.6.1.4.1.37950.1.1.5.10.17.2.5.3
-- 1.3.6.1.4.1.37950.1.1.5.10.17.2.5.3
-- 1.3.6.1.4.1.37950.1.1.5.10.17.2.5.3
-- 1.3.6.1.4.1.37950.1.1.5.10.17.2.5.3
-- 1.3.6.1.4.1.37950.1.1.5.10.17.2.5.3
		-- 1.3.6.1.4.1.37950.1.1.5.10.17.2.5.3
		subnetMask OBJECT-TYPE
			SYNTAX IpAddress
			MAX-ACCESS read-write
			STATUS current
			DESCRIPTION
				"Description."
			::= { ospfAreaSummaryCfg 3 }

		
--         1.3.6.1.4.1.37950.1.1.5.10.17.2.5.4
-- 1.3.6.1.4.1.37950.1.1.5.10.17.2.5.4
-- 1.3.6.1.4.1.37950.1.1.5.10.17.2.5.4
-- 1.3.6.1.4.1.37950.1.1.5.10.17.2.5.4
-- 1.3.6.1.4.1.37950.1.1.5.10.17.2.5.4
-- 1.3.6.1.4.1.37950.1.1.5.10.17.2.5.4
-- 1.3.6.1.4.1.37950.1.1.5.10.17.2.5.4
-- 1.3.6.1.4.1.37950.1.1.5.10.17.2.5.4
		-- 1.3.6.1.4.1.37950.1.1.5.10.17.2.5.4
		areaSummaryAction OBJECT-TYPE
			SYNTAX INTEGER
				{
				add(1),
				del(2)
				}
			MAX-ACCESS read-write
			STATUS current
			DESCRIPTION
				"Description."
			::= { ospfAreaSummaryCfg 4 }

		
--         1.3.6.1.4.1.37950.1.1.5.10.17.2.6
-- 1.3.6.1.4.1.37950.1.1.5.10.17.2.6
-- 1.3.6.1.4.1.37950.1.1.5.10.17.2.6
-- 1.3.6.1.4.1.37950.1.1.5.10.17.2.6
-- 1.3.6.1.4.1.37950.1.1.5.10.17.2.6
-- 1.3.6.1.4.1.37950.1.1.5.10.17.2.6
-- 1.3.6.1.4.1.37950.1.1.5.10.17.2.6
-- 1.3.6.1.4.1.37950.1.1.5.10.17.2.6
		-- 1.3.6.1.4.1.37950.1.1.5.10.17.2.6
		ospfSummaryTable OBJECT-TYPE
			SYNTAX SEQUENCE OF OspfSummaryEntry
			MAX-ACCESS not-accessible
			STATUS current
			DESCRIPTION
				"Description."
			::= { ospfArea 6 }

		
--         1.3.6.1.4.1.37950.1.1.5.10.17.2.6.1
-- 1.3.6.1.4.1.37950.1.1.5.10.17.2.6.1
-- 1.3.6.1.4.1.37950.1.1.5.10.17.2.6.1
-- 1.3.6.1.4.1.37950.1.1.5.10.17.2.6.1
-- 1.3.6.1.4.1.37950.1.1.5.10.17.2.6.1
-- 1.3.6.1.4.1.37950.1.1.5.10.17.2.6.1
-- 1.3.6.1.4.1.37950.1.1.5.10.17.2.6.1
-- 1.3.6.1.4.1.37950.1.1.5.10.17.2.6.1
		-- 1.3.6.1.4.1.37950.1.1.5.10.17.2.6.1
		ospfSummaryEntry OBJECT-TYPE
			SYNTAX OspfSummaryEntry
			MAX-ACCESS not-accessible
			STATUS current
			DESCRIPTION
				"Description."
			INDEX { summaryArea, summaryNetwork }
			::= { ospfSummaryTable 1 }

		
		OspfSummaryEntry ::=
			SEQUENCE { 
				summaryArea
					IpAddress,
				summaryNetwork
					OCTET STRING
			 }

--         1.3.6.1.4.1.37950.1.1.5.10.17.2.6.1.1
-- 1.3.6.1.4.1.37950.1.1.5.10.17.2.6.1.1
-- 1.3.6.1.4.1.37950.1.1.5.10.17.2.6.1.1
-- 1.3.6.1.4.1.37950.1.1.5.10.17.2.6.1.1
-- 1.3.6.1.4.1.37950.1.1.5.10.17.2.6.1.1
-- 1.3.6.1.4.1.37950.1.1.5.10.17.2.6.1.1
-- 1.3.6.1.4.1.37950.1.1.5.10.17.2.6.1.1
-- 1.3.6.1.4.1.37950.1.1.5.10.17.2.6.1.1
		-- 1.3.6.1.4.1.37950.1.1.5.10.17.2.6.1.1
		summaryArea OBJECT-TYPE
			SYNTAX IpAddress
			MAX-ACCESS read-only
			STATUS current
			DESCRIPTION
				"Description."
			::= { ospfSummaryEntry 1 }

		
--         1.3.6.1.4.1.37950.1.1.5.10.17.2.6.1.2
-- 1.3.6.1.4.1.37950.1.1.5.10.17.2.6.1.2
-- 1.3.6.1.4.1.37950.1.1.5.10.17.2.6.1.2
-- 1.3.6.1.4.1.37950.1.1.5.10.17.2.6.1.2
-- 1.3.6.1.4.1.37950.1.1.5.10.17.2.6.1.2
-- 1.3.6.1.4.1.37950.1.1.5.10.17.2.6.1.2
-- 1.3.6.1.4.1.37950.1.1.5.10.17.2.6.1.2
-- 1.3.6.1.4.1.37950.1.1.5.10.17.2.6.1.2
		-- 1.3.6.1.4.1.37950.1.1.5.10.17.2.6.1.2
		summaryNetwork OBJECT-TYPE
			SYNTAX OCTET STRING
			MAX-ACCESS read-only
			STATUS current
			DESCRIPTION
				"Description."
			::= { ospfSummaryEntry 2 }

		
--         1.3.6.1.4.1.37950.1.1.5.10.17.3
-- 1.3.6.1.4.1.37950.1.1.5.10.17.3
-- 1.3.6.1.4.1.37950.1.1.5.10.17.3
-- 1.3.6.1.4.1.37950.1.1.5.10.17.3
-- 1.3.6.1.4.1.37950.1.1.5.10.17.3
-- 1.3.6.1.4.1.37950.1.1.5.10.17.3
-- 1.3.6.1.4.1.37950.1.1.5.10.17.3
-- 1.3.6.1.4.1.37950.1.1.5.10.17.3
		-- 1.3.6.1.4.1.37950.1.1.5.10.17.3
		ospfInterface OBJECT IDENTIFIER ::= { v1600dOspf 3 }

		
--         1.3.6.1.4.1.37950.1.1.5.10.17.3.1
-- 1.3.6.1.4.1.37950.1.1.5.10.17.3.1
-- 1.3.6.1.4.1.37950.1.1.5.10.17.3.1
-- 1.3.6.1.4.1.37950.1.1.5.10.17.3.1
-- 1.3.6.1.4.1.37950.1.1.5.10.17.3.1
-- 1.3.6.1.4.1.37950.1.1.5.10.17.3.1
-- 1.3.6.1.4.1.37950.1.1.5.10.17.3.1
-- 1.3.6.1.4.1.37950.1.1.5.10.17.3.1
		-- 1.3.6.1.4.1.37950.1.1.5.10.17.3.1
		ospfInterfaceTable OBJECT-TYPE
			SYNTAX SEQUENCE OF OspfInterfaceEntry
			MAX-ACCESS not-accessible
			STATUS current
			DESCRIPTION
				"Description."
			::= { ospfInterface 1 }

		
--         1.3.6.1.4.1.37950.1.1.5.10.17.3.1.1
-- 1.3.6.1.4.1.37950.1.1.5.10.17.3.1.1
-- 1.3.6.1.4.1.37950.1.1.5.10.17.3.1.1
-- 1.3.6.1.4.1.37950.1.1.5.10.17.3.1.1
-- 1.3.6.1.4.1.37950.1.1.5.10.17.3.1.1
-- 1.3.6.1.4.1.37950.1.1.5.10.17.3.1.1
-- 1.3.6.1.4.1.37950.1.1.5.10.17.3.1.1
-- 1.3.6.1.4.1.37950.1.1.5.10.17.3.1.1
		-- 1.3.6.1.4.1.37950.1.1.5.10.17.3.1.1
		ospfInterfaceEntry OBJECT-TYPE
			SYNTAX OspfInterfaceEntry
			MAX-ACCESS not-accessible
			STATUS current
			DESCRIPTION
				"Description."
			INDEX { ospfIfAddress }
			::= { ospfInterfaceTable 1 }

		
		OspfInterfaceEntry ::=
			SEQUENCE { 
				ospfIfAddress
					IpAddress,
				cost
					Integer32,
				interPri
					Integer32,
				retransVal
					Integer32,
				transDelay
					Integer32,
				helloVal
					Integer32,
				deadVal
					Integer32,
				auth
					INTEGER,
				key
					Integer32,
				authString
					OCTET STRING
			 }

--         1.3.6.1.4.1.37950.1.1.5.10.17.3.1.1.1
-- 1.3.6.1.4.1.37950.1.1.5.10.17.3.1.1.1
-- 1.3.6.1.4.1.37950.1.1.5.10.17.3.1.1.1
-- 1.3.6.1.4.1.37950.1.1.5.10.17.3.1.1.1
-- 1.3.6.1.4.1.37950.1.1.5.10.17.3.1.1.1
-- 1.3.6.1.4.1.37950.1.1.5.10.17.3.1.1.1
-- 1.3.6.1.4.1.37950.1.1.5.10.17.3.1.1.1
-- 1.3.6.1.4.1.37950.1.1.5.10.17.3.1.1.1
		-- 1.3.6.1.4.1.37950.1.1.5.10.17.3.1.1.1
		ospfIfAddress OBJECT-TYPE
			SYNTAX IpAddress
			MAX-ACCESS read-only
			STATUS current
			DESCRIPTION
				"Description."
			::= { ospfInterfaceEntry 1 }

		
--         1.3.6.1.4.1.37950.1.1.5.10.17.3.1.1.2
-- 1.3.6.1.4.1.37950.1.1.5.10.17.3.1.1.2
-- 1.3.6.1.4.1.37950.1.1.5.10.17.3.1.1.2
-- 1.3.6.1.4.1.37950.1.1.5.10.17.3.1.1.2
-- 1.3.6.1.4.1.37950.1.1.5.10.17.3.1.1.2
-- 1.3.6.1.4.1.37950.1.1.5.10.17.3.1.1.2
-- 1.3.6.1.4.1.37950.1.1.5.10.17.3.1.1.2
-- 1.3.6.1.4.1.37950.1.1.5.10.17.3.1.1.2
		-- 1.3.6.1.4.1.37950.1.1.5.10.17.3.1.1.2
		cost OBJECT-TYPE
			SYNTAX Integer32 (1..65535)
			MAX-ACCESS read-write
			STATUS current
			DESCRIPTION
				"Description."
			::= { ospfInterfaceEntry 2 }

		
--         1.3.6.1.4.1.37950.1.1.5.10.17.3.1.1.3
-- 1.3.6.1.4.1.37950.1.1.5.10.17.3.1.1.3
-- 1.3.6.1.4.1.37950.1.1.5.10.17.3.1.1.3
-- 1.3.6.1.4.1.37950.1.1.5.10.17.3.1.1.3
-- 1.3.6.1.4.1.37950.1.1.5.10.17.3.1.1.3
-- 1.3.6.1.4.1.37950.1.1.5.10.17.3.1.1.3
-- 1.3.6.1.4.1.37950.1.1.5.10.17.3.1.1.3
-- 1.3.6.1.4.1.37950.1.1.5.10.17.3.1.1.3
		-- 1.3.6.1.4.1.37950.1.1.5.10.17.3.1.1.3
		interPri OBJECT-TYPE
			SYNTAX Integer32 (0..255)
			MAX-ACCESS read-write
			STATUS current
			DESCRIPTION
				"Description."
			::= { ospfInterfaceEntry 3 }

		
--         1.3.6.1.4.1.37950.1.1.5.10.17.3.1.1.4
-- 1.3.6.1.4.1.37950.1.1.5.10.17.3.1.1.4
-- 1.3.6.1.4.1.37950.1.1.5.10.17.3.1.1.4
-- 1.3.6.1.4.1.37950.1.1.5.10.17.3.1.1.4
-- 1.3.6.1.4.1.37950.1.1.5.10.17.3.1.1.4
-- 1.3.6.1.4.1.37950.1.1.5.10.17.3.1.1.4
-- 1.3.6.1.4.1.37950.1.1.5.10.17.3.1.1.4
-- 1.3.6.1.4.1.37950.1.1.5.10.17.3.1.1.4
		-- 1.3.6.1.4.1.37950.1.1.5.10.17.3.1.1.4
		retransVal OBJECT-TYPE
			SYNTAX Integer32 (3..65535)
			MAX-ACCESS read-write
			STATUS current
			DESCRIPTION
				"Description."
			::= { ospfInterfaceEntry 4 }

		
--         1.3.6.1.4.1.37950.1.1.5.10.17.3.1.1.5
-- 1.3.6.1.4.1.37950.1.1.5.10.17.3.1.1.5
-- 1.3.6.1.4.1.37950.1.1.5.10.17.3.1.1.5
-- 1.3.6.1.4.1.37950.1.1.5.10.17.3.1.1.5
-- 1.3.6.1.4.1.37950.1.1.5.10.17.3.1.1.5
-- 1.3.6.1.4.1.37950.1.1.5.10.17.3.1.1.5
-- 1.3.6.1.4.1.37950.1.1.5.10.17.3.1.1.5
-- 1.3.6.1.4.1.37950.1.1.5.10.17.3.1.1.5
		-- 1.3.6.1.4.1.37950.1.1.5.10.17.3.1.1.5
		transDelay OBJECT-TYPE
			SYNTAX Integer32 (1..65535)
			MAX-ACCESS read-write
			STATUS current
			DESCRIPTION
				"Description."
			::= { ospfInterfaceEntry 5 }

		
--         1.3.6.1.4.1.37950.1.1.5.10.17.3.1.1.6
-- 1.3.6.1.4.1.37950.1.1.5.10.17.3.1.1.6
-- 1.3.6.1.4.1.37950.1.1.5.10.17.3.1.1.6
-- 1.3.6.1.4.1.37950.1.1.5.10.17.3.1.1.6
-- 1.3.6.1.4.1.37950.1.1.5.10.17.3.1.1.6
-- 1.3.6.1.4.1.37950.1.1.5.10.17.3.1.1.6
-- 1.3.6.1.4.1.37950.1.1.5.10.17.3.1.1.6
-- 1.3.6.1.4.1.37950.1.1.5.10.17.3.1.1.6
		-- 1.3.6.1.4.1.37950.1.1.5.10.17.3.1.1.6
		helloVal OBJECT-TYPE
			SYNTAX Integer32 (1..65535)
			MAX-ACCESS read-write
			STATUS current
			DESCRIPTION
				"Description."
			::= { ospfInterfaceEntry 6 }

		
--         1.3.6.1.4.1.37950.1.1.5.10.17.3.1.1.7
-- 1.3.6.1.4.1.37950.1.1.5.10.17.3.1.1.7
-- 1.3.6.1.4.1.37950.1.1.5.10.17.3.1.1.7
-- 1.3.6.1.4.1.37950.1.1.5.10.17.3.1.1.7
-- 1.3.6.1.4.1.37950.1.1.5.10.17.3.1.1.7
-- 1.3.6.1.4.1.37950.1.1.5.10.17.3.1.1.7
-- 1.3.6.1.4.1.37950.1.1.5.10.17.3.1.1.7
-- 1.3.6.1.4.1.37950.1.1.5.10.17.3.1.1.7
		-- 1.3.6.1.4.1.37950.1.1.5.10.17.3.1.1.7
		deadVal OBJECT-TYPE
			SYNTAX Integer32 (1..65535)
			MAX-ACCESS read-write
			STATUS current
			DESCRIPTION
				"Description."
			::= { ospfInterfaceEntry 7 }

		
--         1.3.6.1.4.1.37950.1.1.5.10.17.3.1.1.8
-- 1.3.6.1.4.1.37950.1.1.5.10.17.3.1.1.8
-- 1.3.6.1.4.1.37950.1.1.5.10.17.3.1.1.8
-- 1.3.6.1.4.1.37950.1.1.5.10.17.3.1.1.8
-- 1.3.6.1.4.1.37950.1.1.5.10.17.3.1.1.8
-- 1.3.6.1.4.1.37950.1.1.5.10.17.3.1.1.8
-- 1.3.6.1.4.1.37950.1.1.5.10.17.3.1.1.8
-- 1.3.6.1.4.1.37950.1.1.5.10.17.3.1.1.8
		-- 1.3.6.1.4.1.37950.1.1.5.10.17.3.1.1.8
		auth OBJECT-TYPE
			SYNTAX INTEGER
				{
				disable(0),
				text(1),
				md5(2)
				}
			MAX-ACCESS read-write
			STATUS current
			DESCRIPTION
				"Description."
			::= { ospfInterfaceEntry 8 }

		
--         1.3.6.1.4.1.37950.1.1.5.10.17.3.1.1.10
-- 1.3.6.1.4.1.37950.1.1.5.10.17.3.1.1.10
-- 1.3.6.1.4.1.37950.1.1.5.10.17.3.1.1.10
-- 1.3.6.1.4.1.37950.1.1.5.10.17.3.1.1.10
-- 1.3.6.1.4.1.37950.1.1.5.10.17.3.1.1.10
-- 1.3.6.1.4.1.37950.1.1.5.10.17.3.1.1.10
-- 1.3.6.1.4.1.37950.1.1.5.10.17.3.1.1.10
-- 1.3.6.1.4.1.37950.1.1.5.10.17.3.1.1.10
		-- 1.3.6.1.4.1.37950.1.1.5.10.17.3.1.1.10
		key OBJECT-TYPE
			SYNTAX Integer32 (0..255)
			MAX-ACCESS read-write
			STATUS current
			DESCRIPTION
				"Description."
			::= { ospfInterfaceEntry 10 }

		
--         1.3.6.1.4.1.37950.1.1.5.10.17.3.1.1.11
-- 1.3.6.1.4.1.37950.1.1.5.10.17.3.1.1.11
-- 1.3.6.1.4.1.37950.1.1.5.10.17.3.1.1.11
-- 1.3.6.1.4.1.37950.1.1.5.10.17.3.1.1.11
-- 1.3.6.1.4.1.37950.1.1.5.10.17.3.1.1.11
-- 1.3.6.1.4.1.37950.1.1.5.10.17.3.1.1.11
-- 1.3.6.1.4.1.37950.1.1.5.10.17.3.1.1.11
-- 1.3.6.1.4.1.37950.1.1.5.10.17.3.1.1.11
		-- 1.3.6.1.4.1.37950.1.1.5.10.17.3.1.1.11
		authString OBJECT-TYPE
			SYNTAX OCTET STRING
			MAX-ACCESS read-write
			STATUS current
			DESCRIPTION
				"Description."
			::= { ospfInterfaceEntry 11 }

		
--         1.3.6.1.4.1.37950.1.1.5.10.17.4
-- 1.3.6.1.4.1.37950.1.1.5.10.17.4
-- 1.3.6.1.4.1.37950.1.1.5.10.17.4
-- 1.3.6.1.4.1.37950.1.1.5.10.17.4
-- 1.3.6.1.4.1.37950.1.1.5.10.17.4
-- 1.3.6.1.4.1.37950.1.1.5.10.17.4
-- 1.3.6.1.4.1.37950.1.1.5.10.17.4
-- 1.3.6.1.4.1.37950.1.1.5.10.17.4
		-- 1.3.6.1.4.1.37950.1.1.5.10.17.4
		ospfInformation OBJECT IDENTIFIER ::= { v1600dOspf 4 }

		
--         1.3.6.1.4.1.37950.1.1.5.10.17.4.1
-- 1.3.6.1.4.1.37950.1.1.5.10.17.4.1
-- 1.3.6.1.4.1.37950.1.1.5.10.17.4.1
-- 1.3.6.1.4.1.37950.1.1.5.10.17.4.1
-- 1.3.6.1.4.1.37950.1.1.5.10.17.4.1
-- 1.3.6.1.4.1.37950.1.1.5.10.17.4.1
-- 1.3.6.1.4.1.37950.1.1.5.10.17.4.1
-- 1.3.6.1.4.1.37950.1.1.5.10.17.4.1
		-- 1.3.6.1.4.1.37950.1.1.5.10.17.4.1
		ospfNeighborTable OBJECT-TYPE
			SYNTAX SEQUENCE OF OspfNeighborEntry
			MAX-ACCESS not-accessible
			STATUS current
			DESCRIPTION
				"Description."
			::= { ospfInformation 1 }

		
--         1.3.6.1.4.1.37950.1.1.5.10.17.4.1.1
-- 1.3.6.1.4.1.37950.1.1.5.10.17.4.1.1
-- 1.3.6.1.4.1.37950.1.1.5.10.17.4.1.1
-- 1.3.6.1.4.1.37950.1.1.5.10.17.4.1.1
-- 1.3.6.1.4.1.37950.1.1.5.10.17.4.1.1
-- 1.3.6.1.4.1.37950.1.1.5.10.17.4.1.1
-- 1.3.6.1.4.1.37950.1.1.5.10.17.4.1.1
-- 1.3.6.1.4.1.37950.1.1.5.10.17.4.1.1
		-- 1.3.6.1.4.1.37950.1.1.5.10.17.4.1.1
		ospfNeighborEntry OBJECT-TYPE
			SYNTAX OspfNeighborEntry
			MAX-ACCESS not-accessible
			STATUS current
			DESCRIPTION
				"Description."
			INDEX { neighborId, address }
			::= { ospfNeighborTable 1 }

		
		OspfNeighborEntry ::=
			SEQUENCE { 
				neighborId
					IpAddress,
				priority
					Integer32,
				state
					OCTET STRING,
				deadTime
					OCTET STRING,
				address
					IpAddress,
				interface
					OCTET STRING,
				rxmtl
					Integer32,
				rqstl
					Integer32,
				dbsml
					Integer32
			 }

--         1.3.6.1.4.1.37950.1.1.5.10.17.4.1.1.1
-- 1.3.6.1.4.1.37950.1.1.5.10.17.4.1.1.1
-- 1.3.6.1.4.1.37950.1.1.5.10.17.4.1.1.1
-- 1.3.6.1.4.1.37950.1.1.5.10.17.4.1.1.1
-- 1.3.6.1.4.1.37950.1.1.5.10.17.4.1.1.1
-- 1.3.6.1.4.1.37950.1.1.5.10.17.4.1.1.1
-- 1.3.6.1.4.1.37950.1.1.5.10.17.4.1.1.1
-- 1.3.6.1.4.1.37950.1.1.5.10.17.4.1.1.1
		-- 1.3.6.1.4.1.37950.1.1.5.10.17.4.1.1.1
		neighborId OBJECT-TYPE
			SYNTAX IpAddress
			MAX-ACCESS read-only
			STATUS current
			DESCRIPTION
				"Description."
			::= { ospfNeighborEntry 1 }

		
--         1.3.6.1.4.1.37950.1.1.5.10.17.4.1.1.2
-- 1.3.6.1.4.1.37950.1.1.5.10.17.4.1.1.2
-- 1.3.6.1.4.1.37950.1.1.5.10.17.4.1.1.2
-- 1.3.6.1.4.1.37950.1.1.5.10.17.4.1.1.2
-- 1.3.6.1.4.1.37950.1.1.5.10.17.4.1.1.2
-- 1.3.6.1.4.1.37950.1.1.5.10.17.4.1.1.2
-- 1.3.6.1.4.1.37950.1.1.5.10.17.4.1.1.2
-- 1.3.6.1.4.1.37950.1.1.5.10.17.4.1.1.2
		-- 1.3.6.1.4.1.37950.1.1.5.10.17.4.1.1.2
		priority OBJECT-TYPE
			SYNTAX Integer32
			MAX-ACCESS read-only
			STATUS current
			DESCRIPTION
				"Description."
			::= { ospfNeighborEntry 2 }

		
--         1.3.6.1.4.1.37950.1.1.5.10.17.4.1.1.3
-- 1.3.6.1.4.1.37950.1.1.5.10.17.4.1.1.3
-- 1.3.6.1.4.1.37950.1.1.5.10.17.4.1.1.3
-- 1.3.6.1.4.1.37950.1.1.5.10.17.4.1.1.3
-- 1.3.6.1.4.1.37950.1.1.5.10.17.4.1.1.3
-- 1.3.6.1.4.1.37950.1.1.5.10.17.4.1.1.3
-- 1.3.6.1.4.1.37950.1.1.5.10.17.4.1.1.3
-- 1.3.6.1.4.1.37950.1.1.5.10.17.4.1.1.3
		-- 1.3.6.1.4.1.37950.1.1.5.10.17.4.1.1.3
		state OBJECT-TYPE
			SYNTAX OCTET STRING
			MAX-ACCESS read-only
			STATUS current
			DESCRIPTION
				"Description."
			::= { ospfNeighborEntry 3 }

		
--         1.3.6.1.4.1.37950.1.1.5.10.17.4.1.1.4
-- 1.3.6.1.4.1.37950.1.1.5.10.17.4.1.1.4
-- 1.3.6.1.4.1.37950.1.1.5.10.17.4.1.1.4
-- 1.3.6.1.4.1.37950.1.1.5.10.17.4.1.1.4
-- 1.3.6.1.4.1.37950.1.1.5.10.17.4.1.1.4
-- 1.3.6.1.4.1.37950.1.1.5.10.17.4.1.1.4
-- 1.3.6.1.4.1.37950.1.1.5.10.17.4.1.1.4
-- 1.3.6.1.4.1.37950.1.1.5.10.17.4.1.1.4
		-- 1.3.6.1.4.1.37950.1.1.5.10.17.4.1.1.4
		deadTime OBJECT-TYPE
			SYNTAX OCTET STRING
			MAX-ACCESS read-only
			STATUS current
			DESCRIPTION
				"Description."
			::= { ospfNeighborEntry 4 }

		
--         1.3.6.1.4.1.37950.1.1.5.10.17.4.1.1.5
-- 1.3.6.1.4.1.37950.1.1.5.10.17.4.1.1.5
-- 1.3.6.1.4.1.37950.1.1.5.10.17.4.1.1.5
-- 1.3.6.1.4.1.37950.1.1.5.10.17.4.1.1.5
-- 1.3.6.1.4.1.37950.1.1.5.10.17.4.1.1.5
-- 1.3.6.1.4.1.37950.1.1.5.10.17.4.1.1.5
-- 1.3.6.1.4.1.37950.1.1.5.10.17.4.1.1.5
-- 1.3.6.1.4.1.37950.1.1.5.10.17.4.1.1.5
		-- 1.3.6.1.4.1.37950.1.1.5.10.17.4.1.1.5
		address OBJECT-TYPE
			SYNTAX IpAddress
			MAX-ACCESS read-only
			STATUS current
			DESCRIPTION
				"Description."
			::= { ospfNeighborEntry 5 }

		
--         1.3.6.1.4.1.37950.1.1.5.10.17.4.1.1.6
-- 1.3.6.1.4.1.37950.1.1.5.10.17.4.1.1.6
-- 1.3.6.1.4.1.37950.1.1.5.10.17.4.1.1.6
-- 1.3.6.1.4.1.37950.1.1.5.10.17.4.1.1.6
-- 1.3.6.1.4.1.37950.1.1.5.10.17.4.1.1.6
-- 1.3.6.1.4.1.37950.1.1.5.10.17.4.1.1.6
-- 1.3.6.1.4.1.37950.1.1.5.10.17.4.1.1.6
-- 1.3.6.1.4.1.37950.1.1.5.10.17.4.1.1.6
		-- 1.3.6.1.4.1.37950.1.1.5.10.17.4.1.1.6
		interface OBJECT-TYPE
			SYNTAX OCTET STRING
			MAX-ACCESS read-only
			STATUS current
			DESCRIPTION
				"Description."
			::= { ospfNeighborEntry 6 }

		
--         1.3.6.1.4.1.37950.1.1.5.10.17.4.1.1.7
-- 1.3.6.1.4.1.37950.1.1.5.10.17.4.1.1.7
-- 1.3.6.1.4.1.37950.1.1.5.10.17.4.1.1.7
-- 1.3.6.1.4.1.37950.1.1.5.10.17.4.1.1.7
-- 1.3.6.1.4.1.37950.1.1.5.10.17.4.1.1.7
-- 1.3.6.1.4.1.37950.1.1.5.10.17.4.1.1.7
-- 1.3.6.1.4.1.37950.1.1.5.10.17.4.1.1.7
-- 1.3.6.1.4.1.37950.1.1.5.10.17.4.1.1.7
		-- 1.3.6.1.4.1.37950.1.1.5.10.17.4.1.1.7
		rxmtl OBJECT-TYPE
			SYNTAX Integer32
			MAX-ACCESS read-only
			STATUS current
			DESCRIPTION
				"Description."
			::= { ospfNeighborEntry 7 }

		
--         1.3.6.1.4.1.37950.1.1.5.10.17.4.1.1.8
-- 1.3.6.1.4.1.37950.1.1.5.10.17.4.1.1.8
-- 1.3.6.1.4.1.37950.1.1.5.10.17.4.1.1.8
-- 1.3.6.1.4.1.37950.1.1.5.10.17.4.1.1.8
-- 1.3.6.1.4.1.37950.1.1.5.10.17.4.1.1.8
-- 1.3.6.1.4.1.37950.1.1.5.10.17.4.1.1.8
-- 1.3.6.1.4.1.37950.1.1.5.10.17.4.1.1.8
-- 1.3.6.1.4.1.37950.1.1.5.10.17.4.1.1.8
		-- 1.3.6.1.4.1.37950.1.1.5.10.17.4.1.1.8
		rqstl OBJECT-TYPE
			SYNTAX Integer32
			MAX-ACCESS read-only
			STATUS current
			DESCRIPTION
				"Description."
			::= { ospfNeighborEntry 8 }

		
--         1.3.6.1.4.1.37950.1.1.5.10.17.4.1.1.9
-- 1.3.6.1.4.1.37950.1.1.5.10.17.4.1.1.9
-- 1.3.6.1.4.1.37950.1.1.5.10.17.4.1.1.9
-- 1.3.6.1.4.1.37950.1.1.5.10.17.4.1.1.9
-- 1.3.6.1.4.1.37950.1.1.5.10.17.4.1.1.9
-- 1.3.6.1.4.1.37950.1.1.5.10.17.4.1.1.9
-- 1.3.6.1.4.1.37950.1.1.5.10.17.4.1.1.9
-- 1.3.6.1.4.1.37950.1.1.5.10.17.4.1.1.9
		-- 1.3.6.1.4.1.37950.1.1.5.10.17.4.1.1.9
		dbsml OBJECT-TYPE
			SYNTAX Integer32
			MAX-ACCESS read-only
			STATUS current
			DESCRIPTION
				"Description."
			::= { ospfNeighborEntry 9 }

		
--         1.3.6.1.4.1.37950.1.1.5.10.17.4.2
-- 1.3.6.1.4.1.37950.1.1.5.10.17.4.2
-- 1.3.6.1.4.1.37950.1.1.5.10.17.4.2
-- 1.3.6.1.4.1.37950.1.1.5.10.17.4.2
-- 1.3.6.1.4.1.37950.1.1.5.10.17.4.2
-- 1.3.6.1.4.1.37950.1.1.5.10.17.4.2
-- 1.3.6.1.4.1.37950.1.1.5.10.17.4.2
-- 1.3.6.1.4.1.37950.1.1.5.10.17.4.2
		-- 1.3.6.1.4.1.37950.1.1.5.10.17.4.2
		ospfRoutingTable OBJECT IDENTIFIER ::= { ospfInformation 2 }

		
--         1.3.6.1.4.1.37950.1.1.5.10.17.4.2.1
-- 1.3.6.1.4.1.37950.1.1.5.10.17.4.2.1
-- 1.3.6.1.4.1.37950.1.1.5.10.17.4.2.1
-- 1.3.6.1.4.1.37950.1.1.5.10.17.4.2.1
-- 1.3.6.1.4.1.37950.1.1.5.10.17.4.2.1
-- 1.3.6.1.4.1.37950.1.1.5.10.17.4.2.1
-- 1.3.6.1.4.1.37950.1.1.5.10.17.4.2.1
-- 1.3.6.1.4.1.37950.1.1.5.10.17.4.2.1
		-- 1.3.6.1.4.1.37950.1.1.5.10.17.4.2.1
		ospfNetworkRoutingTable OBJECT-TYPE
			SYNTAX SEQUENCE OF OspfNetworkRoutingEntry
			MAX-ACCESS not-accessible
			STATUS current
			DESCRIPTION
				"Description."
			::= { ospfRoutingTable 1 }

		
--         1.3.6.1.4.1.37950.1.1.5.10.17.4.2.1.1
-- 1.3.6.1.4.1.37950.1.1.5.10.17.4.2.1.1
-- 1.3.6.1.4.1.37950.1.1.5.10.17.4.2.1.1
-- 1.3.6.1.4.1.37950.1.1.5.10.17.4.2.1.1
-- 1.3.6.1.4.1.37950.1.1.5.10.17.4.2.1.1
-- 1.3.6.1.4.1.37950.1.1.5.10.17.4.2.1.1
-- 1.3.6.1.4.1.37950.1.1.5.10.17.4.2.1.1
-- 1.3.6.1.4.1.37950.1.1.5.10.17.4.2.1.1
		-- 1.3.6.1.4.1.37950.1.1.5.10.17.4.2.1.1
		ospfNetworkRoutingEntry OBJECT-TYPE
			SYNTAX OspfNetworkRoutingEntry
			MAX-ACCESS not-accessible
			STATUS current
			DESCRIPTION
				"Description."
			INDEX { destinationType, routingNetwork }
			::= { ospfNetworkRoutingTable 1 }

		
		OspfNetworkRoutingEntry ::=
			SEQUENCE { 
				destinationType
					OCTET STRING,
				routingNetwork
					OCTET STRING,
				routingCost
					Integer32,
				routingArea
					OCTET STRING,
				routingInterface
					OCTET STRING
			 }

--         1.3.6.1.4.1.37950.1.1.5.10.17.4.2.1.1.1
-- 1.3.6.1.4.1.37950.1.1.5.10.17.4.2.1.1.1
-- 1.3.6.1.4.1.37950.1.1.5.10.17.4.2.1.1.1
-- 1.3.6.1.4.1.37950.1.1.5.10.17.4.2.1.1.1
-- 1.3.6.1.4.1.37950.1.1.5.10.17.4.2.1.1.1
-- 1.3.6.1.4.1.37950.1.1.5.10.17.4.2.1.1.1
-- 1.3.6.1.4.1.37950.1.1.5.10.17.4.2.1.1.1
-- 1.3.6.1.4.1.37950.1.1.5.10.17.4.2.1.1.1
		-- 1.3.6.1.4.1.37950.1.1.5.10.17.4.2.1.1.1
		destinationType OBJECT-TYPE
			SYNTAX OCTET STRING
			MAX-ACCESS read-only
			STATUS current
			DESCRIPTION
				"Description."
			::= { ospfNetworkRoutingEntry 1 }

		
--         1.3.6.1.4.1.37950.1.1.5.10.17.4.2.1.1.2
-- 1.3.6.1.4.1.37950.1.1.5.10.17.4.2.1.1.2
-- 1.3.6.1.4.1.37950.1.1.5.10.17.4.2.1.1.2
-- 1.3.6.1.4.1.37950.1.1.5.10.17.4.2.1.1.2
-- 1.3.6.1.4.1.37950.1.1.5.10.17.4.2.1.1.2
-- 1.3.6.1.4.1.37950.1.1.5.10.17.4.2.1.1.2
-- 1.3.6.1.4.1.37950.1.1.5.10.17.4.2.1.1.2
-- 1.3.6.1.4.1.37950.1.1.5.10.17.4.2.1.1.2
		-- 1.3.6.1.4.1.37950.1.1.5.10.17.4.2.1.1.2
		routingNetwork OBJECT-TYPE
			SYNTAX OCTET STRING
			MAX-ACCESS read-only
			STATUS current
			DESCRIPTION
				"Description."
			::= { ospfNetworkRoutingEntry 2 }

		
--         1.3.6.1.4.1.37950.1.1.5.10.17.4.2.1.1.3
-- 1.3.6.1.4.1.37950.1.1.5.10.17.4.2.1.1.3
-- 1.3.6.1.4.1.37950.1.1.5.10.17.4.2.1.1.3
-- 1.3.6.1.4.1.37950.1.1.5.10.17.4.2.1.1.3
-- 1.3.6.1.4.1.37950.1.1.5.10.17.4.2.1.1.3
-- 1.3.6.1.4.1.37950.1.1.5.10.17.4.2.1.1.3
-- 1.3.6.1.4.1.37950.1.1.5.10.17.4.2.1.1.3
-- 1.3.6.1.4.1.37950.1.1.5.10.17.4.2.1.1.3
		-- 1.3.6.1.4.1.37950.1.1.5.10.17.4.2.1.1.3
		routingCost OBJECT-TYPE
			SYNTAX Integer32
			MAX-ACCESS read-only
			STATUS current
			DESCRIPTION
				"Description."
			::= { ospfNetworkRoutingEntry 3 }

		
--         1.3.6.1.4.1.37950.1.1.5.10.17.4.2.1.1.4
-- 1.3.6.1.4.1.37950.1.1.5.10.17.4.2.1.1.4
-- 1.3.6.1.4.1.37950.1.1.5.10.17.4.2.1.1.4
-- 1.3.6.1.4.1.37950.1.1.5.10.17.4.2.1.1.4
-- 1.3.6.1.4.1.37950.1.1.5.10.17.4.2.1.1.4
-- 1.3.6.1.4.1.37950.1.1.5.10.17.4.2.1.1.4
-- 1.3.6.1.4.1.37950.1.1.5.10.17.4.2.1.1.4
-- 1.3.6.1.4.1.37950.1.1.5.10.17.4.2.1.1.4
		-- 1.3.6.1.4.1.37950.1.1.5.10.17.4.2.1.1.4
		routingArea OBJECT-TYPE
			SYNTAX OCTET STRING
			MAX-ACCESS read-only
			STATUS current
			DESCRIPTION
				"Description."
			::= { ospfNetworkRoutingEntry 4 }

		
--         1.3.6.1.4.1.37950.1.1.5.10.17.4.2.1.1.5
-- 1.3.6.1.4.1.37950.1.1.5.10.17.4.2.1.1.5
-- 1.3.6.1.4.1.37950.1.1.5.10.17.4.2.1.1.5
-- 1.3.6.1.4.1.37950.1.1.5.10.17.4.2.1.1.5
-- 1.3.6.1.4.1.37950.1.1.5.10.17.4.2.1.1.5
-- 1.3.6.1.4.1.37950.1.1.5.10.17.4.2.1.1.5
-- 1.3.6.1.4.1.37950.1.1.5.10.17.4.2.1.1.5
-- 1.3.6.1.4.1.37950.1.1.5.10.17.4.2.1.1.5
		-- 1.3.6.1.4.1.37950.1.1.5.10.17.4.2.1.1.5
		routingInterface OBJECT-TYPE
			SYNTAX OCTET STRING
			MAX-ACCESS read-only
			STATUS current
			DESCRIPTION
				"Description."
			::= { ospfNetworkRoutingEntry 5 }

		
--         1.3.6.1.4.1.37950.1.1.5.10.17.4.2.2
-- 1.3.6.1.4.1.37950.1.1.5.10.17.4.2.2
-- 1.3.6.1.4.1.37950.1.1.5.10.17.4.2.2
-- 1.3.6.1.4.1.37950.1.1.5.10.17.4.2.2
-- 1.3.6.1.4.1.37950.1.1.5.10.17.4.2.2
-- 1.3.6.1.4.1.37950.1.1.5.10.17.4.2.2
-- 1.3.6.1.4.1.37950.1.1.5.10.17.4.2.2
-- 1.3.6.1.4.1.37950.1.1.5.10.17.4.2.2
		-- 1.3.6.1.4.1.37950.1.1.5.10.17.4.2.2
		ospfRouterRoutingTable OBJECT-TYPE
			SYNTAX SEQUENCE OF OspfRouterRoutingEntry
			MAX-ACCESS not-accessible
			STATUS current
			DESCRIPTION
				"Description."
			::= { ospfRoutingTable 2 }

		
--         1.3.6.1.4.1.37950.1.1.5.10.17.4.2.2.1
-- 1.3.6.1.4.1.37950.1.1.5.10.17.4.2.2.1
-- 1.3.6.1.4.1.37950.1.1.5.10.17.4.2.2.1
-- 1.3.6.1.4.1.37950.1.1.5.10.17.4.2.2.1
-- 1.3.6.1.4.1.37950.1.1.5.10.17.4.2.2.1
-- 1.3.6.1.4.1.37950.1.1.5.10.17.4.2.2.1
-- 1.3.6.1.4.1.37950.1.1.5.10.17.4.2.2.1
-- 1.3.6.1.4.1.37950.1.1.5.10.17.4.2.2.1
		-- 1.3.6.1.4.1.37950.1.1.5.10.17.4.2.2.1
		ospfRouterRoutingEntry OBJECT-TYPE
			SYNTAX OspfRouterRoutingEntry
			MAX-ACCESS not-accessible
			STATUS current
			DESCRIPTION
				"Description."
			INDEX { routerDesType, routerNetwork }
			::= { ospfRouterRoutingTable 1 }

		
		OspfRouterRoutingEntry ::=
			SEQUENCE { 
				routerDesType
					OCTET STRING,
				routerNetwork
					OCTET STRING,
				routerCost
					Integer32,
				areaOrtype
					OCTET STRING,
				routerInterface
					OCTET STRING
			 }

--         1.3.6.1.4.1.37950.1.1.5.10.17.4.2.2.1.1
-- 1.3.6.1.4.1.37950.1.1.5.10.17.4.2.2.1.1
-- 1.3.6.1.4.1.37950.1.1.5.10.17.4.2.2.1.1
-- 1.3.6.1.4.1.37950.1.1.5.10.17.4.2.2.1.1
-- 1.3.6.1.4.1.37950.1.1.5.10.17.4.2.2.1.1
-- 1.3.6.1.4.1.37950.1.1.5.10.17.4.2.2.1.1
-- 1.3.6.1.4.1.37950.1.1.5.10.17.4.2.2.1.1
-- 1.3.6.1.4.1.37950.1.1.5.10.17.4.2.2.1.1
		-- 1.3.6.1.4.1.37950.1.1.5.10.17.4.2.2.1.1
		routerDesType OBJECT-TYPE
			SYNTAX OCTET STRING
			MAX-ACCESS read-only
			STATUS current
			DESCRIPTION
				"Description."
			::= { ospfRouterRoutingEntry 1 }

		
--         1.3.6.1.4.1.37950.1.1.5.10.17.4.2.2.1.2
-- 1.3.6.1.4.1.37950.1.1.5.10.17.4.2.2.1.2
-- 1.3.6.1.4.1.37950.1.1.5.10.17.4.2.2.1.2
-- 1.3.6.1.4.1.37950.1.1.5.10.17.4.2.2.1.2
-- 1.3.6.1.4.1.37950.1.1.5.10.17.4.2.2.1.2
-- 1.3.6.1.4.1.37950.1.1.5.10.17.4.2.2.1.2
-- 1.3.6.1.4.1.37950.1.1.5.10.17.4.2.2.1.2
-- 1.3.6.1.4.1.37950.1.1.5.10.17.4.2.2.1.2
		-- 1.3.6.1.4.1.37950.1.1.5.10.17.4.2.2.1.2
		routerNetwork OBJECT-TYPE
			SYNTAX OCTET STRING
			MAX-ACCESS read-only
			STATUS current
			DESCRIPTION
				"Description."
			::= { ospfRouterRoutingEntry 2 }

		
--         1.3.6.1.4.1.37950.1.1.5.10.17.4.2.2.1.3
-- 1.3.6.1.4.1.37950.1.1.5.10.17.4.2.2.1.3
-- 1.3.6.1.4.1.37950.1.1.5.10.17.4.2.2.1.3
-- 1.3.6.1.4.1.37950.1.1.5.10.17.4.2.2.1.3
-- 1.3.6.1.4.1.37950.1.1.5.10.17.4.2.2.1.3
-- 1.3.6.1.4.1.37950.1.1.5.10.17.4.2.2.1.3
-- 1.3.6.1.4.1.37950.1.1.5.10.17.4.2.2.1.3
-- 1.3.6.1.4.1.37950.1.1.5.10.17.4.2.2.1.3
		-- 1.3.6.1.4.1.37950.1.1.5.10.17.4.2.2.1.3
		routerCost OBJECT-TYPE
			SYNTAX Integer32
			MAX-ACCESS read-only
			STATUS current
			DESCRIPTION
				"Description."
			::= { ospfRouterRoutingEntry 3 }

		
--         1.3.6.1.4.1.37950.1.1.5.10.17.4.2.2.1.4
-- 1.3.6.1.4.1.37950.1.1.5.10.17.4.2.2.1.4
-- 1.3.6.1.4.1.37950.1.1.5.10.17.4.2.2.1.4
-- 1.3.6.1.4.1.37950.1.1.5.10.17.4.2.2.1.4
-- 1.3.6.1.4.1.37950.1.1.5.10.17.4.2.2.1.4
-- 1.3.6.1.4.1.37950.1.1.5.10.17.4.2.2.1.4
-- 1.3.6.1.4.1.37950.1.1.5.10.17.4.2.2.1.4
-- 1.3.6.1.4.1.37950.1.1.5.10.17.4.2.2.1.4
		-- 1.3.6.1.4.1.37950.1.1.5.10.17.4.2.2.1.4
		areaOrtype OBJECT-TYPE
			SYNTAX OCTET STRING
			MAX-ACCESS read-only
			STATUS current
			DESCRIPTION
				"Description."
			::= { ospfRouterRoutingEntry 4 }

		
--         1.3.6.1.4.1.37950.1.1.5.10.17.4.2.2.1.5
-- 1.3.6.1.4.1.37950.1.1.5.10.17.4.2.2.1.5
-- 1.3.6.1.4.1.37950.1.1.5.10.17.4.2.2.1.5
-- 1.3.6.1.4.1.37950.1.1.5.10.17.4.2.2.1.5
-- 1.3.6.1.4.1.37950.1.1.5.10.17.4.2.2.1.5
-- 1.3.6.1.4.1.37950.1.1.5.10.17.4.2.2.1.5
-- 1.3.6.1.4.1.37950.1.1.5.10.17.4.2.2.1.5
-- 1.3.6.1.4.1.37950.1.1.5.10.17.4.2.2.1.5
		-- 1.3.6.1.4.1.37950.1.1.5.10.17.4.2.2.1.5
		routerInterface OBJECT-TYPE
			SYNTAX OCTET STRING
			MAX-ACCESS read-write
			STATUS current
			DESCRIPTION
				"Description."
			::= { ospfRouterRoutingEntry 5 }

		
--         1.3.6.1.4.1.37950.1.1.5.10.17.4.2.3
-- 1.3.6.1.4.1.37950.1.1.5.10.17.4.2.3
-- 1.3.6.1.4.1.37950.1.1.5.10.17.4.2.3
-- 1.3.6.1.4.1.37950.1.1.5.10.17.4.2.3
-- 1.3.6.1.4.1.37950.1.1.5.10.17.4.2.3
-- 1.3.6.1.4.1.37950.1.1.5.10.17.4.2.3
-- 1.3.6.1.4.1.37950.1.1.5.10.17.4.2.3
-- 1.3.6.1.4.1.37950.1.1.5.10.17.4.2.3
		-- 1.3.6.1.4.1.37950.1.1.5.10.17.4.2.3
		ospfExternalRoutingTable OBJECT-TYPE
			SYNTAX SEQUENCE OF OspfExternalRoutingEntry
			MAX-ACCESS not-accessible
			STATUS current
			DESCRIPTION
				"Description."
			::= { ospfRoutingTable 3 }

		
--         1.3.6.1.4.1.37950.1.1.5.10.17.4.2.3.1
-- 1.3.6.1.4.1.37950.1.1.5.10.17.4.2.3.1
-- 1.3.6.1.4.1.37950.1.1.5.10.17.4.2.3.1
-- 1.3.6.1.4.1.37950.1.1.5.10.17.4.2.3.1
-- 1.3.6.1.4.1.37950.1.1.5.10.17.4.2.3.1
-- 1.3.6.1.4.1.37950.1.1.5.10.17.4.2.3.1
-- 1.3.6.1.4.1.37950.1.1.5.10.17.4.2.3.1
-- 1.3.6.1.4.1.37950.1.1.5.10.17.4.2.3.1
		-- 1.3.6.1.4.1.37950.1.1.5.10.17.4.2.3.1
		ospfExternalRoutingEntry OBJECT-TYPE
			SYNTAX OspfExternalRoutingEntry
			MAX-ACCESS not-accessible
			STATUS current
			DESCRIPTION
				"Description."
			INDEX { externalDesType, externalNetwork }
			::= { ospfExternalRoutingTable 1 }

		
		OspfExternalRoutingEntry ::=
			SEQUENCE { 
				externalDesType
					OCTET STRING,
				externalNetwork
					OCTET STRING,
				costOrTypeTwoCost
					OCTET STRING,
				externalTag
					Integer32,
				externalInterface
					OCTET STRING
			 }

--         1.3.6.1.4.1.37950.1.1.5.10.17.4.2.3.1.1
-- 1.3.6.1.4.1.37950.1.1.5.10.17.4.2.3.1.1
-- 1.3.6.1.4.1.37950.1.1.5.10.17.4.2.3.1.1
-- 1.3.6.1.4.1.37950.1.1.5.10.17.4.2.3.1.1
-- 1.3.6.1.4.1.37950.1.1.5.10.17.4.2.3.1.1
-- 1.3.6.1.4.1.37950.1.1.5.10.17.4.2.3.1.1
-- 1.3.6.1.4.1.37950.1.1.5.10.17.4.2.3.1.1
-- 1.3.6.1.4.1.37950.1.1.5.10.17.4.2.3.1.1
		-- 1.3.6.1.4.1.37950.1.1.5.10.17.4.2.3.1.1
		externalDesType OBJECT-TYPE
			SYNTAX OCTET STRING
			MAX-ACCESS read-only
			STATUS current
			DESCRIPTION
				"Description."
			::= { ospfExternalRoutingEntry 1 }

		
--         1.3.6.1.4.1.37950.1.1.5.10.17.4.2.3.1.2
-- 1.3.6.1.4.1.37950.1.1.5.10.17.4.2.3.1.2
-- 1.3.6.1.4.1.37950.1.1.5.10.17.4.2.3.1.2
-- 1.3.6.1.4.1.37950.1.1.5.10.17.4.2.3.1.2
-- 1.3.6.1.4.1.37950.1.1.5.10.17.4.2.3.1.2
-- 1.3.6.1.4.1.37950.1.1.5.10.17.4.2.3.1.2
-- 1.3.6.1.4.1.37950.1.1.5.10.17.4.2.3.1.2
-- 1.3.6.1.4.1.37950.1.1.5.10.17.4.2.3.1.2
		-- 1.3.6.1.4.1.37950.1.1.5.10.17.4.2.3.1.2
		externalNetwork OBJECT-TYPE
			SYNTAX OCTET STRING
			MAX-ACCESS read-only
			STATUS current
			DESCRIPTION
				"Description."
			::= { ospfExternalRoutingEntry 2 }

		
--         1.3.6.1.4.1.37950.1.1.5.10.17.4.2.3.1.3
-- 1.3.6.1.4.1.37950.1.1.5.10.17.4.2.3.1.3
-- 1.3.6.1.4.1.37950.1.1.5.10.17.4.2.3.1.3
-- 1.3.6.1.4.1.37950.1.1.5.10.17.4.2.3.1.3
-- 1.3.6.1.4.1.37950.1.1.5.10.17.4.2.3.1.3
-- 1.3.6.1.4.1.37950.1.1.5.10.17.4.2.3.1.3
-- 1.3.6.1.4.1.37950.1.1.5.10.17.4.2.3.1.3
-- 1.3.6.1.4.1.37950.1.1.5.10.17.4.2.3.1.3
		-- 1.3.6.1.4.1.37950.1.1.5.10.17.4.2.3.1.3
		costOrTypeTwoCost OBJECT-TYPE
			SYNTAX OCTET STRING
			MAX-ACCESS read-only
			STATUS current
			DESCRIPTION
				"Description."
			::= { ospfExternalRoutingEntry 3 }

		
--         1.3.6.1.4.1.37950.1.1.5.10.17.4.2.3.1.4
-- 1.3.6.1.4.1.37950.1.1.5.10.17.4.2.3.1.4
-- 1.3.6.1.4.1.37950.1.1.5.10.17.4.2.3.1.4
-- 1.3.6.1.4.1.37950.1.1.5.10.17.4.2.3.1.4
-- 1.3.6.1.4.1.37950.1.1.5.10.17.4.2.3.1.4
-- 1.3.6.1.4.1.37950.1.1.5.10.17.4.2.3.1.4
-- 1.3.6.1.4.1.37950.1.1.5.10.17.4.2.3.1.4
-- 1.3.6.1.4.1.37950.1.1.5.10.17.4.2.3.1.4
		-- 1.3.6.1.4.1.37950.1.1.5.10.17.4.2.3.1.4
		externalTag OBJECT-TYPE
			SYNTAX Integer32
			MAX-ACCESS read-only
			STATUS current
			DESCRIPTION
				"Description."
			::= { ospfExternalRoutingEntry 4 }

		
--         1.3.6.1.4.1.37950.1.1.5.10.17.4.2.3.1.5
-- 1.3.6.1.4.1.37950.1.1.5.10.17.4.2.3.1.5
-- 1.3.6.1.4.1.37950.1.1.5.10.17.4.2.3.1.5
-- 1.3.6.1.4.1.37950.1.1.5.10.17.4.2.3.1.5
-- 1.3.6.1.4.1.37950.1.1.5.10.17.4.2.3.1.5
-- 1.3.6.1.4.1.37950.1.1.5.10.17.4.2.3.1.5
-- 1.3.6.1.4.1.37950.1.1.5.10.17.4.2.3.1.5
-- 1.3.6.1.4.1.37950.1.1.5.10.17.4.2.3.1.5
		-- 1.3.6.1.4.1.37950.1.1.5.10.17.4.2.3.1.5
		externalInterface OBJECT-TYPE
			SYNTAX OCTET STRING
			MAX-ACCESS read-only
			STATUS current
			DESCRIPTION
				"Description."
			::= { ospfExternalRoutingEntry 5 }

		
--         1.3.6.1.4.1.37950.1.1.5.10.17.4.3
-- 1.3.6.1.4.1.37950.1.1.5.10.17.4.3
-- 1.3.6.1.4.1.37950.1.1.5.10.17.4.3
-- 1.3.6.1.4.1.37950.1.1.5.10.17.4.3
-- 1.3.6.1.4.1.37950.1.1.5.10.17.4.3
-- 1.3.6.1.4.1.37950.1.1.5.10.17.4.3
-- 1.3.6.1.4.1.37950.1.1.5.10.17.4.3
-- 1.3.6.1.4.1.37950.1.1.5.10.17.4.3
		-- 1.3.6.1.4.1.37950.1.1.5.10.17.4.3
		ospfDatabaseTable OBJECT-TYPE
			SYNTAX SEQUENCE OF OspfDatabaseEntry
			MAX-ACCESS not-accessible
			STATUS current
			DESCRIPTION
				"Description."
			::= { ospfInformation 3 }

		
--         1.3.6.1.4.1.37950.1.1.5.10.17.4.3.1
-- 1.3.6.1.4.1.37950.1.1.5.10.17.4.3.1
-- 1.3.6.1.4.1.37950.1.1.5.10.17.4.3.1
-- 1.3.6.1.4.1.37950.1.1.5.10.17.4.3.1
-- 1.3.6.1.4.1.37950.1.1.5.10.17.4.3.1
-- 1.3.6.1.4.1.37950.1.1.5.10.17.4.3.1
-- 1.3.6.1.4.1.37950.1.1.5.10.17.4.3.1
-- 1.3.6.1.4.1.37950.1.1.5.10.17.4.3.1
		-- 1.3.6.1.4.1.37950.1.1.5.10.17.4.3.1
		ospfDatabaseEntry OBJECT-TYPE
			SYNTAX OspfDatabaseEntry
			MAX-ACCESS not-accessible
			STATUS current
			DESCRIPTION
				"Description."
			INDEX { lsaArea, lsaType, linkId }
			::= { ospfDatabaseTable 1 }

		
		OspfDatabaseEntry ::=
			SEQUENCE { 
				lsaArea
					OCTET STRING,
				lsaType
					OCTET STRING,
				linkId
					IpAddress,
				advRouter
					IpAddress,
				age
					Integer32,
				sequence
					OCTET STRING,
				ckSum
					OCTET STRING,
				linkCount
					Integer32,
				route
					OCTET STRING
			 }

--         1.3.6.1.4.1.37950.1.1.5.10.17.4.3.1.1
-- 1.3.6.1.4.1.37950.1.1.5.10.17.4.3.1.1
-- 1.3.6.1.4.1.37950.1.1.5.10.17.4.3.1.1
-- 1.3.6.1.4.1.37950.1.1.5.10.17.4.3.1.1
-- 1.3.6.1.4.1.37950.1.1.5.10.17.4.3.1.1
-- 1.3.6.1.4.1.37950.1.1.5.10.17.4.3.1.1
-- 1.3.6.1.4.1.37950.1.1.5.10.17.4.3.1.1
-- 1.3.6.1.4.1.37950.1.1.5.10.17.4.3.1.1
		-- 1.3.6.1.4.1.37950.1.1.5.10.17.4.3.1.1
		lsaArea OBJECT-TYPE
			SYNTAX OCTET STRING
			MAX-ACCESS read-only
			STATUS current
			DESCRIPTION
				"Description."
			::= { ospfDatabaseEntry 1 }

		
--         1.3.6.1.4.1.37950.1.1.5.10.17.4.3.1.2
-- 1.3.6.1.4.1.37950.1.1.5.10.17.4.3.1.2
-- 1.3.6.1.4.1.37950.1.1.5.10.17.4.3.1.2
-- 1.3.6.1.4.1.37950.1.1.5.10.17.4.3.1.2
-- 1.3.6.1.4.1.37950.1.1.5.10.17.4.3.1.2
-- 1.3.6.1.4.1.37950.1.1.5.10.17.4.3.1.2
-- 1.3.6.1.4.1.37950.1.1.5.10.17.4.3.1.2
-- 1.3.6.1.4.1.37950.1.1.5.10.17.4.3.1.2
		-- 1.3.6.1.4.1.37950.1.1.5.10.17.4.3.1.2
		lsaType OBJECT-TYPE
			SYNTAX OCTET STRING
			MAX-ACCESS read-only
			STATUS current
			DESCRIPTION
				"Description."
			::= { ospfDatabaseEntry 2 }

		
--         1.3.6.1.4.1.37950.1.1.5.10.17.4.3.1.3
-- 1.3.6.1.4.1.37950.1.1.5.10.17.4.3.1.3
-- 1.3.6.1.4.1.37950.1.1.5.10.17.4.3.1.3
-- 1.3.6.1.4.1.37950.1.1.5.10.17.4.3.1.3
-- 1.3.6.1.4.1.37950.1.1.5.10.17.4.3.1.3
-- 1.3.6.1.4.1.37950.1.1.5.10.17.4.3.1.3
-- 1.3.6.1.4.1.37950.1.1.5.10.17.4.3.1.3
-- 1.3.6.1.4.1.37950.1.1.5.10.17.4.3.1.3
		-- 1.3.6.1.4.1.37950.1.1.5.10.17.4.3.1.3
		linkId OBJECT-TYPE
			SYNTAX IpAddress
			MAX-ACCESS read-only
			STATUS current
			DESCRIPTION
				"Description."
			::= { ospfDatabaseEntry 3 }

		
--         1.3.6.1.4.1.37950.1.1.5.10.17.4.3.1.4
-- 1.3.6.1.4.1.37950.1.1.5.10.17.4.3.1.4
-- 1.3.6.1.4.1.37950.1.1.5.10.17.4.3.1.4
-- 1.3.6.1.4.1.37950.1.1.5.10.17.4.3.1.4
-- 1.3.6.1.4.1.37950.1.1.5.10.17.4.3.1.4
-- 1.3.6.1.4.1.37950.1.1.5.10.17.4.3.1.4
-- 1.3.6.1.4.1.37950.1.1.5.10.17.4.3.1.4
-- 1.3.6.1.4.1.37950.1.1.5.10.17.4.3.1.4
		-- 1.3.6.1.4.1.37950.1.1.5.10.17.4.3.1.4
		advRouter OBJECT-TYPE
			SYNTAX IpAddress
			MAX-ACCESS read-only
			STATUS current
			DESCRIPTION
				"Description."
			::= { ospfDatabaseEntry 4 }

		
--         1.3.6.1.4.1.37950.1.1.5.10.17.4.3.1.5
-- 1.3.6.1.4.1.37950.1.1.5.10.17.4.3.1.5
-- 1.3.6.1.4.1.37950.1.1.5.10.17.4.3.1.5
-- 1.3.6.1.4.1.37950.1.1.5.10.17.4.3.1.5
-- 1.3.6.1.4.1.37950.1.1.5.10.17.4.3.1.5
-- 1.3.6.1.4.1.37950.1.1.5.10.17.4.3.1.5
-- 1.3.6.1.4.1.37950.1.1.5.10.17.4.3.1.5
-- 1.3.6.1.4.1.37950.1.1.5.10.17.4.3.1.5
		-- 1.3.6.1.4.1.37950.1.1.5.10.17.4.3.1.5
		age OBJECT-TYPE
			SYNTAX Integer32
			MAX-ACCESS read-only
			STATUS current
			DESCRIPTION
				"Description."
			::= { ospfDatabaseEntry 5 }

		
--         1.3.6.1.4.1.37950.1.1.5.10.17.4.3.1.6
-- 1.3.6.1.4.1.37950.1.1.5.10.17.4.3.1.6
-- 1.3.6.1.4.1.37950.1.1.5.10.17.4.3.1.6
-- 1.3.6.1.4.1.37950.1.1.5.10.17.4.3.1.6
-- 1.3.6.1.4.1.37950.1.1.5.10.17.4.3.1.6
-- 1.3.6.1.4.1.37950.1.1.5.10.17.4.3.1.6
-- 1.3.6.1.4.1.37950.1.1.5.10.17.4.3.1.6
-- 1.3.6.1.4.1.37950.1.1.5.10.17.4.3.1.6
		-- 1.3.6.1.4.1.37950.1.1.5.10.17.4.3.1.6
		sequence OBJECT-TYPE
			SYNTAX OCTET STRING
			MAX-ACCESS read-only
			STATUS current
			DESCRIPTION
				"Description."
			::= { ospfDatabaseEntry 6 }

		
--         1.3.6.1.4.1.37950.1.1.5.10.17.4.3.1.7
-- 1.3.6.1.4.1.37950.1.1.5.10.17.4.3.1.7
-- 1.3.6.1.4.1.37950.1.1.5.10.17.4.3.1.7
-- 1.3.6.1.4.1.37950.1.1.5.10.17.4.3.1.7
-- 1.3.6.1.4.1.37950.1.1.5.10.17.4.3.1.7
-- 1.3.6.1.4.1.37950.1.1.5.10.17.4.3.1.7
-- 1.3.6.1.4.1.37950.1.1.5.10.17.4.3.1.7
-- 1.3.6.1.4.1.37950.1.1.5.10.17.4.3.1.7
		-- 1.3.6.1.4.1.37950.1.1.5.10.17.4.3.1.7
		ckSum OBJECT-TYPE
			SYNTAX OCTET STRING
			MAX-ACCESS read-only
			STATUS current
			DESCRIPTION
				"Description."
			::= { ospfDatabaseEntry 7 }

		
--         1.3.6.1.4.1.37950.1.1.5.10.17.4.3.1.8
-- 1.3.6.1.4.1.37950.1.1.5.10.17.4.3.1.8
-- 1.3.6.1.4.1.37950.1.1.5.10.17.4.3.1.8
-- 1.3.6.1.4.1.37950.1.1.5.10.17.4.3.1.8
-- 1.3.6.1.4.1.37950.1.1.5.10.17.4.3.1.8
-- 1.3.6.1.4.1.37950.1.1.5.10.17.4.3.1.8
-- 1.3.6.1.4.1.37950.1.1.5.10.17.4.3.1.8
-- 1.3.6.1.4.1.37950.1.1.5.10.17.4.3.1.8
		-- 1.3.6.1.4.1.37950.1.1.5.10.17.4.3.1.8
		linkCount OBJECT-TYPE
			SYNTAX Integer32
			MAX-ACCESS read-only
			STATUS current
			DESCRIPTION
				"Description."
			::= { ospfDatabaseEntry 8 }

		
--         1.3.6.1.4.1.37950.1.1.5.10.17.4.3.1.9
-- 1.3.6.1.4.1.37950.1.1.5.10.17.4.3.1.9
-- 1.3.6.1.4.1.37950.1.1.5.10.17.4.3.1.9
-- 1.3.6.1.4.1.37950.1.1.5.10.17.4.3.1.9
-- 1.3.6.1.4.1.37950.1.1.5.10.17.4.3.1.9
-- 1.3.6.1.4.1.37950.1.1.5.10.17.4.3.1.9
-- 1.3.6.1.4.1.37950.1.1.5.10.17.4.3.1.9
-- 1.3.6.1.4.1.37950.1.1.5.10.17.4.3.1.9
		-- 1.3.6.1.4.1.37950.1.1.5.10.17.4.3.1.9
		route OBJECT-TYPE
			SYNTAX OCTET STRING
			MAX-ACCESS read-only
			STATUS current
			DESCRIPTION
				"Description."
			::= { ospfDatabaseEntry 9 }

		
--         1.3.6.1.4.1.37950.1.1.5.10.18
-- 1.3.6.1.4.1.37950.1.1.5.10.18
-- 1.3.6.1.4.1.37950.1.1.5.10.18
-- 1.3.6.1.4.1.37950.1.1.5.10.18
-- 1.3.6.1.4.1.37950.1.1.5.10.18
-- 1.3.6.1.4.1.37950.1.1.5.10.18
-- 1.3.6.1.4.1.37950.1.1.5.10.18
-- 1.3.6.1.4.1.37950.1.1.5.10.18
		-- 1.3.6.1.4.1.37950.1.1.5.10.18
		v1600dRouteList OBJECT IDENTIFIER ::= { v1600dSwitch 18 }

		
--         1.3.6.1.4.1.37950.1.1.5.10.18.1
-- 1.3.6.1.4.1.37950.1.1.5.10.18.1
-- 1.3.6.1.4.1.37950.1.1.5.10.18.1
-- 1.3.6.1.4.1.37950.1.1.5.10.18.1
-- 1.3.6.1.4.1.37950.1.1.5.10.18.1
-- 1.3.6.1.4.1.37950.1.1.5.10.18.1
-- 1.3.6.1.4.1.37950.1.1.5.10.18.1
-- 1.3.6.1.4.1.37950.1.1.5.10.18.1
		-- 1.3.6.1.4.1.37950.1.1.5.10.18.1
		accessListCfg OBJECT IDENTIFIER ::= { v1600dRouteList 1 }

		
--         1.3.6.1.4.1.37950.1.1.5.10.18.1.1
-- 1.3.6.1.4.1.37950.1.1.5.10.18.1.1
-- 1.3.6.1.4.1.37950.1.1.5.10.18.1.1
-- 1.3.6.1.4.1.37950.1.1.5.10.18.1.1
-- 1.3.6.1.4.1.37950.1.1.5.10.18.1.1
-- 1.3.6.1.4.1.37950.1.1.5.10.18.1.1
-- 1.3.6.1.4.1.37950.1.1.5.10.18.1.1
-- 1.3.6.1.4.1.37950.1.1.5.10.18.1.1
		-- 1.3.6.1.4.1.37950.1.1.5.10.18.1.1
		accessListMode OBJECT-TYPE
			SYNTAX INTEGER
				{
				standard(0),
				extended(1)
				}
			MAX-ACCESS read-write
			STATUS current
			DESCRIPTION
				"Description."
			::= { accessListCfg 1 }

		
--         1.3.6.1.4.1.37950.1.1.5.10.18.1.2
-- 1.3.6.1.4.1.37950.1.1.5.10.18.1.2
-- 1.3.6.1.4.1.37950.1.1.5.10.18.1.2
-- 1.3.6.1.4.1.37950.1.1.5.10.18.1.2
-- 1.3.6.1.4.1.37950.1.1.5.10.18.1.2
-- 1.3.6.1.4.1.37950.1.1.5.10.18.1.2
-- 1.3.6.1.4.1.37950.1.1.5.10.18.1.2
-- 1.3.6.1.4.1.37950.1.1.5.10.18.1.2
		-- 1.3.6.1.4.1.37950.1.1.5.10.18.1.2
		accessListId OBJECT-TYPE
			SYNTAX Integer32 (1..99 | 100..199 | 1300..1999 | 2000..2699)
			MAX-ACCESS read-write
			STATUS current
			DESCRIPTION
				"Description."
			::= { accessListCfg 2 }

		
--         1.3.6.1.4.1.37950.1.1.5.10.18.1.3
-- 1.3.6.1.4.1.37950.1.1.5.10.18.1.3
-- 1.3.6.1.4.1.37950.1.1.5.10.18.1.3
-- 1.3.6.1.4.1.37950.1.1.5.10.18.1.3
-- 1.3.6.1.4.1.37950.1.1.5.10.18.1.3
-- 1.3.6.1.4.1.37950.1.1.5.10.18.1.3
-- 1.3.6.1.4.1.37950.1.1.5.10.18.1.3
-- 1.3.6.1.4.1.37950.1.1.5.10.18.1.3
		-- 1.3.6.1.4.1.37950.1.1.5.10.18.1.3
		accessListFilterAction OBJECT-TYPE
			SYNTAX INTEGER
				{
				permit(1),
				deny(2)
				}
			MAX-ACCESS read-write
			STATUS current
			DESCRIPTION
				"Description."
			::= { accessListCfg 3 }

		
--         1.3.6.1.4.1.37950.1.1.5.10.18.1.4
-- 1.3.6.1.4.1.37950.1.1.5.10.18.1.4
-- 1.3.6.1.4.1.37950.1.1.5.10.18.1.4
-- 1.3.6.1.4.1.37950.1.1.5.10.18.1.4
-- 1.3.6.1.4.1.37950.1.1.5.10.18.1.4
-- 1.3.6.1.4.1.37950.1.1.5.10.18.1.4
-- 1.3.6.1.4.1.37950.1.1.5.10.18.1.4
-- 1.3.6.1.4.1.37950.1.1.5.10.18.1.4
		-- 1.3.6.1.4.1.37950.1.1.5.10.18.1.4
		accessListSrcType OBJECT-TYPE
			SYNTAX INTEGER
				{
				matchAddress(1),
				any(2),
				host(3)
				}
			MAX-ACCESS read-write
			STATUS current
			DESCRIPTION
				"Description."
			::= { accessListCfg 4 }

		
--         1.3.6.1.4.1.37950.1.1.5.10.18.1.5
-- 1.3.6.1.4.1.37950.1.1.5.10.18.1.5
-- 1.3.6.1.4.1.37950.1.1.5.10.18.1.5
-- 1.3.6.1.4.1.37950.1.1.5.10.18.1.5
-- 1.3.6.1.4.1.37950.1.1.5.10.18.1.5
-- 1.3.6.1.4.1.37950.1.1.5.10.18.1.5
-- 1.3.6.1.4.1.37950.1.1.5.10.18.1.5
-- 1.3.6.1.4.1.37950.1.1.5.10.18.1.5
		-- 1.3.6.1.4.1.37950.1.1.5.10.18.1.5
		srcIpAddress OBJECT-TYPE
			SYNTAX IpAddress
			MAX-ACCESS read-write
			STATUS current
			DESCRIPTION
				"Description."
			::= { accessListCfg 5 }

		
--         1.3.6.1.4.1.37950.1.1.5.10.18.1.6
-- 1.3.6.1.4.1.37950.1.1.5.10.18.1.6
-- 1.3.6.1.4.1.37950.1.1.5.10.18.1.6
-- 1.3.6.1.4.1.37950.1.1.5.10.18.1.6
-- 1.3.6.1.4.1.37950.1.1.5.10.18.1.6
-- 1.3.6.1.4.1.37950.1.1.5.10.18.1.6
-- 1.3.6.1.4.1.37950.1.1.5.10.18.1.6
-- 1.3.6.1.4.1.37950.1.1.5.10.18.1.6
		-- 1.3.6.1.4.1.37950.1.1.5.10.18.1.6
		srcSubnetMask OBJECT-TYPE
			SYNTAX IpAddress
			MAX-ACCESS read-write
			STATUS current
			DESCRIPTION
				"Description."
			::= { accessListCfg 6 }

		
--         1.3.6.1.4.1.37950.1.1.5.10.18.1.7
-- 1.3.6.1.4.1.37950.1.1.5.10.18.1.7
-- 1.3.6.1.4.1.37950.1.1.5.10.18.1.7
-- 1.3.6.1.4.1.37950.1.1.5.10.18.1.7
-- 1.3.6.1.4.1.37950.1.1.5.10.18.1.7
-- 1.3.6.1.4.1.37950.1.1.5.10.18.1.7
-- 1.3.6.1.4.1.37950.1.1.5.10.18.1.7
-- 1.3.6.1.4.1.37950.1.1.5.10.18.1.7
		-- 1.3.6.1.4.1.37950.1.1.5.10.18.1.7
		accessListDestType OBJECT-TYPE
			SYNTAX INTEGER
				{
				matchAddress(1),
				any(2),
				host(3)
				}
			MAX-ACCESS read-write
			STATUS current
			DESCRIPTION
				"Description."
			::= { accessListCfg 7 }

		
--         1.3.6.1.4.1.37950.1.1.5.10.18.1.8
-- 1.3.6.1.4.1.37950.1.1.5.10.18.1.8
-- 1.3.6.1.4.1.37950.1.1.5.10.18.1.8
-- 1.3.6.1.4.1.37950.1.1.5.10.18.1.8
-- 1.3.6.1.4.1.37950.1.1.5.10.18.1.8
-- 1.3.6.1.4.1.37950.1.1.5.10.18.1.8
-- 1.3.6.1.4.1.37950.1.1.5.10.18.1.8
-- 1.3.6.1.4.1.37950.1.1.5.10.18.1.8
		-- 1.3.6.1.4.1.37950.1.1.5.10.18.1.8
		destIpAddress OBJECT-TYPE
			SYNTAX IpAddress
			MAX-ACCESS read-write
			STATUS current
			DESCRIPTION
				"Description."
			::= { accessListCfg 8 }

		
--         1.3.6.1.4.1.37950.1.1.5.10.18.1.9
-- 1.3.6.1.4.1.37950.1.1.5.10.18.1.9
-- 1.3.6.1.4.1.37950.1.1.5.10.18.1.9
-- 1.3.6.1.4.1.37950.1.1.5.10.18.1.9
-- 1.3.6.1.4.1.37950.1.1.5.10.18.1.9
-- 1.3.6.1.4.1.37950.1.1.5.10.18.1.9
-- 1.3.6.1.4.1.37950.1.1.5.10.18.1.9
-- 1.3.6.1.4.1.37950.1.1.5.10.18.1.9
		-- 1.3.6.1.4.1.37950.1.1.5.10.18.1.9
		destSubnetMask OBJECT-TYPE
			SYNTAX IpAddress
			MAX-ACCESS read-write
			STATUS current
			DESCRIPTION
				"Description."
			::= { accessListCfg 9 }

		
--         1.3.6.1.4.1.37950.1.1.5.10.18.1.10
-- 1.3.6.1.4.1.37950.1.1.5.10.18.1.10
-- 1.3.6.1.4.1.37950.1.1.5.10.18.1.10
-- 1.3.6.1.4.1.37950.1.1.5.10.18.1.10
-- 1.3.6.1.4.1.37950.1.1.5.10.18.1.10
-- 1.3.6.1.4.1.37950.1.1.5.10.18.1.10
-- 1.3.6.1.4.1.37950.1.1.5.10.18.1.10
-- 1.3.6.1.4.1.37950.1.1.5.10.18.1.10
		-- 1.3.6.1.4.1.37950.1.1.5.10.18.1.10
		accessListAction OBJECT-TYPE
			SYNTAX INTEGER
				{
				add(1),
				del(2)
				}
			MAX-ACCESS read-write
			STATUS current
			DESCRIPTION
				"Description."
			::= { accessListCfg 10 }

		
--         1.3.6.1.4.1.37950.1.1.5.10.18.2
-- 1.3.6.1.4.1.37950.1.1.5.10.18.2
-- 1.3.6.1.4.1.37950.1.1.5.10.18.2
-- 1.3.6.1.4.1.37950.1.1.5.10.18.2
-- 1.3.6.1.4.1.37950.1.1.5.10.18.2
-- 1.3.6.1.4.1.37950.1.1.5.10.18.2
-- 1.3.6.1.4.1.37950.1.1.5.10.18.2
-- 1.3.6.1.4.1.37950.1.1.5.10.18.2
		-- 1.3.6.1.4.1.37950.1.1.5.10.18.2
		accessListTable OBJECT-TYPE
			SYNTAX SEQUENCE OF AccessListEntry
			MAX-ACCESS not-accessible
			STATUS current
			DESCRIPTION
				"Description."
			::= { v1600dRouteList 2 }

		
--         1.3.6.1.4.1.37950.1.1.5.10.18.2.1
-- 1.3.6.1.4.1.37950.1.1.5.10.18.2.1
-- 1.3.6.1.4.1.37950.1.1.5.10.18.2.1
-- 1.3.6.1.4.1.37950.1.1.5.10.18.2.1
-- 1.3.6.1.4.1.37950.1.1.5.10.18.2.1
-- 1.3.6.1.4.1.37950.1.1.5.10.18.2.1
-- 1.3.6.1.4.1.37950.1.1.5.10.18.2.1
-- 1.3.6.1.4.1.37950.1.1.5.10.18.2.1
		-- 1.3.6.1.4.1.37950.1.1.5.10.18.2.1
		accessListEntry OBJECT-TYPE
			SYNTAX AccessListEntry
			MAX-ACCESS not-accessible
			STATUS current
			DESCRIPTION
				"Description."
			INDEX { listId, listFilterAction, listSrcType, listSrcIpAddress, listSrcSubnetMask, 
				listDestType, listDestIpAddress, listDestSubnetMask }
			::= { accessListTable 1 }

		
		AccessListEntry ::=
			SEQUENCE { 
				listId
					Integer32,
				listFilterAction
					INTEGER,
				listSrcType
					INTEGER,
				listSrcIpAddress
					IpAddress,
				listSrcSubnetMask
					IpAddress,
				listDestType
					INTEGER,
				listDestIpAddress
					IpAddress,
				listDestSubnetMask
					IpAddress
			 }

--         1.3.6.1.4.1.37950.1.1.5.10.18.2.1.1
-- 1.3.6.1.4.1.37950.1.1.5.10.18.2.1.1
-- 1.3.6.1.4.1.37950.1.1.5.10.18.2.1.1
-- 1.3.6.1.4.1.37950.1.1.5.10.18.2.1.1
-- 1.3.6.1.4.1.37950.1.1.5.10.18.2.1.1
-- 1.3.6.1.4.1.37950.1.1.5.10.18.2.1.1
-- 1.3.6.1.4.1.37950.1.1.5.10.18.2.1.1
-- 1.3.6.1.4.1.37950.1.1.5.10.18.2.1.1
		-- 1.3.6.1.4.1.37950.1.1.5.10.18.2.1.1
		listId OBJECT-TYPE
			SYNTAX Integer32
			MAX-ACCESS read-only
			STATUS current
			DESCRIPTION
				"Description."
			::= { accessListEntry 1 }

		
--         1.3.6.1.4.1.37950.1.1.5.10.18.2.1.2
-- 1.3.6.1.4.1.37950.1.1.5.10.18.2.1.2
-- 1.3.6.1.4.1.37950.1.1.5.10.18.2.1.2
-- 1.3.6.1.4.1.37950.1.1.5.10.18.2.1.2
-- 1.3.6.1.4.1.37950.1.1.5.10.18.2.1.2
-- 1.3.6.1.4.1.37950.1.1.5.10.18.2.1.2
-- 1.3.6.1.4.1.37950.1.1.5.10.18.2.1.2
-- 1.3.6.1.4.1.37950.1.1.5.10.18.2.1.2
		-- 1.3.6.1.4.1.37950.1.1.5.10.18.2.1.2
		listFilterAction OBJECT-TYPE
			SYNTAX INTEGER
				{
				deny(0),
				permit(1)
				}
			MAX-ACCESS read-only
			STATUS current
			DESCRIPTION
				"Description."
			::= { accessListEntry 2 }

		
--         1.3.6.1.4.1.37950.1.1.5.10.18.2.1.3
-- 1.3.6.1.4.1.37950.1.1.5.10.18.2.1.3
-- 1.3.6.1.4.1.37950.1.1.5.10.18.2.1.3
-- 1.3.6.1.4.1.37950.1.1.5.10.18.2.1.3
-- 1.3.6.1.4.1.37950.1.1.5.10.18.2.1.3
-- 1.3.6.1.4.1.37950.1.1.5.10.18.2.1.3
-- 1.3.6.1.4.1.37950.1.1.5.10.18.2.1.3
-- 1.3.6.1.4.1.37950.1.1.5.10.18.2.1.3
		-- 1.3.6.1.4.1.37950.1.1.5.10.18.2.1.3
		listSrcType OBJECT-TYPE
			SYNTAX INTEGER
				{
				matchAddress(1),
				any(2),
				host(3)
				}
			MAX-ACCESS read-only
			STATUS current
			DESCRIPTION
				"Description."
			::= { accessListEntry 3 }

		
--         1.3.6.1.4.1.37950.1.1.5.10.18.2.1.4
-- 1.3.6.1.4.1.37950.1.1.5.10.18.2.1.4
-- 1.3.6.1.4.1.37950.1.1.5.10.18.2.1.4
-- 1.3.6.1.4.1.37950.1.1.5.10.18.2.1.4
-- 1.3.6.1.4.1.37950.1.1.5.10.18.2.1.4
-- 1.3.6.1.4.1.37950.1.1.5.10.18.2.1.4
-- 1.3.6.1.4.1.37950.1.1.5.10.18.2.1.4
-- 1.3.6.1.4.1.37950.1.1.5.10.18.2.1.4
		-- 1.3.6.1.4.1.37950.1.1.5.10.18.2.1.4
		listSrcIpAddress OBJECT-TYPE
			SYNTAX IpAddress
			MAX-ACCESS read-only
			STATUS current
			DESCRIPTION
				"Description."
			::= { accessListEntry 4 }

		
--         1.3.6.1.4.1.37950.1.1.5.10.18.2.1.5
-- 1.3.6.1.4.1.37950.1.1.5.10.18.2.1.5
-- 1.3.6.1.4.1.37950.1.1.5.10.18.2.1.5
-- 1.3.6.1.4.1.37950.1.1.5.10.18.2.1.5
-- 1.3.6.1.4.1.37950.1.1.5.10.18.2.1.5
-- 1.3.6.1.4.1.37950.1.1.5.10.18.2.1.5
-- 1.3.6.1.4.1.37950.1.1.5.10.18.2.1.5
-- 1.3.6.1.4.1.37950.1.1.5.10.18.2.1.5
		-- 1.3.6.1.4.1.37950.1.1.5.10.18.2.1.5
		listSrcSubnetMask OBJECT-TYPE
			SYNTAX IpAddress
			MAX-ACCESS read-only
			STATUS current
			DESCRIPTION
				"Description."
			::= { accessListEntry 5 }

		
--         1.3.6.1.4.1.37950.1.1.5.10.18.2.1.6
-- 1.3.6.1.4.1.37950.1.1.5.10.18.2.1.6
-- 1.3.6.1.4.1.37950.1.1.5.10.18.2.1.6
-- 1.3.6.1.4.1.37950.1.1.5.10.18.2.1.6
-- 1.3.6.1.4.1.37950.1.1.5.10.18.2.1.6
-- 1.3.6.1.4.1.37950.1.1.5.10.18.2.1.6
-- 1.3.6.1.4.1.37950.1.1.5.10.18.2.1.6
-- 1.3.6.1.4.1.37950.1.1.5.10.18.2.1.6
		-- 1.3.6.1.4.1.37950.1.1.5.10.18.2.1.6
		listDestType OBJECT-TYPE
			SYNTAX INTEGER
				{
				matchAddress(1),
				any(2),
				host(3)
				}
			MAX-ACCESS read-only
			STATUS current
			DESCRIPTION
				"Description."
			::= { accessListEntry 6 }

		
--         1.3.6.1.4.1.37950.1.1.5.10.18.2.1.7
-- 1.3.6.1.4.1.37950.1.1.5.10.18.2.1.7
-- 1.3.6.1.4.1.37950.1.1.5.10.18.2.1.7
-- 1.3.6.1.4.1.37950.1.1.5.10.18.2.1.7
-- 1.3.6.1.4.1.37950.1.1.5.10.18.2.1.7
-- 1.3.6.1.4.1.37950.1.1.5.10.18.2.1.7
-- 1.3.6.1.4.1.37950.1.1.5.10.18.2.1.7
-- 1.3.6.1.4.1.37950.1.1.5.10.18.2.1.7
		-- 1.3.6.1.4.1.37950.1.1.5.10.18.2.1.7
		listDestIpAddress OBJECT-TYPE
			SYNTAX IpAddress
			MAX-ACCESS read-only
			STATUS current
			DESCRIPTION
				"Description."
			::= { accessListEntry 7 }

		
--         1.3.6.1.4.1.37950.1.1.5.10.18.2.1.8
-- 1.3.6.1.4.1.37950.1.1.5.10.18.2.1.8
-- 1.3.6.1.4.1.37950.1.1.5.10.18.2.1.8
-- 1.3.6.1.4.1.37950.1.1.5.10.18.2.1.8
-- 1.3.6.1.4.1.37950.1.1.5.10.18.2.1.8
-- 1.3.6.1.4.1.37950.1.1.5.10.18.2.1.8
-- 1.3.6.1.4.1.37950.1.1.5.10.18.2.1.8
-- 1.3.6.1.4.1.37950.1.1.5.10.18.2.1.8
		-- 1.3.6.1.4.1.37950.1.1.5.10.18.2.1.8
		listDestSubnetMask OBJECT-TYPE
			SYNTAX IpAddress
			MAX-ACCESS read-only
			STATUS current
			DESCRIPTION
				"Description."
			::= { accessListEntry 8 }

		
--         1.3.6.1.4.1.37950.1.1.5.10.18.3
-- 1.3.6.1.4.1.37950.1.1.5.10.18.3
-- 1.3.6.1.4.1.37950.1.1.5.10.18.3
-- 1.3.6.1.4.1.37950.1.1.5.10.18.3
-- 1.3.6.1.4.1.37950.1.1.5.10.18.3
-- 1.3.6.1.4.1.37950.1.1.5.10.18.3
-- 1.3.6.1.4.1.37950.1.1.5.10.18.3
-- 1.3.6.1.4.1.37950.1.1.5.10.18.3
		-- 1.3.6.1.4.1.37950.1.1.5.10.18.3
		prefixListCfg OBJECT IDENTIFIER ::= { v1600dRouteList 3 }

		
--         1.3.6.1.4.1.37950.1.1.5.10.18.3.1
-- 1.3.6.1.4.1.37950.1.1.5.10.18.3.1
-- 1.3.6.1.4.1.37950.1.1.5.10.18.3.1
-- 1.3.6.1.4.1.37950.1.1.5.10.18.3.1
-- 1.3.6.1.4.1.37950.1.1.5.10.18.3.1
-- 1.3.6.1.4.1.37950.1.1.5.10.18.3.1
-- 1.3.6.1.4.1.37950.1.1.5.10.18.3.1
-- 1.3.6.1.4.1.37950.1.1.5.10.18.3.1
		-- 1.3.6.1.4.1.37950.1.1.5.10.18.3.1
		prefixList OBJECT-TYPE
			SYNTAX OCTET STRING
			MAX-ACCESS read-write
			STATUS current
			DESCRIPTION
				"Description."
			::= { prefixListCfg 1 }

		
--         1.3.6.1.4.1.37950.1.1.5.10.18.3.2
-- 1.3.6.1.4.1.37950.1.1.5.10.18.3.2
-- 1.3.6.1.4.1.37950.1.1.5.10.18.3.2
-- 1.3.6.1.4.1.37950.1.1.5.10.18.3.2
-- 1.3.6.1.4.1.37950.1.1.5.10.18.3.2
-- 1.3.6.1.4.1.37950.1.1.5.10.18.3.2
-- 1.3.6.1.4.1.37950.1.1.5.10.18.3.2
-- 1.3.6.1.4.1.37950.1.1.5.10.18.3.2
		-- 1.3.6.1.4.1.37950.1.1.5.10.18.3.2
		prefixListseq OBJECT-TYPE
			SYNTAX Unsigned32 (0..4294967295)
			MAX-ACCESS read-write
			STATUS current
			DESCRIPTION
				"Description."
			::= { prefixListCfg 2 }

		
--         1.3.6.1.4.1.37950.1.1.5.10.18.3.3
-- 1.3.6.1.4.1.37950.1.1.5.10.18.3.3
-- 1.3.6.1.4.1.37950.1.1.5.10.18.3.3
-- 1.3.6.1.4.1.37950.1.1.5.10.18.3.3
-- 1.3.6.1.4.1.37950.1.1.5.10.18.3.3
-- 1.3.6.1.4.1.37950.1.1.5.10.18.3.3
-- 1.3.6.1.4.1.37950.1.1.5.10.18.3.3
-- 1.3.6.1.4.1.37950.1.1.5.10.18.3.3
		-- 1.3.6.1.4.1.37950.1.1.5.10.18.3.3
		prefixListFilterAction OBJECT-TYPE
			SYNTAX INTEGER
				{
				deny(0),
				permit(1)
				}
			MAX-ACCESS read-write
			STATUS current
			DESCRIPTION
				"Description."
			::= { prefixListCfg 3 }

		
--         1.3.6.1.4.1.37950.1.1.5.10.18.3.4
-- 1.3.6.1.4.1.37950.1.1.5.10.18.3.4
-- 1.3.6.1.4.1.37950.1.1.5.10.18.3.4
-- 1.3.6.1.4.1.37950.1.1.5.10.18.3.4
-- 1.3.6.1.4.1.37950.1.1.5.10.18.3.4
-- 1.3.6.1.4.1.37950.1.1.5.10.18.3.4
-- 1.3.6.1.4.1.37950.1.1.5.10.18.3.4
-- 1.3.6.1.4.1.37950.1.1.5.10.18.3.4
		-- 1.3.6.1.4.1.37950.1.1.5.10.18.3.4
		prefixListType OBJECT-TYPE
			SYNTAX INTEGER
				{
				address(1),
				any(2)
				}
			MAX-ACCESS read-write
			STATUS current
			DESCRIPTION
				"Description."
			::= { prefixListCfg 4 }

		
--         1.3.6.1.4.1.37950.1.1.5.10.18.3.5
-- 1.3.6.1.4.1.37950.1.1.5.10.18.3.5
-- 1.3.6.1.4.1.37950.1.1.5.10.18.3.5
-- 1.3.6.1.4.1.37950.1.1.5.10.18.3.5
-- 1.3.6.1.4.1.37950.1.1.5.10.18.3.5
-- 1.3.6.1.4.1.37950.1.1.5.10.18.3.5
-- 1.3.6.1.4.1.37950.1.1.5.10.18.3.5
-- 1.3.6.1.4.1.37950.1.1.5.10.18.3.5
		-- 1.3.6.1.4.1.37950.1.1.5.10.18.3.5
		prefixListIp OBJECT-TYPE
			SYNTAX IpAddress
			MAX-ACCESS read-write
			STATUS current
			DESCRIPTION
				"Description."
			::= { prefixListCfg 5 }

		
--         1.3.6.1.4.1.37950.1.1.5.10.18.3.6
-- 1.3.6.1.4.1.37950.1.1.5.10.18.3.6
-- 1.3.6.1.4.1.37950.1.1.5.10.18.3.6
-- 1.3.6.1.4.1.37950.1.1.5.10.18.3.6
-- 1.3.6.1.4.1.37950.1.1.5.10.18.3.6
-- 1.3.6.1.4.1.37950.1.1.5.10.18.3.6
-- 1.3.6.1.4.1.37950.1.1.5.10.18.3.6
-- 1.3.6.1.4.1.37950.1.1.5.10.18.3.6
		-- 1.3.6.1.4.1.37950.1.1.5.10.18.3.6
		prefixListMask OBJECT-TYPE
			SYNTAX IpAddress
			MAX-ACCESS read-write
			STATUS current
			DESCRIPTION
				"Description."
			::= { prefixListCfg 6 }

		
--         1.3.6.1.4.1.37950.1.1.5.10.18.3.7
-- 1.3.6.1.4.1.37950.1.1.5.10.18.3.7
-- 1.3.6.1.4.1.37950.1.1.5.10.18.3.7
-- 1.3.6.1.4.1.37950.1.1.5.10.18.3.7
-- 1.3.6.1.4.1.37950.1.1.5.10.18.3.7
-- 1.3.6.1.4.1.37950.1.1.5.10.18.3.7
-- 1.3.6.1.4.1.37950.1.1.5.10.18.3.7
-- 1.3.6.1.4.1.37950.1.1.5.10.18.3.7
		-- 1.3.6.1.4.1.37950.1.1.5.10.18.3.7
		prefixListGe OBJECT-TYPE
			SYNTAX Integer32 (0..32)
			MAX-ACCESS read-write
			STATUS current
			DESCRIPTION
				"Description."
			::= { prefixListCfg 7 }

		
--         1.3.6.1.4.1.37950.1.1.5.10.18.3.8
-- 1.3.6.1.4.1.37950.1.1.5.10.18.3.8
-- 1.3.6.1.4.1.37950.1.1.5.10.18.3.8
-- 1.3.6.1.4.1.37950.1.1.5.10.18.3.8
-- 1.3.6.1.4.1.37950.1.1.5.10.18.3.8
-- 1.3.6.1.4.1.37950.1.1.5.10.18.3.8
-- 1.3.6.1.4.1.37950.1.1.5.10.18.3.8
-- 1.3.6.1.4.1.37950.1.1.5.10.18.3.8
		-- 1.3.6.1.4.1.37950.1.1.5.10.18.3.8
		prefixListLe OBJECT-TYPE
			SYNTAX Integer32 (0..32)
			MAX-ACCESS read-write
			STATUS current
			DESCRIPTION
				"Description."
			::= { prefixListCfg 8 }

		
--         1.3.6.1.4.1.37950.1.1.5.10.18.3.9
-- 1.3.6.1.4.1.37950.1.1.5.10.18.3.9
-- 1.3.6.1.4.1.37950.1.1.5.10.18.3.9
-- 1.3.6.1.4.1.37950.1.1.5.10.18.3.9
-- 1.3.6.1.4.1.37950.1.1.5.10.18.3.9
-- 1.3.6.1.4.1.37950.1.1.5.10.18.3.9
-- 1.3.6.1.4.1.37950.1.1.5.10.18.3.9
-- 1.3.6.1.4.1.37950.1.1.5.10.18.3.9
		-- 1.3.6.1.4.1.37950.1.1.5.10.18.3.9
		prefixListAction OBJECT-TYPE
			SYNTAX INTEGER
				{
				add(1),
				del(2)
				}
			MAX-ACCESS read-write
			STATUS current
			DESCRIPTION
				"Description."
			::= { prefixListCfg 9 }

		
--         1.3.6.1.4.1.37950.1.1.5.10.18.4
-- 1.3.6.1.4.1.37950.1.1.5.10.18.4
-- 1.3.6.1.4.1.37950.1.1.5.10.18.4
-- 1.3.6.1.4.1.37950.1.1.5.10.18.4
-- 1.3.6.1.4.1.37950.1.1.5.10.18.4
-- 1.3.6.1.4.1.37950.1.1.5.10.18.4
-- 1.3.6.1.4.1.37950.1.1.5.10.18.4
-- 1.3.6.1.4.1.37950.1.1.5.10.18.4
		-- 1.3.6.1.4.1.37950.1.1.5.10.18.4
		prefixListTable OBJECT-TYPE
			SYNTAX SEQUENCE OF PrefixListEntry
			MAX-ACCESS not-accessible
			STATUS current
			DESCRIPTION
				"Description."
			::= { v1600dRouteList 4 }

		
--         1.3.6.1.4.1.37950.1.1.5.10.18.4.1
-- 1.3.6.1.4.1.37950.1.1.5.10.18.4.1
-- 1.3.6.1.4.1.37950.1.1.5.10.18.4.1
-- 1.3.6.1.4.1.37950.1.1.5.10.18.4.1
-- 1.3.6.1.4.1.37950.1.1.5.10.18.4.1
-- 1.3.6.1.4.1.37950.1.1.5.10.18.4.1
-- 1.3.6.1.4.1.37950.1.1.5.10.18.4.1
-- 1.3.6.1.4.1.37950.1.1.5.10.18.4.1
		-- 1.3.6.1.4.1.37950.1.1.5.10.18.4.1
		prefixListEntry OBJECT-TYPE
			SYNTAX PrefixListEntry
			MAX-ACCESS not-accessible
			STATUS current
			DESCRIPTION
				"Description."
			INDEX { listName, listSequence }
			::= { prefixListTable 1 }

		
		PrefixListEntry ::=
			SEQUENCE { 
				listName
					OCTET STRING,
				listSequence
					Unsigned32,
				preListFilterAction
					INTEGER,
				preListType
					INTEGER,
				listNetwork
					OCTET STRING,
				listGe
					Integer32,
				listLe
					Integer32
			 }

--         1.3.6.1.4.1.37950.1.1.5.10.18.4.1.1
-- 1.3.6.1.4.1.37950.1.1.5.10.18.4.1.1
-- 1.3.6.1.4.1.37950.1.1.5.10.18.4.1.1
-- 1.3.6.1.4.1.37950.1.1.5.10.18.4.1.1
-- 1.3.6.1.4.1.37950.1.1.5.10.18.4.1.1
-- 1.3.6.1.4.1.37950.1.1.5.10.18.4.1.1
-- 1.3.6.1.4.1.37950.1.1.5.10.18.4.1.1
-- 1.3.6.1.4.1.37950.1.1.5.10.18.4.1.1
		-- 1.3.6.1.4.1.37950.1.1.5.10.18.4.1.1
		listName OBJECT-TYPE
			SYNTAX OCTET STRING
			MAX-ACCESS read-only
			STATUS current
			DESCRIPTION
				"Description."
			::= { prefixListEntry 1 }

		
--         1.3.6.1.4.1.37950.1.1.5.10.18.4.1.2
-- 1.3.6.1.4.1.37950.1.1.5.10.18.4.1.2
-- 1.3.6.1.4.1.37950.1.1.5.10.18.4.1.2
-- 1.3.6.1.4.1.37950.1.1.5.10.18.4.1.2
-- 1.3.6.1.4.1.37950.1.1.5.10.18.4.1.2
-- 1.3.6.1.4.1.37950.1.1.5.10.18.4.1.2
-- 1.3.6.1.4.1.37950.1.1.5.10.18.4.1.2
-- 1.3.6.1.4.1.37950.1.1.5.10.18.4.1.2
		-- 1.3.6.1.4.1.37950.1.1.5.10.18.4.1.2
		listSequence OBJECT-TYPE
			SYNTAX Unsigned32
			MAX-ACCESS read-only
			STATUS current
			DESCRIPTION
				"Description."
			::= { prefixListEntry 2 }

		
--         1.3.6.1.4.1.37950.1.1.5.10.18.4.1.3
-- 1.3.6.1.4.1.37950.1.1.5.10.18.4.1.3
-- 1.3.6.1.4.1.37950.1.1.5.10.18.4.1.3
-- 1.3.6.1.4.1.37950.1.1.5.10.18.4.1.3
-- 1.3.6.1.4.1.37950.1.1.5.10.18.4.1.3
-- 1.3.6.1.4.1.37950.1.1.5.10.18.4.1.3
-- 1.3.6.1.4.1.37950.1.1.5.10.18.4.1.3
-- 1.3.6.1.4.1.37950.1.1.5.10.18.4.1.3
		-- 1.3.6.1.4.1.37950.1.1.5.10.18.4.1.3
		preListFilterAction OBJECT-TYPE
			SYNTAX INTEGER
				{
				deny(0),
				permit(1)
				}
			MAX-ACCESS read-only
			STATUS current
			DESCRIPTION
				"Description."
			::= { prefixListEntry 3 }

		
--         1.3.6.1.4.1.37950.1.1.5.10.18.4.1.4
-- 1.3.6.1.4.1.37950.1.1.5.10.18.4.1.4
-- 1.3.6.1.4.1.37950.1.1.5.10.18.4.1.4
-- 1.3.6.1.4.1.37950.1.1.5.10.18.4.1.4
-- 1.3.6.1.4.1.37950.1.1.5.10.18.4.1.4
-- 1.3.6.1.4.1.37950.1.1.5.10.18.4.1.4
-- 1.3.6.1.4.1.37950.1.1.5.10.18.4.1.4
-- 1.3.6.1.4.1.37950.1.1.5.10.18.4.1.4
		-- 1.3.6.1.4.1.37950.1.1.5.10.18.4.1.4
		preListType OBJECT-TYPE
			SYNTAX INTEGER
				{
				address(1),
				any(2)
				}
			MAX-ACCESS read-only
			STATUS current
			DESCRIPTION
				"Description."
			::= { prefixListEntry 4 }

		
--         1.3.6.1.4.1.37950.1.1.5.10.18.4.1.5
-- 1.3.6.1.4.1.37950.1.1.5.10.18.4.1.5
-- 1.3.6.1.4.1.37950.1.1.5.10.18.4.1.5
-- 1.3.6.1.4.1.37950.1.1.5.10.18.4.1.5
-- 1.3.6.1.4.1.37950.1.1.5.10.18.4.1.5
-- 1.3.6.1.4.1.37950.1.1.5.10.18.4.1.5
-- 1.3.6.1.4.1.37950.1.1.5.10.18.4.1.5
-- 1.3.6.1.4.1.37950.1.1.5.10.18.4.1.5
		-- 1.3.6.1.4.1.37950.1.1.5.10.18.4.1.5
		listNetwork OBJECT-TYPE
			SYNTAX OCTET STRING
			MAX-ACCESS read-only
			STATUS current
			DESCRIPTION
				"Description."
			::= { prefixListEntry 5 }

		
--         1.3.6.1.4.1.37950.1.1.5.10.18.4.1.6
-- 1.3.6.1.4.1.37950.1.1.5.10.18.4.1.6
-- 1.3.6.1.4.1.37950.1.1.5.10.18.4.1.6
-- 1.3.6.1.4.1.37950.1.1.5.10.18.4.1.6
-- 1.3.6.1.4.1.37950.1.1.5.10.18.4.1.6
-- 1.3.6.1.4.1.37950.1.1.5.10.18.4.1.6
-- 1.3.6.1.4.1.37950.1.1.5.10.18.4.1.6
-- 1.3.6.1.4.1.37950.1.1.5.10.18.4.1.6
		-- 1.3.6.1.4.1.37950.1.1.5.10.18.4.1.6
		listGe OBJECT-TYPE
			SYNTAX Integer32
			MAX-ACCESS read-only
			STATUS current
			DESCRIPTION
				"Description."
			::= { prefixListEntry 6 }

		
--         1.3.6.1.4.1.37950.1.1.5.10.18.4.1.7
-- 1.3.6.1.4.1.37950.1.1.5.10.18.4.1.7
-- 1.3.6.1.4.1.37950.1.1.5.10.18.4.1.7
-- 1.3.6.1.4.1.37950.1.1.5.10.18.4.1.7
-- 1.3.6.1.4.1.37950.1.1.5.10.18.4.1.7
-- 1.3.6.1.4.1.37950.1.1.5.10.18.4.1.7
-- 1.3.6.1.4.1.37950.1.1.5.10.18.4.1.7
-- 1.3.6.1.4.1.37950.1.1.5.10.18.4.1.7
		-- 1.3.6.1.4.1.37950.1.1.5.10.18.4.1.7
		listLe OBJECT-TYPE
			SYNTAX Integer32
			MAX-ACCESS read-only
			STATUS current
			DESCRIPTION
				"Description."
			::= { prefixListEntry 7 }

		
--         1.3.6.1.4.1.37950.1.1.5.10.18.5
-- 1.3.6.1.4.1.37950.1.1.5.10.18.5
-- 1.3.6.1.4.1.37950.1.1.5.10.18.5
-- 1.3.6.1.4.1.37950.1.1.5.10.18.5
-- 1.3.6.1.4.1.37950.1.1.5.10.18.5
-- 1.3.6.1.4.1.37950.1.1.5.10.18.5
-- 1.3.6.1.4.1.37950.1.1.5.10.18.5
-- 1.3.6.1.4.1.37950.1.1.5.10.18.5
		-- 1.3.6.1.4.1.37950.1.1.5.10.18.5
		routeMapCfg OBJECT IDENTIFIER ::= { v1600dRouteList 5 }

		
--         1.3.6.1.4.1.37950.1.1.5.10.18.5.1
-- 1.3.6.1.4.1.37950.1.1.5.10.18.5.1
-- 1.3.6.1.4.1.37950.1.1.5.10.18.5.1
-- 1.3.6.1.4.1.37950.1.1.5.10.18.5.1
-- 1.3.6.1.4.1.37950.1.1.5.10.18.5.1
-- 1.3.6.1.4.1.37950.1.1.5.10.18.5.1
-- 1.3.6.1.4.1.37950.1.1.5.10.18.5.1
-- 1.3.6.1.4.1.37950.1.1.5.10.18.5.1
		-- 1.3.6.1.4.1.37950.1.1.5.10.18.5.1
		routeMap OBJECT-TYPE
			SYNTAX OCTET STRING
			MAX-ACCESS read-write
			STATUS current
			DESCRIPTION
				"Description."
			::= { routeMapCfg 1 }

		
--         1.3.6.1.4.1.37950.1.1.5.10.18.5.2
-- 1.3.6.1.4.1.37950.1.1.5.10.18.5.2
-- 1.3.6.1.4.1.37950.1.1.5.10.18.5.2
-- 1.3.6.1.4.1.37950.1.1.5.10.18.5.2
-- 1.3.6.1.4.1.37950.1.1.5.10.18.5.2
-- 1.3.6.1.4.1.37950.1.1.5.10.18.5.2
-- 1.3.6.1.4.1.37950.1.1.5.10.18.5.2
-- 1.3.6.1.4.1.37950.1.1.5.10.18.5.2
		-- 1.3.6.1.4.1.37950.1.1.5.10.18.5.2
		filterType OBJECT-TYPE
			SYNTAX INTEGER
				{
				permit(0),
				deny(1)
				}
			MAX-ACCESS read-write
			STATUS current
			DESCRIPTION
				"Description."
			::= { routeMapCfg 2 }

		
--         1.3.6.1.4.1.37950.1.1.5.10.18.5.3
-- 1.3.6.1.4.1.37950.1.1.5.10.18.5.3
-- 1.3.6.1.4.1.37950.1.1.5.10.18.5.3
-- 1.3.6.1.4.1.37950.1.1.5.10.18.5.3
-- 1.3.6.1.4.1.37950.1.1.5.10.18.5.3
-- 1.3.6.1.4.1.37950.1.1.5.10.18.5.3
-- 1.3.6.1.4.1.37950.1.1.5.10.18.5.3
-- 1.3.6.1.4.1.37950.1.1.5.10.18.5.3
		-- 1.3.6.1.4.1.37950.1.1.5.10.18.5.3
		routeMapSequence OBJECT-TYPE
			SYNTAX Integer32 (1..65535)
			MAX-ACCESS read-write
			STATUS current
			DESCRIPTION
				"Description."
			::= { routeMapCfg 3 }

		
--         1.3.6.1.4.1.37950.1.1.5.10.18.5.4
-- 1.3.6.1.4.1.37950.1.1.5.10.18.5.4
-- 1.3.6.1.4.1.37950.1.1.5.10.18.5.4
-- 1.3.6.1.4.1.37950.1.1.5.10.18.5.4
-- 1.3.6.1.4.1.37950.1.1.5.10.18.5.4
-- 1.3.6.1.4.1.37950.1.1.5.10.18.5.4
-- 1.3.6.1.4.1.37950.1.1.5.10.18.5.4
-- 1.3.6.1.4.1.37950.1.1.5.10.18.5.4
		-- 1.3.6.1.4.1.37950.1.1.5.10.18.5.4
		routeMapType OBJECT-TYPE
			SYNTAX INTEGER
				{
				match(1),
				set(2)
				}
			MAX-ACCESS read-write
			STATUS current
			DESCRIPTION
				"Description."
			::= { routeMapCfg 4 }

		
--         1.3.6.1.4.1.37950.1.1.5.10.18.5.5
-- 1.3.6.1.4.1.37950.1.1.5.10.18.5.5
-- 1.3.6.1.4.1.37950.1.1.5.10.18.5.5
-- 1.3.6.1.4.1.37950.1.1.5.10.18.5.5
-- 1.3.6.1.4.1.37950.1.1.5.10.18.5.5
-- 1.3.6.1.4.1.37950.1.1.5.10.18.5.5
-- 1.3.6.1.4.1.37950.1.1.5.10.18.5.5
-- 1.3.6.1.4.1.37950.1.1.5.10.18.5.5
		-- 1.3.6.1.4.1.37950.1.1.5.10.18.5.5
		addressAccessList OBJECT-TYPE
			SYNTAX Integer32 (0 | 1..99 | 100..199 | 1300..1999 | 2000..2699)
			MAX-ACCESS read-write
			STATUS current
			DESCRIPTION
				"Description."
			::= { routeMapCfg 5 }

		
--         1.3.6.1.4.1.37950.1.1.5.10.18.5.6
-- 1.3.6.1.4.1.37950.1.1.5.10.18.5.6
-- 1.3.6.1.4.1.37950.1.1.5.10.18.5.6
-- 1.3.6.1.4.1.37950.1.1.5.10.18.5.6
-- 1.3.6.1.4.1.37950.1.1.5.10.18.5.6
-- 1.3.6.1.4.1.37950.1.1.5.10.18.5.6
-- 1.3.6.1.4.1.37950.1.1.5.10.18.5.6
-- 1.3.6.1.4.1.37950.1.1.5.10.18.5.6
		-- 1.3.6.1.4.1.37950.1.1.5.10.18.5.6
		addressPrefixList OBJECT-TYPE
			SYNTAX OCTET STRING
			MAX-ACCESS read-write
			STATUS current
			DESCRIPTION
				"Description."
			::= { routeMapCfg 6 }

		
--         1.3.6.1.4.1.37950.1.1.5.10.18.5.7
-- 1.3.6.1.4.1.37950.1.1.5.10.18.5.7
-- 1.3.6.1.4.1.37950.1.1.5.10.18.5.7
-- 1.3.6.1.4.1.37950.1.1.5.10.18.5.7
-- 1.3.6.1.4.1.37950.1.1.5.10.18.5.7
-- 1.3.6.1.4.1.37950.1.1.5.10.18.5.7
-- 1.3.6.1.4.1.37950.1.1.5.10.18.5.7
-- 1.3.6.1.4.1.37950.1.1.5.10.18.5.7
		-- 1.3.6.1.4.1.37950.1.1.5.10.18.5.7
		nexthopAccessList OBJECT-TYPE
			SYNTAX Integer32 (0 | 1..99 | 100..199 | 1300..1999 | 2000..2699)
			MAX-ACCESS read-write
			STATUS current
			DESCRIPTION
				"Description."
			::= { routeMapCfg 7 }

		
--         1.3.6.1.4.1.37950.1.1.5.10.18.5.8
-- 1.3.6.1.4.1.37950.1.1.5.10.18.5.8
-- 1.3.6.1.4.1.37950.1.1.5.10.18.5.8
-- 1.3.6.1.4.1.37950.1.1.5.10.18.5.8
-- 1.3.6.1.4.1.37950.1.1.5.10.18.5.8
-- 1.3.6.1.4.1.37950.1.1.5.10.18.5.8
-- 1.3.6.1.4.1.37950.1.1.5.10.18.5.8
-- 1.3.6.1.4.1.37950.1.1.5.10.18.5.8
		-- 1.3.6.1.4.1.37950.1.1.5.10.18.5.8
		nexthopPrefixList OBJECT-TYPE
			SYNTAX OCTET STRING
			MAX-ACCESS read-write
			STATUS current
			DESCRIPTION
				"Description."
			::= { routeMapCfg 8 }

		
--         1.3.6.1.4.1.37950.1.1.5.10.18.5.9
-- 1.3.6.1.4.1.37950.1.1.5.10.18.5.9
-- 1.3.6.1.4.1.37950.1.1.5.10.18.5.9
-- 1.3.6.1.4.1.37950.1.1.5.10.18.5.9
-- 1.3.6.1.4.1.37950.1.1.5.10.18.5.9
-- 1.3.6.1.4.1.37950.1.1.5.10.18.5.9
-- 1.3.6.1.4.1.37950.1.1.5.10.18.5.9
-- 1.3.6.1.4.1.37950.1.1.5.10.18.5.9
		-- 1.3.6.1.4.1.37950.1.1.5.10.18.5.9
		routeMapInterface OBJECT-TYPE
			SYNTAX OCTET STRING
			MAX-ACCESS read-write
			STATUS current
			DESCRIPTION
				"Description."
			::= { routeMapCfg 9 }

		
--         1.3.6.1.4.1.37950.1.1.5.10.18.5.10
-- 1.3.6.1.4.1.37950.1.1.5.10.18.5.10
-- 1.3.6.1.4.1.37950.1.1.5.10.18.5.10
-- 1.3.6.1.4.1.37950.1.1.5.10.18.5.10
-- 1.3.6.1.4.1.37950.1.1.5.10.18.5.10
-- 1.3.6.1.4.1.37950.1.1.5.10.18.5.10
-- 1.3.6.1.4.1.37950.1.1.5.10.18.5.10
-- 1.3.6.1.4.1.37950.1.1.5.10.18.5.10
		-- 1.3.6.1.4.1.37950.1.1.5.10.18.5.10
		matchTag OBJECT-TYPE
			SYNTAX Unsigned32 (0..4294967295)
			MAX-ACCESS read-write
			STATUS current
			DESCRIPTION
				"Description."
			::= { routeMapCfg 10 }

		
--         1.3.6.1.4.1.37950.1.1.5.10.18.5.11
-- 1.3.6.1.4.1.37950.1.1.5.10.18.5.11
-- 1.3.6.1.4.1.37950.1.1.5.10.18.5.11
-- 1.3.6.1.4.1.37950.1.1.5.10.18.5.11
-- 1.3.6.1.4.1.37950.1.1.5.10.18.5.11
-- 1.3.6.1.4.1.37950.1.1.5.10.18.5.11
-- 1.3.6.1.4.1.37950.1.1.5.10.18.5.11
-- 1.3.6.1.4.1.37950.1.1.5.10.18.5.11
		-- 1.3.6.1.4.1.37950.1.1.5.10.18.5.11
		routeMapMetric OBJECT-TYPE
			SYNTAX OCTET STRING
			MAX-ACCESS read-write
			STATUS current
			DESCRIPTION
				"Description."
			::= { routeMapCfg 11 }

		
--         1.3.6.1.4.1.37950.1.1.5.10.18.5.12
-- 1.3.6.1.4.1.37950.1.1.5.10.18.5.12
-- 1.3.6.1.4.1.37950.1.1.5.10.18.5.12
-- 1.3.6.1.4.1.37950.1.1.5.10.18.5.12
-- 1.3.6.1.4.1.37950.1.1.5.10.18.5.12
-- 1.3.6.1.4.1.37950.1.1.5.10.18.5.12
-- 1.3.6.1.4.1.37950.1.1.5.10.18.5.12
-- 1.3.6.1.4.1.37950.1.1.5.10.18.5.12
		-- 1.3.6.1.4.1.37950.1.1.5.10.18.5.12
		routeMapMetricType OBJECT-TYPE
			SYNTAX INTEGER
				{
				null(0),
				type1(1),
				type2(2)
				}
			MAX-ACCESS read-write
			STATUS current
			DESCRIPTION
				"Description."
			::= { routeMapCfg 12 }

		
--         1.3.6.1.4.1.37950.1.1.5.10.18.5.13
-- 1.3.6.1.4.1.37950.1.1.5.10.18.5.13
-- 1.3.6.1.4.1.37950.1.1.5.10.18.5.13
-- 1.3.6.1.4.1.37950.1.1.5.10.18.5.13
-- 1.3.6.1.4.1.37950.1.1.5.10.18.5.13
-- 1.3.6.1.4.1.37950.1.1.5.10.18.5.13
-- 1.3.6.1.4.1.37950.1.1.5.10.18.5.13
-- 1.3.6.1.4.1.37950.1.1.5.10.18.5.13
		-- 1.3.6.1.4.1.37950.1.1.5.10.18.5.13
		setTag OBJECT-TYPE
			SYNTAX Unsigned32 (0..4294967295)
			MAX-ACCESS read-write
			STATUS current
			DESCRIPTION
				"Description."
			::= { routeMapCfg 13 }

		
--         1.3.6.1.4.1.37950.1.1.5.10.18.5.14
-- 1.3.6.1.4.1.37950.1.1.5.10.18.5.14
-- 1.3.6.1.4.1.37950.1.1.5.10.18.5.14
-- 1.3.6.1.4.1.37950.1.1.5.10.18.5.14
-- 1.3.6.1.4.1.37950.1.1.5.10.18.5.14
-- 1.3.6.1.4.1.37950.1.1.5.10.18.5.14
-- 1.3.6.1.4.1.37950.1.1.5.10.18.5.14
-- 1.3.6.1.4.1.37950.1.1.5.10.18.5.14
		-- 1.3.6.1.4.1.37950.1.1.5.10.18.5.14
		routeMapAction OBJECT-TYPE
			SYNTAX INTEGER
				{
				add(1),
				del(2)
				}
			MAX-ACCESS read-write
			STATUS current
			DESCRIPTION
				"Description."
			::= { routeMapCfg 14 }

		
--         1.3.6.1.4.1.37950.1.1.5.10.18.6
-- 1.3.6.1.4.1.37950.1.1.5.10.18.6
-- 1.3.6.1.4.1.37950.1.1.5.10.18.6
-- 1.3.6.1.4.1.37950.1.1.5.10.18.6
-- 1.3.6.1.4.1.37950.1.1.5.10.18.6
-- 1.3.6.1.4.1.37950.1.1.5.10.18.6
-- 1.3.6.1.4.1.37950.1.1.5.10.18.6
-- 1.3.6.1.4.1.37950.1.1.5.10.18.6
		-- 1.3.6.1.4.1.37950.1.1.5.10.18.6
		routeMapTable OBJECT-TYPE
			SYNTAX SEQUENCE OF RouteMapEntry
			MAX-ACCESS not-accessible
			STATUS current
			DESCRIPTION
				"Description."
			::= { v1600dRouteList 6 }

		
--         1.3.6.1.4.1.37950.1.1.5.10.18.6.1
-- 1.3.6.1.4.1.37950.1.1.5.10.18.6.1
-- 1.3.6.1.4.1.37950.1.1.5.10.18.6.1
-- 1.3.6.1.4.1.37950.1.1.5.10.18.6.1
-- 1.3.6.1.4.1.37950.1.1.5.10.18.6.1
-- 1.3.6.1.4.1.37950.1.1.5.10.18.6.1
-- 1.3.6.1.4.1.37950.1.1.5.10.18.6.1
-- 1.3.6.1.4.1.37950.1.1.5.10.18.6.1
		-- 1.3.6.1.4.1.37950.1.1.5.10.18.6.1
		routeMapEntry OBJECT-TYPE
			SYNTAX RouteMapEntry
			MAX-ACCESS not-accessible
			STATUS current
			DESCRIPTION
				"Description."
			INDEX { routeMapName, mapFilterType, mapSequence }
			::= { routeMapTable 1 }

		
		RouteMapEntry ::=
			SEQUENCE { 
				routeMapName
					OCTET STRING,
				mapFilterType
					INTEGER,
				mapSequence
					Integer32,
				clauses
					OCTET STRING
			 }

--         1.3.6.1.4.1.37950.1.1.5.10.18.6.1.1
-- 1.3.6.1.4.1.37950.1.1.5.10.18.6.1.1
-- 1.3.6.1.4.1.37950.1.1.5.10.18.6.1.1
-- 1.3.6.1.4.1.37950.1.1.5.10.18.6.1.1
-- 1.3.6.1.4.1.37950.1.1.5.10.18.6.1.1
-- 1.3.6.1.4.1.37950.1.1.5.10.18.6.1.1
-- 1.3.6.1.4.1.37950.1.1.5.10.18.6.1.1
-- 1.3.6.1.4.1.37950.1.1.5.10.18.6.1.1
		-- 1.3.6.1.4.1.37950.1.1.5.10.18.6.1.1
		routeMapName OBJECT-TYPE
			SYNTAX OCTET STRING
			MAX-ACCESS read-only
			STATUS current
			DESCRIPTION
				"Description."
			::= { routeMapEntry 1 }

		
--         1.3.6.1.4.1.37950.1.1.5.10.18.6.1.2
-- 1.3.6.1.4.1.37950.1.1.5.10.18.6.1.2
-- 1.3.6.1.4.1.37950.1.1.5.10.18.6.1.2
-- 1.3.6.1.4.1.37950.1.1.5.10.18.6.1.2
-- 1.3.6.1.4.1.37950.1.1.5.10.18.6.1.2
-- 1.3.6.1.4.1.37950.1.1.5.10.18.6.1.2
-- 1.3.6.1.4.1.37950.1.1.5.10.18.6.1.2
-- 1.3.6.1.4.1.37950.1.1.5.10.18.6.1.2
		-- 1.3.6.1.4.1.37950.1.1.5.10.18.6.1.2
		mapFilterType OBJECT-TYPE
			SYNTAX INTEGER
				{
				permit(0),
				deny(1)
				}
			MAX-ACCESS read-only
			STATUS current
			DESCRIPTION
				"Description."
			::= { routeMapEntry 2 }

		
--         1.3.6.1.4.1.37950.1.1.5.10.18.6.1.3
-- 1.3.6.1.4.1.37950.1.1.5.10.18.6.1.3
-- 1.3.6.1.4.1.37950.1.1.5.10.18.6.1.3
-- 1.3.6.1.4.1.37950.1.1.5.10.18.6.1.3
-- 1.3.6.1.4.1.37950.1.1.5.10.18.6.1.3
-- 1.3.6.1.4.1.37950.1.1.5.10.18.6.1.3
-- 1.3.6.1.4.1.37950.1.1.5.10.18.6.1.3
-- 1.3.6.1.4.1.37950.1.1.5.10.18.6.1.3
		-- 1.3.6.1.4.1.37950.1.1.5.10.18.6.1.3
		mapSequence OBJECT-TYPE
			SYNTAX Integer32
			MAX-ACCESS read-only
			STATUS current
			DESCRIPTION
				"Description."
			::= { routeMapEntry 3 }

		
--         1.3.6.1.4.1.37950.1.1.5.10.18.6.1.4
-- 1.3.6.1.4.1.37950.1.1.5.10.18.6.1.4
-- 1.3.6.1.4.1.37950.1.1.5.10.18.6.1.4
-- 1.3.6.1.4.1.37950.1.1.5.10.18.6.1.4
-- 1.3.6.1.4.1.37950.1.1.5.10.18.6.1.4
-- 1.3.6.1.4.1.37950.1.1.5.10.18.6.1.4
-- 1.3.6.1.4.1.37950.1.1.5.10.18.6.1.4
-- 1.3.6.1.4.1.37950.1.1.5.10.18.6.1.4
		-- 1.3.6.1.4.1.37950.1.1.5.10.18.6.1.4
		clauses OBJECT-TYPE
			SYNTAX OCTET STRING
			MAX-ACCESS read-only
			STATUS current
			DESCRIPTION
				"Description."
			::= { routeMapEntry 4 }

		
--         1.3.6.1.4.1.37950.1.1.5.10.18.7
-- 1.3.6.1.4.1.37950.1.1.5.10.18.7
-- 1.3.6.1.4.1.37950.1.1.5.10.18.7
-- 1.3.6.1.4.1.37950.1.1.5.10.18.7
-- 1.3.6.1.4.1.37950.1.1.5.10.18.7
-- 1.3.6.1.4.1.37950.1.1.5.10.18.7
-- 1.3.6.1.4.1.37950.1.1.5.10.18.7
-- 1.3.6.1.4.1.37950.1.1.5.10.18.7
		-- 1.3.6.1.4.1.37950.1.1.5.10.18.7
		routeTable OBJECT-TYPE
			SYNTAX SEQUENCE OF RouteEntry
			MAX-ACCESS not-accessible
			STATUS current
			DESCRIPTION
				"Description."
			::= { v1600dRouteList 7 }

		
--         1.3.6.1.4.1.37950.1.1.5.10.18.7.1
-- 1.3.6.1.4.1.37950.1.1.5.10.18.7.1
-- 1.3.6.1.4.1.37950.1.1.5.10.18.7.1
-- 1.3.6.1.4.1.37950.1.1.5.10.18.7.1
-- 1.3.6.1.4.1.37950.1.1.5.10.18.7.1
-- 1.3.6.1.4.1.37950.1.1.5.10.18.7.1
-- 1.3.6.1.4.1.37950.1.1.5.10.18.7.1
-- 1.3.6.1.4.1.37950.1.1.5.10.18.7.1
		-- 1.3.6.1.4.1.37950.1.1.5.10.18.7.1
		routeEntry OBJECT-TYPE
			SYNTAX RouteEntry
			MAX-ACCESS not-accessible
			STATUS current
			DESCRIPTION
				"Description."
			INDEX { routeType, routeNetwork }
			::= { routeTable 1 }

		
		RouteEntry ::=
			SEQUENCE { 
				routeType
					OCTET STRING,
				routeNetwork
					OCTET STRING,
				routeDistance
					OCTET STRING,
				routeMetric
					OCTET STRING,
				routeInterface
					OCTET STRING,
				routeTime
					OCTET STRING
			 }

--         1.3.6.1.4.1.37950.1.1.5.10.18.7.1.1
-- 1.3.6.1.4.1.37950.1.1.5.10.18.7.1.1
-- 1.3.6.1.4.1.37950.1.1.5.10.18.7.1.1
-- 1.3.6.1.4.1.37950.1.1.5.10.18.7.1.1
-- 1.3.6.1.4.1.37950.1.1.5.10.18.7.1.1
-- 1.3.6.1.4.1.37950.1.1.5.10.18.7.1.1
-- 1.3.6.1.4.1.37950.1.1.5.10.18.7.1.1
-- 1.3.6.1.4.1.37950.1.1.5.10.18.7.1.1
		-- 1.3.6.1.4.1.37950.1.1.5.10.18.7.1.1
		routeType OBJECT-TYPE
			SYNTAX OCTET STRING
			MAX-ACCESS read-only
			STATUS current
			DESCRIPTION
				"Description."
			::= { routeEntry 1 }

		
--         1.3.6.1.4.1.37950.1.1.5.10.18.7.1.2
-- 1.3.6.1.4.1.37950.1.1.5.10.18.7.1.2
-- 1.3.6.1.4.1.37950.1.1.5.10.18.7.1.2
-- 1.3.6.1.4.1.37950.1.1.5.10.18.7.1.2
-- 1.3.6.1.4.1.37950.1.1.5.10.18.7.1.2
-- 1.3.6.1.4.1.37950.1.1.5.10.18.7.1.2
-- 1.3.6.1.4.1.37950.1.1.5.10.18.7.1.2
-- 1.3.6.1.4.1.37950.1.1.5.10.18.7.1.2
		-- 1.3.6.1.4.1.37950.1.1.5.10.18.7.1.2
		routeNetwork OBJECT-TYPE
			SYNTAX OCTET STRING
			MAX-ACCESS read-only
			STATUS current
			DESCRIPTION
				"Description."
			::= { routeEntry 2 }

		
--         1.3.6.1.4.1.37950.1.1.5.10.18.7.1.3
-- 1.3.6.1.4.1.37950.1.1.5.10.18.7.1.3
-- 1.3.6.1.4.1.37950.1.1.5.10.18.7.1.3
-- 1.3.6.1.4.1.37950.1.1.5.10.18.7.1.3
-- 1.3.6.1.4.1.37950.1.1.5.10.18.7.1.3
-- 1.3.6.1.4.1.37950.1.1.5.10.18.7.1.3
-- 1.3.6.1.4.1.37950.1.1.5.10.18.7.1.3
-- 1.3.6.1.4.1.37950.1.1.5.10.18.7.1.3
		-- 1.3.6.1.4.1.37950.1.1.5.10.18.7.1.3
		routeDistance OBJECT-TYPE
			SYNTAX OCTET STRING
			MAX-ACCESS read-only
			STATUS current
			DESCRIPTION
				"Description."
			::= { routeEntry 3 }

		
--         1.3.6.1.4.1.37950.1.1.5.10.18.7.1.4
-- 1.3.6.1.4.1.37950.1.1.5.10.18.7.1.4
-- 1.3.6.1.4.1.37950.1.1.5.10.18.7.1.4
-- 1.3.6.1.4.1.37950.1.1.5.10.18.7.1.4
-- 1.3.6.1.4.1.37950.1.1.5.10.18.7.1.4
-- 1.3.6.1.4.1.37950.1.1.5.10.18.7.1.4
-- 1.3.6.1.4.1.37950.1.1.5.10.18.7.1.4
-- 1.3.6.1.4.1.37950.1.1.5.10.18.7.1.4
		-- 1.3.6.1.4.1.37950.1.1.5.10.18.7.1.4
		routeMetric OBJECT-TYPE
			SYNTAX OCTET STRING
			MAX-ACCESS read-only
			STATUS current
			DESCRIPTION
				"Description."
			::= { routeEntry 4 }

		
--         1.3.6.1.4.1.37950.1.1.5.10.18.7.1.5
-- 1.3.6.1.4.1.37950.1.1.5.10.18.7.1.5
-- 1.3.6.1.4.1.37950.1.1.5.10.18.7.1.5
-- 1.3.6.1.4.1.37950.1.1.5.10.18.7.1.5
-- 1.3.6.1.4.1.37950.1.1.5.10.18.7.1.5
-- 1.3.6.1.4.1.37950.1.1.5.10.18.7.1.5
-- 1.3.6.1.4.1.37950.1.1.5.10.18.7.1.5
-- 1.3.6.1.4.1.37950.1.1.5.10.18.7.1.5
		-- 1.3.6.1.4.1.37950.1.1.5.10.18.7.1.5
		routeInterface OBJECT-TYPE
			SYNTAX OCTET STRING
			MAX-ACCESS read-only
			STATUS current
			DESCRIPTION
				"Description."
			::= { routeEntry 5 }

		
--         1.3.6.1.4.1.37950.1.1.5.10.18.7.1.6
-- 1.3.6.1.4.1.37950.1.1.5.10.18.7.1.6
-- 1.3.6.1.4.1.37950.1.1.5.10.18.7.1.6
-- 1.3.6.1.4.1.37950.1.1.5.10.18.7.1.6
-- 1.3.6.1.4.1.37950.1.1.5.10.18.7.1.6
-- 1.3.6.1.4.1.37950.1.1.5.10.18.7.1.6
-- 1.3.6.1.4.1.37950.1.1.5.10.18.7.1.6
-- 1.3.6.1.4.1.37950.1.1.5.10.18.7.1.6
		-- 1.3.6.1.4.1.37950.1.1.5.10.18.7.1.6
		routeTime OBJECT-TYPE
			SYNTAX OCTET STRING
			MAX-ACCESS read-only
			STATUS current
			DESCRIPTION
				"Description."
			::= { routeEntry 6 }

		
--         1.3.6.1.4.1.37950.1.1.5.10.18.8
-- 1.3.6.1.4.1.37950.1.1.5.10.18.8
-- 1.3.6.1.4.1.37950.1.1.5.10.18.8
-- 1.3.6.1.4.1.37950.1.1.5.10.18.8
-- 1.3.6.1.4.1.37950.1.1.5.10.18.8
-- 1.3.6.1.4.1.37950.1.1.5.10.18.8
-- 1.3.6.1.4.1.37950.1.1.5.10.18.8
-- 1.3.6.1.4.1.37950.1.1.5.10.18.8
		-- 1.3.6.1.4.1.37950.1.1.5.10.18.8
		routeIPv6Table OBJECT-TYPE
			SYNTAX SEQUENCE OF RouteIPv6Entry
			MAX-ACCESS not-accessible
			STATUS current
			DESCRIPTION
				"Description."
			::= { v1600dRouteList 8 }

		
--         1.3.6.1.4.1.37950.1.1.5.10.18.8.1
-- 1.3.6.1.4.1.37950.1.1.5.10.18.8.1
-- 1.3.6.1.4.1.37950.1.1.5.10.18.8.1
-- 1.3.6.1.4.1.37950.1.1.5.10.18.8.1
-- 1.3.6.1.4.1.37950.1.1.5.10.18.8.1
-- 1.3.6.1.4.1.37950.1.1.5.10.18.8.1
-- 1.3.6.1.4.1.37950.1.1.5.10.18.8.1
-- 1.3.6.1.4.1.37950.1.1.5.10.18.8.1
		-- 1.3.6.1.4.1.37950.1.1.5.10.18.8.1
		routeIPv6Entry OBJECT-TYPE
			SYNTAX RouteIPv6Entry
			MAX-ACCESS not-accessible
			STATUS current
			DESCRIPTION
				"Description."
			INDEX { routeIPv6Type, routeIPv6Network }
			::= { routeIPv6Table 1 }

		
		RouteIPv6Entry ::=
			SEQUENCE { 
				routeIPv6Type
					OCTET STRING,
				routeIPv6Network
					OCTET STRING,
				routeIPv6Distance
					OCTET STRING,
				routeIPv6Metric
					OCTET STRING,
				routeIPv6Interface
					OCTET STRING,
				routeIPv6Time
					OCTET STRING
			 }

--         1.3.6.1.4.1.37950.1.1.5.10.18.8.1.1
-- 1.3.6.1.4.1.37950.1.1.5.10.18.8.1.1
-- 1.3.6.1.4.1.37950.1.1.5.10.18.8.1.1
-- 1.3.6.1.4.1.37950.1.1.5.10.18.8.1.1
-- 1.3.6.1.4.1.37950.1.1.5.10.18.8.1.1
-- 1.3.6.1.4.1.37950.1.1.5.10.18.8.1.1
-- 1.3.6.1.4.1.37950.1.1.5.10.18.8.1.1
-- 1.3.6.1.4.1.37950.1.1.5.10.18.8.1.1
		-- 1.3.6.1.4.1.37950.1.1.5.10.18.8.1.1
		routeIPv6Type OBJECT-TYPE
			SYNTAX OCTET STRING
			MAX-ACCESS read-only
			STATUS current
			DESCRIPTION
				"Description."
			::= { routeIPv6Entry 1 }

		
--         1.3.6.1.4.1.37950.1.1.5.10.18.8.1.2
-- 1.3.6.1.4.1.37950.1.1.5.10.18.8.1.2
-- 1.3.6.1.4.1.37950.1.1.5.10.18.8.1.2
-- 1.3.6.1.4.1.37950.1.1.5.10.18.8.1.2
-- 1.3.6.1.4.1.37950.1.1.5.10.18.8.1.2
-- 1.3.6.1.4.1.37950.1.1.5.10.18.8.1.2
-- 1.3.6.1.4.1.37950.1.1.5.10.18.8.1.2
-- 1.3.6.1.4.1.37950.1.1.5.10.18.8.1.2
		-- 1.3.6.1.4.1.37950.1.1.5.10.18.8.1.2
		routeIPv6Network OBJECT-TYPE
			SYNTAX OCTET STRING
			MAX-ACCESS read-only
			STATUS current
			DESCRIPTION
				"Description."
			::= { routeIPv6Entry 2 }

		
--         1.3.6.1.4.1.37950.1.1.5.10.18.8.1.3
-- 1.3.6.1.4.1.37950.1.1.5.10.18.8.1.3
-- 1.3.6.1.4.1.37950.1.1.5.10.18.8.1.3
-- 1.3.6.1.4.1.37950.1.1.5.10.18.8.1.3
-- 1.3.6.1.4.1.37950.1.1.5.10.18.8.1.3
-- 1.3.6.1.4.1.37950.1.1.5.10.18.8.1.3
-- 1.3.6.1.4.1.37950.1.1.5.10.18.8.1.3
-- 1.3.6.1.4.1.37950.1.1.5.10.18.8.1.3
		-- 1.3.6.1.4.1.37950.1.1.5.10.18.8.1.3
		routeIPv6Distance OBJECT-TYPE
			SYNTAX OCTET STRING
			MAX-ACCESS read-write
			STATUS current
			DESCRIPTION
				"Description."
			::= { routeIPv6Entry 3 }

		
--         1.3.6.1.4.1.37950.1.1.5.10.18.8.1.4
-- 1.3.6.1.4.1.37950.1.1.5.10.18.8.1.4
-- 1.3.6.1.4.1.37950.1.1.5.10.18.8.1.4
-- 1.3.6.1.4.1.37950.1.1.5.10.18.8.1.4
-- 1.3.6.1.4.1.37950.1.1.5.10.18.8.1.4
-- 1.3.6.1.4.1.37950.1.1.5.10.18.8.1.4
-- 1.3.6.1.4.1.37950.1.1.5.10.18.8.1.4
-- 1.3.6.1.4.1.37950.1.1.5.10.18.8.1.4
		-- 1.3.6.1.4.1.37950.1.1.5.10.18.8.1.4
		routeIPv6Metric OBJECT-TYPE
			SYNTAX OCTET STRING
			MAX-ACCESS read-write
			STATUS current
			DESCRIPTION
				"Description."
			::= { routeIPv6Entry 4 }

		
--         1.3.6.1.4.1.37950.1.1.5.10.18.8.1.5
-- 1.3.6.1.4.1.37950.1.1.5.10.18.8.1.5
-- 1.3.6.1.4.1.37950.1.1.5.10.18.8.1.5
-- 1.3.6.1.4.1.37950.1.1.5.10.18.8.1.5
-- 1.3.6.1.4.1.37950.1.1.5.10.18.8.1.5
-- 1.3.6.1.4.1.37950.1.1.5.10.18.8.1.5
-- 1.3.6.1.4.1.37950.1.1.5.10.18.8.1.5
-- 1.3.6.1.4.1.37950.1.1.5.10.18.8.1.5
		-- 1.3.6.1.4.1.37950.1.1.5.10.18.8.1.5
		routeIPv6Interface OBJECT-TYPE
			SYNTAX OCTET STRING
			MAX-ACCESS read-write
			STATUS current
			DESCRIPTION
				"Description."
			::= { routeIPv6Entry 5 }

		
--         1.3.6.1.4.1.37950.1.1.5.10.18.8.1.6
-- 1.3.6.1.4.1.37950.1.1.5.10.18.8.1.6
-- 1.3.6.1.4.1.37950.1.1.5.10.18.8.1.6
-- 1.3.6.1.4.1.37950.1.1.5.10.18.8.1.6
-- 1.3.6.1.4.1.37950.1.1.5.10.18.8.1.6
-- 1.3.6.1.4.1.37950.1.1.5.10.18.8.1.6
-- 1.3.6.1.4.1.37950.1.1.5.10.18.8.1.6
-- 1.3.6.1.4.1.37950.1.1.5.10.18.8.1.6
		-- 1.3.6.1.4.1.37950.1.1.5.10.18.8.1.6
		routeIPv6Time OBJECT-TYPE
			SYNTAX OCTET STRING
			MAX-ACCESS read-write
			STATUS current
			DESCRIPTION
				"Description."
			::= { routeIPv6Entry 6 }

		
--         1.3.6.1.4.1.37950.1.1.5.10.19
-- 1.3.6.1.4.1.37950.1.1.5.10.19
-- 1.3.6.1.4.1.37950.1.1.5.10.19
-- 1.3.6.1.4.1.37950.1.1.5.10.19
-- 1.3.6.1.4.1.37950.1.1.5.10.19
-- 1.3.6.1.4.1.37950.1.1.5.10.19
-- 1.3.6.1.4.1.37950.1.1.5.10.19
-- 1.3.6.1.4.1.37950.1.1.5.10.19
		-- 1.3.6.1.4.1.37950.1.1.5.10.19
		v1600dDHCPv6 OBJECT IDENTIFIER ::= { v1600dSwitch 19 }

		
--         1.3.6.1.4.1.37950.1.1.5.10.19.1
-- 1.3.6.1.4.1.37950.1.1.5.10.19.1
-- 1.3.6.1.4.1.37950.1.1.5.10.19.1
-- 1.3.6.1.4.1.37950.1.1.5.10.19.1
-- 1.3.6.1.4.1.37950.1.1.5.10.19.1
-- 1.3.6.1.4.1.37950.1.1.5.10.19.1
-- 1.3.6.1.4.1.37950.1.1.5.10.19.1
-- 1.3.6.1.4.1.37950.1.1.5.10.19.1
		-- 1.3.6.1.4.1.37950.1.1.5.10.19.1
		dhcpv6Server OBJECT IDENTIFIER ::= { v1600dDHCPv6 1 }

		
--         1.3.6.1.4.1.37950.1.1.5.10.19.1.1
-- 1.3.6.1.4.1.37950.1.1.5.10.19.1.1
-- 1.3.6.1.4.1.37950.1.1.5.10.19.1.1
-- 1.3.6.1.4.1.37950.1.1.5.10.19.1.1
-- 1.3.6.1.4.1.37950.1.1.5.10.19.1.1
-- 1.3.6.1.4.1.37950.1.1.5.10.19.1.1
-- 1.3.6.1.4.1.37950.1.1.5.10.19.1.1
-- 1.3.6.1.4.1.37950.1.1.5.10.19.1.1
		-- 1.3.6.1.4.1.37950.1.1.5.10.19.1.1
		dhcpv6ServerPoolCfg OBJECT IDENTIFIER ::= { dhcpv6Server 1 }

		
--         1.3.6.1.4.1.37950.1.1.5.10.19.1.1.1
-- 1.3.6.1.4.1.37950.1.1.5.10.19.1.1.1
-- 1.3.6.1.4.1.37950.1.1.5.10.19.1.1.1
-- 1.3.6.1.4.1.37950.1.1.5.10.19.1.1.1
-- 1.3.6.1.4.1.37950.1.1.5.10.19.1.1.1
-- 1.3.6.1.4.1.37950.1.1.5.10.19.1.1.1
-- 1.3.6.1.4.1.37950.1.1.5.10.19.1.1.1
-- 1.3.6.1.4.1.37950.1.1.5.10.19.1.1.1
		-- 1.3.6.1.4.1.37950.1.1.5.10.19.1.1.1
		dhcpv6ServerPoolname OBJECT-TYPE
			SYNTAX OCTET STRING
			MAX-ACCESS read-write
			STATUS current
			DESCRIPTION
				"Description."
			::= { dhcpv6ServerPoolCfg 1 }

		
--         1.3.6.1.4.1.37950.1.1.5.10.19.1.1.2
-- 1.3.6.1.4.1.37950.1.1.5.10.19.1.1.2
-- 1.3.6.1.4.1.37950.1.1.5.10.19.1.1.2
-- 1.3.6.1.4.1.37950.1.1.5.10.19.1.1.2
-- 1.3.6.1.4.1.37950.1.1.5.10.19.1.1.2
-- 1.3.6.1.4.1.37950.1.1.5.10.19.1.1.2
-- 1.3.6.1.4.1.37950.1.1.5.10.19.1.1.2
-- 1.3.6.1.4.1.37950.1.1.5.10.19.1.1.2
		-- 1.3.6.1.4.1.37950.1.1.5.10.19.1.1.2
		dhcpv6ServerPoolStartIpv6 OBJECT-TYPE
			SYNTAX OCTET STRING
			MAX-ACCESS read-write
			STATUS current
			DESCRIPTION
				"Description."
			::= { dhcpv6ServerPoolCfg 2 }

		
--         1.3.6.1.4.1.37950.1.1.5.10.19.1.1.3
-- 1.3.6.1.4.1.37950.1.1.5.10.19.1.1.3
-- 1.3.6.1.4.1.37950.1.1.5.10.19.1.1.3
-- 1.3.6.1.4.1.37950.1.1.5.10.19.1.1.3
-- 1.3.6.1.4.1.37950.1.1.5.10.19.1.1.3
-- 1.3.6.1.4.1.37950.1.1.5.10.19.1.1.3
-- 1.3.6.1.4.1.37950.1.1.5.10.19.1.1.3
-- 1.3.6.1.4.1.37950.1.1.5.10.19.1.1.3
		-- 1.3.6.1.4.1.37950.1.1.5.10.19.1.1.3
		dhcpv6ServerPoolEndIPv6 OBJECT-TYPE
			SYNTAX OCTET STRING
			MAX-ACCESS read-write
			STATUS current
			DESCRIPTION
				"Description."
			::= { dhcpv6ServerPoolCfg 3 }

		
--         1.3.6.1.4.1.37950.1.1.5.10.19.1.1.4
-- 1.3.6.1.4.1.37950.1.1.5.10.19.1.1.4
-- 1.3.6.1.4.1.37950.1.1.5.10.19.1.1.4
-- 1.3.6.1.4.1.37950.1.1.5.10.19.1.1.4
-- 1.3.6.1.4.1.37950.1.1.5.10.19.1.1.4
-- 1.3.6.1.4.1.37950.1.1.5.10.19.1.1.4
-- 1.3.6.1.4.1.37950.1.1.5.10.19.1.1.4
-- 1.3.6.1.4.1.37950.1.1.5.10.19.1.1.4
		-- 1.3.6.1.4.1.37950.1.1.5.10.19.1.1.4
		dhcpv6ServerPoolPfxValidTime OBJECT-TYPE
			SYNTAX OCTET STRING
			MAX-ACCESS read-write
			STATUS current
			DESCRIPTION
				"Description."
			DEFVAL { "172800" }
			::= { dhcpv6ServerPoolCfg 4 }

		
--         1.3.6.1.4.1.37950.1.1.5.10.19.1.1.5
-- 1.3.6.1.4.1.37950.1.1.5.10.19.1.1.5
-- 1.3.6.1.4.1.37950.1.1.5.10.19.1.1.5
-- 1.3.6.1.4.1.37950.1.1.5.10.19.1.1.5
-- 1.3.6.1.4.1.37950.1.1.5.10.19.1.1.5
-- 1.3.6.1.4.1.37950.1.1.5.10.19.1.1.5
-- 1.3.6.1.4.1.37950.1.1.5.10.19.1.1.5
-- 1.3.6.1.4.1.37950.1.1.5.10.19.1.1.5
		-- 1.3.6.1.4.1.37950.1.1.5.10.19.1.1.5
		dhcpv6ServerPoolPfxPreferredTime OBJECT-TYPE
			SYNTAX OCTET STRING
			MAX-ACCESS read-write
			STATUS current
			DESCRIPTION
				"Description."
			DEFVAL { "86400" }
			::= { dhcpv6ServerPoolCfg 5 }

		
--         1.3.6.1.4.1.37950.1.1.5.10.19.1.1.6
-- 1.3.6.1.4.1.37950.1.1.5.10.19.1.1.6
-- 1.3.6.1.4.1.37950.1.1.5.10.19.1.1.6
-- 1.3.6.1.4.1.37950.1.1.5.10.19.1.1.6
-- 1.3.6.1.4.1.37950.1.1.5.10.19.1.1.6
-- 1.3.6.1.4.1.37950.1.1.5.10.19.1.1.6
-- 1.3.6.1.4.1.37950.1.1.5.10.19.1.1.6
-- 1.3.6.1.4.1.37950.1.1.5.10.19.1.1.6
		-- 1.3.6.1.4.1.37950.1.1.5.10.19.1.1.6
		dhcpv6ServerPoolDNS OBJECT-TYPE
			SYNTAX OCTET STRING
			MAX-ACCESS read-write
			STATUS current
			DESCRIPTION
				"Description."
			::= { dhcpv6ServerPoolCfg 6 }

		
--         1.3.6.1.4.1.37950.1.1.5.10.19.1.1.7
-- 1.3.6.1.4.1.37950.1.1.5.10.19.1.1.7
-- 1.3.6.1.4.1.37950.1.1.5.10.19.1.1.7
-- 1.3.6.1.4.1.37950.1.1.5.10.19.1.1.7
-- 1.3.6.1.4.1.37950.1.1.5.10.19.1.1.7
-- 1.3.6.1.4.1.37950.1.1.5.10.19.1.1.7
-- 1.3.6.1.4.1.37950.1.1.5.10.19.1.1.7
-- 1.3.6.1.4.1.37950.1.1.5.10.19.1.1.7
		-- 1.3.6.1.4.1.37950.1.1.5.10.19.1.1.7
		dhcpv6ServerPoolDomain OBJECT-TYPE
			SYNTAX OCTET STRING
			MAX-ACCESS read-write
			STATUS current
			DESCRIPTION
				"Description."
			::= { dhcpv6ServerPoolCfg 7 }

		
--         1.3.6.1.4.1.37950.1.1.5.10.19.1.1.8
-- 1.3.6.1.4.1.37950.1.1.5.10.19.1.1.8
-- 1.3.6.1.4.1.37950.1.1.5.10.19.1.1.8
-- 1.3.6.1.4.1.37950.1.1.5.10.19.1.1.8
-- 1.3.6.1.4.1.37950.1.1.5.10.19.1.1.8
-- 1.3.6.1.4.1.37950.1.1.5.10.19.1.1.8
-- 1.3.6.1.4.1.37950.1.1.5.10.19.1.1.8
-- 1.3.6.1.4.1.37950.1.1.5.10.19.1.1.8
		-- 1.3.6.1.4.1.37950.1.1.5.10.19.1.1.8
		dhcpv6ServerPoolAction OBJECT-TYPE
			SYNTAX INTEGER
				{
				add(1),
				del(2)
				}
			MAX-ACCESS read-write
			STATUS current
			DESCRIPTION
				"Description."
			::= { dhcpv6ServerPoolCfg 8 }

		
--         1.3.6.1.4.1.37950.1.1.5.10.19.1.1.9
-- 1.3.6.1.4.1.37950.1.1.5.10.19.1.1.9
-- 1.3.6.1.4.1.37950.1.1.5.10.19.1.1.9
-- 1.3.6.1.4.1.37950.1.1.5.10.19.1.1.9
-- 1.3.6.1.4.1.37950.1.1.5.10.19.1.1.9
-- 1.3.6.1.4.1.37950.1.1.5.10.19.1.1.9
-- 1.3.6.1.4.1.37950.1.1.5.10.19.1.1.9
-- 1.3.6.1.4.1.37950.1.1.5.10.19.1.1.9
		-- 1.3.6.1.4.1.37950.1.1.5.10.19.1.1.9
		dhcpv6ServerPoolInfRefreshTime OBJECT-TYPE
			SYNTAX OCTET STRING
			MAX-ACCESS read-write
			STATUS current
			DESCRIPTION
				"Description."
			::= { dhcpv6ServerPoolCfg 9 }

		
--         1.3.6.1.4.1.37950.1.1.5.10.19.1.2
-- 1.3.6.1.4.1.37950.1.1.5.10.19.1.2
-- 1.3.6.1.4.1.37950.1.1.5.10.19.1.2
-- 1.3.6.1.4.1.37950.1.1.5.10.19.1.2
-- 1.3.6.1.4.1.37950.1.1.5.10.19.1.2
-- 1.3.6.1.4.1.37950.1.1.5.10.19.1.2
-- 1.3.6.1.4.1.37950.1.1.5.10.19.1.2
-- 1.3.6.1.4.1.37950.1.1.5.10.19.1.2
		-- 1.3.6.1.4.1.37950.1.1.5.10.19.1.2
		dhcpv6ServerPoolTable OBJECT-TYPE
			SYNTAX SEQUENCE OF Dhcpv6ServerPoolEntry
			MAX-ACCESS not-accessible
			STATUS current
			DESCRIPTION
				"Description."
			::= { dhcpv6Server 2 }

		
--         1.3.6.1.4.1.37950.1.1.5.10.19.1.2.1
-- 1.3.6.1.4.1.37950.1.1.5.10.19.1.2.1
-- 1.3.6.1.4.1.37950.1.1.5.10.19.1.2.1
-- 1.3.6.1.4.1.37950.1.1.5.10.19.1.2.1
-- 1.3.6.1.4.1.37950.1.1.5.10.19.1.2.1
-- 1.3.6.1.4.1.37950.1.1.5.10.19.1.2.1
-- 1.3.6.1.4.1.37950.1.1.5.10.19.1.2.1
-- 1.3.6.1.4.1.37950.1.1.5.10.19.1.2.1
		-- 1.3.6.1.4.1.37950.1.1.5.10.19.1.2.1
		dhcpv6ServerPoolEntry OBJECT-TYPE
			SYNTAX Dhcpv6ServerPoolEntry
			MAX-ACCESS not-accessible
			STATUS current
			DESCRIPTION
				"Description."
			INDEX { dhcpv6ServerPoolIndex }
			::= { dhcpv6ServerPoolTable 1 }

		
		Dhcpv6ServerPoolEntry ::=
			SEQUENCE { 
				dhcpv6ServerPoolIndex
					Integer32,
				dhcpv6ServerPoolName
					OCTET STRING,
				dhcpv6ServerPoolStartIPv6Addr
					OCTET STRING,
				dhcpv6ServerPoolEndIPv6Addr
					OCTET STRING,
				dhcpv6ServerPoolAddrValidLifetime
					OCTET STRING,
				dhcpv6ServerPoolAddrPreferredLifetime
					OCTET STRING,
				dhcpv6ServerPoolDNSServer
					OCTET STRING,
				dhcpv6ServerPoolDomainName
					OCTET STRING,
				dhcpv6ServerPoolInfoRefrehTime
					OCTET STRING
			 }

--         1.3.6.1.4.1.37950.1.1.5.10.19.1.2.1.1
-- 1.3.6.1.4.1.37950.1.1.5.10.19.1.2.1.1
-- 1.3.6.1.4.1.37950.1.1.5.10.19.1.2.1.1
-- 1.3.6.1.4.1.37950.1.1.5.10.19.1.2.1.1
-- 1.3.6.1.4.1.37950.1.1.5.10.19.1.2.1.1
-- 1.3.6.1.4.1.37950.1.1.5.10.19.1.2.1.1
-- 1.3.6.1.4.1.37950.1.1.5.10.19.1.2.1.1
-- 1.3.6.1.4.1.37950.1.1.5.10.19.1.2.1.1
		-- 1.3.6.1.4.1.37950.1.1.5.10.19.1.2.1.1
		dhcpv6ServerPoolIndex OBJECT-TYPE
			SYNTAX Integer32
			MAX-ACCESS read-only
			STATUS current
			DESCRIPTION
				"Description."
			::= { dhcpv6ServerPoolEntry 1 }

		
--         1.3.6.1.4.1.37950.1.1.5.10.19.1.2.1.2
-- 1.3.6.1.4.1.37950.1.1.5.10.19.1.2.1.2
-- 1.3.6.1.4.1.37950.1.1.5.10.19.1.2.1.2
-- 1.3.6.1.4.1.37950.1.1.5.10.19.1.2.1.2
-- 1.3.6.1.4.1.37950.1.1.5.10.19.1.2.1.2
-- 1.3.6.1.4.1.37950.1.1.5.10.19.1.2.1.2
-- 1.3.6.1.4.1.37950.1.1.5.10.19.1.2.1.2
-- 1.3.6.1.4.1.37950.1.1.5.10.19.1.2.1.2
		-- 1.3.6.1.4.1.37950.1.1.5.10.19.1.2.1.2
		dhcpv6ServerPoolName OBJECT-TYPE
			SYNTAX OCTET STRING
			MAX-ACCESS read-only
			STATUS current
			DESCRIPTION
				"Description."
			::= { dhcpv6ServerPoolEntry 2 }

		
--         1.3.6.1.4.1.37950.1.1.5.10.19.1.2.1.3
-- 1.3.6.1.4.1.37950.1.1.5.10.19.1.2.1.3
-- 1.3.6.1.4.1.37950.1.1.5.10.19.1.2.1.3
-- 1.3.6.1.4.1.37950.1.1.5.10.19.1.2.1.3
-- 1.3.6.1.4.1.37950.1.1.5.10.19.1.2.1.3
-- 1.3.6.1.4.1.37950.1.1.5.10.19.1.2.1.3
-- 1.3.6.1.4.1.37950.1.1.5.10.19.1.2.1.3
-- 1.3.6.1.4.1.37950.1.1.5.10.19.1.2.1.3
		-- 1.3.6.1.4.1.37950.1.1.5.10.19.1.2.1.3
		dhcpv6ServerPoolStartIPv6Addr OBJECT-TYPE
			SYNTAX OCTET STRING
			MAX-ACCESS read-only
			STATUS current
			DESCRIPTION
				"Description."
			::= { dhcpv6ServerPoolEntry 3 }

		
--         1.3.6.1.4.1.37950.1.1.5.10.19.1.2.1.4
-- 1.3.6.1.4.1.37950.1.1.5.10.19.1.2.1.4
-- 1.3.6.1.4.1.37950.1.1.5.10.19.1.2.1.4
-- 1.3.6.1.4.1.37950.1.1.5.10.19.1.2.1.4
-- 1.3.6.1.4.1.37950.1.1.5.10.19.1.2.1.4
-- 1.3.6.1.4.1.37950.1.1.5.10.19.1.2.1.4
-- 1.3.6.1.4.1.37950.1.1.5.10.19.1.2.1.4
-- 1.3.6.1.4.1.37950.1.1.5.10.19.1.2.1.4
		-- 1.3.6.1.4.1.37950.1.1.5.10.19.1.2.1.4
		dhcpv6ServerPoolEndIPv6Addr OBJECT-TYPE
			SYNTAX OCTET STRING
			MAX-ACCESS read-only
			STATUS current
			DESCRIPTION
				"Description."
			::= { dhcpv6ServerPoolEntry 4 }

		
--         1.3.6.1.4.1.37950.1.1.5.10.19.1.2.1.5
-- 1.3.6.1.4.1.37950.1.1.5.10.19.1.2.1.5
-- 1.3.6.1.4.1.37950.1.1.5.10.19.1.2.1.5
-- 1.3.6.1.4.1.37950.1.1.5.10.19.1.2.1.5
-- 1.3.6.1.4.1.37950.1.1.5.10.19.1.2.1.5
-- 1.3.6.1.4.1.37950.1.1.5.10.19.1.2.1.5
-- 1.3.6.1.4.1.37950.1.1.5.10.19.1.2.1.5
-- 1.3.6.1.4.1.37950.1.1.5.10.19.1.2.1.5
		-- 1.3.6.1.4.1.37950.1.1.5.10.19.1.2.1.5
		dhcpv6ServerPoolAddrValidLifetime OBJECT-TYPE
			SYNTAX OCTET STRING
			MAX-ACCESS read-only
			STATUS current
			DESCRIPTION
				"Description."
			DEFVAL { "172800" }
			::= { dhcpv6ServerPoolEntry 5 }

		
--         1.3.6.1.4.1.37950.1.1.5.10.19.1.2.1.6
-- 1.3.6.1.4.1.37950.1.1.5.10.19.1.2.1.6
-- 1.3.6.1.4.1.37950.1.1.5.10.19.1.2.1.6
-- 1.3.6.1.4.1.37950.1.1.5.10.19.1.2.1.6
-- 1.3.6.1.4.1.37950.1.1.5.10.19.1.2.1.6
-- 1.3.6.1.4.1.37950.1.1.5.10.19.1.2.1.6
-- 1.3.6.1.4.1.37950.1.1.5.10.19.1.2.1.6
-- 1.3.6.1.4.1.37950.1.1.5.10.19.1.2.1.6
		-- 1.3.6.1.4.1.37950.1.1.5.10.19.1.2.1.6
		dhcpv6ServerPoolAddrPreferredLifetime OBJECT-TYPE
			SYNTAX OCTET STRING
			MAX-ACCESS read-only
			STATUS current
			DESCRIPTION
				"Description."
			DEFVAL { "86400" }
			::= { dhcpv6ServerPoolEntry 6 }

		
--         1.3.6.1.4.1.37950.1.1.5.10.19.1.2.1.7
-- 1.3.6.1.4.1.37950.1.1.5.10.19.1.2.1.7
-- 1.3.6.1.4.1.37950.1.1.5.10.19.1.2.1.7
-- 1.3.6.1.4.1.37950.1.1.5.10.19.1.2.1.7
-- 1.3.6.1.4.1.37950.1.1.5.10.19.1.2.1.7
-- 1.3.6.1.4.1.37950.1.1.5.10.19.1.2.1.7
-- 1.3.6.1.4.1.37950.1.1.5.10.19.1.2.1.7
-- 1.3.6.1.4.1.37950.1.1.5.10.19.1.2.1.7
		-- 1.3.6.1.4.1.37950.1.1.5.10.19.1.2.1.7
		dhcpv6ServerPoolDNSServer OBJECT-TYPE
			SYNTAX OCTET STRING
			MAX-ACCESS read-only
			STATUS current
			DESCRIPTION
				"Description."
			::= { dhcpv6ServerPoolEntry 7 }

		
--         1.3.6.1.4.1.37950.1.1.5.10.19.1.2.1.8
-- 1.3.6.1.4.1.37950.1.1.5.10.19.1.2.1.8
-- 1.3.6.1.4.1.37950.1.1.5.10.19.1.2.1.8
-- 1.3.6.1.4.1.37950.1.1.5.10.19.1.2.1.8
-- 1.3.6.1.4.1.37950.1.1.5.10.19.1.2.1.8
-- 1.3.6.1.4.1.37950.1.1.5.10.19.1.2.1.8
-- 1.3.6.1.4.1.37950.1.1.5.10.19.1.2.1.8
-- 1.3.6.1.4.1.37950.1.1.5.10.19.1.2.1.8
		-- 1.3.6.1.4.1.37950.1.1.5.10.19.1.2.1.8
		dhcpv6ServerPoolDomainName OBJECT-TYPE
			SYNTAX OCTET STRING
			MAX-ACCESS read-only
			STATUS current
			DESCRIPTION
				"Description."
			::= { dhcpv6ServerPoolEntry 8 }

		
--         1.3.6.1.4.1.37950.1.1.5.10.19.1.2.1.9
-- 1.3.6.1.4.1.37950.1.1.5.10.19.1.2.1.9
-- 1.3.6.1.4.1.37950.1.1.5.10.19.1.2.1.9
-- 1.3.6.1.4.1.37950.1.1.5.10.19.1.2.1.9
-- 1.3.6.1.4.1.37950.1.1.5.10.19.1.2.1.9
-- 1.3.6.1.4.1.37950.1.1.5.10.19.1.2.1.9
-- 1.3.6.1.4.1.37950.1.1.5.10.19.1.2.1.9
-- 1.3.6.1.4.1.37950.1.1.5.10.19.1.2.1.9
		-- 1.3.6.1.4.1.37950.1.1.5.10.19.1.2.1.9
		dhcpv6ServerPoolInfoRefrehTime OBJECT-TYPE
			SYNTAX OCTET STRING
			MAX-ACCESS read-only
			STATUS current
			DESCRIPTION
				"Description."
			DEFVAL { "0" }
			::= { dhcpv6ServerPoolEntry 9 }

		
--         1.3.6.1.4.1.37950.1.1.5.10.19.1.3
-- 1.3.6.1.4.1.37950.1.1.5.10.19.1.3
-- 1.3.6.1.4.1.37950.1.1.5.10.19.1.3
-- 1.3.6.1.4.1.37950.1.1.5.10.19.1.3
-- 1.3.6.1.4.1.37950.1.1.5.10.19.1.3
-- 1.3.6.1.4.1.37950.1.1.5.10.19.1.3
-- 1.3.6.1.4.1.37950.1.1.5.10.19.1.3
-- 1.3.6.1.4.1.37950.1.1.5.10.19.1.3
		-- 1.3.6.1.4.1.37950.1.1.5.10.19.1.3
		dhcpv6ServerInterface OBJECT IDENTIFIER ::= { dhcpv6Server 3 }

		
--         1.3.6.1.4.1.37950.1.1.5.10.19.1.3.1
-- 1.3.6.1.4.1.37950.1.1.5.10.19.1.3.1
-- 1.3.6.1.4.1.37950.1.1.5.10.19.1.3.1
-- 1.3.6.1.4.1.37950.1.1.5.10.19.1.3.1
-- 1.3.6.1.4.1.37950.1.1.5.10.19.1.3.1
-- 1.3.6.1.4.1.37950.1.1.5.10.19.1.3.1
-- 1.3.6.1.4.1.37950.1.1.5.10.19.1.3.1
-- 1.3.6.1.4.1.37950.1.1.5.10.19.1.3.1
		-- 1.3.6.1.4.1.37950.1.1.5.10.19.1.3.1
		dhcpv6ServerBindingsClientInterfaceVlanid OBJECT-TYPE
			SYNTAX Integer32
			MAX-ACCESS read-write
			STATUS current
			DESCRIPTION
				"Description."
			::= { dhcpv6ServerInterface 1 }

		
--         1.3.6.1.4.1.37950.1.1.5.10.19.1.3.2
-- 1.3.6.1.4.1.37950.1.1.5.10.19.1.3.2
-- 1.3.6.1.4.1.37950.1.1.5.10.19.1.3.2
-- 1.3.6.1.4.1.37950.1.1.5.10.19.1.3.2
-- 1.3.6.1.4.1.37950.1.1.5.10.19.1.3.2
-- 1.3.6.1.4.1.37950.1.1.5.10.19.1.3.2
-- 1.3.6.1.4.1.37950.1.1.5.10.19.1.3.2
-- 1.3.6.1.4.1.37950.1.1.5.10.19.1.3.2
		-- 1.3.6.1.4.1.37950.1.1.5.10.19.1.3.2
		dhcpv6ServerBindingsClientInterfacePool OBJECT-TYPE
			SYNTAX OCTET STRING
			MAX-ACCESS read-write
			STATUS current
			DESCRIPTION
				"Description."
			::= { dhcpv6ServerInterface 2 }

		
--         1.3.6.1.4.1.37950.1.1.5.10.19.1.3.3
-- 1.3.6.1.4.1.37950.1.1.5.10.19.1.3.3
-- 1.3.6.1.4.1.37950.1.1.5.10.19.1.3.3
-- 1.3.6.1.4.1.37950.1.1.5.10.19.1.3.3
-- 1.3.6.1.4.1.37950.1.1.5.10.19.1.3.3
-- 1.3.6.1.4.1.37950.1.1.5.10.19.1.3.3
-- 1.3.6.1.4.1.37950.1.1.5.10.19.1.3.3
-- 1.3.6.1.4.1.37950.1.1.5.10.19.1.3.3
		-- 1.3.6.1.4.1.37950.1.1.5.10.19.1.3.3
		dhcpv6ServerPreferenceValue OBJECT-TYPE
			SYNTAX OCTET STRING
			MAX-ACCESS read-write
			STATUS current
			DESCRIPTION
				"Description."
			::= { dhcpv6ServerInterface 3 }

		
--         1.3.6.1.4.1.37950.1.1.5.10.19.1.3.4
-- 1.3.6.1.4.1.37950.1.1.5.10.19.1.3.4
-- 1.3.6.1.4.1.37950.1.1.5.10.19.1.3.4
-- 1.3.6.1.4.1.37950.1.1.5.10.19.1.3.4
-- 1.3.6.1.4.1.37950.1.1.5.10.19.1.3.4
-- 1.3.6.1.4.1.37950.1.1.5.10.19.1.3.4
-- 1.3.6.1.4.1.37950.1.1.5.10.19.1.3.4
-- 1.3.6.1.4.1.37950.1.1.5.10.19.1.3.4
		-- 1.3.6.1.4.1.37950.1.1.5.10.19.1.3.4
		dhcpv6ServerAllowClientshint OBJECT-TYPE
			SYNTAX INTEGER
				{
				ignored(1),
				allow(2)
				}
			MAX-ACCESS read-write
			STATUS current
			DESCRIPTION
				"Description."
			::= { dhcpv6ServerInterface 4 }

		
--         1.3.6.1.4.1.37950.1.1.5.10.19.1.3.5
-- 1.3.6.1.4.1.37950.1.1.5.10.19.1.3.5
-- 1.3.6.1.4.1.37950.1.1.5.10.19.1.3.5
-- 1.3.6.1.4.1.37950.1.1.5.10.19.1.3.5
-- 1.3.6.1.4.1.37950.1.1.5.10.19.1.3.5
-- 1.3.6.1.4.1.37950.1.1.5.10.19.1.3.5
-- 1.3.6.1.4.1.37950.1.1.5.10.19.1.3.5
-- 1.3.6.1.4.1.37950.1.1.5.10.19.1.3.5
		-- 1.3.6.1.4.1.37950.1.1.5.10.19.1.3.5
		dhcpv6ServerRapidcommit OBJECT-TYPE
			SYNTAX INTEGER
				{
				disabled(1),
				enabled(2)
				}
			MAX-ACCESS read-write
			STATUS current
			DESCRIPTION
				"Description."
			::= { dhcpv6ServerInterface 5 }

		
--         1.3.6.1.4.1.37950.1.1.5.10.19.1.3.6
-- 1.3.6.1.4.1.37950.1.1.5.10.19.1.3.6
-- 1.3.6.1.4.1.37950.1.1.5.10.19.1.3.6
-- 1.3.6.1.4.1.37950.1.1.5.10.19.1.3.6
-- 1.3.6.1.4.1.37950.1.1.5.10.19.1.3.6
-- 1.3.6.1.4.1.37950.1.1.5.10.19.1.3.6
-- 1.3.6.1.4.1.37950.1.1.5.10.19.1.3.6
-- 1.3.6.1.4.1.37950.1.1.5.10.19.1.3.6
		-- 1.3.6.1.4.1.37950.1.1.5.10.19.1.3.6
		dhcpv6ServerBindingsClientInterfaceAction OBJECT-TYPE
			SYNTAX INTEGER
				{
				enable(1),
				disable(2)
				}
			MAX-ACCESS read-write
			STATUS current
			DESCRIPTION
				"Description."
			::= { dhcpv6ServerInterface 6 }

		
--         1.3.6.1.4.1.37950.1.1.5.10.19.1.4
-- 1.3.6.1.4.1.37950.1.1.5.10.19.1.4
-- 1.3.6.1.4.1.37950.1.1.5.10.19.1.4
-- 1.3.6.1.4.1.37950.1.1.5.10.19.1.4
-- 1.3.6.1.4.1.37950.1.1.5.10.19.1.4
-- 1.3.6.1.4.1.37950.1.1.5.10.19.1.4
-- 1.3.6.1.4.1.37950.1.1.5.10.19.1.4
-- 1.3.6.1.4.1.37950.1.1.5.10.19.1.4
		-- 1.3.6.1.4.1.37950.1.1.5.10.19.1.4
		dhcpv6ServerInterfaceTable OBJECT-TYPE
			SYNTAX SEQUENCE OF Dhcpv6ServerInterfaceEntry
			MAX-ACCESS not-accessible
			STATUS current
			DESCRIPTION
				"Description."
			::= { dhcpv6Server 4 }

		
--         1.3.6.1.4.1.37950.1.1.5.10.19.1.4.1
-- 1.3.6.1.4.1.37950.1.1.5.10.19.1.4.1
-- 1.3.6.1.4.1.37950.1.1.5.10.19.1.4.1
-- 1.3.6.1.4.1.37950.1.1.5.10.19.1.4.1
-- 1.3.6.1.4.1.37950.1.1.5.10.19.1.4.1
-- 1.3.6.1.4.1.37950.1.1.5.10.19.1.4.1
-- 1.3.6.1.4.1.37950.1.1.5.10.19.1.4.1
-- 1.3.6.1.4.1.37950.1.1.5.10.19.1.4.1
		-- 1.3.6.1.4.1.37950.1.1.5.10.19.1.4.1
		dhcpv6ServerInterfaceEntry OBJECT-TYPE
			SYNTAX Dhcpv6ServerInterfaceEntry
			MAX-ACCESS not-accessible
			STATUS current
			DESCRIPTION
				"Description."
			INDEX { dhcpv6ServerBindingsClientInterfaceVlanId }
			::= { dhcpv6ServerInterfaceTable 1 }

		
		Dhcpv6ServerInterfaceEntry ::=
			SEQUENCE { 
				dhcpv6ServerBindingsClientInterfaceVlanId
					Integer32,
				dhcpv6ServerBindingsClientPoolName
					OCTET STRING,
				dhcpv6InterfacePreferenceValue
					Integer32,
				dhcpv6ServerAllowClientsHint
					INTEGER,
				dhcpv6ServerRapidCommit
					INTEGER
			 }

--         1.3.6.1.4.1.37950.1.1.5.10.19.1.4.1.1
-- 1.3.6.1.4.1.37950.1.1.5.10.19.1.4.1.1
-- 1.3.6.1.4.1.37950.1.1.5.10.19.1.4.1.1
-- 1.3.6.1.4.1.37950.1.1.5.10.19.1.4.1.1
-- 1.3.6.1.4.1.37950.1.1.5.10.19.1.4.1.1
-- 1.3.6.1.4.1.37950.1.1.5.10.19.1.4.1.1
-- 1.3.6.1.4.1.37950.1.1.5.10.19.1.4.1.1
-- 1.3.6.1.4.1.37950.1.1.5.10.19.1.4.1.1
		-- 1.3.6.1.4.1.37950.1.1.5.10.19.1.4.1.1
		dhcpv6ServerBindingsClientInterfaceVlanId OBJECT-TYPE
			SYNTAX Integer32
			MAX-ACCESS read-only
			STATUS current
			DESCRIPTION
				"Description."
			::= { dhcpv6ServerInterfaceEntry 1 }

		
--         1.3.6.1.4.1.37950.1.1.5.10.19.1.4.1.2
-- 1.3.6.1.4.1.37950.1.1.5.10.19.1.4.1.2
-- 1.3.6.1.4.1.37950.1.1.5.10.19.1.4.1.2
-- 1.3.6.1.4.1.37950.1.1.5.10.19.1.4.1.2
-- 1.3.6.1.4.1.37950.1.1.5.10.19.1.4.1.2
-- 1.3.6.1.4.1.37950.1.1.5.10.19.1.4.1.2
-- 1.3.6.1.4.1.37950.1.1.5.10.19.1.4.1.2
-- 1.3.6.1.4.1.37950.1.1.5.10.19.1.4.1.2
		-- 1.3.6.1.4.1.37950.1.1.5.10.19.1.4.1.2
		dhcpv6ServerBindingsClientPoolName OBJECT-TYPE
			SYNTAX OCTET STRING
			MAX-ACCESS read-only
			STATUS current
			DESCRIPTION
				"Description."
			::= { dhcpv6ServerInterfaceEntry 2 }

		
--         1.3.6.1.4.1.37950.1.1.5.10.19.1.4.1.3
-- 1.3.6.1.4.1.37950.1.1.5.10.19.1.4.1.3
-- 1.3.6.1.4.1.37950.1.1.5.10.19.1.4.1.3
-- 1.3.6.1.4.1.37950.1.1.5.10.19.1.4.1.3
-- 1.3.6.1.4.1.37950.1.1.5.10.19.1.4.1.3
-- 1.3.6.1.4.1.37950.1.1.5.10.19.1.4.1.3
-- 1.3.6.1.4.1.37950.1.1.5.10.19.1.4.1.3
-- 1.3.6.1.4.1.37950.1.1.5.10.19.1.4.1.3
		-- 1.3.6.1.4.1.37950.1.1.5.10.19.1.4.1.3
		dhcpv6InterfacePreferenceValue OBJECT-TYPE
			SYNTAX Integer32
			MAX-ACCESS read-only
			STATUS current
			DESCRIPTION
				"Description."
			::= { dhcpv6ServerInterfaceEntry 3 }

		
--         1.3.6.1.4.1.37950.1.1.5.10.19.1.4.1.4
-- 1.3.6.1.4.1.37950.1.1.5.10.19.1.4.1.4
-- 1.3.6.1.4.1.37950.1.1.5.10.19.1.4.1.4
-- 1.3.6.1.4.1.37950.1.1.5.10.19.1.4.1.4
-- 1.3.6.1.4.1.37950.1.1.5.10.19.1.4.1.4
-- 1.3.6.1.4.1.37950.1.1.5.10.19.1.4.1.4
-- 1.3.6.1.4.1.37950.1.1.5.10.19.1.4.1.4
-- 1.3.6.1.4.1.37950.1.1.5.10.19.1.4.1.4
		-- 1.3.6.1.4.1.37950.1.1.5.10.19.1.4.1.4
		dhcpv6ServerAllowClientsHint OBJECT-TYPE
			SYNTAX INTEGER
				{
				ignored(1),
				allow(2)
				}
			MAX-ACCESS read-write
			STATUS current
			DESCRIPTION
				"Description."
			::= { dhcpv6ServerInterfaceEntry 4 }

		
--         1.3.6.1.4.1.37950.1.1.5.10.19.1.4.1.5
-- 1.3.6.1.4.1.37950.1.1.5.10.19.1.4.1.5
-- 1.3.6.1.4.1.37950.1.1.5.10.19.1.4.1.5
-- 1.3.6.1.4.1.37950.1.1.5.10.19.1.4.1.5
-- 1.3.6.1.4.1.37950.1.1.5.10.19.1.4.1.5
-- 1.3.6.1.4.1.37950.1.1.5.10.19.1.4.1.5
-- 1.3.6.1.4.1.37950.1.1.5.10.19.1.4.1.5
-- 1.3.6.1.4.1.37950.1.1.5.10.19.1.4.1.5
		-- 1.3.6.1.4.1.37950.1.1.5.10.19.1.4.1.5
		dhcpv6ServerRapidCommit OBJECT-TYPE
			SYNTAX INTEGER
				{
				disabled(1),
				enabled(2)
				}
			MAX-ACCESS read-only
			STATUS current
			DESCRIPTION
				"Description."
			::= { dhcpv6ServerInterfaceEntry 5 }

		
--         1.3.6.1.4.1.37950.1.1.5.10.19.1.5
-- 1.3.6.1.4.1.37950.1.1.5.10.19.1.5
-- 1.3.6.1.4.1.37950.1.1.5.10.19.1.5
-- 1.3.6.1.4.1.37950.1.1.5.10.19.1.5
-- 1.3.6.1.4.1.37950.1.1.5.10.19.1.5
-- 1.3.6.1.4.1.37950.1.1.5.10.19.1.5
-- 1.3.6.1.4.1.37950.1.1.5.10.19.1.5
-- 1.3.6.1.4.1.37950.1.1.5.10.19.1.5
		-- 1.3.6.1.4.1.37950.1.1.5.10.19.1.5
		dhcpv6ServerBindingsTable OBJECT-TYPE
			SYNTAX SEQUENCE OF Dhcpv6ServerBindingsEntry
			MAX-ACCESS not-accessible
			STATUS current
			DESCRIPTION
				"Description."
			::= { dhcpv6Server 5 }

		
--         1.3.6.1.4.1.37950.1.1.5.10.19.1.5.1
-- 1.3.6.1.4.1.37950.1.1.5.10.19.1.5.1
-- 1.3.6.1.4.1.37950.1.1.5.10.19.1.5.1
-- 1.3.6.1.4.1.37950.1.1.5.10.19.1.5.1
-- 1.3.6.1.4.1.37950.1.1.5.10.19.1.5.1
-- 1.3.6.1.4.1.37950.1.1.5.10.19.1.5.1
-- 1.3.6.1.4.1.37950.1.1.5.10.19.1.5.1
-- 1.3.6.1.4.1.37950.1.1.5.10.19.1.5.1
		-- 1.3.6.1.4.1.37950.1.1.5.10.19.1.5.1
		dhcpv6ServerBindingsEntry OBJECT-TYPE
			SYNTAX Dhcpv6ServerBindingsEntry
			MAX-ACCESS not-accessible
			STATUS current
			DESCRIPTION
				"Description."
			INDEX { dhcpv6ServerBindingsindex }
			::= { dhcpv6ServerBindingsTable 1 }

		
		Dhcpv6ServerBindingsEntry ::=
			SEQUENCE { 
				dhcpv6ServerBindingsindex
					Integer32,
				dhcpv6ServerBindingsClientAddress
					OCTET STRING,
				dhcpv6ServerBindingsCLientDUID
					OCTET STRING,
				dhcpv6ServerBindingsClientPrefix
					OCTET STRING,
				dhcpv6ServerBindingsClientPfxValidTime
					Unsigned32,
				dhcpv6ServerBindingsClientPfxPreferrefTime
					Unsigned32,
				dhcpv6ServerBindingsLeaseExpireTime
					OCTET STRING
			 }

--         1.3.6.1.4.1.37950.1.1.5.10.19.1.5.1.1
-- 1.3.6.1.4.1.37950.1.1.5.10.19.1.5.1.1
-- 1.3.6.1.4.1.37950.1.1.5.10.19.1.5.1.1
-- 1.3.6.1.4.1.37950.1.1.5.10.19.1.5.1.1
-- 1.3.6.1.4.1.37950.1.1.5.10.19.1.5.1.1
-- 1.3.6.1.4.1.37950.1.1.5.10.19.1.5.1.1
-- 1.3.6.1.4.1.37950.1.1.5.10.19.1.5.1.1
-- 1.3.6.1.4.1.37950.1.1.5.10.19.1.5.1.1
		-- 1.3.6.1.4.1.37950.1.1.5.10.19.1.5.1.1
		dhcpv6ServerBindingsindex OBJECT-TYPE
			SYNTAX Integer32
			MAX-ACCESS read-write
			STATUS current
			DESCRIPTION
				"Description."
			::= { dhcpv6ServerBindingsEntry 1 }

		
--         1.3.6.1.4.1.37950.1.1.5.10.19.1.5.1.2
-- 1.3.6.1.4.1.37950.1.1.5.10.19.1.5.1.2
-- 1.3.6.1.4.1.37950.1.1.5.10.19.1.5.1.2
-- 1.3.6.1.4.1.37950.1.1.5.10.19.1.5.1.2
-- 1.3.6.1.4.1.37950.1.1.5.10.19.1.5.1.2
-- 1.3.6.1.4.1.37950.1.1.5.10.19.1.5.1.2
-- 1.3.6.1.4.1.37950.1.1.5.10.19.1.5.1.2
-- 1.3.6.1.4.1.37950.1.1.5.10.19.1.5.1.2
		-- 1.3.6.1.4.1.37950.1.1.5.10.19.1.5.1.2
		dhcpv6ServerBindingsClientAddress OBJECT-TYPE
			SYNTAX OCTET STRING
			MAX-ACCESS read-write
			STATUS current
			DESCRIPTION
				"Description."
			::= { dhcpv6ServerBindingsEntry 2 }

		
--         1.3.6.1.4.1.37950.1.1.5.10.19.1.5.1.3
-- 1.3.6.1.4.1.37950.1.1.5.10.19.1.5.1.3
-- 1.3.6.1.4.1.37950.1.1.5.10.19.1.5.1.3
-- 1.3.6.1.4.1.37950.1.1.5.10.19.1.5.1.3
-- 1.3.6.1.4.1.37950.1.1.5.10.19.1.5.1.3
-- 1.3.6.1.4.1.37950.1.1.5.10.19.1.5.1.3
-- 1.3.6.1.4.1.37950.1.1.5.10.19.1.5.1.3
-- 1.3.6.1.4.1.37950.1.1.5.10.19.1.5.1.3
		-- 1.3.6.1.4.1.37950.1.1.5.10.19.1.5.1.3
		dhcpv6ServerBindingsCLientDUID OBJECT-TYPE
			SYNTAX OCTET STRING
			MAX-ACCESS read-write
			STATUS current
			DESCRIPTION
				"Description."
			::= { dhcpv6ServerBindingsEntry 3 }

		
--         1.3.6.1.4.1.37950.1.1.5.10.19.1.5.1.4
-- 1.3.6.1.4.1.37950.1.1.5.10.19.1.5.1.4
-- 1.3.6.1.4.1.37950.1.1.5.10.19.1.5.1.4
-- 1.3.6.1.4.1.37950.1.1.5.10.19.1.5.1.4
-- 1.3.6.1.4.1.37950.1.1.5.10.19.1.5.1.4
-- 1.3.6.1.4.1.37950.1.1.5.10.19.1.5.1.4
-- 1.3.6.1.4.1.37950.1.1.5.10.19.1.5.1.4
-- 1.3.6.1.4.1.37950.1.1.5.10.19.1.5.1.4
		-- 1.3.6.1.4.1.37950.1.1.5.10.19.1.5.1.4
		dhcpv6ServerBindingsClientPrefix OBJECT-TYPE
			SYNTAX OCTET STRING
			MAX-ACCESS read-write
			STATUS current
			DESCRIPTION
				"Description."
			::= { dhcpv6ServerBindingsEntry 4 }

		
--         1.3.6.1.4.1.37950.1.1.5.10.19.1.5.1.5
-- 1.3.6.1.4.1.37950.1.1.5.10.19.1.5.1.5
-- 1.3.6.1.4.1.37950.1.1.5.10.19.1.5.1.5
-- 1.3.6.1.4.1.37950.1.1.5.10.19.1.5.1.5
-- 1.3.6.1.4.1.37950.1.1.5.10.19.1.5.1.5
-- 1.3.6.1.4.1.37950.1.1.5.10.19.1.5.1.5
-- 1.3.6.1.4.1.37950.1.1.5.10.19.1.5.1.5
-- 1.3.6.1.4.1.37950.1.1.5.10.19.1.5.1.5
		-- 1.3.6.1.4.1.37950.1.1.5.10.19.1.5.1.5
		dhcpv6ServerBindingsClientPfxValidTime OBJECT-TYPE
			SYNTAX Unsigned32
			MAX-ACCESS read-write
			STATUS current
			DESCRIPTION
				"Description."
			::= { dhcpv6ServerBindingsEntry 5 }

		
--         1.3.6.1.4.1.37950.1.1.5.10.19.1.5.1.6
-- 1.3.6.1.4.1.37950.1.1.5.10.19.1.5.1.6
-- 1.3.6.1.4.1.37950.1.1.5.10.19.1.5.1.6
-- 1.3.6.1.4.1.37950.1.1.5.10.19.1.5.1.6
-- 1.3.6.1.4.1.37950.1.1.5.10.19.1.5.1.6
-- 1.3.6.1.4.1.37950.1.1.5.10.19.1.5.1.6
-- 1.3.6.1.4.1.37950.1.1.5.10.19.1.5.1.6
-- 1.3.6.1.4.1.37950.1.1.5.10.19.1.5.1.6
		-- 1.3.6.1.4.1.37950.1.1.5.10.19.1.5.1.6
		dhcpv6ServerBindingsClientPfxPreferrefTime OBJECT-TYPE
			SYNTAX Unsigned32
			MAX-ACCESS read-write
			STATUS current
			DESCRIPTION
				"Description."
			::= { dhcpv6ServerBindingsEntry 6 }

		
--         1.3.6.1.4.1.37950.1.1.5.10.19.1.5.1.7
-- 1.3.6.1.4.1.37950.1.1.5.10.19.1.5.1.7
-- 1.3.6.1.4.1.37950.1.1.5.10.19.1.5.1.7
-- 1.3.6.1.4.1.37950.1.1.5.10.19.1.5.1.7
-- 1.3.6.1.4.1.37950.1.1.5.10.19.1.5.1.7
-- 1.3.6.1.4.1.37950.1.1.5.10.19.1.5.1.7
-- 1.3.6.1.4.1.37950.1.1.5.10.19.1.5.1.7
-- 1.3.6.1.4.1.37950.1.1.5.10.19.1.5.1.7
		-- 1.3.6.1.4.1.37950.1.1.5.10.19.1.5.1.7
		dhcpv6ServerBindingsLeaseExpireTime OBJECT-TYPE
			SYNTAX OCTET STRING
			MAX-ACCESS read-write
			STATUS current
			DESCRIPTION
				"Description."
			::= { dhcpv6ServerBindingsEntry 7 }

		
--         1.3.6.1.4.1.37950.1.1.5.10.19.1.6
-- 1.3.6.1.4.1.37950.1.1.5.10.19.1.6
-- 1.3.6.1.4.1.37950.1.1.5.10.19.1.6
-- 1.3.6.1.4.1.37950.1.1.5.10.19.1.6
-- 1.3.6.1.4.1.37950.1.1.5.10.19.1.6
-- 1.3.6.1.4.1.37950.1.1.5.10.19.1.6
-- 1.3.6.1.4.1.37950.1.1.5.10.19.1.6
-- 1.3.6.1.4.1.37950.1.1.5.10.19.1.6
		-- 1.3.6.1.4.1.37950.1.1.5.10.19.1.6
		dhcpv6Duid OBJECT IDENTIFIER ::= { dhcpv6Server 6 }

		
--         1.3.6.1.4.1.37950.1.1.5.10.19.1.6.1
-- 1.3.6.1.4.1.37950.1.1.5.10.19.1.6.1
-- 1.3.6.1.4.1.37950.1.1.5.10.19.1.6.1
-- 1.3.6.1.4.1.37950.1.1.5.10.19.1.6.1
-- 1.3.6.1.4.1.37950.1.1.5.10.19.1.6.1
-- 1.3.6.1.4.1.37950.1.1.5.10.19.1.6.1
-- 1.3.6.1.4.1.37950.1.1.5.10.19.1.6.1
-- 1.3.6.1.4.1.37950.1.1.5.10.19.1.6.1
		-- 1.3.6.1.4.1.37950.1.1.5.10.19.1.6.1
		dhcpv6DuidType OBJECT-TYPE
			SYNTAX INTEGER
				{
				duid-llt(1),
				duid-en(2),
				duid-ll(3)
				}
			MAX-ACCESS read-write
			STATUS current
			DESCRIPTION
				"Description."
			::= { dhcpv6Duid 1 }

		
--         1.3.6.1.4.1.37950.1.1.5.10.19.1.6.2
-- 1.3.6.1.4.1.37950.1.1.5.10.19.1.6.2
-- 1.3.6.1.4.1.37950.1.1.5.10.19.1.6.2
-- 1.3.6.1.4.1.37950.1.1.5.10.19.1.6.2
-- 1.3.6.1.4.1.37950.1.1.5.10.19.1.6.2
-- 1.3.6.1.4.1.37950.1.1.5.10.19.1.6.2
-- 1.3.6.1.4.1.37950.1.1.5.10.19.1.6.2
-- 1.3.6.1.4.1.37950.1.1.5.10.19.1.6.2
		-- 1.3.6.1.4.1.37950.1.1.5.10.19.1.6.2
		dhcpv6DuidEnterprise OBJECT-TYPE
			SYNTAX OCTET STRING
			MAX-ACCESS read-write
			STATUS current
			DESCRIPTION
				"Description."
			::= { dhcpv6Duid 2 }

		
--         1.3.6.1.4.1.37950.1.1.5.10.19.1.6.3
-- 1.3.6.1.4.1.37950.1.1.5.10.19.1.6.3
-- 1.3.6.1.4.1.37950.1.1.5.10.19.1.6.3
-- 1.3.6.1.4.1.37950.1.1.5.10.19.1.6.3
-- 1.3.6.1.4.1.37950.1.1.5.10.19.1.6.3
-- 1.3.6.1.4.1.37950.1.1.5.10.19.1.6.3
-- 1.3.6.1.4.1.37950.1.1.5.10.19.1.6.3
-- 1.3.6.1.4.1.37950.1.1.5.10.19.1.6.3
		-- 1.3.6.1.4.1.37950.1.1.5.10.19.1.6.3
		dhcpv6DuidIdentifier OBJECT-TYPE
			SYNTAX OCTET STRING
			MAX-ACCESS read-write
			STATUS current
			DESCRIPTION
				"Description."
			::= { dhcpv6Duid 3 }

		
--         1.3.6.1.4.1.37950.1.1.5.10.19.1.6.4
-- 1.3.6.1.4.1.37950.1.1.5.10.19.1.6.4
-- 1.3.6.1.4.1.37950.1.1.5.10.19.1.6.4
-- 1.3.6.1.4.1.37950.1.1.5.10.19.1.6.4
-- 1.3.6.1.4.1.37950.1.1.5.10.19.1.6.4
-- 1.3.6.1.4.1.37950.1.1.5.10.19.1.6.4
-- 1.3.6.1.4.1.37950.1.1.5.10.19.1.6.4
-- 1.3.6.1.4.1.37950.1.1.5.10.19.1.6.4
		-- 1.3.6.1.4.1.37950.1.1.5.10.19.1.6.4
		dhcpv6DuidAction OBJECT-TYPE
			SYNTAX INTEGER { submit(1) }
			MAX-ACCESS read-write
			STATUS current
			DESCRIPTION
				"Description."
			::= { dhcpv6Duid 4 }

		
--         1.3.6.1.4.1.37950.1.1.5.10.19.1.7
-- 1.3.6.1.4.1.37950.1.1.5.10.19.1.7
-- 1.3.6.1.4.1.37950.1.1.5.10.19.1.7
-- 1.3.6.1.4.1.37950.1.1.5.10.19.1.7
-- 1.3.6.1.4.1.37950.1.1.5.10.19.1.7
-- 1.3.6.1.4.1.37950.1.1.5.10.19.1.7
-- 1.3.6.1.4.1.37950.1.1.5.10.19.1.7
-- 1.3.6.1.4.1.37950.1.1.5.10.19.1.7
		-- 1.3.6.1.4.1.37950.1.1.5.10.19.1.7
		dhcpv6DuidTable OBJECT-TYPE
			SYNTAX SEQUENCE OF Dhcpv6DuidEntry
			MAX-ACCESS not-accessible
			STATUS current
			DESCRIPTION
				"Description."
			::= { dhcpv6Server 7 }

		
--         1.3.6.1.4.1.37950.1.1.5.10.19.1.7.1
-- 1.3.6.1.4.1.37950.1.1.5.10.19.1.7.1
-- 1.3.6.1.4.1.37950.1.1.5.10.19.1.7.1
-- 1.3.6.1.4.1.37950.1.1.5.10.19.1.7.1
-- 1.3.6.1.4.1.37950.1.1.5.10.19.1.7.1
-- 1.3.6.1.4.1.37950.1.1.5.10.19.1.7.1
-- 1.3.6.1.4.1.37950.1.1.5.10.19.1.7.1
-- 1.3.6.1.4.1.37950.1.1.5.10.19.1.7.1
		-- 1.3.6.1.4.1.37950.1.1.5.10.19.1.7.1
		dhcpv6DuidEntry OBJECT-TYPE
			SYNTAX Dhcpv6DuidEntry
			MAX-ACCESS not-accessible
			STATUS current
			DESCRIPTION
				"Description."
			INDEX { dhcpv6DuidTableDuidType }
			::= { dhcpv6DuidTable 1 }

		
		Dhcpv6DuidEntry ::=
			SEQUENCE { 
				dhcpv6DuidTableDuidType
					OCTET STRING,
				dhcpv6DuidTableDuid
					OCTET STRING
			 }

--         1.3.6.1.4.1.37950.1.1.5.10.19.1.7.1.1
-- 1.3.6.1.4.1.37950.1.1.5.10.19.1.7.1.1
-- 1.3.6.1.4.1.37950.1.1.5.10.19.1.7.1.1
-- 1.3.6.1.4.1.37950.1.1.5.10.19.1.7.1.1
-- 1.3.6.1.4.1.37950.1.1.5.10.19.1.7.1.1
-- 1.3.6.1.4.1.37950.1.1.5.10.19.1.7.1.1
-- 1.3.6.1.4.1.37950.1.1.5.10.19.1.7.1.1
-- 1.3.6.1.4.1.37950.1.1.5.10.19.1.7.1.1
		-- 1.3.6.1.4.1.37950.1.1.5.10.19.1.7.1.1
		dhcpv6DuidTableDuidType OBJECT-TYPE
			SYNTAX OCTET STRING
			MAX-ACCESS read-only
			STATUS current
			DESCRIPTION
				"Description."
			::= { dhcpv6DuidEntry 1 }

		
--         1.3.6.1.4.1.37950.1.1.5.10.19.1.7.1.2
-- 1.3.6.1.4.1.37950.1.1.5.10.19.1.7.1.2
-- 1.3.6.1.4.1.37950.1.1.5.10.19.1.7.1.2
-- 1.3.6.1.4.1.37950.1.1.5.10.19.1.7.1.2
-- 1.3.6.1.4.1.37950.1.1.5.10.19.1.7.1.2
-- 1.3.6.1.4.1.37950.1.1.5.10.19.1.7.1.2
-- 1.3.6.1.4.1.37950.1.1.5.10.19.1.7.1.2
-- 1.3.6.1.4.1.37950.1.1.5.10.19.1.7.1.2
		-- 1.3.6.1.4.1.37950.1.1.5.10.19.1.7.1.2
		dhcpv6DuidTableDuid OBJECT-TYPE
			SYNTAX OCTET STRING
			MAX-ACCESS read-only
			STATUS current
			DESCRIPTION
				"Description."
			::= { dhcpv6DuidEntry 2 }

		
--         1.3.6.1.4.1.37950.1.1.5.10.19.2
-- 1.3.6.1.4.1.37950.1.1.5.10.19.2
-- 1.3.6.1.4.1.37950.1.1.5.10.19.2
-- 1.3.6.1.4.1.37950.1.1.5.10.19.2
-- 1.3.6.1.4.1.37950.1.1.5.10.19.2
-- 1.3.6.1.4.1.37950.1.1.5.10.19.2
-- 1.3.6.1.4.1.37950.1.1.5.10.19.2
-- 1.3.6.1.4.1.37950.1.1.5.10.19.2
		-- 1.3.6.1.4.1.37950.1.1.5.10.19.2
		dhcpv6Relay OBJECT IDENTIFIER ::= { v1600dDHCPv6 2 }

		
--         1.3.6.1.4.1.37950.1.1.5.10.19.2.1
-- 1.3.6.1.4.1.37950.1.1.5.10.19.2.1
-- 1.3.6.1.4.1.37950.1.1.5.10.19.2.1
-- 1.3.6.1.4.1.37950.1.1.5.10.19.2.1
-- 1.3.6.1.4.1.37950.1.1.5.10.19.2.1
-- 1.3.6.1.4.1.37950.1.1.5.10.19.2.1
-- 1.3.6.1.4.1.37950.1.1.5.10.19.2.1
-- 1.3.6.1.4.1.37950.1.1.5.10.19.2.1
		-- 1.3.6.1.4.1.37950.1.1.5.10.19.2.1
		dhcpv6RelayCfg OBJECT IDENTIFIER ::= { dhcpv6Relay 1 }

		
--         1.3.6.1.4.1.37950.1.1.5.10.19.2.1.1
-- 1.3.6.1.4.1.37950.1.1.5.10.19.2.1.1
-- 1.3.6.1.4.1.37950.1.1.5.10.19.2.1.1
-- 1.3.6.1.4.1.37950.1.1.5.10.19.2.1.1
-- 1.3.6.1.4.1.37950.1.1.5.10.19.2.1.1
-- 1.3.6.1.4.1.37950.1.1.5.10.19.2.1.1
-- 1.3.6.1.4.1.37950.1.1.5.10.19.2.1.1
-- 1.3.6.1.4.1.37950.1.1.5.10.19.2.1.1
		-- 1.3.6.1.4.1.37950.1.1.5.10.19.2.1.1
		dhcpv6RelayServerVlanId OBJECT-TYPE
			SYNTAX Integer32
			MAX-ACCESS read-write
			STATUS current
			DESCRIPTION
				"Description."
			::= { dhcpv6RelayCfg 1 }

		
--         1.3.6.1.4.1.37950.1.1.5.10.19.2.1.2
-- 1.3.6.1.4.1.37950.1.1.5.10.19.2.1.2
-- 1.3.6.1.4.1.37950.1.1.5.10.19.2.1.2
-- 1.3.6.1.4.1.37950.1.1.5.10.19.2.1.2
-- 1.3.6.1.4.1.37950.1.1.5.10.19.2.1.2
-- 1.3.6.1.4.1.37950.1.1.5.10.19.2.1.2
-- 1.3.6.1.4.1.37950.1.1.5.10.19.2.1.2
-- 1.3.6.1.4.1.37950.1.1.5.10.19.2.1.2
		-- 1.3.6.1.4.1.37950.1.1.5.10.19.2.1.2
		dhcpv6RelayServerAddr OBJECT-TYPE
			SYNTAX OCTET STRING
			MAX-ACCESS read-write
			STATUS current
			DESCRIPTION
				"Description."
			::= { dhcpv6RelayCfg 2 }

		
--         1.3.6.1.4.1.37950.1.1.5.10.19.2.1.3
-- 1.3.6.1.4.1.37950.1.1.5.10.19.2.1.3
-- 1.3.6.1.4.1.37950.1.1.5.10.19.2.1.3
-- 1.3.6.1.4.1.37950.1.1.5.10.19.2.1.3
-- 1.3.6.1.4.1.37950.1.1.5.10.19.2.1.3
-- 1.3.6.1.4.1.37950.1.1.5.10.19.2.1.3
-- 1.3.6.1.4.1.37950.1.1.5.10.19.2.1.3
-- 1.3.6.1.4.1.37950.1.1.5.10.19.2.1.3
		-- 1.3.6.1.4.1.37950.1.1.5.10.19.2.1.3
		dhcpv6RelayServerAction OBJECT-TYPE
			SYNTAX INTEGER
				{
				add(1),
				del(2)
				}
			MAX-ACCESS read-write
			STATUS current
			DESCRIPTION
				"Description."
			::= { dhcpv6RelayCfg 3 }

		
--         1.3.6.1.4.1.37950.1.1.5.10.19.2.2
-- 1.3.6.1.4.1.37950.1.1.5.10.19.2.2
-- 1.3.6.1.4.1.37950.1.1.5.10.19.2.2
-- 1.3.6.1.4.1.37950.1.1.5.10.19.2.2
-- 1.3.6.1.4.1.37950.1.1.5.10.19.2.2
-- 1.3.6.1.4.1.37950.1.1.5.10.19.2.2
-- 1.3.6.1.4.1.37950.1.1.5.10.19.2.2
-- 1.3.6.1.4.1.37950.1.1.5.10.19.2.2
		-- 1.3.6.1.4.1.37950.1.1.5.10.19.2.2
		dhcpv6RelayServerTable OBJECT-TYPE
			SYNTAX SEQUENCE OF Dhcpv6RelayServerEntry
			MAX-ACCESS not-accessible
			STATUS current
			DESCRIPTION
				"Description."
			::= { dhcpv6Relay 2 }

		
--         1.3.6.1.4.1.37950.1.1.5.10.19.2.2.1
-- 1.3.6.1.4.1.37950.1.1.5.10.19.2.2.1
-- 1.3.6.1.4.1.37950.1.1.5.10.19.2.2.1
-- 1.3.6.1.4.1.37950.1.1.5.10.19.2.2.1
-- 1.3.6.1.4.1.37950.1.1.5.10.19.2.2.1
-- 1.3.6.1.4.1.37950.1.1.5.10.19.2.2.1
-- 1.3.6.1.4.1.37950.1.1.5.10.19.2.2.1
-- 1.3.6.1.4.1.37950.1.1.5.10.19.2.2.1
		-- 1.3.6.1.4.1.37950.1.1.5.10.19.2.2.1
		dhcpv6RelayServerEntry OBJECT-TYPE
			SYNTAX Dhcpv6RelayServerEntry
			MAX-ACCESS not-accessible
			STATUS current
			DESCRIPTION
				"Description."
			INDEX { dhcpv6RelayServerVlanID }
			::= { dhcpv6RelayServerTable 1 }

		
		Dhcpv6RelayServerEntry ::=
			SEQUENCE { 
				dhcpv6RelayServerVlanID
					Integer32,
				dhcpv6RelayServerAddress
					OCTET STRING
			 }

--         1.3.6.1.4.1.37950.1.1.5.10.19.2.2.1.1
-- 1.3.6.1.4.1.37950.1.1.5.10.19.2.2.1.1
-- 1.3.6.1.4.1.37950.1.1.5.10.19.2.2.1.1
-- 1.3.6.1.4.1.37950.1.1.5.10.19.2.2.1.1
-- 1.3.6.1.4.1.37950.1.1.5.10.19.2.2.1.1
-- 1.3.6.1.4.1.37950.1.1.5.10.19.2.2.1.1
-- 1.3.6.1.4.1.37950.1.1.5.10.19.2.2.1.1
-- 1.3.6.1.4.1.37950.1.1.5.10.19.2.2.1.1
		-- 1.3.6.1.4.1.37950.1.1.5.10.19.2.2.1.1
		dhcpv6RelayServerVlanID OBJECT-TYPE
			SYNTAX Integer32
			MAX-ACCESS read-write
			STATUS current
			DESCRIPTION
				"Description."
			::= { dhcpv6RelayServerEntry 1 }

		
--         1.3.6.1.4.1.37950.1.1.5.10.19.2.2.1.2
-- 1.3.6.1.4.1.37950.1.1.5.10.19.2.2.1.2
-- 1.3.6.1.4.1.37950.1.1.5.10.19.2.2.1.2
-- 1.3.6.1.4.1.37950.1.1.5.10.19.2.2.1.2
-- 1.3.6.1.4.1.37950.1.1.5.10.19.2.2.1.2
-- 1.3.6.1.4.1.37950.1.1.5.10.19.2.2.1.2
-- 1.3.6.1.4.1.37950.1.1.5.10.19.2.2.1.2
-- 1.3.6.1.4.1.37950.1.1.5.10.19.2.2.1.2
		-- 1.3.6.1.4.1.37950.1.1.5.10.19.2.2.1.2
		dhcpv6RelayServerAddress OBJECT-TYPE
			SYNTAX OCTET STRING
			MAX-ACCESS read-write
			STATUS current
			DESCRIPTION
				"Description."
			::= { dhcpv6RelayServerEntry 2 }

		
--           1.3.6.1.4.1.37950.1.1.5.10.19.3
-- 1.3.6.1.4.1.37950.1.1.5.10.19.3
-- 1.3.6.1.4.1.37950.1.1.5.10.19.3
-- 1.3.6.1.4.1.37950.1.1.5.10.19.3
-- 1.3.6.1.4.1.37950.1.1.5.10.19.3
-- 1.3.6.1.4.1.37950.1.1.5.10.19.3
-- 1.3.6.1.4.1.37950.1.1.5.10.19.3
-- 1.3.6.1.4.1.37950.1.1.5.10.19.3
-- 1.3.6.1.4.1.37950.1.1.5.10.19.3
-- 1.3.6.1.4.1.37950.1.1.5.10.19.3
		-- 1.3.6.1.4.1.37950.1.1.5.10.19.3
		dhcp6Snooping OBJECT IDENTIFIER ::= { v1600dDHCPv6 3 }

		
--           1.3.6.1.4.1.37950.1.1.5.10.19.3.1
-- 1.3.6.1.4.1.37950.1.1.5.10.19.3.1
-- 1.3.6.1.4.1.37950.1.1.5.10.19.3.1
-- 1.3.6.1.4.1.37950.1.1.5.10.19.3.1
-- 1.3.6.1.4.1.37950.1.1.5.10.19.3.1
-- 1.3.6.1.4.1.37950.1.1.5.10.19.3.1
-- 1.3.6.1.4.1.37950.1.1.5.10.19.3.1
-- 1.3.6.1.4.1.37950.1.1.5.10.19.3.1
-- 1.3.6.1.4.1.37950.1.1.5.10.19.3.1
-- 1.3.6.1.4.1.37950.1.1.5.10.19.3.1
		-- 1.3.6.1.4.1.37950.1.1.5.10.19.3.1
		dhcp6SnoopingEnable OBJECT-TYPE
			SYNTAX INTEGER
				{
				disable(0),
				enable(1)
				}
			MAX-ACCESS read-write
			STATUS current
			DESCRIPTION
				"Description."
			::= { dhcp6Snooping 1 }

		
--           1.3.6.1.4.1.37950.1.1.5.10.19.3.2
-- 1.3.6.1.4.1.37950.1.1.5.10.19.3.2
-- 1.3.6.1.4.1.37950.1.1.5.10.19.3.2
-- 1.3.6.1.4.1.37950.1.1.5.10.19.3.2
-- 1.3.6.1.4.1.37950.1.1.5.10.19.3.2
-- 1.3.6.1.4.1.37950.1.1.5.10.19.3.2
-- 1.3.6.1.4.1.37950.1.1.5.10.19.3.2
-- 1.3.6.1.4.1.37950.1.1.5.10.19.3.2
-- 1.3.6.1.4.1.37950.1.1.5.10.19.3.2
-- 1.3.6.1.4.1.37950.1.1.5.10.19.3.2
		-- 1.3.6.1.4.1.37950.1.1.5.10.19.3.2
		dhcp6SnoopingVLAN OBJECT IDENTIFIER ::= { dhcp6Snooping 2 }

		
--           1.3.6.1.4.1.37950.1.1.5.10.19.3.2.1
-- 1.3.6.1.4.1.37950.1.1.5.10.19.3.2.1
-- 1.3.6.1.4.1.37950.1.1.5.10.19.3.2.1
-- 1.3.6.1.4.1.37950.1.1.5.10.19.3.2.1
-- 1.3.6.1.4.1.37950.1.1.5.10.19.3.2.1
-- 1.3.6.1.4.1.37950.1.1.5.10.19.3.2.1
-- 1.3.6.1.4.1.37950.1.1.5.10.19.3.2.1
-- 1.3.6.1.4.1.37950.1.1.5.10.19.3.2.1
-- 1.3.6.1.4.1.37950.1.1.5.10.19.3.2.1
-- 1.3.6.1.4.1.37950.1.1.5.10.19.3.2.1
		-- 1.3.6.1.4.1.37950.1.1.5.10.19.3.2.1
		dhcp6SnoopingVLANID OBJECT-TYPE
			SYNTAX Integer32 (1..4095)
			MAX-ACCESS read-write
			STATUS current
			DESCRIPTION
				"Description."
			::= { dhcp6SnoopingVLAN 1 }

		
--           1.3.6.1.4.1.37950.1.1.5.10.19.3.2.2
-- 1.3.6.1.4.1.37950.1.1.5.10.19.3.2.2
-- 1.3.6.1.4.1.37950.1.1.5.10.19.3.2.2
-- 1.3.6.1.4.1.37950.1.1.5.10.19.3.2.2
-- 1.3.6.1.4.1.37950.1.1.5.10.19.3.2.2
-- 1.3.6.1.4.1.37950.1.1.5.10.19.3.2.2
-- 1.3.6.1.4.1.37950.1.1.5.10.19.3.2.2
-- 1.3.6.1.4.1.37950.1.1.5.10.19.3.2.2
-- 1.3.6.1.4.1.37950.1.1.5.10.19.3.2.2
-- 1.3.6.1.4.1.37950.1.1.5.10.19.3.2.2
		-- 1.3.6.1.4.1.37950.1.1.5.10.19.3.2.2
		dhcp6SnoopingVLANAction OBJECT-TYPE
			SYNTAX INTEGER
				{
				del(0),
				add(1)
				}
			MAX-ACCESS read-write
			STATUS current
			DESCRIPTION
				"Description."
			::= { dhcp6SnoopingVLAN 2 }

		
--           1.3.6.1.4.1.37950.1.1.5.10.19.3.2.3
-- 1.3.6.1.4.1.37950.1.1.5.10.19.3.2.3
-- 1.3.6.1.4.1.37950.1.1.5.10.19.3.2.3
-- 1.3.6.1.4.1.37950.1.1.5.10.19.3.2.3
-- 1.3.6.1.4.1.37950.1.1.5.10.19.3.2.3
-- 1.3.6.1.4.1.37950.1.1.5.10.19.3.2.3
-- 1.3.6.1.4.1.37950.1.1.5.10.19.3.2.3
-- 1.3.6.1.4.1.37950.1.1.5.10.19.3.2.3
-- 1.3.6.1.4.1.37950.1.1.5.10.19.3.2.3
-- 1.3.6.1.4.1.37950.1.1.5.10.19.3.2.3
		-- 1.3.6.1.4.1.37950.1.1.5.10.19.3.2.3
		dhcp6SnoopingVLANList OBJECT-TYPE
			SYNTAX OCTET STRING
			MAX-ACCESS read-only
			STATUS current
			DESCRIPTION
				"Description."
			::= { dhcp6SnoopingVLAN 3 }

		
--           1.3.6.1.4.1.37950.1.1.5.10.19.3.3
-- 1.3.6.1.4.1.37950.1.1.5.10.19.3.3
-- 1.3.6.1.4.1.37950.1.1.5.10.19.3.3
-- 1.3.6.1.4.1.37950.1.1.5.10.19.3.3
-- 1.3.6.1.4.1.37950.1.1.5.10.19.3.3
-- 1.3.6.1.4.1.37950.1.1.5.10.19.3.3
-- 1.3.6.1.4.1.37950.1.1.5.10.19.3.3
-- 1.3.6.1.4.1.37950.1.1.5.10.19.3.3
-- 1.3.6.1.4.1.37950.1.1.5.10.19.3.3
-- 1.3.6.1.4.1.37950.1.1.5.10.19.3.3
		-- 1.3.6.1.4.1.37950.1.1.5.10.19.3.3
		dhcp6SnoopingOption OBJECT IDENTIFIER ::= { dhcp6Snooping 3 }

		
--           1.3.6.1.4.1.37950.1.1.5.10.19.3.3.1
-- 1.3.6.1.4.1.37950.1.1.5.10.19.3.3.1
-- 1.3.6.1.4.1.37950.1.1.5.10.19.3.3.1
-- 1.3.6.1.4.1.37950.1.1.5.10.19.3.3.1
-- 1.3.6.1.4.1.37950.1.1.5.10.19.3.3.1
-- 1.3.6.1.4.1.37950.1.1.5.10.19.3.3.1
-- 1.3.6.1.4.1.37950.1.1.5.10.19.3.3.1
-- 1.3.6.1.4.1.37950.1.1.5.10.19.3.3.1
-- 1.3.6.1.4.1.37950.1.1.5.10.19.3.3.1
-- 1.3.6.1.4.1.37950.1.1.5.10.19.3.3.1
		-- 1.3.6.1.4.1.37950.1.1.5.10.19.3.3.1
		dhcp6SnoopingOptionInterfaceEnable OBJECT-TYPE
			SYNTAX INTEGER
				{
				disable(0),
				enable(1)
				}
			MAX-ACCESS read-write
			STATUS current
			DESCRIPTION
				"Description."
			::= { dhcp6SnoopingOption 1 }

		
--           1.3.6.1.4.1.37950.1.1.5.10.19.3.3.2
-- 1.3.6.1.4.1.37950.1.1.5.10.19.3.3.2
-- 1.3.6.1.4.1.37950.1.1.5.10.19.3.3.2
-- 1.3.6.1.4.1.37950.1.1.5.10.19.3.3.2
-- 1.3.6.1.4.1.37950.1.1.5.10.19.3.3.2
-- 1.3.6.1.4.1.37950.1.1.5.10.19.3.3.2
-- 1.3.6.1.4.1.37950.1.1.5.10.19.3.3.2
-- 1.3.6.1.4.1.37950.1.1.5.10.19.3.3.2
-- 1.3.6.1.4.1.37950.1.1.5.10.19.3.3.2
-- 1.3.6.1.4.1.37950.1.1.5.10.19.3.3.2
		-- 1.3.6.1.4.1.37950.1.1.5.10.19.3.3.2
		dhcp6SnoopingOptionInterfacePolicy OBJECT-TYPE
			SYNTAX INTEGER
				{
				drop(0),
				keep(1),
				replace(2)
				}
			MAX-ACCESS read-write
			STATUS current
			DESCRIPTION
				"Description."
			::= { dhcp6SnoopingOption 2 }

		
--           1.3.6.1.4.1.37950.1.1.5.10.19.3.3.3
-- 1.3.6.1.4.1.37950.1.1.5.10.19.3.3.3
-- 1.3.6.1.4.1.37950.1.1.5.10.19.3.3.3
-- 1.3.6.1.4.1.37950.1.1.5.10.19.3.3.3
-- 1.3.6.1.4.1.37950.1.1.5.10.19.3.3.3
-- 1.3.6.1.4.1.37950.1.1.5.10.19.3.3.3
-- 1.3.6.1.4.1.37950.1.1.5.10.19.3.3.3
-- 1.3.6.1.4.1.37950.1.1.5.10.19.3.3.3
-- 1.3.6.1.4.1.37950.1.1.5.10.19.3.3.3
-- 1.3.6.1.4.1.37950.1.1.5.10.19.3.3.3
		-- 1.3.6.1.4.1.37950.1.1.5.10.19.3.3.3
		dhcp6SnoopingOptionRemoteEnable OBJECT-TYPE
			SYNTAX INTEGER
				{
				disable(0),
				enable(1)
				}
			MAX-ACCESS read-write
			STATUS current
			DESCRIPTION
				"Description."
			::= { dhcp6SnoopingOption 3 }

		
--           1.3.6.1.4.1.37950.1.1.5.10.19.3.3.4
-- 1.3.6.1.4.1.37950.1.1.5.10.19.3.3.4
-- 1.3.6.1.4.1.37950.1.1.5.10.19.3.3.4
-- 1.3.6.1.4.1.37950.1.1.5.10.19.3.3.4
-- 1.3.6.1.4.1.37950.1.1.5.10.19.3.3.4
-- 1.3.6.1.4.1.37950.1.1.5.10.19.3.3.4
-- 1.3.6.1.4.1.37950.1.1.5.10.19.3.3.4
-- 1.3.6.1.4.1.37950.1.1.5.10.19.3.3.4
-- 1.3.6.1.4.1.37950.1.1.5.10.19.3.3.4
-- 1.3.6.1.4.1.37950.1.1.5.10.19.3.3.4
		-- 1.3.6.1.4.1.37950.1.1.5.10.19.3.3.4
		dhcp6SnoopingOptionRemotePolicy OBJECT-TYPE
			SYNTAX INTEGER
				{
				drop(0),
				keep(1),
				replace(2)
				}
			MAX-ACCESS read-write
			STATUS current
			DESCRIPTION
				"Description."
			::= { dhcp6SnoopingOption 4 }

		
--           1.3.6.1.4.1.37950.1.1.5.10.19.3.3.5
-- 1.3.6.1.4.1.37950.1.1.5.10.19.3.3.5
-- 1.3.6.1.4.1.37950.1.1.5.10.19.3.3.5
-- 1.3.6.1.4.1.37950.1.1.5.10.19.3.3.5
-- 1.3.6.1.4.1.37950.1.1.5.10.19.3.3.5
-- 1.3.6.1.4.1.37950.1.1.5.10.19.3.3.5
-- 1.3.6.1.4.1.37950.1.1.5.10.19.3.3.5
-- 1.3.6.1.4.1.37950.1.1.5.10.19.3.3.5
-- 1.3.6.1.4.1.37950.1.1.5.10.19.3.3.5
-- 1.3.6.1.4.1.37950.1.1.5.10.19.3.3.5
		-- 1.3.6.1.4.1.37950.1.1.5.10.19.3.3.5
		dhcp6SnoopingOptionSubscriberEnable OBJECT-TYPE
			SYNTAX INTEGER
				{
				disable(0),
				enable(1)
				}
			MAX-ACCESS read-write
			STATUS current
			DESCRIPTION
				"Description."
			::= { dhcp6SnoopingOption 5 }

		
--           1.3.6.1.4.1.37950.1.1.5.10.19.3.3.6
-- 1.3.6.1.4.1.37950.1.1.5.10.19.3.3.6
-- 1.3.6.1.4.1.37950.1.1.5.10.19.3.3.6
-- 1.3.6.1.4.1.37950.1.1.5.10.19.3.3.6
-- 1.3.6.1.4.1.37950.1.1.5.10.19.3.3.6
-- 1.3.6.1.4.1.37950.1.1.5.10.19.3.3.6
-- 1.3.6.1.4.1.37950.1.1.5.10.19.3.3.6
-- 1.3.6.1.4.1.37950.1.1.5.10.19.3.3.6
-- 1.3.6.1.4.1.37950.1.1.5.10.19.3.3.6
-- 1.3.6.1.4.1.37950.1.1.5.10.19.3.3.6
		-- 1.3.6.1.4.1.37950.1.1.5.10.19.3.3.6
		dhcp6SnoopingOptionSubscriberPolicy OBJECT-TYPE
			SYNTAX INTEGER
				{
				drop(0),
				keep(1),
				replace(2)
				}
			MAX-ACCESS read-write
			STATUS current
			DESCRIPTION
				"Description."
			::= { dhcp6SnoopingOption 6 }

		
--           1.3.6.1.4.1.37950.1.1.5.10.19.3.3.7
-- 1.3.6.1.4.1.37950.1.1.5.10.19.3.3.7
-- 1.3.6.1.4.1.37950.1.1.5.10.19.3.3.7
-- 1.3.6.1.4.1.37950.1.1.5.10.19.3.3.7
-- 1.3.6.1.4.1.37950.1.1.5.10.19.3.3.7
-- 1.3.6.1.4.1.37950.1.1.5.10.19.3.3.7
-- 1.3.6.1.4.1.37950.1.1.5.10.19.3.3.7
-- 1.3.6.1.4.1.37950.1.1.5.10.19.3.3.7
-- 1.3.6.1.4.1.37950.1.1.5.10.19.3.3.7
-- 1.3.6.1.4.1.37950.1.1.5.10.19.3.3.7
		-- 1.3.6.1.4.1.37950.1.1.5.10.19.3.3.7
		dhcp6SnoopingOptionAction OBJECT-TYPE
			SYNTAX INTEGER { change(1) }
			MAX-ACCESS read-write
			STATUS current
			DESCRIPTION
				"Description."
			::= { dhcp6SnoopingOption 7 }

		
--           1.3.6.1.4.1.37950.1.1.5.10.19.3.4
-- 1.3.6.1.4.1.37950.1.1.5.10.19.3.4
-- 1.3.6.1.4.1.37950.1.1.5.10.19.3.4
-- 1.3.6.1.4.1.37950.1.1.5.10.19.3.4
-- 1.3.6.1.4.1.37950.1.1.5.10.19.3.4
-- 1.3.6.1.4.1.37950.1.1.5.10.19.3.4
-- 1.3.6.1.4.1.37950.1.1.5.10.19.3.4
-- 1.3.6.1.4.1.37950.1.1.5.10.19.3.4
-- 1.3.6.1.4.1.37950.1.1.5.10.19.3.4
-- 1.3.6.1.4.1.37950.1.1.5.10.19.3.4
		-- 1.3.6.1.4.1.37950.1.1.5.10.19.3.4
		dhcp6SnoopingPortCfgTable OBJECT-TYPE
			SYNTAX SEQUENCE OF Dhcp6SnoopingPortCfgEntry
			MAX-ACCESS not-accessible
			STATUS current
			DESCRIPTION
				"Description."
			::= { dhcp6Snooping 4 }

		
--           1.3.6.1.4.1.37950.1.1.5.10.19.3.4.1
-- 1.3.6.1.4.1.37950.1.1.5.10.19.3.4.1
-- 1.3.6.1.4.1.37950.1.1.5.10.19.3.4.1
-- 1.3.6.1.4.1.37950.1.1.5.10.19.3.4.1
-- 1.3.6.1.4.1.37950.1.1.5.10.19.3.4.1
-- 1.3.6.1.4.1.37950.1.1.5.10.19.3.4.1
-- 1.3.6.1.4.1.37950.1.1.5.10.19.3.4.1
-- 1.3.6.1.4.1.37950.1.1.5.10.19.3.4.1
-- 1.3.6.1.4.1.37950.1.1.5.10.19.3.4.1
-- 1.3.6.1.4.1.37950.1.1.5.10.19.3.4.1
		-- 1.3.6.1.4.1.37950.1.1.5.10.19.3.4.1
		dhcp6SnoopingPortCfgEntry OBJECT-TYPE
			SYNTAX Dhcp6SnoopingPortCfgEntry
			MAX-ACCESS not-accessible
			STATUS current
			DESCRIPTION
				"Description."
			INDEX { dhcp6SnoopingPortIndex }
			::= { dhcp6SnoopingPortCfgTable 1 }

		
		Dhcp6SnoopingPortCfgEntry ::=
			SEQUENCE { 
				dhcp6SnoopingPortIndex
					Integer32,
				dhcp6SnoopingPortType
					INTEGER,
				dhcp6SnoopingPortInterfaceid
					OCTET STRING,
				dhcp6SnoopingPortRemoteid
					OCTET STRING,
				dhcp6SnoopingPortSubscriberd
					OCTET STRING,
				dhcp6SnoopingPortRateLimit
					INTEGER,
				dhcp6SnoopingPortDeny
					INTEGER,
				dhcp6SnoopingPortCheck
					INTEGER
			 }

--           1.3.6.1.4.1.37950.1.1.5.10.19.3.4.1.1
-- 1.3.6.1.4.1.37950.1.1.5.10.19.3.4.1.1
-- 1.3.6.1.4.1.37950.1.1.5.10.19.3.4.1.1
-- 1.3.6.1.4.1.37950.1.1.5.10.19.3.4.1.1
-- 1.3.6.1.4.1.37950.1.1.5.10.19.3.4.1.1
-- 1.3.6.1.4.1.37950.1.1.5.10.19.3.4.1.1
-- 1.3.6.1.4.1.37950.1.1.5.10.19.3.4.1.1
-- 1.3.6.1.4.1.37950.1.1.5.10.19.3.4.1.1
-- 1.3.6.1.4.1.37950.1.1.5.10.19.3.4.1.1
-- 1.3.6.1.4.1.37950.1.1.5.10.19.3.4.1.1
		-- 1.3.6.1.4.1.37950.1.1.5.10.19.3.4.1.1
		dhcp6SnoopingPortIndex OBJECT-TYPE
			SYNTAX Integer32
			MAX-ACCESS read-only
			STATUS current
			DESCRIPTION
				"Description."
			::= { dhcp6SnoopingPortCfgEntry 1 }

		
--           1.3.6.1.4.1.37950.1.1.5.10.19.3.4.1.2
-- 1.3.6.1.4.1.37950.1.1.5.10.19.3.4.1.2
-- 1.3.6.1.4.1.37950.1.1.5.10.19.3.4.1.2
-- 1.3.6.1.4.1.37950.1.1.5.10.19.3.4.1.2
-- 1.3.6.1.4.1.37950.1.1.5.10.19.3.4.1.2
-- 1.3.6.1.4.1.37950.1.1.5.10.19.3.4.1.2
-- 1.3.6.1.4.1.37950.1.1.5.10.19.3.4.1.2
-- 1.3.6.1.4.1.37950.1.1.5.10.19.3.4.1.2
-- 1.3.6.1.4.1.37950.1.1.5.10.19.3.4.1.2
-- 1.3.6.1.4.1.37950.1.1.5.10.19.3.4.1.2
		-- 1.3.6.1.4.1.37950.1.1.5.10.19.3.4.1.2
		dhcp6SnoopingPortType OBJECT-TYPE
			SYNTAX INTEGER
				{
				untrust(0),
				trust(1)
				}
			MAX-ACCESS read-write
			STATUS current
			DESCRIPTION
				"Description."
			::= { dhcp6SnoopingPortCfgEntry 2 }

		
--         1.3.6.1.4.1.37950.1.1.5.10.19.3.4.1.3
-- 1.3.6.1.4.1.37950.1.1.5.10.19.3.4.1.3
-- 1.3.6.1.4.1.37950.1.1.5.10.19.3.4.1.3
-- 1.3.6.1.4.1.37950.1.1.5.10.19.3.4.1.3
-- 1.3.6.1.4.1.37950.1.1.5.10.19.3.4.1.3
-- 1.3.6.1.4.1.37950.1.1.5.10.19.3.4.1.3
-- 1.3.6.1.4.1.37950.1.1.5.10.19.3.4.1.3
-- 1.3.6.1.4.1.37950.1.1.5.10.19.3.4.1.3
		-- 1.3.6.1.4.1.37950.1.1.5.10.19.3.4.1.3
		dhcp6SnoopingPortInterfaceid OBJECT-TYPE
			SYNTAX OCTET STRING
			MAX-ACCESS read-write
			STATUS current
			DESCRIPTION
				"Description."
			::= { dhcp6SnoopingPortCfgEntry 3 }

		
--         1.3.6.1.4.1.37950.1.1.5.10.19.3.4.1.4
-- 1.3.6.1.4.1.37950.1.1.5.10.19.3.4.1.4
-- 1.3.6.1.4.1.37950.1.1.5.10.19.3.4.1.4
-- 1.3.6.1.4.1.37950.1.1.5.10.19.3.4.1.4
-- 1.3.6.1.4.1.37950.1.1.5.10.19.3.4.1.4
-- 1.3.6.1.4.1.37950.1.1.5.10.19.3.4.1.4
-- 1.3.6.1.4.1.37950.1.1.5.10.19.3.4.1.4
-- 1.3.6.1.4.1.37950.1.1.5.10.19.3.4.1.4
		-- 1.3.6.1.4.1.37950.1.1.5.10.19.3.4.1.4
		dhcp6SnoopingPortRemoteid OBJECT-TYPE
			SYNTAX OCTET STRING
			MAX-ACCESS read-write
			STATUS current
			DESCRIPTION
				"Description."
			::= { dhcp6SnoopingPortCfgEntry 4 }

		
--         1.3.6.1.4.1.37950.1.1.5.10.19.3.4.1.5
-- 1.3.6.1.4.1.37950.1.1.5.10.19.3.4.1.5
-- 1.3.6.1.4.1.37950.1.1.5.10.19.3.4.1.5
-- 1.3.6.1.4.1.37950.1.1.5.10.19.3.4.1.5
-- 1.3.6.1.4.1.37950.1.1.5.10.19.3.4.1.5
-- 1.3.6.1.4.1.37950.1.1.5.10.19.3.4.1.5
-- 1.3.6.1.4.1.37950.1.1.5.10.19.3.4.1.5
-- 1.3.6.1.4.1.37950.1.1.5.10.19.3.4.1.5
		-- 1.3.6.1.4.1.37950.1.1.5.10.19.3.4.1.5
		dhcp6SnoopingPortSubscriberd OBJECT-TYPE
			SYNTAX OCTET STRING
			MAX-ACCESS read-write
			STATUS current
			DESCRIPTION
				"Description."
			::= { dhcp6SnoopingPortCfgEntry 5 }

		
--         1.3.6.1.4.1.37950.1.1.5.10.19.3.4.1.6
-- 1.3.6.1.4.1.37950.1.1.5.10.19.3.4.1.6
-- 1.3.6.1.4.1.37950.1.1.5.10.19.3.4.1.6
-- 1.3.6.1.4.1.37950.1.1.5.10.19.3.4.1.6
-- 1.3.6.1.4.1.37950.1.1.5.10.19.3.4.1.6
-- 1.3.6.1.4.1.37950.1.1.5.10.19.3.4.1.6
-- 1.3.6.1.4.1.37950.1.1.5.10.19.3.4.1.6
-- 1.3.6.1.4.1.37950.1.1.5.10.19.3.4.1.6
		-- 1.3.6.1.4.1.37950.1.1.5.10.19.3.4.1.6
		dhcp6SnoopingPortRateLimit OBJECT-TYPE
			SYNTAX INTEGER (0..4096)
			MAX-ACCESS read-write
			STATUS current
			DESCRIPTION
				"Description."
			::= { dhcp6SnoopingPortCfgEntry 6 }

		
--         1.3.6.1.4.1.37950.1.1.5.10.19.3.4.1.7
-- 1.3.6.1.4.1.37950.1.1.5.10.19.3.4.1.7
-- 1.3.6.1.4.1.37950.1.1.5.10.19.3.4.1.7
-- 1.3.6.1.4.1.37950.1.1.5.10.19.3.4.1.7
-- 1.3.6.1.4.1.37950.1.1.5.10.19.3.4.1.7
-- 1.3.6.1.4.1.37950.1.1.5.10.19.3.4.1.7
-- 1.3.6.1.4.1.37950.1.1.5.10.19.3.4.1.7
-- 1.3.6.1.4.1.37950.1.1.5.10.19.3.4.1.7
		-- 1.3.6.1.4.1.37950.1.1.5.10.19.3.4.1.7
		dhcp6SnoopingPortDeny OBJECT-TYPE
			SYNTAX INTEGER
				{
				disable(0),
				enable(1)
				}
			MAX-ACCESS read-write
			STATUS current
			DESCRIPTION
				"Description."
			::= { dhcp6SnoopingPortCfgEntry 7 }

		
--         1.3.6.1.4.1.37950.1.1.5.10.19.3.4.1.8
-- 1.3.6.1.4.1.37950.1.1.5.10.19.3.4.1.8
-- 1.3.6.1.4.1.37950.1.1.5.10.19.3.4.1.8
-- 1.3.6.1.4.1.37950.1.1.5.10.19.3.4.1.8
-- 1.3.6.1.4.1.37950.1.1.5.10.19.3.4.1.8
-- 1.3.6.1.4.1.37950.1.1.5.10.19.3.4.1.8
-- 1.3.6.1.4.1.37950.1.1.5.10.19.3.4.1.8
-- 1.3.6.1.4.1.37950.1.1.5.10.19.3.4.1.8
		-- 1.3.6.1.4.1.37950.1.1.5.10.19.3.4.1.8
		dhcp6SnoopingPortCheck OBJECT-TYPE
			SYNTAX INTEGER
				{
				disable(0),
				enable(1)
				}
			MAX-ACCESS read-write
			STATUS current
			DESCRIPTION
				"Description."
			::= { dhcp6SnoopingPortCfgEntry 8 }

		
--         1.3.6.1.4.1.37950.1.1.5.10.19.3.5
-- 1.3.6.1.4.1.37950.1.1.5.10.19.3.5
-- 1.3.6.1.4.1.37950.1.1.5.10.19.3.5
-- 1.3.6.1.4.1.37950.1.1.5.10.19.3.5
-- 1.3.6.1.4.1.37950.1.1.5.10.19.3.5
-- 1.3.6.1.4.1.37950.1.1.5.10.19.3.5
-- 1.3.6.1.4.1.37950.1.1.5.10.19.3.5
-- 1.3.6.1.4.1.37950.1.1.5.10.19.3.5
		-- 1.3.6.1.4.1.37950.1.1.5.10.19.3.5
		dhcp6SnoopingBinding OBJECT IDENTIFIER ::= { dhcp6Snooping 5 }

		
--         1.3.6.1.4.1.37950.1.1.5.10.19.3.5.1
-- 1.3.6.1.4.1.37950.1.1.5.10.19.3.5.1
-- 1.3.6.1.4.1.37950.1.1.5.10.19.3.5.1
-- 1.3.6.1.4.1.37950.1.1.5.10.19.3.5.1
-- 1.3.6.1.4.1.37950.1.1.5.10.19.3.5.1
-- 1.3.6.1.4.1.37950.1.1.5.10.19.3.5.1
-- 1.3.6.1.4.1.37950.1.1.5.10.19.3.5.1
-- 1.3.6.1.4.1.37950.1.1.5.10.19.3.5.1
		-- 1.3.6.1.4.1.37950.1.1.5.10.19.3.5.1
		dhcp6SnoopingBindingConfig OBJECT IDENTIFIER ::= { dhcp6SnoopingBinding 1 }

		
--         1.3.6.1.4.1.37950.1.1.5.10.19.3.5.1.1
-- 1.3.6.1.4.1.37950.1.1.5.10.19.3.5.1.1
-- 1.3.6.1.4.1.37950.1.1.5.10.19.3.5.1.1
-- 1.3.6.1.4.1.37950.1.1.5.10.19.3.5.1.1
-- 1.3.6.1.4.1.37950.1.1.5.10.19.3.5.1.1
-- 1.3.6.1.4.1.37950.1.1.5.10.19.3.5.1.1
-- 1.3.6.1.4.1.37950.1.1.5.10.19.3.5.1.1
-- 1.3.6.1.4.1.37950.1.1.5.10.19.3.5.1.1
		-- 1.3.6.1.4.1.37950.1.1.5.10.19.3.5.1.1
		dhcp6SnoopingBindMAC OBJECT-TYPE
			SYNTAX OCTET STRING
			MAX-ACCESS read-write
			STATUS current
			DESCRIPTION
				"Description."
			::= { dhcp6SnoopingBindingConfig 1 }

		
--         1.3.6.1.4.1.37950.1.1.5.10.19.3.5.1.2
-- 1.3.6.1.4.1.37950.1.1.5.10.19.3.5.1.2
-- 1.3.6.1.4.1.37950.1.1.5.10.19.3.5.1.2
-- 1.3.6.1.4.1.37950.1.1.5.10.19.3.5.1.2
-- 1.3.6.1.4.1.37950.1.1.5.10.19.3.5.1.2
-- 1.3.6.1.4.1.37950.1.1.5.10.19.3.5.1.2
-- 1.3.6.1.4.1.37950.1.1.5.10.19.3.5.1.2
-- 1.3.6.1.4.1.37950.1.1.5.10.19.3.5.1.2
		-- 1.3.6.1.4.1.37950.1.1.5.10.19.3.5.1.2
		dhcp6SnoopingBindVLAN OBJECT-TYPE
			SYNTAX Integer32 (1..4095)
			MAX-ACCESS read-write
			STATUS current
			DESCRIPTION
				"Description."
			::= { dhcp6SnoopingBindingConfig 2 }

		
--         1.3.6.1.4.1.37950.1.1.5.10.19.3.5.1.3
-- 1.3.6.1.4.1.37950.1.1.5.10.19.3.5.1.3
-- 1.3.6.1.4.1.37950.1.1.5.10.19.3.5.1.3
-- 1.3.6.1.4.1.37950.1.1.5.10.19.3.5.1.3
-- 1.3.6.1.4.1.37950.1.1.5.10.19.3.5.1.3
-- 1.3.6.1.4.1.37950.1.1.5.10.19.3.5.1.3
-- 1.3.6.1.4.1.37950.1.1.5.10.19.3.5.1.3
-- 1.3.6.1.4.1.37950.1.1.5.10.19.3.5.1.3
		-- 1.3.6.1.4.1.37950.1.1.5.10.19.3.5.1.3
		dhcp6SnoopingBindIPv6 OBJECT-TYPE
			SYNTAX OCTET STRING
			MAX-ACCESS read-write
			STATUS current
			DESCRIPTION
				"Description."
			::= { dhcp6SnoopingBindingConfig 3 }

		
--         1.3.6.1.4.1.37950.1.1.5.10.19.3.5.1.4
-- 1.3.6.1.4.1.37950.1.1.5.10.19.3.5.1.4
-- 1.3.6.1.4.1.37950.1.1.5.10.19.3.5.1.4
-- 1.3.6.1.4.1.37950.1.1.5.10.19.3.5.1.4
-- 1.3.6.1.4.1.37950.1.1.5.10.19.3.5.1.4
-- 1.3.6.1.4.1.37950.1.1.5.10.19.3.5.1.4
-- 1.3.6.1.4.1.37950.1.1.5.10.19.3.5.1.4
-- 1.3.6.1.4.1.37950.1.1.5.10.19.3.5.1.4
		-- 1.3.6.1.4.1.37950.1.1.5.10.19.3.5.1.4
		dhcp6SnoopingBindPortIndex OBJECT-TYPE
			SYNTAX INTEGER (1..28)
			MAX-ACCESS read-write
			STATUS current
			DESCRIPTION
				"Description."
			::= { dhcp6SnoopingBindingConfig 4 }

		
--         1.3.6.1.4.1.37950.1.1.5.10.19.3.5.1.5
-- 1.3.6.1.4.1.37950.1.1.5.10.19.3.5.1.5
-- 1.3.6.1.4.1.37950.1.1.5.10.19.3.5.1.5
-- 1.3.6.1.4.1.37950.1.1.5.10.19.3.5.1.5
-- 1.3.6.1.4.1.37950.1.1.5.10.19.3.5.1.5
-- 1.3.6.1.4.1.37950.1.1.5.10.19.3.5.1.5
-- 1.3.6.1.4.1.37950.1.1.5.10.19.3.5.1.5
-- 1.3.6.1.4.1.37950.1.1.5.10.19.3.5.1.5
		-- 1.3.6.1.4.1.37950.1.1.5.10.19.3.5.1.5
		dhcp6SnoopingBindValidTime OBJECT-TYPE
			SYNTAX Unsigned32 (60..4294967295)
			MAX-ACCESS read-write
			STATUS current
			DESCRIPTION
				"Description."
			::= { dhcp6SnoopingBindingConfig 5 }

		
--         1.3.6.1.4.1.37950.1.1.5.10.19.3.5.1.6
-- 1.3.6.1.4.1.37950.1.1.5.10.19.3.5.1.6
-- 1.3.6.1.4.1.37950.1.1.5.10.19.3.5.1.6
-- 1.3.6.1.4.1.37950.1.1.5.10.19.3.5.1.6
-- 1.3.6.1.4.1.37950.1.1.5.10.19.3.5.1.6
-- 1.3.6.1.4.1.37950.1.1.5.10.19.3.5.1.6
-- 1.3.6.1.4.1.37950.1.1.5.10.19.3.5.1.6
-- 1.3.6.1.4.1.37950.1.1.5.10.19.3.5.1.6
		-- 1.3.6.1.4.1.37950.1.1.5.10.19.3.5.1.6
		dhcp6SnoopingBindPreferredTime OBJECT-TYPE
			SYNTAX Unsigned32 (60..4294967295)
			MAX-ACCESS read-write
			STATUS current
			DESCRIPTION
				"Description."
			::= { dhcp6SnoopingBindingConfig 6 }

		
--         1.3.6.1.4.1.37950.1.1.5.10.19.3.5.1.7
-- 1.3.6.1.4.1.37950.1.1.5.10.19.3.5.1.7
-- 1.3.6.1.4.1.37950.1.1.5.10.19.3.5.1.7
-- 1.3.6.1.4.1.37950.1.1.5.10.19.3.5.1.7
-- 1.3.6.1.4.1.37950.1.1.5.10.19.3.5.1.7
-- 1.3.6.1.4.1.37950.1.1.5.10.19.3.5.1.7
-- 1.3.6.1.4.1.37950.1.1.5.10.19.3.5.1.7
-- 1.3.6.1.4.1.37950.1.1.5.10.19.3.5.1.7
		-- 1.3.6.1.4.1.37950.1.1.5.10.19.3.5.1.7
		dhcp6SnoopingBindAction OBJECT-TYPE
			SYNTAX INTEGER
				{
				del(0),
				add(1)
				}
			MAX-ACCESS read-write
			STATUS current
			DESCRIPTION
				"Description."
			::= { dhcp6SnoopingBindingConfig 7 }

		
--         1.3.6.1.4.1.37950.1.1.5.10.19.3.5.2
-- 1.3.6.1.4.1.37950.1.1.5.10.19.3.5.2
-- 1.3.6.1.4.1.37950.1.1.5.10.19.3.5.2
-- 1.3.6.1.4.1.37950.1.1.5.10.19.3.5.2
-- 1.3.6.1.4.1.37950.1.1.5.10.19.3.5.2
-- 1.3.6.1.4.1.37950.1.1.5.10.19.3.5.2
-- 1.3.6.1.4.1.37950.1.1.5.10.19.3.5.2
-- 1.3.6.1.4.1.37950.1.1.5.10.19.3.5.2
		-- 1.3.6.1.4.1.37950.1.1.5.10.19.3.5.2
		dhcp6SnoopingBindingTable OBJECT-TYPE
			SYNTAX SEQUENCE OF Dhcp6SnoopingBindingEntry
			MAX-ACCESS not-accessible
			STATUS current
			DESCRIPTION
				"Description."
			::= { dhcp6SnoopingBinding 2 }

		
--         1.3.6.1.4.1.37950.1.1.5.10.19.3.5.2.1
-- 1.3.6.1.4.1.37950.1.1.5.10.19.3.5.2.1
-- 1.3.6.1.4.1.37950.1.1.5.10.19.3.5.2.1
-- 1.3.6.1.4.1.37950.1.1.5.10.19.3.5.2.1
-- 1.3.6.1.4.1.37950.1.1.5.10.19.3.5.2.1
-- 1.3.6.1.4.1.37950.1.1.5.10.19.3.5.2.1
-- 1.3.6.1.4.1.37950.1.1.5.10.19.3.5.2.1
-- 1.3.6.1.4.1.37950.1.1.5.10.19.3.5.2.1
		-- 1.3.6.1.4.1.37950.1.1.5.10.19.3.5.2.1
		dhcp6SnoopingBindingEntry OBJECT-TYPE
			SYNTAX Dhcp6SnoopingBindingEntry
			MAX-ACCESS not-accessible
			STATUS current
			DESCRIPTION
				"Description."
			INDEX { dhcp6SnoopingBindingID }
			::= { dhcp6SnoopingBindingTable 1 }

		
		Dhcp6SnoopingBindingEntry ::=
			SEQUENCE { 
				dhcp6SnoopingBindingID
					Integer32,
				dhcp6SnoopingBindingMAC
					OCTET STRING,
				dhcp6SnoopingBindingIPv6
					OCTET STRING,
				dhcp6SnoopingBindingPreferredTime
					Unsigned32,
				dhcp6SnoopingBindingValidTime
					Unsigned32,
				dhcp6SnoopingBindingType
					INTEGER,
				dhcp6SnoopingBindingVLAN
					Integer32,
				dhcp6SnoopingBindingInterface
					Integer32
			 }

--         1.3.6.1.4.1.37950.1.1.5.10.19.3.5.2.1.1
-- 1.3.6.1.4.1.37950.1.1.5.10.19.3.5.2.1.1
-- 1.3.6.1.4.1.37950.1.1.5.10.19.3.5.2.1.1
-- 1.3.6.1.4.1.37950.1.1.5.10.19.3.5.2.1.1
-- 1.3.6.1.4.1.37950.1.1.5.10.19.3.5.2.1.1
-- 1.3.6.1.4.1.37950.1.1.5.10.19.3.5.2.1.1
-- 1.3.6.1.4.1.37950.1.1.5.10.19.3.5.2.1.1
-- 1.3.6.1.4.1.37950.1.1.5.10.19.3.5.2.1.1
		-- 1.3.6.1.4.1.37950.1.1.5.10.19.3.5.2.1.1
		dhcp6SnoopingBindingID OBJECT-TYPE
			SYNTAX Integer32
			MAX-ACCESS read-only
			STATUS current
			DESCRIPTION
				"Description."
			::= { dhcp6SnoopingBindingEntry 1 }

		
--         1.3.6.1.4.1.37950.1.1.5.10.19.3.5.2.1.2
-- 1.3.6.1.4.1.37950.1.1.5.10.19.3.5.2.1.2
-- 1.3.6.1.4.1.37950.1.1.5.10.19.3.5.2.1.2
-- 1.3.6.1.4.1.37950.1.1.5.10.19.3.5.2.1.2
-- 1.3.6.1.4.1.37950.1.1.5.10.19.3.5.2.1.2
-- 1.3.6.1.4.1.37950.1.1.5.10.19.3.5.2.1.2
-- 1.3.6.1.4.1.37950.1.1.5.10.19.3.5.2.1.2
-- 1.3.6.1.4.1.37950.1.1.5.10.19.3.5.2.1.2
		-- 1.3.6.1.4.1.37950.1.1.5.10.19.3.5.2.1.2
		dhcp6SnoopingBindingMAC OBJECT-TYPE
			SYNTAX OCTET STRING
			MAX-ACCESS read-only
			STATUS current
			DESCRIPTION
				"Description."
			::= { dhcp6SnoopingBindingEntry 2 }

		
--         1.3.6.1.4.1.37950.1.1.5.10.19.3.5.2.1.3
-- 1.3.6.1.4.1.37950.1.1.5.10.19.3.5.2.1.3
-- 1.3.6.1.4.1.37950.1.1.5.10.19.3.5.2.1.3
-- 1.3.6.1.4.1.37950.1.1.5.10.19.3.5.2.1.3
-- 1.3.6.1.4.1.37950.1.1.5.10.19.3.5.2.1.3
-- 1.3.6.1.4.1.37950.1.1.5.10.19.3.5.2.1.3
-- 1.3.6.1.4.1.37950.1.1.5.10.19.3.5.2.1.3
-- 1.3.6.1.4.1.37950.1.1.5.10.19.3.5.2.1.3
		-- 1.3.6.1.4.1.37950.1.1.5.10.19.3.5.2.1.3
		dhcp6SnoopingBindingIPv6 OBJECT-TYPE
			SYNTAX OCTET STRING
			MAX-ACCESS read-only
			STATUS current
			DESCRIPTION
				"Description."
			::= { dhcp6SnoopingBindingEntry 3 }

		
--         1.3.6.1.4.1.37950.1.1.5.10.19.3.5.2.1.4
-- 1.3.6.1.4.1.37950.1.1.5.10.19.3.5.2.1.4
-- 1.3.6.1.4.1.37950.1.1.5.10.19.3.5.2.1.4
-- 1.3.6.1.4.1.37950.1.1.5.10.19.3.5.2.1.4
-- 1.3.6.1.4.1.37950.1.1.5.10.19.3.5.2.1.4
-- 1.3.6.1.4.1.37950.1.1.5.10.19.3.5.2.1.4
-- 1.3.6.1.4.1.37950.1.1.5.10.19.3.5.2.1.4
-- 1.3.6.1.4.1.37950.1.1.5.10.19.3.5.2.1.4
		-- 1.3.6.1.4.1.37950.1.1.5.10.19.3.5.2.1.4
		dhcp6SnoopingBindingPreferredTime OBJECT-TYPE
			SYNTAX Unsigned32
			MAX-ACCESS read-only
			STATUS current
			DESCRIPTION
				"Description."
			::= { dhcp6SnoopingBindingEntry 4 }

		
--         1.3.6.1.4.1.37950.1.1.5.10.19.3.5.2.1.5
-- 1.3.6.1.4.1.37950.1.1.5.10.19.3.5.2.1.5
-- 1.3.6.1.4.1.37950.1.1.5.10.19.3.5.2.1.5
-- 1.3.6.1.4.1.37950.1.1.5.10.19.3.5.2.1.5
-- 1.3.6.1.4.1.37950.1.1.5.10.19.3.5.2.1.5
-- 1.3.6.1.4.1.37950.1.1.5.10.19.3.5.2.1.5
-- 1.3.6.1.4.1.37950.1.1.5.10.19.3.5.2.1.5
-- 1.3.6.1.4.1.37950.1.1.5.10.19.3.5.2.1.5
		-- 1.3.6.1.4.1.37950.1.1.5.10.19.3.5.2.1.5
		dhcp6SnoopingBindingValidTime OBJECT-TYPE
			SYNTAX Unsigned32
			MAX-ACCESS read-only
			STATUS current
			DESCRIPTION
				"Description."
			::= { dhcp6SnoopingBindingEntry 5 }

		
--         1.3.6.1.4.1.37950.1.1.5.10.19.3.5.2.1.6
-- 1.3.6.1.4.1.37950.1.1.5.10.19.3.5.2.1.6
-- 1.3.6.1.4.1.37950.1.1.5.10.19.3.5.2.1.6
-- 1.3.6.1.4.1.37950.1.1.5.10.19.3.5.2.1.6
-- 1.3.6.1.4.1.37950.1.1.5.10.19.3.5.2.1.6
-- 1.3.6.1.4.1.37950.1.1.5.10.19.3.5.2.1.6
-- 1.3.6.1.4.1.37950.1.1.5.10.19.3.5.2.1.6
-- 1.3.6.1.4.1.37950.1.1.5.10.19.3.5.2.1.6
		-- 1.3.6.1.4.1.37950.1.1.5.10.19.3.5.2.1.6
		dhcp6SnoopingBindingType OBJECT-TYPE
			SYNTAX INTEGER
				{
				static(0),
				dynamic(1)
				}
			MAX-ACCESS read-only
			STATUS current
			DESCRIPTION
				"Description."
			::= { dhcp6SnoopingBindingEntry 6 }

		
--         1.3.6.1.4.1.37950.1.1.5.10.19.3.5.2.1.7
-- 1.3.6.1.4.1.37950.1.1.5.10.19.3.5.2.1.7
-- 1.3.6.1.4.1.37950.1.1.5.10.19.3.5.2.1.7
-- 1.3.6.1.4.1.37950.1.1.5.10.19.3.5.2.1.7
-- 1.3.6.1.4.1.37950.1.1.5.10.19.3.5.2.1.7
-- 1.3.6.1.4.1.37950.1.1.5.10.19.3.5.2.1.7
-- 1.3.6.1.4.1.37950.1.1.5.10.19.3.5.2.1.7
-- 1.3.6.1.4.1.37950.1.1.5.10.19.3.5.2.1.7
		-- 1.3.6.1.4.1.37950.1.1.5.10.19.3.5.2.1.7
		dhcp6SnoopingBindingVLAN OBJECT-TYPE
			SYNTAX Integer32
			MAX-ACCESS read-only
			STATUS current
			DESCRIPTION
				"Description."
			::= { dhcp6SnoopingBindingEntry 7 }

		
--         1.3.6.1.4.1.37950.1.1.5.10.19.3.5.2.1.8
-- 1.3.6.1.4.1.37950.1.1.5.10.19.3.5.2.1.8
-- 1.3.6.1.4.1.37950.1.1.5.10.19.3.5.2.1.8
-- 1.3.6.1.4.1.37950.1.1.5.10.19.3.5.2.1.8
-- 1.3.6.1.4.1.37950.1.1.5.10.19.3.5.2.1.8
-- 1.3.6.1.4.1.37950.1.1.5.10.19.3.5.2.1.8
-- 1.3.6.1.4.1.37950.1.1.5.10.19.3.5.2.1.8
-- 1.3.6.1.4.1.37950.1.1.5.10.19.3.5.2.1.8
		-- 1.3.6.1.4.1.37950.1.1.5.10.19.3.5.2.1.8
		dhcp6SnoopingBindingInterface OBJECT-TYPE
			SYNTAX Integer32
			MAX-ACCESS read-only
			STATUS current
			DESCRIPTION
				"Description."
			::= { dhcp6SnoopingBindingEntry 8 }

		
--         1.3.6.1.4.1.37950.1.1.5.10.20
-- 1.3.6.1.4.1.37950.1.1.5.10.20
-- 1.3.6.1.4.1.37950.1.1.5.10.20
-- 1.3.6.1.4.1.37950.1.1.5.10.20
-- 1.3.6.1.4.1.37950.1.1.5.10.20
-- 1.3.6.1.4.1.37950.1.1.5.10.20
-- 1.3.6.1.4.1.37950.1.1.5.10.20
-- 1.3.6.1.4.1.37950.1.1.5.10.20
		-- 1.3.6.1.4.1.37950.1.1.5.10.20
		v1600dIPv6MldSnooping OBJECT IDENTIFIER ::= { v1600dSwitch 20 }

		
--         1.3.6.1.4.1.37950.1.1.5.10.20.1
-- 1.3.6.1.4.1.37950.1.1.5.10.20.1
-- 1.3.6.1.4.1.37950.1.1.5.10.20.1
-- 1.3.6.1.4.1.37950.1.1.5.10.20.1
-- 1.3.6.1.4.1.37950.1.1.5.10.20.1
-- 1.3.6.1.4.1.37950.1.1.5.10.20.1
-- 1.3.6.1.4.1.37950.1.1.5.10.20.1
-- 1.3.6.1.4.1.37950.1.1.5.10.20.1
		-- 1.3.6.1.4.1.37950.1.1.5.10.20.1
		mldGlobalTable OBJECT-TYPE
			SYNTAX SEQUENCE OF MldGlobalEntry
			MAX-ACCESS not-accessible
			STATUS current
			DESCRIPTION
				"Description."
			::= { v1600dIPv6MldSnooping 1 }

		
--         1.3.6.1.4.1.37950.1.1.5.10.20.1.1
-- 1.3.6.1.4.1.37950.1.1.5.10.20.1.1
-- 1.3.6.1.4.1.37950.1.1.5.10.20.1.1
-- 1.3.6.1.4.1.37950.1.1.5.10.20.1.1
-- 1.3.6.1.4.1.37950.1.1.5.10.20.1.1
-- 1.3.6.1.4.1.37950.1.1.5.10.20.1.1
-- 1.3.6.1.4.1.37950.1.1.5.10.20.1.1
-- 1.3.6.1.4.1.37950.1.1.5.10.20.1.1
		-- 1.3.6.1.4.1.37950.1.1.5.10.20.1.1
		mldGlobalEntry OBJECT-TYPE
			SYNTAX MldGlobalEntry
			MAX-ACCESS not-accessible
			STATUS current
			DESCRIPTION
				"Description."
			INDEX { mldGlobalIndex }
			::= { mldGlobalTable 1 }

		
		MldGlobalEntry ::=
			SEQUENCE { 
				mldGlobalIndex
					Integer32,
				mldLastListenQueryCount
					Integer32,
				sendGeneralQueryPacket
					INTEGER,
				generalQueryInterval
					Integer32,
				querySourceIp
					OCTET STRING,
				mldStatus
					INTEGER
			 }

--         1.3.6.1.4.1.37950.1.1.5.10.20.1.1.1
-- 1.3.6.1.4.1.37950.1.1.5.10.20.1.1.1
-- 1.3.6.1.4.1.37950.1.1.5.10.20.1.1.1
-- 1.3.6.1.4.1.37950.1.1.5.10.20.1.1.1
-- 1.3.6.1.4.1.37950.1.1.5.10.20.1.1.1
-- 1.3.6.1.4.1.37950.1.1.5.10.20.1.1.1
-- 1.3.6.1.4.1.37950.1.1.5.10.20.1.1.1
-- 1.3.6.1.4.1.37950.1.1.5.10.20.1.1.1
		-- 1.3.6.1.4.1.37950.1.1.5.10.20.1.1.1
		mldGlobalIndex OBJECT-TYPE
			SYNTAX Integer32
			MAX-ACCESS read-only
			STATUS current
			DESCRIPTION
				"Description."
			::= { mldGlobalEntry 1 }

		
--         1.3.6.1.4.1.37950.1.1.5.10.20.1.1.2
-- 1.3.6.1.4.1.37950.1.1.5.10.20.1.1.2
-- 1.3.6.1.4.1.37950.1.1.5.10.20.1.1.2
-- 1.3.6.1.4.1.37950.1.1.5.10.20.1.1.2
-- 1.3.6.1.4.1.37950.1.1.5.10.20.1.1.2
-- 1.3.6.1.4.1.37950.1.1.5.10.20.1.1.2
-- 1.3.6.1.4.1.37950.1.1.5.10.20.1.1.2
-- 1.3.6.1.4.1.37950.1.1.5.10.20.1.1.2
		-- 1.3.6.1.4.1.37950.1.1.5.10.20.1.1.2
		mldLastListenQueryCount OBJECT-TYPE
			SYNTAX Integer32 (1..7)
			MAX-ACCESS read-write
			STATUS current
			DESCRIPTION
				"Description."
			::= { mldGlobalEntry 2 }

		
--         1.3.6.1.4.1.37950.1.1.5.10.20.1.1.3
-- 1.3.6.1.4.1.37950.1.1.5.10.20.1.1.3
-- 1.3.6.1.4.1.37950.1.1.5.10.20.1.1.3
-- 1.3.6.1.4.1.37950.1.1.5.10.20.1.1.3
-- 1.3.6.1.4.1.37950.1.1.5.10.20.1.1.3
-- 1.3.6.1.4.1.37950.1.1.5.10.20.1.1.3
-- 1.3.6.1.4.1.37950.1.1.5.10.20.1.1.3
-- 1.3.6.1.4.1.37950.1.1.5.10.20.1.1.3
		-- 1.3.6.1.4.1.37950.1.1.5.10.20.1.1.3
		sendGeneralQueryPacket OBJECT-TYPE
			SYNTAX INTEGER
				{
				disable(0),
				enable(1)
				}
			MAX-ACCESS read-write
			STATUS current
			DESCRIPTION
				"Description."
			::= { mldGlobalEntry 3 }

		
--         1.3.6.1.4.1.37950.1.1.5.10.20.1.1.4
-- 1.3.6.1.4.1.37950.1.1.5.10.20.1.1.4
-- 1.3.6.1.4.1.37950.1.1.5.10.20.1.1.4
-- 1.3.6.1.4.1.37950.1.1.5.10.20.1.1.4
-- 1.3.6.1.4.1.37950.1.1.5.10.20.1.1.4
-- 1.3.6.1.4.1.37950.1.1.5.10.20.1.1.4
-- 1.3.6.1.4.1.37950.1.1.5.10.20.1.1.4
-- 1.3.6.1.4.1.37950.1.1.5.10.20.1.1.4
		-- 1.3.6.1.4.1.37950.1.1.5.10.20.1.1.4
		generalQueryInterval OBJECT-TYPE
			SYNTAX Integer32 (10..3600)
			MAX-ACCESS read-write
			STATUS current
			DESCRIPTION
				"Description."
			::= { mldGlobalEntry 4 }

		
--         1.3.6.1.4.1.37950.1.1.5.10.20.1.1.5
-- 1.3.6.1.4.1.37950.1.1.5.10.20.1.1.5
-- 1.3.6.1.4.1.37950.1.1.5.10.20.1.1.5
-- 1.3.6.1.4.1.37950.1.1.5.10.20.1.1.5
-- 1.3.6.1.4.1.37950.1.1.5.10.20.1.1.5
-- 1.3.6.1.4.1.37950.1.1.5.10.20.1.1.5
-- 1.3.6.1.4.1.37950.1.1.5.10.20.1.1.5
-- 1.3.6.1.4.1.37950.1.1.5.10.20.1.1.5
		-- 1.3.6.1.4.1.37950.1.1.5.10.20.1.1.5
		querySourceIp OBJECT-TYPE
			SYNTAX OCTET STRING
			MAX-ACCESS read-write
			STATUS current
			DESCRIPTION
				"Description."
			::= { mldGlobalEntry 5 }

		
--         1.3.6.1.4.1.37950.1.1.5.10.20.1.1.6
-- 1.3.6.1.4.1.37950.1.1.5.10.20.1.1.6
-- 1.3.6.1.4.1.37950.1.1.5.10.20.1.1.6
-- 1.3.6.1.4.1.37950.1.1.5.10.20.1.1.6
-- 1.3.6.1.4.1.37950.1.1.5.10.20.1.1.6
-- 1.3.6.1.4.1.37950.1.1.5.10.20.1.1.6
-- 1.3.6.1.4.1.37950.1.1.5.10.20.1.1.6
-- 1.3.6.1.4.1.37950.1.1.5.10.20.1.1.6
		-- 1.3.6.1.4.1.37950.1.1.5.10.20.1.1.6
		mldStatus OBJECT-TYPE
			SYNTAX INTEGER
				{
				disable(0),
				enable(1)
				}
			MAX-ACCESS read-write
			STATUS current
			DESCRIPTION
				"Description."
			::= { mldGlobalEntry 6 }

		
--         1.3.6.1.4.1.37950.1.1.5.10.20.2
-- 1.3.6.1.4.1.37950.1.1.5.10.20.2
-- 1.3.6.1.4.1.37950.1.1.5.10.20.2
-- 1.3.6.1.4.1.37950.1.1.5.10.20.2
-- 1.3.6.1.4.1.37950.1.1.5.10.20.2
-- 1.3.6.1.4.1.37950.1.1.5.10.20.2
-- 1.3.6.1.4.1.37950.1.1.5.10.20.2
-- 1.3.6.1.4.1.37950.1.1.5.10.20.2
		-- 1.3.6.1.4.1.37950.1.1.5.10.20.2
		mldUserVlanCfg OBJECT IDENTIFIER ::= { v1600dIPv6MldSnooping 2 }

		
--         1.3.6.1.4.1.37950.1.1.5.10.20.2.1
-- 1.3.6.1.4.1.37950.1.1.5.10.20.2.1
-- 1.3.6.1.4.1.37950.1.1.5.10.20.2.1
-- 1.3.6.1.4.1.37950.1.1.5.10.20.2.1
-- 1.3.6.1.4.1.37950.1.1.5.10.20.2.1
-- 1.3.6.1.4.1.37950.1.1.5.10.20.2.1
-- 1.3.6.1.4.1.37950.1.1.5.10.20.2.1
-- 1.3.6.1.4.1.37950.1.1.5.10.20.2.1
		-- 1.3.6.1.4.1.37950.1.1.5.10.20.2.1
		mldUserPortIndexCfg OBJECT-TYPE
			SYNTAX Integer32
			MAX-ACCESS read-write
			STATUS current
			DESCRIPTION
				"Description."
			::= { mldUserVlanCfg 1 }

		
--         1.3.6.1.4.1.37950.1.1.5.10.20.2.2
-- 1.3.6.1.4.1.37950.1.1.5.10.20.2.2
-- 1.3.6.1.4.1.37950.1.1.5.10.20.2.2
-- 1.3.6.1.4.1.37950.1.1.5.10.20.2.2
-- 1.3.6.1.4.1.37950.1.1.5.10.20.2.2
-- 1.3.6.1.4.1.37950.1.1.5.10.20.2.2
-- 1.3.6.1.4.1.37950.1.1.5.10.20.2.2
-- 1.3.6.1.4.1.37950.1.1.5.10.20.2.2
		-- 1.3.6.1.4.1.37950.1.1.5.10.20.2.2
		mldUserVlanIdCfg OBJECT-TYPE
			SYNTAX Integer32 (1..4094)
			MAX-ACCESS read-write
			STATUS current
			DESCRIPTION
				"Description."
			::= { mldUserVlanCfg 2 }

		
--          1.3.6.1.4.1.37950.1.1.5.10.20.2.3
-- 1.3.6.1.4.1.37950.1.1.5.10.20.2.3
-- 1.3.6.1.4.1.37950.1.1.5.10.20.2.3
-- 1.3.6.1.4.1.37950.1.1.5.10.20.2.3
-- 1.3.6.1.4.1.37950.1.1.5.10.20.2.3
-- 1.3.6.1.4.1.37950.1.1.5.10.20.2.3
-- 1.3.6.1.4.1.37950.1.1.5.10.20.2.3
-- 1.3.6.1.4.1.37950.1.1.5.10.20.2.3
		-- 1.3.6.1.4.1.37950.1.1.5.10.20.2.3
		mldGroupVlanIdCfg OBJECT-TYPE
			SYNTAX Integer32 (1..4094)
			MAX-ACCESS read-write
			STATUS current
			DESCRIPTION
				"Description."
			::= { mldUserVlanCfg 3 }

		
--         1.3.6.1.4.1.37950.1.1.5.10.20.2.4
-- 1.3.6.1.4.1.37950.1.1.5.10.20.2.4
-- 1.3.6.1.4.1.37950.1.1.5.10.20.2.4
-- 1.3.6.1.4.1.37950.1.1.5.10.20.2.4
-- 1.3.6.1.4.1.37950.1.1.5.10.20.2.4
-- 1.3.6.1.4.1.37950.1.1.5.10.20.2.4
-- 1.3.6.1.4.1.37950.1.1.5.10.20.2.4
-- 1.3.6.1.4.1.37950.1.1.5.10.20.2.4
		-- 1.3.6.1.4.1.37950.1.1.5.10.20.2.4
		mldUserVlanAction OBJECT-TYPE
			SYNTAX INTEGER
				{
				add(1),
				del(2)
				}
			MAX-ACCESS read-write
			STATUS current
			DESCRIPTION
				"Description."
			::= { mldUserVlanCfg 4 }

		
--         1.3.6.1.4.1.37950.1.1.5.10.20.3
-- 1.3.6.1.4.1.37950.1.1.5.10.20.3
-- 1.3.6.1.4.1.37950.1.1.5.10.20.3
-- 1.3.6.1.4.1.37950.1.1.5.10.20.3
-- 1.3.6.1.4.1.37950.1.1.5.10.20.3
-- 1.3.6.1.4.1.37950.1.1.5.10.20.3
-- 1.3.6.1.4.1.37950.1.1.5.10.20.3
-- 1.3.6.1.4.1.37950.1.1.5.10.20.3
		-- 1.3.6.1.4.1.37950.1.1.5.10.20.3
		mldUserVlanTable OBJECT-TYPE
			SYNTAX SEQUENCE OF MldUserVlanEntry
			MAX-ACCESS not-accessible
			STATUS current
			DESCRIPTION
				"Description."
			::= { v1600dIPv6MldSnooping 3 }

		
--         1.3.6.1.4.1.37950.1.1.5.10.20.3.1
-- 1.3.6.1.4.1.37950.1.1.5.10.20.3.1
-- 1.3.6.1.4.1.37950.1.1.5.10.20.3.1
-- 1.3.6.1.4.1.37950.1.1.5.10.20.3.1
-- 1.3.6.1.4.1.37950.1.1.5.10.20.3.1
-- 1.3.6.1.4.1.37950.1.1.5.10.20.3.1
-- 1.3.6.1.4.1.37950.1.1.5.10.20.3.1
-- 1.3.6.1.4.1.37950.1.1.5.10.20.3.1
		-- 1.3.6.1.4.1.37950.1.1.5.10.20.3.1
		mldUserVlanEntry OBJECT-TYPE
			SYNTAX MldUserVlanEntry
			MAX-ACCESS not-accessible
			STATUS current
			DESCRIPTION
				"Description."
			INDEX { mldUserPortIndex, mldUserVlanId }
			::= { mldUserVlanTable 1 }

		
		MldUserVlanEntry ::=
			SEQUENCE { 
				mldUserPortIndex
					Integer32,
				mldUserVlanId
					Integer32,
				mldGroupVlanId
					Integer32
			 }

--         1.3.6.1.4.1.37950.1.1.5.10.20.3.1.1
-- 1.3.6.1.4.1.37950.1.1.5.10.20.3.1.1
-- 1.3.6.1.4.1.37950.1.1.5.10.20.3.1.1
-- 1.3.6.1.4.1.37950.1.1.5.10.20.3.1.1
-- 1.3.6.1.4.1.37950.1.1.5.10.20.3.1.1
-- 1.3.6.1.4.1.37950.1.1.5.10.20.3.1.1
-- 1.3.6.1.4.1.37950.1.1.5.10.20.3.1.1
-- 1.3.6.1.4.1.37950.1.1.5.10.20.3.1.1
		-- 1.3.6.1.4.1.37950.1.1.5.10.20.3.1.1
		mldUserPortIndex OBJECT-TYPE
			SYNTAX Integer32
			MAX-ACCESS read-only
			STATUS current
			DESCRIPTION
				"Description."
			::= { mldUserVlanEntry 1 }

		
--         1.3.6.1.4.1.37950.1.1.5.10.20.3.1.2
-- 1.3.6.1.4.1.37950.1.1.5.10.20.3.1.2
-- 1.3.6.1.4.1.37950.1.1.5.10.20.3.1.2
-- 1.3.6.1.4.1.37950.1.1.5.10.20.3.1.2
-- 1.3.6.1.4.1.37950.1.1.5.10.20.3.1.2
-- 1.3.6.1.4.1.37950.1.1.5.10.20.3.1.2
-- 1.3.6.1.4.1.37950.1.1.5.10.20.3.1.2
-- 1.3.6.1.4.1.37950.1.1.5.10.20.3.1.2
		-- 1.3.6.1.4.1.37950.1.1.5.10.20.3.1.2
		mldUserVlanId OBJECT-TYPE
			SYNTAX Integer32
			MAX-ACCESS read-only
			STATUS current
			DESCRIPTION
				"Description."
			::= { mldUserVlanEntry 2 }

		
--         1.3.6.1.4.1.37950.1.1.5.10.20.3.1.3
-- 1.3.6.1.4.1.37950.1.1.5.10.20.3.1.3
-- 1.3.6.1.4.1.37950.1.1.5.10.20.3.1.3
-- 1.3.6.1.4.1.37950.1.1.5.10.20.3.1.3
-- 1.3.6.1.4.1.37950.1.1.5.10.20.3.1.3
-- 1.3.6.1.4.1.37950.1.1.5.10.20.3.1.3
-- 1.3.6.1.4.1.37950.1.1.5.10.20.3.1.3
-- 1.3.6.1.4.1.37950.1.1.5.10.20.3.1.3
		-- 1.3.6.1.4.1.37950.1.1.5.10.20.3.1.3
		mldGroupVlanId OBJECT-TYPE
			SYNTAX Integer32
			MAX-ACCESS read-only
			STATUS current
			DESCRIPTION
				"Description."
			::= { mldUserVlanEntry 3 }

		
--         1.3.6.1.4.1.37950.1.1.5.10.20.4
-- 1.3.6.1.4.1.37950.1.1.5.10.20.4
-- 1.3.6.1.4.1.37950.1.1.5.10.20.4
-- 1.3.6.1.4.1.37950.1.1.5.10.20.4
-- 1.3.6.1.4.1.37950.1.1.5.10.20.4
-- 1.3.6.1.4.1.37950.1.1.5.10.20.4
-- 1.3.6.1.4.1.37950.1.1.5.10.20.4
-- 1.3.6.1.4.1.37950.1.1.5.10.20.4
		-- 1.3.6.1.4.1.37950.1.1.5.10.20.4
		mldPortTable OBJECT-TYPE
			SYNTAX SEQUENCE OF MldPortEntry
			MAX-ACCESS not-accessible
			STATUS current
			DESCRIPTION
				"Description."
			::= { v1600dIPv6MldSnooping 4 }

		
--         1.3.6.1.4.1.37950.1.1.5.10.20.4.1
-- 1.3.6.1.4.1.37950.1.1.5.10.20.4.1
-- 1.3.6.1.4.1.37950.1.1.5.10.20.4.1
-- 1.3.6.1.4.1.37950.1.1.5.10.20.4.1
-- 1.3.6.1.4.1.37950.1.1.5.10.20.4.1
-- 1.3.6.1.4.1.37950.1.1.5.10.20.4.1
-- 1.3.6.1.4.1.37950.1.1.5.10.20.4.1
-- 1.3.6.1.4.1.37950.1.1.5.10.20.4.1
		-- 1.3.6.1.4.1.37950.1.1.5.10.20.4.1
		mldPortEntry OBJECT-TYPE
			SYNTAX MldPortEntry
			MAX-ACCESS not-accessible
			STATUS current
			DESCRIPTION
				"Description."
			INDEX { mldPortIndex }
			::= { mldPortTable 1 }

		
		MldPortEntry ::=
			SEQUENCE { 
				mldPortIndex
					Integer32,
				mldPortFastLeave
					INTEGER,
				mldPortGroupLimit
					Integer32
			 }

--         1.3.6.1.4.1.37950.1.1.5.10.20.4.1.1
-- 1.3.6.1.4.1.37950.1.1.5.10.20.4.1.1
-- 1.3.6.1.4.1.37950.1.1.5.10.20.4.1.1
-- 1.3.6.1.4.1.37950.1.1.5.10.20.4.1.1
-- 1.3.6.1.4.1.37950.1.1.5.10.20.4.1.1
-- 1.3.6.1.4.1.37950.1.1.5.10.20.4.1.1
-- 1.3.6.1.4.1.37950.1.1.5.10.20.4.1.1
-- 1.3.6.1.4.1.37950.1.1.5.10.20.4.1.1
		-- 1.3.6.1.4.1.37950.1.1.5.10.20.4.1.1
		mldPortIndex OBJECT-TYPE
			SYNTAX Integer32
			MAX-ACCESS read-only
			STATUS current
			DESCRIPTION
				"Description."
			::= { mldPortEntry 1 }

		
--         1.3.6.1.4.1.37950.1.1.5.10.20.4.1.2
-- 1.3.6.1.4.1.37950.1.1.5.10.20.4.1.2
-- 1.3.6.1.4.1.37950.1.1.5.10.20.4.1.2
-- 1.3.6.1.4.1.37950.1.1.5.10.20.4.1.2
-- 1.3.6.1.4.1.37950.1.1.5.10.20.4.1.2
-- 1.3.6.1.4.1.37950.1.1.5.10.20.4.1.2
-- 1.3.6.1.4.1.37950.1.1.5.10.20.4.1.2
-- 1.3.6.1.4.1.37950.1.1.5.10.20.4.1.2
		-- 1.3.6.1.4.1.37950.1.1.5.10.20.4.1.2
		mldPortFastLeave OBJECT-TYPE
			SYNTAX INTEGER
				{
				disable(0),
				enable(1)
				}
			MAX-ACCESS read-write
			STATUS current
			DESCRIPTION
				"Description."
			::= { mldPortEntry 2 }

		
--         1.3.6.1.4.1.37950.1.1.5.10.20.4.1.3
-- 1.3.6.1.4.1.37950.1.1.5.10.20.4.1.3
-- 1.3.6.1.4.1.37950.1.1.5.10.20.4.1.3
-- 1.3.6.1.4.1.37950.1.1.5.10.20.4.1.3
-- 1.3.6.1.4.1.37950.1.1.5.10.20.4.1.3
-- 1.3.6.1.4.1.37950.1.1.5.10.20.4.1.3
-- 1.3.6.1.4.1.37950.1.1.5.10.20.4.1.3
-- 1.3.6.1.4.1.37950.1.1.5.10.20.4.1.3
		-- 1.3.6.1.4.1.37950.1.1.5.10.20.4.1.3
		mldPortGroupLimit OBJECT-TYPE
			SYNTAX Integer32 (0..256)
			MAX-ACCESS read-write
			STATUS current
			DESCRIPTION
				"Description."
			::= { mldPortEntry 3 }

		
--         1.3.6.1.4.1.37950.1.1.5.10.20.5
-- 1.3.6.1.4.1.37950.1.1.5.10.20.5
-- 1.3.6.1.4.1.37950.1.1.5.10.20.5
-- 1.3.6.1.4.1.37950.1.1.5.10.20.5
-- 1.3.6.1.4.1.37950.1.1.5.10.20.5
-- 1.3.6.1.4.1.37950.1.1.5.10.20.5
-- 1.3.6.1.4.1.37950.1.1.5.10.20.5
-- 1.3.6.1.4.1.37950.1.1.5.10.20.5
		-- 1.3.6.1.4.1.37950.1.1.5.10.20.5
		mldMrouterPortCfg OBJECT IDENTIFIER ::= { v1600dIPv6MldSnooping 5 }

		
--         1.3.6.1.4.1.37950.1.1.5.10.20.5.1
-- 1.3.6.1.4.1.37950.1.1.5.10.20.5.1
-- 1.3.6.1.4.1.37950.1.1.5.10.20.5.1
-- 1.3.6.1.4.1.37950.1.1.5.10.20.5.1
-- 1.3.6.1.4.1.37950.1.1.5.10.20.5.1
-- 1.3.6.1.4.1.37950.1.1.5.10.20.5.1
-- 1.3.6.1.4.1.37950.1.1.5.10.20.5.1
-- 1.3.6.1.4.1.37950.1.1.5.10.20.5.1
		-- 1.3.6.1.4.1.37950.1.1.5.10.20.5.1
		mldMrouterPort OBJECT-TYPE
			SYNTAX Integer32
			MAX-ACCESS read-write
			STATUS current
			DESCRIPTION
				"Description."
			::= { mldMrouterPortCfg 1 }

		
--         1.3.6.1.4.1.37950.1.1.5.10.20.5.2
-- 1.3.6.1.4.1.37950.1.1.5.10.20.5.2
-- 1.3.6.1.4.1.37950.1.1.5.10.20.5.2
-- 1.3.6.1.4.1.37950.1.1.5.10.20.5.2
-- 1.3.6.1.4.1.37950.1.1.5.10.20.5.2
-- 1.3.6.1.4.1.37950.1.1.5.10.20.5.2
-- 1.3.6.1.4.1.37950.1.1.5.10.20.5.2
-- 1.3.6.1.4.1.37950.1.1.5.10.20.5.2
		-- 1.3.6.1.4.1.37950.1.1.5.10.20.5.2
		mldMrouterVlan OBJECT-TYPE
			SYNTAX Integer32 (1..4094)
			MAX-ACCESS read-write
			STATUS current
			DESCRIPTION
				"Description."
			::= { mldMrouterPortCfg 2 }

		
--         1.3.6.1.4.1.37950.1.1.5.10.20.5.3
-- 1.3.6.1.4.1.37950.1.1.5.10.20.5.3
-- 1.3.6.1.4.1.37950.1.1.5.10.20.5.3
-- 1.3.6.1.4.1.37950.1.1.5.10.20.5.3
-- 1.3.6.1.4.1.37950.1.1.5.10.20.5.3
-- 1.3.6.1.4.1.37950.1.1.5.10.20.5.3
-- 1.3.6.1.4.1.37950.1.1.5.10.20.5.3
-- 1.3.6.1.4.1.37950.1.1.5.10.20.5.3
		-- 1.3.6.1.4.1.37950.1.1.5.10.20.5.3
		mldMrouterAction OBJECT-TYPE
			SYNTAX INTEGER
				{
				add(1),
				del(2)
				}
			MAX-ACCESS read-write
			STATUS current
			DESCRIPTION
				"Description."
			::= { mldMrouterPortCfg 3 }

		
--         1.3.6.1.4.1.37950.1.1.5.10.20.6
-- 1.3.6.1.4.1.37950.1.1.5.10.20.6
-- 1.3.6.1.4.1.37950.1.1.5.10.20.6
-- 1.3.6.1.4.1.37950.1.1.5.10.20.6
-- 1.3.6.1.4.1.37950.1.1.5.10.20.6
-- 1.3.6.1.4.1.37950.1.1.5.10.20.6
-- 1.3.6.1.4.1.37950.1.1.5.10.20.6
-- 1.3.6.1.4.1.37950.1.1.5.10.20.6
		-- 1.3.6.1.4.1.37950.1.1.5.10.20.6
		mldMrouterPortTable OBJECT-TYPE
			SYNTAX SEQUENCE OF MldMrouterPortEntry
			MAX-ACCESS not-accessible
			STATUS current
			DESCRIPTION
				"Description."
			::= { v1600dIPv6MldSnooping 6 }

		
--         1.3.6.1.4.1.37950.1.1.5.10.20.6.1
-- 1.3.6.1.4.1.37950.1.1.5.10.20.6.1
-- 1.3.6.1.4.1.37950.1.1.5.10.20.6.1
-- 1.3.6.1.4.1.37950.1.1.5.10.20.6.1
-- 1.3.6.1.4.1.37950.1.1.5.10.20.6.1
-- 1.3.6.1.4.1.37950.1.1.5.10.20.6.1
-- 1.3.6.1.4.1.37950.1.1.5.10.20.6.1
-- 1.3.6.1.4.1.37950.1.1.5.10.20.6.1
		-- 1.3.6.1.4.1.37950.1.1.5.10.20.6.1
		mldMrouterPortEntry OBJECT-TYPE
			SYNTAX MldMrouterPortEntry
			MAX-ACCESS not-accessible
			STATUS current
			DESCRIPTION
				"Description."
			INDEX { mldMrouterItem }
			::= { mldMrouterPortTable 1 }

		
		MldMrouterPortEntry ::=
			SEQUENCE { 
				mldMrouterItem
					Integer32,
				mldMrouterVlanId
					Integer32,
				mldMrouterType
					INTEGER
			 }

--         1.3.6.1.4.1.37950.1.1.5.10.20.6.1.1
-- 1.3.6.1.4.1.37950.1.1.5.10.20.6.1.1
-- 1.3.6.1.4.1.37950.1.1.5.10.20.6.1.1
-- 1.3.6.1.4.1.37950.1.1.5.10.20.6.1.1
-- 1.3.6.1.4.1.37950.1.1.5.10.20.6.1.1
-- 1.3.6.1.4.1.37950.1.1.5.10.20.6.1.1
-- 1.3.6.1.4.1.37950.1.1.5.10.20.6.1.1
-- 1.3.6.1.4.1.37950.1.1.5.10.20.6.1.1
		-- 1.3.6.1.4.1.37950.1.1.5.10.20.6.1.1
		mldMrouterItem OBJECT-TYPE
			SYNTAX Integer32
			MAX-ACCESS read-only
			STATUS current
			DESCRIPTION
				"Description."
			::= { mldMrouterPortEntry 1 }

		
--         1.3.6.1.4.1.37950.1.1.5.10.20.6.1.2
-- 1.3.6.1.4.1.37950.1.1.5.10.20.6.1.2
-- 1.3.6.1.4.1.37950.1.1.5.10.20.6.1.2
-- 1.3.6.1.4.1.37950.1.1.5.10.20.6.1.2
-- 1.3.6.1.4.1.37950.1.1.5.10.20.6.1.2
-- 1.3.6.1.4.1.37950.1.1.5.10.20.6.1.2
-- 1.3.6.1.4.1.37950.1.1.5.10.20.6.1.2
-- 1.3.6.1.4.1.37950.1.1.5.10.20.6.1.2
		-- 1.3.6.1.4.1.37950.1.1.5.10.20.6.1.2
		mldMrouterVlanId OBJECT-TYPE
			SYNTAX Integer32
			MAX-ACCESS read-only
			STATUS current
			DESCRIPTION
				"Description."
			::= { mldMrouterPortEntry 2 }

		
--         1.3.6.1.4.1.37950.1.1.5.10.20.6.1.3
-- 1.3.6.1.4.1.37950.1.1.5.10.20.6.1.3
-- 1.3.6.1.4.1.37950.1.1.5.10.20.6.1.3
-- 1.3.6.1.4.1.37950.1.1.5.10.20.6.1.3
-- 1.3.6.1.4.1.37950.1.1.5.10.20.6.1.3
-- 1.3.6.1.4.1.37950.1.1.5.10.20.6.1.3
-- 1.3.6.1.4.1.37950.1.1.5.10.20.6.1.3
-- 1.3.6.1.4.1.37950.1.1.5.10.20.6.1.3
		-- 1.3.6.1.4.1.37950.1.1.5.10.20.6.1.3
		mldMrouterType OBJECT-TYPE
			SYNTAX INTEGER
				{
				static(1),
				dynamic(2)
				}
			MAX-ACCESS read-only
			STATUS current
			DESCRIPTION
				"Description."
			::= { mldMrouterPortEntry 3 }

		
--         1.3.6.1.4.1.37950.1.1.5.10.20.7
-- 1.3.6.1.4.1.37950.1.1.5.10.20.7
-- 1.3.6.1.4.1.37950.1.1.5.10.20.7
-- 1.3.6.1.4.1.37950.1.1.5.10.20.7
-- 1.3.6.1.4.1.37950.1.1.5.10.20.7
-- 1.3.6.1.4.1.37950.1.1.5.10.20.7
-- 1.3.6.1.4.1.37950.1.1.5.10.20.7
-- 1.3.6.1.4.1.37950.1.1.5.10.20.7
		-- 1.3.6.1.4.1.37950.1.1.5.10.20.7
		mldStaticGroupCfg OBJECT IDENTIFIER ::= { v1600dIPv6MldSnooping 7 }

		
--         1.3.6.1.4.1.37950.1.1.5.10.20.7.1
-- 1.3.6.1.4.1.37950.1.1.5.10.20.7.1
-- 1.3.6.1.4.1.37950.1.1.5.10.20.7.1
-- 1.3.6.1.4.1.37950.1.1.5.10.20.7.1
-- 1.3.6.1.4.1.37950.1.1.5.10.20.7.1
-- 1.3.6.1.4.1.37950.1.1.5.10.20.7.1
-- 1.3.6.1.4.1.37950.1.1.5.10.20.7.1
-- 1.3.6.1.4.1.37950.1.1.5.10.20.7.1
		-- 1.3.6.1.4.1.37950.1.1.5.10.20.7.1
		mldStaticGroupPort OBJECT-TYPE
			SYNTAX Integer32
			MAX-ACCESS read-write
			STATUS current
			DESCRIPTION
				"Description."
			::= { mldStaticGroupCfg 1 }

		
--         1.3.6.1.4.1.37950.1.1.5.10.20.7.2
-- 1.3.6.1.4.1.37950.1.1.5.10.20.7.2
-- 1.3.6.1.4.1.37950.1.1.5.10.20.7.2
-- 1.3.6.1.4.1.37950.1.1.5.10.20.7.2
-- 1.3.6.1.4.1.37950.1.1.5.10.20.7.2
-- 1.3.6.1.4.1.37950.1.1.5.10.20.7.2
-- 1.3.6.1.4.1.37950.1.1.5.10.20.7.2
-- 1.3.6.1.4.1.37950.1.1.5.10.20.7.2
		-- 1.3.6.1.4.1.37950.1.1.5.10.20.7.2
		mldStaticGroupIpv6 OBJECT-TYPE
			SYNTAX OCTET STRING
			MAX-ACCESS read-write
			STATUS current
			DESCRIPTION
				"Description."
			::= { mldStaticGroupCfg 2 }

		
--         1.3.6.1.4.1.37950.1.1.5.10.20.7.3
-- 1.3.6.1.4.1.37950.1.1.5.10.20.7.3
-- 1.3.6.1.4.1.37950.1.1.5.10.20.7.3
-- 1.3.6.1.4.1.37950.1.1.5.10.20.7.3
-- 1.3.6.1.4.1.37950.1.1.5.10.20.7.3
-- 1.3.6.1.4.1.37950.1.1.5.10.20.7.3
-- 1.3.6.1.4.1.37950.1.1.5.10.20.7.3
-- 1.3.6.1.4.1.37950.1.1.5.10.20.7.3
		-- 1.3.6.1.4.1.37950.1.1.5.10.20.7.3
		mldStaticGroupVlan OBJECT-TYPE
			SYNTAX Integer32 (1..4094)
			MAX-ACCESS read-write
			STATUS current
			DESCRIPTION
				"Description."
			::= { mldStaticGroupCfg 3 }

		
--         1.3.6.1.4.1.37950.1.1.5.10.20.7.4
-- 1.3.6.1.4.1.37950.1.1.5.10.20.7.4
-- 1.3.6.1.4.1.37950.1.1.5.10.20.7.4
-- 1.3.6.1.4.1.37950.1.1.5.10.20.7.4
-- 1.3.6.1.4.1.37950.1.1.5.10.20.7.4
-- 1.3.6.1.4.1.37950.1.1.5.10.20.7.4
-- 1.3.6.1.4.1.37950.1.1.5.10.20.7.4
-- 1.3.6.1.4.1.37950.1.1.5.10.20.7.4
		-- 1.3.6.1.4.1.37950.1.1.5.10.20.7.4
		mldStaticGroupAction OBJECT-TYPE
			SYNTAX INTEGER
				{
				add(1),
				del(2)
				}
			MAX-ACCESS read-write
			STATUS current
			DESCRIPTION
				"Description."
			::= { mldStaticGroupCfg 4 }

		
--         1.3.6.1.4.1.37950.1.1.5.10.20.8
-- 1.3.6.1.4.1.37950.1.1.5.10.20.8
-- 1.3.6.1.4.1.37950.1.1.5.10.20.8
-- 1.3.6.1.4.1.37950.1.1.5.10.20.8
-- 1.3.6.1.4.1.37950.1.1.5.10.20.8
-- 1.3.6.1.4.1.37950.1.1.5.10.20.8
-- 1.3.6.1.4.1.37950.1.1.5.10.20.8
-- 1.3.6.1.4.1.37950.1.1.5.10.20.8
		-- 1.3.6.1.4.1.37950.1.1.5.10.20.8
		mldStaticGroupTable OBJECT-TYPE
			SYNTAX SEQUENCE OF MldStaticGroupEntry
			MAX-ACCESS not-accessible
			STATUS current
			DESCRIPTION
				"Description."
			::= { v1600dIPv6MldSnooping 8 }

		
--         1.3.6.1.4.1.37950.1.1.5.10.20.8.1
-- 1.3.6.1.4.1.37950.1.1.5.10.20.8.1
-- 1.3.6.1.4.1.37950.1.1.5.10.20.8.1
-- 1.3.6.1.4.1.37950.1.1.5.10.20.8.1
-- 1.3.6.1.4.1.37950.1.1.5.10.20.8.1
-- 1.3.6.1.4.1.37950.1.1.5.10.20.8.1
-- 1.3.6.1.4.1.37950.1.1.5.10.20.8.1
-- 1.3.6.1.4.1.37950.1.1.5.10.20.8.1
		-- 1.3.6.1.4.1.37950.1.1.5.10.20.8.1
		mldStaticGroupEntry OBJECT-TYPE
			SYNTAX MldStaticGroupEntry
			MAX-ACCESS not-accessible
			STATUS current
			DESCRIPTION
				"Description."
			INDEX { mldStaticGroupVlanId, mldStaticGroupIpv6Addr }
			::= { mldStaticGroupTable 1 }

		
		MldStaticGroupEntry ::=
			SEQUENCE { 
				mldStaticGroupVlanId
					Integer32,
				mldStaticGroupIpv6Addr
					OCTET STRING,
				mldStaticGroupType
					INTEGER,
				mldStaticGroupVersion
					INTEGER,
				mldStaticGroupPortLlist
					OCTET STRING
			 }

--         1.3.6.1.4.1.37950.1.1.5.10.20.8.1.1
-- 1.3.6.1.4.1.37950.1.1.5.10.20.8.1.1
-- 1.3.6.1.4.1.37950.1.1.5.10.20.8.1.1
-- 1.3.6.1.4.1.37950.1.1.5.10.20.8.1.1
-- 1.3.6.1.4.1.37950.1.1.5.10.20.8.1.1
-- 1.3.6.1.4.1.37950.1.1.5.10.20.8.1.1
-- 1.3.6.1.4.1.37950.1.1.5.10.20.8.1.1
-- 1.3.6.1.4.1.37950.1.1.5.10.20.8.1.1
		-- 1.3.6.1.4.1.37950.1.1.5.10.20.8.1.1
		mldStaticGroupVlanId OBJECT-TYPE
			SYNTAX Integer32
			MAX-ACCESS read-only
			STATUS current
			DESCRIPTION
				"Description."
			::= { mldStaticGroupEntry 1 }

		
--         1.3.6.1.4.1.37950.1.1.5.10.20.8.1.2
-- 1.3.6.1.4.1.37950.1.1.5.10.20.8.1.2
-- 1.3.6.1.4.1.37950.1.1.5.10.20.8.1.2
-- 1.3.6.1.4.1.37950.1.1.5.10.20.8.1.2
-- 1.3.6.1.4.1.37950.1.1.5.10.20.8.1.2
-- 1.3.6.1.4.1.37950.1.1.5.10.20.8.1.2
-- 1.3.6.1.4.1.37950.1.1.5.10.20.8.1.2
-- 1.3.6.1.4.1.37950.1.1.5.10.20.8.1.2
		-- 1.3.6.1.4.1.37950.1.1.5.10.20.8.1.2
		mldStaticGroupIpv6Addr OBJECT-TYPE
			SYNTAX OCTET STRING
			MAX-ACCESS read-only
			STATUS current
			DESCRIPTION
				"Description."
			::= { mldStaticGroupEntry 2 }

		
--         1.3.6.1.4.1.37950.1.1.5.10.20.8.1.3
-- 1.3.6.1.4.1.37950.1.1.5.10.20.8.1.3
-- 1.3.6.1.4.1.37950.1.1.5.10.20.8.1.3
-- 1.3.6.1.4.1.37950.1.1.5.10.20.8.1.3
-- 1.3.6.1.4.1.37950.1.1.5.10.20.8.1.3
-- 1.3.6.1.4.1.37950.1.1.5.10.20.8.1.3
-- 1.3.6.1.4.1.37950.1.1.5.10.20.8.1.3
-- 1.3.6.1.4.1.37950.1.1.5.10.20.8.1.3
		-- 1.3.6.1.4.1.37950.1.1.5.10.20.8.1.3
		mldStaticGroupType OBJECT-TYPE
			SYNTAX INTEGER
				{
				static(1),
				dynamic(2)
				}
			MAX-ACCESS read-only
			STATUS current
			DESCRIPTION
				"Description."
			::= { mldStaticGroupEntry 3 }

		
--         1.3.6.1.4.1.37950.1.1.5.10.20.8.1.4
-- 1.3.6.1.4.1.37950.1.1.5.10.20.8.1.4
-- 1.3.6.1.4.1.37950.1.1.5.10.20.8.1.4
-- 1.3.6.1.4.1.37950.1.1.5.10.20.8.1.4
-- 1.3.6.1.4.1.37950.1.1.5.10.20.8.1.4
-- 1.3.6.1.4.1.37950.1.1.5.10.20.8.1.4
-- 1.3.6.1.4.1.37950.1.1.5.10.20.8.1.4
-- 1.3.6.1.4.1.37950.1.1.5.10.20.8.1.4
		-- 1.3.6.1.4.1.37950.1.1.5.10.20.8.1.4
		mldStaticGroupVersion OBJECT-TYPE
			SYNTAX INTEGER
				{
				v1(1),
				v2(2)
				}
			MAX-ACCESS read-only
			STATUS current
			DESCRIPTION
				"Description."
			::= { mldStaticGroupEntry 4 }

		
--         1.3.6.1.4.1.37950.1.1.5.10.20.8.1.5
-- 1.3.6.1.4.1.37950.1.1.5.10.20.8.1.5
-- 1.3.6.1.4.1.37950.1.1.5.10.20.8.1.5
-- 1.3.6.1.4.1.37950.1.1.5.10.20.8.1.5
-- 1.3.6.1.4.1.37950.1.1.5.10.20.8.1.5
-- 1.3.6.1.4.1.37950.1.1.5.10.20.8.1.5
-- 1.3.6.1.4.1.37950.1.1.5.10.20.8.1.5
-- 1.3.6.1.4.1.37950.1.1.5.10.20.8.1.5
		-- 1.3.6.1.4.1.37950.1.1.5.10.20.8.1.5
		mldStaticGroupPortLlist OBJECT-TYPE
			SYNTAX OCTET STRING
			MAX-ACCESS read-only
			STATUS current
			DESCRIPTION
				"Description."
			::= { mldStaticGroupEntry 5 }

		
--         1.3.6.1.4.1.37950.1.1.5.10.20.9
-- 1.3.6.1.4.1.37950.1.1.5.10.20.9
-- 1.3.6.1.4.1.37950.1.1.5.10.20.9
-- 1.3.6.1.4.1.37950.1.1.5.10.20.9
-- 1.3.6.1.4.1.37950.1.1.5.10.20.9
-- 1.3.6.1.4.1.37950.1.1.5.10.20.9
-- 1.3.6.1.4.1.37950.1.1.5.10.20.9
-- 1.3.6.1.4.1.37950.1.1.5.10.20.9
		-- 1.3.6.1.4.1.37950.1.1.5.10.20.9
		mldGroupMemberTable OBJECT-TYPE
			SYNTAX SEQUENCE OF MldGroupMemberEntry
			MAX-ACCESS not-accessible
			STATUS current
			DESCRIPTION
				"Description."
			::= { v1600dIPv6MldSnooping 9 }

		
--         1.3.6.1.4.1.37950.1.1.5.10.20.9.1
-- 1.3.6.1.4.1.37950.1.1.5.10.20.9.1
-- 1.3.6.1.4.1.37950.1.1.5.10.20.9.1
-- 1.3.6.1.4.1.37950.1.1.5.10.20.9.1
-- 1.3.6.1.4.1.37950.1.1.5.10.20.9.1
-- 1.3.6.1.4.1.37950.1.1.5.10.20.9.1
-- 1.3.6.1.4.1.37950.1.1.5.10.20.9.1
-- 1.3.6.1.4.1.37950.1.1.5.10.20.9.1
		-- 1.3.6.1.4.1.37950.1.1.5.10.20.9.1
		mldGroupMemberEntry OBJECT-TYPE
			SYNTAX MldGroupMemberEntry
			MAX-ACCESS not-accessible
			STATUS current
			DESCRIPTION
				"Description."
			INDEX { mldGroupMemberVlanId, mldGroupMemberIpv6 }
			::= { mldGroupMemberTable 1 }

		
		MldGroupMemberEntry ::=
			SEQUENCE { 
				mldGroupMemberVlanId
					Integer32,
				mldGroupMemberIpv6
					OCTET STRING,
				mldGroupMemberPortId
					Integer32,
				mldGroupMemberType
					INTEGER,
				mldGroupMemberUserVlanId
					Integer32
			 }

--         1.3.6.1.4.1.37950.1.1.5.10.20.9.1.1
-- 1.3.6.1.4.1.37950.1.1.5.10.20.9.1.1
-- 1.3.6.1.4.1.37950.1.1.5.10.20.9.1.1
-- 1.3.6.1.4.1.37950.1.1.5.10.20.9.1.1
-- 1.3.6.1.4.1.37950.1.1.5.10.20.9.1.1
-- 1.3.6.1.4.1.37950.1.1.5.10.20.9.1.1
-- 1.3.6.1.4.1.37950.1.1.5.10.20.9.1.1
-- 1.3.6.1.4.1.37950.1.1.5.10.20.9.1.1
		-- 1.3.6.1.4.1.37950.1.1.5.10.20.9.1.1
		mldGroupMemberVlanId OBJECT-TYPE
			SYNTAX Integer32
			MAX-ACCESS read-only
			STATUS current
			DESCRIPTION
				"Description."
			::= { mldGroupMemberEntry 1 }

		
--         1.3.6.1.4.1.37950.1.1.5.10.20.9.1.2
-- 1.3.6.1.4.1.37950.1.1.5.10.20.9.1.2
-- 1.3.6.1.4.1.37950.1.1.5.10.20.9.1.2
-- 1.3.6.1.4.1.37950.1.1.5.10.20.9.1.2
-- 1.3.6.1.4.1.37950.1.1.5.10.20.9.1.2
-- 1.3.6.1.4.1.37950.1.1.5.10.20.9.1.2
-- 1.3.6.1.4.1.37950.1.1.5.10.20.9.1.2
-- 1.3.6.1.4.1.37950.1.1.5.10.20.9.1.2
		-- 1.3.6.1.4.1.37950.1.1.5.10.20.9.1.2
		mldGroupMemberIpv6 OBJECT-TYPE
			SYNTAX OCTET STRING
			MAX-ACCESS read-only
			STATUS current
			DESCRIPTION
				"Description."
			::= { mldGroupMemberEntry 2 }

		
--         1.3.6.1.4.1.37950.1.1.5.10.20.9.1.3
-- 1.3.6.1.4.1.37950.1.1.5.10.20.9.1.3
-- 1.3.6.1.4.1.37950.1.1.5.10.20.9.1.3
-- 1.3.6.1.4.1.37950.1.1.5.10.20.9.1.3
-- 1.3.6.1.4.1.37950.1.1.5.10.20.9.1.3
-- 1.3.6.1.4.1.37950.1.1.5.10.20.9.1.3
-- 1.3.6.1.4.1.37950.1.1.5.10.20.9.1.3
-- 1.3.6.1.4.1.37950.1.1.5.10.20.9.1.3
		-- 1.3.6.1.4.1.37950.1.1.5.10.20.9.1.3
		mldGroupMemberPortId OBJECT-TYPE
			SYNTAX Integer32
			MAX-ACCESS read-only
			STATUS current
			DESCRIPTION
				"Description."
			::= { mldGroupMemberEntry 3 }

		
--         1.3.6.1.4.1.37950.1.1.5.10.20.9.1.4
-- 1.3.6.1.4.1.37950.1.1.5.10.20.9.1.4
-- 1.3.6.1.4.1.37950.1.1.5.10.20.9.1.4
-- 1.3.6.1.4.1.37950.1.1.5.10.20.9.1.4
-- 1.3.6.1.4.1.37950.1.1.5.10.20.9.1.4
-- 1.3.6.1.4.1.37950.1.1.5.10.20.9.1.4
-- 1.3.6.1.4.1.37950.1.1.5.10.20.9.1.4
-- 1.3.6.1.4.1.37950.1.1.5.10.20.9.1.4
		-- 1.3.6.1.4.1.37950.1.1.5.10.20.9.1.4
		mldGroupMemberType OBJECT-TYPE
			SYNTAX INTEGER
				{
				static(1),
				dynamic(2)
				}
			MAX-ACCESS read-only
			STATUS current
			DESCRIPTION
				"Description."
			::= { mldGroupMemberEntry 4 }

		
--         1.3.6.1.4.1.37950.1.1.5.10.20.9.1.5
-- 1.3.6.1.4.1.37950.1.1.5.10.20.9.1.5
-- 1.3.6.1.4.1.37950.1.1.5.10.20.9.1.5
-- 1.3.6.1.4.1.37950.1.1.5.10.20.9.1.5
-- 1.3.6.1.4.1.37950.1.1.5.10.20.9.1.5
-- 1.3.6.1.4.1.37950.1.1.5.10.20.9.1.5
-- 1.3.6.1.4.1.37950.1.1.5.10.20.9.1.5
-- 1.3.6.1.4.1.37950.1.1.5.10.20.9.1.5
		-- 1.3.6.1.4.1.37950.1.1.5.10.20.9.1.5
		mldGroupMemberUserVlanId OBJECT-TYPE
			SYNTAX Integer32
			MAX-ACCESS read-only
			STATUS current
			DESCRIPTION
				"Description."
			::= { mldGroupMemberEntry 5 }

		
--       1.3.6.1.4.1.37950.1.1.5.10.20.10
-- 1.3.6.1.4.1.37950.1.1.5.10.20.10
-- 1.3.6.1.4.1.37950.1.1.5.10.20.10
-- 1.3.6.1.4.1.37950.1.1.5.10.20.10
-- 1.3.6.1.4.1.37950.1.1.5.10.20.10
-- 1.3.6.1.4.1.37950.1.1.5.10.20.10
		-- 1.3.6.1.4.1.37950.1.1.5.10.20.10
		mldDefaultVlanCfg OBJECT IDENTIFIER ::= { v1600dIPv6MldSnooping 10 }

		
--       1.3.6.1.4.1.37950.1.1.5.10.20.10.1
-- 1.3.6.1.4.1.37950.1.1.5.10.20.10.1
-- 1.3.6.1.4.1.37950.1.1.5.10.20.10.1
-- 1.3.6.1.4.1.37950.1.1.5.10.20.10.1
-- 1.3.6.1.4.1.37950.1.1.5.10.20.10.1
-- 1.3.6.1.4.1.37950.1.1.5.10.20.10.1
		-- 1.3.6.1.4.1.37950.1.1.5.10.20.10.1
		mldDefaultVlanIdCfg OBJECT-TYPE
			SYNTAX Integer32 (1..4094)
			MAX-ACCESS read-write
			STATUS current
			DESCRIPTION
				"Description."
			::= { mldDefaultVlanCfg 1 }

		
--       1.3.6.1.4.1.37950.1.1.5.10.20.10.2
-- 1.3.6.1.4.1.37950.1.1.5.10.20.10.2
-- 1.3.6.1.4.1.37950.1.1.5.10.20.10.2
-- 1.3.6.1.4.1.37950.1.1.5.10.20.10.2
-- 1.3.6.1.4.1.37950.1.1.5.10.20.10.2
-- 1.3.6.1.4.1.37950.1.1.5.10.20.10.2
		-- 1.3.6.1.4.1.37950.1.1.5.10.20.10.2
		mldDefaultVlanAction OBJECT-TYPE
			SYNTAX INTEGER
				{
				add(1),
				delete(2)
				}
			MAX-ACCESS read-write
			STATUS current
			DESCRIPTION
				"Description."
			::= { mldDefaultVlanCfg 2 }

		
--         1.3.6.1.4.1.37950.1.1.5.10.21
-- 1.3.6.1.4.1.37950.1.1.5.10.21
-- 1.3.6.1.4.1.37950.1.1.5.10.21
-- 1.3.6.1.4.1.37950.1.1.5.10.21
-- 1.3.6.1.4.1.37950.1.1.5.10.21
-- 1.3.6.1.4.1.37950.1.1.5.10.21
-- 1.3.6.1.4.1.37950.1.1.5.10.21
-- 1.3.6.1.4.1.37950.1.1.5.10.21
		-- 1.3.6.1.4.1.37950.1.1.5.10.21
		v1600dSSH OBJECT IDENTIFIER ::= { v1600dSwitch 21 }

		
--         1.3.6.1.4.1.37950.1.1.5.10.21.1
-- 1.3.6.1.4.1.37950.1.1.5.10.21.1
-- 1.3.6.1.4.1.37950.1.1.5.10.21.1
-- 1.3.6.1.4.1.37950.1.1.5.10.21.1
-- 1.3.6.1.4.1.37950.1.1.5.10.21.1
-- 1.3.6.1.4.1.37950.1.1.5.10.21.1
-- 1.3.6.1.4.1.37950.1.1.5.10.21.1
-- 1.3.6.1.4.1.37950.1.1.5.10.21.1
		-- 1.3.6.1.4.1.37950.1.1.5.10.21.1
		sshConnectInfoTable OBJECT-TYPE
			SYNTAX SEQUENCE OF SshConnectInfoEntry
			MAX-ACCESS not-accessible
			STATUS current
			DESCRIPTION
				"Description."
			::= { v1600dSSH 1 }

		
--         1.3.6.1.4.1.37950.1.1.5.10.21.1.1
-- 1.3.6.1.4.1.37950.1.1.5.10.21.1.1
-- 1.3.6.1.4.1.37950.1.1.5.10.21.1.1
-- 1.3.6.1.4.1.37950.1.1.5.10.21.1.1
-- 1.3.6.1.4.1.37950.1.1.5.10.21.1.1
-- 1.3.6.1.4.1.37950.1.1.5.10.21.1.1
-- 1.3.6.1.4.1.37950.1.1.5.10.21.1.1
-- 1.3.6.1.4.1.37950.1.1.5.10.21.1.1
		-- 1.3.6.1.4.1.37950.1.1.5.10.21.1.1
		sshConnectInfoEntry OBJECT-TYPE
			SYNTAX SshConnectInfoEntry
			MAX-ACCESS not-accessible
			STATUS current
			DESCRIPTION
				"Description."
			INDEX { sshConnections }
			::= { sshConnectInfoTable 1 }

		
		SshConnectInfoEntry ::=
			SEQUENCE { 
				sshConnections
					Integer32,
				sshVersion
					INTEGER,
				sshMode
					OCTET STRING,
				sshEncryption
					OCTET STRING,
				sshHmac
					OCTET STRING,
				sshState
					OCTET STRING,
				sshUsername
					OCTET STRING
			 }

--         1.3.6.1.4.1.37950.1.1.5.10.21.1.1.1
-- 1.3.6.1.4.1.37950.1.1.5.10.21.1.1.1
-- 1.3.6.1.4.1.37950.1.1.5.10.21.1.1.1
-- 1.3.6.1.4.1.37950.1.1.5.10.21.1.1.1
-- 1.3.6.1.4.1.37950.1.1.5.10.21.1.1.1
-- 1.3.6.1.4.1.37950.1.1.5.10.21.1.1.1
-- 1.3.6.1.4.1.37950.1.1.5.10.21.1.1.1
-- 1.3.6.1.4.1.37950.1.1.5.10.21.1.1.1
		-- 1.3.6.1.4.1.37950.1.1.5.10.21.1.1.1
		sshConnections OBJECT-TYPE
			SYNTAX Integer32
			MAX-ACCESS read-only
			STATUS current
			DESCRIPTION
				"Description."
			::= { sshConnectInfoEntry 1 }

		
--         1.3.6.1.4.1.37950.1.1.5.10.21.1.1.2
-- 1.3.6.1.4.1.37950.1.1.5.10.21.1.1.2
-- 1.3.6.1.4.1.37950.1.1.5.10.21.1.1.2
-- 1.3.6.1.4.1.37950.1.1.5.10.21.1.1.2
-- 1.3.6.1.4.1.37950.1.1.5.10.21.1.1.2
-- 1.3.6.1.4.1.37950.1.1.5.10.21.1.1.2
-- 1.3.6.1.4.1.37950.1.1.5.10.21.1.1.2
-- 1.3.6.1.4.1.37950.1.1.5.10.21.1.1.2
		-- 1.3.6.1.4.1.37950.1.1.5.10.21.1.1.2
		sshVersion OBJECT-TYPE
			SYNTAX INTEGER
				{
				version1(1),
				version2(2)
				}
			MAX-ACCESS read-only
			STATUS current
			DESCRIPTION
				"Description."
			::= { sshConnectInfoEntry 2 }

		
--         1.3.6.1.4.1.37950.1.1.5.10.21.1.1.3
-- 1.3.6.1.4.1.37950.1.1.5.10.21.1.1.3
-- 1.3.6.1.4.1.37950.1.1.5.10.21.1.1.3
-- 1.3.6.1.4.1.37950.1.1.5.10.21.1.1.3
-- 1.3.6.1.4.1.37950.1.1.5.10.21.1.1.3
-- 1.3.6.1.4.1.37950.1.1.5.10.21.1.1.3
-- 1.3.6.1.4.1.37950.1.1.5.10.21.1.1.3
-- 1.3.6.1.4.1.37950.1.1.5.10.21.1.1.3
		-- 1.3.6.1.4.1.37950.1.1.5.10.21.1.1.3
		sshMode OBJECT-TYPE
			SYNTAX OCTET STRING
			MAX-ACCESS read-only
			STATUS current
			DESCRIPTION
				"Description."
			::= { sshConnectInfoEntry 3 }

		
--         1.3.6.1.4.1.37950.1.1.5.10.21.1.1.4
-- 1.3.6.1.4.1.37950.1.1.5.10.21.1.1.4
-- 1.3.6.1.4.1.37950.1.1.5.10.21.1.1.4
-- 1.3.6.1.4.1.37950.1.1.5.10.21.1.1.4
-- 1.3.6.1.4.1.37950.1.1.5.10.21.1.1.4
-- 1.3.6.1.4.1.37950.1.1.5.10.21.1.1.4
-- 1.3.6.1.4.1.37950.1.1.5.10.21.1.1.4
-- 1.3.6.1.4.1.37950.1.1.5.10.21.1.1.4
		-- 1.3.6.1.4.1.37950.1.1.5.10.21.1.1.4
		sshEncryption OBJECT-TYPE
			SYNTAX OCTET STRING
			MAX-ACCESS read-only
			STATUS current
			DESCRIPTION
				"Description."
			::= { sshConnectInfoEntry 4 }

		
--         1.3.6.1.4.1.37950.1.1.5.10.21.1.1.5
-- 1.3.6.1.4.1.37950.1.1.5.10.21.1.1.5
-- 1.3.6.1.4.1.37950.1.1.5.10.21.1.1.5
-- 1.3.6.1.4.1.37950.1.1.5.10.21.1.1.5
-- 1.3.6.1.4.1.37950.1.1.5.10.21.1.1.5
-- 1.3.6.1.4.1.37950.1.1.5.10.21.1.1.5
-- 1.3.6.1.4.1.37950.1.1.5.10.21.1.1.5
-- 1.3.6.1.4.1.37950.1.1.5.10.21.1.1.5
		-- 1.3.6.1.4.1.37950.1.1.5.10.21.1.1.5
		sshHmac OBJECT-TYPE
			SYNTAX OCTET STRING
			MAX-ACCESS read-only
			STATUS current
			DESCRIPTION
				"Description."
			::= { sshConnectInfoEntry 5 }

		
--         1.3.6.1.4.1.37950.1.1.5.10.21.1.1.6
-- 1.3.6.1.4.1.37950.1.1.5.10.21.1.1.6
-- 1.3.6.1.4.1.37950.1.1.5.10.21.1.1.6
-- 1.3.6.1.4.1.37950.1.1.5.10.21.1.1.6
-- 1.3.6.1.4.1.37950.1.1.5.10.21.1.1.6
-- 1.3.6.1.4.1.37950.1.1.5.10.21.1.1.6
-- 1.3.6.1.4.1.37950.1.1.5.10.21.1.1.6
-- 1.3.6.1.4.1.37950.1.1.5.10.21.1.1.6
		-- 1.3.6.1.4.1.37950.1.1.5.10.21.1.1.6
		sshState OBJECT-TYPE
			SYNTAX OCTET STRING
			MAX-ACCESS read-only
			STATUS current
			DESCRIPTION
				"Description."
			::= { sshConnectInfoEntry 6 }

		
--         1.3.6.1.4.1.37950.1.1.5.10.21.1.1.7
-- 1.3.6.1.4.1.37950.1.1.5.10.21.1.1.7
-- 1.3.6.1.4.1.37950.1.1.5.10.21.1.1.7
-- 1.3.6.1.4.1.37950.1.1.5.10.21.1.1.7
-- 1.3.6.1.4.1.37950.1.1.5.10.21.1.1.7
-- 1.3.6.1.4.1.37950.1.1.5.10.21.1.1.7
-- 1.3.6.1.4.1.37950.1.1.5.10.21.1.1.7
-- 1.3.6.1.4.1.37950.1.1.5.10.21.1.1.7
		-- 1.3.6.1.4.1.37950.1.1.5.10.21.1.1.7
		sshUsername OBJECT-TYPE
			SYNTAX OCTET STRING
			MAX-ACCESS read-only
			STATUS current
			DESCRIPTION
				"Description."
			::= { sshConnectInfoEntry 7 }

		
--         1.3.6.1.4.1.37950.1.1.5.10.21.2
-- 1.3.6.1.4.1.37950.1.1.5.10.21.2
-- 1.3.6.1.4.1.37950.1.1.5.10.21.2
-- 1.3.6.1.4.1.37950.1.1.5.10.21.2
-- 1.3.6.1.4.1.37950.1.1.5.10.21.2
-- 1.3.6.1.4.1.37950.1.1.5.10.21.2
-- 1.3.6.1.4.1.37950.1.1.5.10.21.2
-- 1.3.6.1.4.1.37950.1.1.5.10.21.2
		-- 1.3.6.1.4.1.37950.1.1.5.10.21.2
		sshEnable OBJECT IDENTIFIER ::= { v1600dSSH 2 }

		
--         1.3.6.1.4.1.37950.1.1.5.10.21.2.1
-- 1.3.6.1.4.1.37950.1.1.5.10.21.2.1
-- 1.3.6.1.4.1.37950.1.1.5.10.21.2.1
-- 1.3.6.1.4.1.37950.1.1.5.10.21.2.1
-- 1.3.6.1.4.1.37950.1.1.5.10.21.2.1
-- 1.3.6.1.4.1.37950.1.1.5.10.21.2.1
-- 1.3.6.1.4.1.37950.1.1.5.10.21.2.1
-- 1.3.6.1.4.1.37950.1.1.5.10.21.2.1
		-- 1.3.6.1.4.1.37950.1.1.5.10.21.2.1
		sshEn OBJECT-TYPE
			SYNTAX INTEGER
				{
				sshdisable(0),
				sshenable(1)
				}
			MAX-ACCESS read-write
			STATUS current
			DESCRIPTION
				"Description."
			DEFVAL { 1 }
			::= { sshEnable 1 }

		
--         1.3.6.1.4.1.37950.1.1.5.10.21.2.2
-- 1.3.6.1.4.1.37950.1.1.5.10.21.2.2
-- 1.3.6.1.4.1.37950.1.1.5.10.21.2.2
-- 1.3.6.1.4.1.37950.1.1.5.10.21.2.2
-- 1.3.6.1.4.1.37950.1.1.5.10.21.2.2
-- 1.3.6.1.4.1.37950.1.1.5.10.21.2.2
-- 1.3.6.1.4.1.37950.1.1.5.10.21.2.2
-- 1.3.6.1.4.1.37950.1.1.5.10.21.2.2
		-- 1.3.6.1.4.1.37950.1.1.5.10.21.2.2
		sshversion OBJECT-TYPE
			SYNTAX INTEGER
				{
				version1(1),
				version2(2)
				}
			MAX-ACCESS read-write
			STATUS current
			DESCRIPTION
				"Description."
			DEFVAL { 2 }
			::= { sshEnable 2 }

		
--         1.3.6.1.4.1.37950.1.1.5.10.21.2.3
-- 1.3.6.1.4.1.37950.1.1.5.10.21.2.3
-- 1.3.6.1.4.1.37950.1.1.5.10.21.2.3
-- 1.3.6.1.4.1.37950.1.1.5.10.21.2.3
-- 1.3.6.1.4.1.37950.1.1.5.10.21.2.3
-- 1.3.6.1.4.1.37950.1.1.5.10.21.2.3
-- 1.3.6.1.4.1.37950.1.1.5.10.21.2.3
-- 1.3.6.1.4.1.37950.1.1.5.10.21.2.3
		-- 1.3.6.1.4.1.37950.1.1.5.10.21.2.3
		sshAuthRetries OBJECT-TYPE
			SYNTAX Integer32
			MAX-ACCESS read-write
			STATUS current
			DESCRIPTION
				"Description."
			DEFVAL { 6 }
			::= { sshEnable 3 }

		
--         1.3.6.1.4.1.37950.1.1.5.10.21.2.4
-- 1.3.6.1.4.1.37950.1.1.5.10.21.2.4
-- 1.3.6.1.4.1.37950.1.1.5.10.21.2.4
-- 1.3.6.1.4.1.37950.1.1.5.10.21.2.4
-- 1.3.6.1.4.1.37950.1.1.5.10.21.2.4
-- 1.3.6.1.4.1.37950.1.1.5.10.21.2.4
-- 1.3.6.1.4.1.37950.1.1.5.10.21.2.4
-- 1.3.6.1.4.1.37950.1.1.5.10.21.2.4
		-- 1.3.6.1.4.1.37950.1.1.5.10.21.2.4
		sshTimeout OBJECT-TYPE
			SYNTAX Integer32
			MAX-ACCESS read-write
			STATUS current
			DESCRIPTION
				"Description."
			DEFVAL { 120 }
			::= { sshEnable 4 }

		
		-- 1.3.6.1.4.1.37950.1.1.5.10.21.2.5
		sshMaxStartups OBJECT-TYPE
			SYNTAX Integer32 (1..5)
			MAX-ACCESS read-write
			STATUS current
			DESCRIPTION
				"Description."
			::= { sshEnable 5 }

		
		-- 1.3.6.1.4.1.37950.1.1.5.10.21.2.6
		sshMaxSessions OBJECT-TYPE
			SYNTAX Integer32 (1..12)
			MAX-ACCESS read-write
			STATUS current
			DESCRIPTION
				"Description."
			::= { sshEnable 6 }

		
		-- 1.3.6.1.4.1.37950.1.1.5.10.21.2.7
		sshKeyType OBJECT-TYPE
			SYNTAX INTEGER
				{
				rsa(0),
				ecdsa(1)
				}
			MAX-ACCESS read-write
			STATUS current
			DESCRIPTION
				"Description."
			::= { sshEnable 7 }

		
--         1.3.6.1.4.1.37950.1.1.5.10.21.2.5
-- 1.3.6.1.4.1.37950.1.1.5.10.21.2.5
-- 1.3.6.1.4.1.37950.1.1.5.10.21.2.5
-- 1.3.6.1.4.1.37950.1.1.5.10.21.2.5
-- 1.3.6.1.4.1.37950.1.1.5.10.21.2.5
-- 1.3.6.1.4.1.37950.1.1.5.10.21.2.5
-- 1.3.6.1.4.1.37950.1.1.5.10.21.2.5
-- 1.3.6.1.4.1.37950.1.1.5.10.21.2.5
		-- 1.3.6.1.4.1.37950.1.1.5.10.21.2.8
		sshModulus OBJECT-TYPE
			SYNTAX Integer32
			MAX-ACCESS read-write
			STATUS current
			DESCRIPTION
				"Description."
			DEFVAL { 2048 }
			::= { sshEnable 8 }

		
--         1.3.6.1.4.1.37950.1.1.5.10.21.2.6
-- 1.3.6.1.4.1.37950.1.1.5.10.21.2.6
-- 1.3.6.1.4.1.37950.1.1.5.10.21.2.6
-- 1.3.6.1.4.1.37950.1.1.5.10.21.2.6
-- 1.3.6.1.4.1.37950.1.1.5.10.21.2.6
-- 1.3.6.1.4.1.37950.1.1.5.10.21.2.6
-- 1.3.6.1.4.1.37950.1.1.5.10.21.2.6
-- 1.3.6.1.4.1.37950.1.1.5.10.21.2.6
		-- 1.3.6.1.4.1.37950.1.1.5.10.21.2.9
		sshEnableAction OBJECT-TYPE
			SYNTAX INTEGER
				{
				add(1),
				del(2)
				}
			MAX-ACCESS read-write
			STATUS current
			DESCRIPTION
				"Description."
			::= { sshEnable 9 }

		
--         1.3.6.1.4.1.37950.1.1.5.10.22
-- 1.3.6.1.4.1.37950.1.1.5.10.22
-- 1.3.6.1.4.1.37950.1.1.5.10.22
-- 1.3.6.1.4.1.37950.1.1.5.10.22
-- 1.3.6.1.4.1.37950.1.1.5.10.22
-- 1.3.6.1.4.1.37950.1.1.5.10.22
-- 1.3.6.1.4.1.37950.1.1.5.10.22
-- 1.3.6.1.4.1.37950.1.1.5.10.22
		-- 1.3.6.1.4.1.37950.1.1.5.10.22
		v3500DHCP OBJECT IDENTIFIER ::= { v1600dSwitch 22 }

		
--         1.3.6.1.4.1.37950.1.1.5.10.22.1
-- 1.3.6.1.4.1.37950.1.1.5.10.22.1
-- 1.3.6.1.4.1.37950.1.1.5.10.22.1
-- 1.3.6.1.4.1.37950.1.1.5.10.22.1
-- 1.3.6.1.4.1.37950.1.1.5.10.22.1
-- 1.3.6.1.4.1.37950.1.1.5.10.22.1
-- 1.3.6.1.4.1.37950.1.1.5.10.22.1
-- 1.3.6.1.4.1.37950.1.1.5.10.22.1
		-- 1.3.6.1.4.1.37950.1.1.5.10.22.1
		v3500DHCPServer OBJECT IDENTIFIER ::= { v3500DHCP 1 }

		
--         1.3.6.1.4.1.37950.1.1.5.10.22.1.1
-- 1.3.6.1.4.1.37950.1.1.5.10.22.1.1
-- 1.3.6.1.4.1.37950.1.1.5.10.22.1.1
-- 1.3.6.1.4.1.37950.1.1.5.10.22.1.1
-- 1.3.6.1.4.1.37950.1.1.5.10.22.1.1
-- 1.3.6.1.4.1.37950.1.1.5.10.22.1.1
-- 1.3.6.1.4.1.37950.1.1.5.10.22.1.1
-- 1.3.6.1.4.1.37950.1.1.5.10.22.1.1
		-- 1.3.6.1.4.1.37950.1.1.5.10.22.1.1
		dhcpPool OBJECT IDENTIFIER ::= { v3500DHCPServer 1 }

		
--         1.3.6.1.4.1.37950.1.1.5.10.22.1.1.1
-- 1.3.6.1.4.1.37950.1.1.5.10.22.1.1.1
-- 1.3.6.1.4.1.37950.1.1.5.10.22.1.1.1
-- 1.3.6.1.4.1.37950.1.1.5.10.22.1.1.1
-- 1.3.6.1.4.1.37950.1.1.5.10.22.1.1.1
-- 1.3.6.1.4.1.37950.1.1.5.10.22.1.1.1
-- 1.3.6.1.4.1.37950.1.1.5.10.22.1.1.1
-- 1.3.6.1.4.1.37950.1.1.5.10.22.1.1.1
		-- 1.3.6.1.4.1.37950.1.1.5.10.22.1.1.1
		dhcpPoolName OBJECT-TYPE
			SYNTAX OCTET STRING
			MAX-ACCESS read-write
			STATUS current
			DESCRIPTION
				"Description."
			::= { dhcpPool 1 }

		
--         1.3.6.1.4.1.37950.1.1.5.10.22.1.1.2
-- 1.3.6.1.4.1.37950.1.1.5.10.22.1.1.2
-- 1.3.6.1.4.1.37950.1.1.5.10.22.1.1.2
-- 1.3.6.1.4.1.37950.1.1.5.10.22.1.1.2
-- 1.3.6.1.4.1.37950.1.1.5.10.22.1.1.2
-- 1.3.6.1.4.1.37950.1.1.5.10.22.1.1.2
-- 1.3.6.1.4.1.37950.1.1.5.10.22.1.1.2
-- 1.3.6.1.4.1.37950.1.1.5.10.22.1.1.2
		-- 1.3.6.1.4.1.37950.1.1.5.10.22.1.1.2
		dhcpPoolLeasetime OBJECT-TYPE
			SYNTAX Unsigned32 (60..864000)
			MAX-ACCESS read-write
			STATUS current
			DESCRIPTION
				"Description."
			::= { dhcpPool 2 }

		
--         1.3.6.1.4.1.37950.1.1.5.10.22.1.1.3
-- 1.3.6.1.4.1.37950.1.1.5.10.22.1.1.3
-- 1.3.6.1.4.1.37950.1.1.5.10.22.1.1.3
-- 1.3.6.1.4.1.37950.1.1.5.10.22.1.1.3
-- 1.3.6.1.4.1.37950.1.1.5.10.22.1.1.3
-- 1.3.6.1.4.1.37950.1.1.5.10.22.1.1.3
-- 1.3.6.1.4.1.37950.1.1.5.10.22.1.1.3
-- 1.3.6.1.4.1.37950.1.1.5.10.22.1.1.3
		-- 1.3.6.1.4.1.37950.1.1.5.10.22.1.1.3
		dhcpPoolGw OBJECT-TYPE
			SYNTAX IpAddress
			MAX-ACCESS read-write
			STATUS current
			DESCRIPTION
				"Description."
			DEFVAL { '0000'h }
			::= { dhcpPool 3 }

		
--         1.3.6.1.4.1.37950.1.1.5.10.22.1.1.4
-- 1.3.6.1.4.1.37950.1.1.5.10.22.1.1.4
-- 1.3.6.1.4.1.37950.1.1.5.10.22.1.1.4
-- 1.3.6.1.4.1.37950.1.1.5.10.22.1.1.4
-- 1.3.6.1.4.1.37950.1.1.5.10.22.1.1.4
-- 1.3.6.1.4.1.37950.1.1.5.10.22.1.1.4
-- 1.3.6.1.4.1.37950.1.1.5.10.22.1.1.4
-- 1.3.6.1.4.1.37950.1.1.5.10.22.1.1.4
		-- 1.3.6.1.4.1.37950.1.1.5.10.22.1.1.4
		dhcpPoolDNS1 OBJECT-TYPE
			SYNTAX IpAddress
			MAX-ACCESS read-write
			STATUS current
			DESCRIPTION
				"Description."
			DEFVAL { '0000'h }
			::= { dhcpPool 4 }

		
--         1.3.6.1.4.1.37950.1.1.5.10.22.1.1.5
-- 1.3.6.1.4.1.37950.1.1.5.10.22.1.1.5
-- 1.3.6.1.4.1.37950.1.1.5.10.22.1.1.5
-- 1.3.6.1.4.1.37950.1.1.5.10.22.1.1.5
-- 1.3.6.1.4.1.37950.1.1.5.10.22.1.1.5
-- 1.3.6.1.4.1.37950.1.1.5.10.22.1.1.5
-- 1.3.6.1.4.1.37950.1.1.5.10.22.1.1.5
-- 1.3.6.1.4.1.37950.1.1.5.10.22.1.1.5
		-- 1.3.6.1.4.1.37950.1.1.5.10.22.1.1.5
		dhcpPoolDNS2 OBJECT-TYPE
			SYNTAX IpAddress
			MAX-ACCESS read-write
			STATUS current
			DESCRIPTION
				"Description."
			::= { dhcpPool 5 }

		
--         1.3.6.1.4.1.37950.1.1.5.10.22.1.1.6
-- 1.3.6.1.4.1.37950.1.1.5.10.22.1.1.6
-- 1.3.6.1.4.1.37950.1.1.5.10.22.1.1.6
-- 1.3.6.1.4.1.37950.1.1.5.10.22.1.1.6
-- 1.3.6.1.4.1.37950.1.1.5.10.22.1.1.6
-- 1.3.6.1.4.1.37950.1.1.5.10.22.1.1.6
-- 1.3.6.1.4.1.37950.1.1.5.10.22.1.1.6
-- 1.3.6.1.4.1.37950.1.1.5.10.22.1.1.6
		-- 1.3.6.1.4.1.37950.1.1.5.10.22.1.1.6
		dhcpPoolDNS3 OBJECT-TYPE
			SYNTAX IpAddress
			MAX-ACCESS read-write
			STATUS current
			DESCRIPTION
				"Description."
			::= { dhcpPool 6 }

		
--         1.3.6.1.4.1.37950.1.1.5.10.22.1.1.7
-- 1.3.6.1.4.1.37950.1.1.5.10.22.1.1.7
-- 1.3.6.1.4.1.37950.1.1.5.10.22.1.1.7
-- 1.3.6.1.4.1.37950.1.1.5.10.22.1.1.7
-- 1.3.6.1.4.1.37950.1.1.5.10.22.1.1.7
-- 1.3.6.1.4.1.37950.1.1.5.10.22.1.1.7
-- 1.3.6.1.4.1.37950.1.1.5.10.22.1.1.7
-- 1.3.6.1.4.1.37950.1.1.5.10.22.1.1.7
		-- 1.3.6.1.4.1.37950.1.1.5.10.22.1.1.7
		dhcpPoolWins OBJECT-TYPE
			SYNTAX IpAddress
			MAX-ACCESS read-write
			STATUS current
			DESCRIPTION
				"Description."
			::= { dhcpPool 7 }

		
--         1.3.6.1.4.1.37950.1.1.5.10.22.1.1.8
-- 1.3.6.1.4.1.37950.1.1.5.10.22.1.1.8
-- 1.3.6.1.4.1.37950.1.1.5.10.22.1.1.8
-- 1.3.6.1.4.1.37950.1.1.5.10.22.1.1.8
-- 1.3.6.1.4.1.37950.1.1.5.10.22.1.1.8
-- 1.3.6.1.4.1.37950.1.1.5.10.22.1.1.8
-- 1.3.6.1.4.1.37950.1.1.5.10.22.1.1.8
-- 1.3.6.1.4.1.37950.1.1.5.10.22.1.1.8
		-- 1.3.6.1.4.1.37950.1.1.5.10.22.1.1.8
		dhcpPoolNetwork OBJECT-TYPE
			SYNTAX IpAddress
			MAX-ACCESS read-write
			STATUS current
			DESCRIPTION
				"Description."
			::= { dhcpPool 8 }

		
--         1.3.6.1.4.1.37950.1.1.5.10.22.1.1.9
-- 1.3.6.1.4.1.37950.1.1.5.10.22.1.1.9
-- 1.3.6.1.4.1.37950.1.1.5.10.22.1.1.9
-- 1.3.6.1.4.1.37950.1.1.5.10.22.1.1.9
-- 1.3.6.1.4.1.37950.1.1.5.10.22.1.1.9
-- 1.3.6.1.4.1.37950.1.1.5.10.22.1.1.9
-- 1.3.6.1.4.1.37950.1.1.5.10.22.1.1.9
-- 1.3.6.1.4.1.37950.1.1.5.10.22.1.1.9
		-- 1.3.6.1.4.1.37950.1.1.5.10.22.1.1.9
		dhcpPoolNetworkSubnet OBJECT-TYPE
			SYNTAX IpAddress
			MAX-ACCESS read-write
			STATUS current
			DESCRIPTION
				"Description."
			::= { dhcpPool 9 }

		
--         1.3.6.1.4.1.37950.1.1.5.10.22.1.1.10
-- 1.3.6.1.4.1.37950.1.1.5.10.22.1.1.10
-- 1.3.6.1.4.1.37950.1.1.5.10.22.1.1.10
-- 1.3.6.1.4.1.37950.1.1.5.10.22.1.1.10
-- 1.3.6.1.4.1.37950.1.1.5.10.22.1.1.10
-- 1.3.6.1.4.1.37950.1.1.5.10.22.1.1.10
-- 1.3.6.1.4.1.37950.1.1.5.10.22.1.1.10
-- 1.3.6.1.4.1.37950.1.1.5.10.22.1.1.10
		-- 1.3.6.1.4.1.37950.1.1.5.10.22.1.1.10
		dhcpPoolAction OBJECT-TYPE
			SYNTAX INTEGER
				{
				del(0),
				add(1)
				}
			MAX-ACCESS read-write
			STATUS current
			DESCRIPTION
				"Description."
			::= { dhcpPool 10 }

		
--         1.3.6.1.4.1.37950.1.1.5.10.22.1.2
-- 1.3.6.1.4.1.37950.1.1.5.10.22.1.2
-- 1.3.6.1.4.1.37950.1.1.5.10.22.1.2
-- 1.3.6.1.4.1.37950.1.1.5.10.22.1.2
-- 1.3.6.1.4.1.37950.1.1.5.10.22.1.2
-- 1.3.6.1.4.1.37950.1.1.5.10.22.1.2
-- 1.3.6.1.4.1.37950.1.1.5.10.22.1.2
-- 1.3.6.1.4.1.37950.1.1.5.10.22.1.2
		-- 1.3.6.1.4.1.37950.1.1.5.10.22.1.2
		dhcpPoolReservedAddr OBJECT IDENTIFIER ::= { v3500DHCPServer 2 }

		
--         1.3.6.1.4.1.37950.1.1.5.10.22.1.2.1
-- 1.3.6.1.4.1.37950.1.1.5.10.22.1.2.1
-- 1.3.6.1.4.1.37950.1.1.5.10.22.1.2.1
-- 1.3.6.1.4.1.37950.1.1.5.10.22.1.2.1
-- 1.3.6.1.4.1.37950.1.1.5.10.22.1.2.1
-- 1.3.6.1.4.1.37950.1.1.5.10.22.1.2.1
-- 1.3.6.1.4.1.37950.1.1.5.10.22.1.2.1
-- 1.3.6.1.4.1.37950.1.1.5.10.22.1.2.1
		-- 1.3.6.1.4.1.37950.1.1.5.10.22.1.2.1
		dhcpPoolReservedPoolname OBJECT-TYPE
			SYNTAX OCTET STRING
			MAX-ACCESS read-write
			STATUS current
			DESCRIPTION
				"Description."
			::= { dhcpPoolReservedAddr 1 }

		
--         1.3.6.1.4.1.37950.1.1.5.10.22.1.2.2
-- 1.3.6.1.4.1.37950.1.1.5.10.22.1.2.2
-- 1.3.6.1.4.1.37950.1.1.5.10.22.1.2.2
-- 1.3.6.1.4.1.37950.1.1.5.10.22.1.2.2
-- 1.3.6.1.4.1.37950.1.1.5.10.22.1.2.2
-- 1.3.6.1.4.1.37950.1.1.5.10.22.1.2.2
-- 1.3.6.1.4.1.37950.1.1.5.10.22.1.2.2
-- 1.3.6.1.4.1.37950.1.1.5.10.22.1.2.2
		-- 1.3.6.1.4.1.37950.1.1.5.10.22.1.2.2
		dhcpPoolReservedAdd OBJECT-TYPE
			SYNTAX IpAddress
			MAX-ACCESS read-write
			STATUS current
			DESCRIPTION
				"Description."
			::= { dhcpPoolReservedAddr 2 }

		
--         1.3.6.1.4.1.37950.1.1.5.10.22.1.2.3
-- 1.3.6.1.4.1.37950.1.1.5.10.22.1.2.3
-- 1.3.6.1.4.1.37950.1.1.5.10.22.1.2.3
-- 1.3.6.1.4.1.37950.1.1.5.10.22.1.2.3
-- 1.3.6.1.4.1.37950.1.1.5.10.22.1.2.3
-- 1.3.6.1.4.1.37950.1.1.5.10.22.1.2.3
-- 1.3.6.1.4.1.37950.1.1.5.10.22.1.2.3
-- 1.3.6.1.4.1.37950.1.1.5.10.22.1.2.3
		-- 1.3.6.1.4.1.37950.1.1.5.10.22.1.2.3
		dhcpPoolClientMac OBJECT-TYPE
			SYNTAX OCTET STRING
			MAX-ACCESS read-write
			STATUS current
			DESCRIPTION
				"Description."
			::= { dhcpPoolReservedAddr 3 }

		
--         1.3.6.1.4.1.37950.1.1.5.10.22.1.2.4
-- 1.3.6.1.4.1.37950.1.1.5.10.22.1.2.4
-- 1.3.6.1.4.1.37950.1.1.5.10.22.1.2.4
-- 1.3.6.1.4.1.37950.1.1.5.10.22.1.2.4
-- 1.3.6.1.4.1.37950.1.1.5.10.22.1.2.4
-- 1.3.6.1.4.1.37950.1.1.5.10.22.1.2.4
-- 1.3.6.1.4.1.37950.1.1.5.10.22.1.2.4
-- 1.3.6.1.4.1.37950.1.1.5.10.22.1.2.4
		-- 1.3.6.1.4.1.37950.1.1.5.10.22.1.2.4
		dhcpPoolReservedAction OBJECT-TYPE
			SYNTAX INTEGER
				{
				del(0),
				add(1)
				}
			MAX-ACCESS read-write
			STATUS current
			DESCRIPTION
				"Description."
			::= { dhcpPoolReservedAddr 4 }

		
--         1.3.6.1.4.1.37950.1.1.5.10.22.1.3
-- 1.3.6.1.4.1.37950.1.1.5.10.22.1.3
-- 1.3.6.1.4.1.37950.1.1.5.10.22.1.3
-- 1.3.6.1.4.1.37950.1.1.5.10.22.1.3
-- 1.3.6.1.4.1.37950.1.1.5.10.22.1.3
-- 1.3.6.1.4.1.37950.1.1.5.10.22.1.3
-- 1.3.6.1.4.1.37950.1.1.5.10.22.1.3
-- 1.3.6.1.4.1.37950.1.1.5.10.22.1.3
		-- 1.3.6.1.4.1.37950.1.1.5.10.22.1.3
		dhcpPoolExcludeAddr OBJECT IDENTIFIER ::= { v3500DHCPServer 3 }

		
--         1.3.6.1.4.1.37950.1.1.5.10.22.1.3.1
-- 1.3.6.1.4.1.37950.1.1.5.10.22.1.3.1
-- 1.3.6.1.4.1.37950.1.1.5.10.22.1.3.1
-- 1.3.6.1.4.1.37950.1.1.5.10.22.1.3.1
-- 1.3.6.1.4.1.37950.1.1.5.10.22.1.3.1
-- 1.3.6.1.4.1.37950.1.1.5.10.22.1.3.1
-- 1.3.6.1.4.1.37950.1.1.5.10.22.1.3.1
-- 1.3.6.1.4.1.37950.1.1.5.10.22.1.3.1
		-- 1.3.6.1.4.1.37950.1.1.5.10.22.1.3.1
		dhcpPoolExcludePoolname OBJECT-TYPE
			SYNTAX OCTET STRING
			MAX-ACCESS read-write
			STATUS current
			DESCRIPTION
				"Description."
			::= { dhcpPoolExcludeAddr 1 }

		
--         1.3.6.1.4.1.37950.1.1.5.10.22.1.3.2
-- 1.3.6.1.4.1.37950.1.1.5.10.22.1.3.2
-- 1.3.6.1.4.1.37950.1.1.5.10.22.1.3.2
-- 1.3.6.1.4.1.37950.1.1.5.10.22.1.3.2
-- 1.3.6.1.4.1.37950.1.1.5.10.22.1.3.2
-- 1.3.6.1.4.1.37950.1.1.5.10.22.1.3.2
-- 1.3.6.1.4.1.37950.1.1.5.10.22.1.3.2
-- 1.3.6.1.4.1.37950.1.1.5.10.22.1.3.2
		-- 1.3.6.1.4.1.37950.1.1.5.10.22.1.3.2
		dhcpPoolExcludeLowAddr OBJECT-TYPE
			SYNTAX IpAddress
			MAX-ACCESS read-write
			STATUS current
			DESCRIPTION
				"Description."
			::= { dhcpPoolExcludeAddr 2 }

		
--         1.3.6.1.4.1.37950.1.1.5.10.22.1.3.3
-- 1.3.6.1.4.1.37950.1.1.5.10.22.1.3.3
-- 1.3.6.1.4.1.37950.1.1.5.10.22.1.3.3
-- 1.3.6.1.4.1.37950.1.1.5.10.22.1.3.3
-- 1.3.6.1.4.1.37950.1.1.5.10.22.1.3.3
-- 1.3.6.1.4.1.37950.1.1.5.10.22.1.3.3
-- 1.3.6.1.4.1.37950.1.1.5.10.22.1.3.3
-- 1.3.6.1.4.1.37950.1.1.5.10.22.1.3.3
		-- 1.3.6.1.4.1.37950.1.1.5.10.22.1.3.3
		dhcpPoolExcludeHighAddr OBJECT-TYPE
			SYNTAX IpAddress
			MAX-ACCESS read-write
			STATUS current
			DESCRIPTION
				"Description."
			::= { dhcpPoolExcludeAddr 3 }

		
--         1.3.6.1.4.1.37950.1.1.5.10.22.1.3.4
-- 1.3.6.1.4.1.37950.1.1.5.10.22.1.3.4
-- 1.3.6.1.4.1.37950.1.1.5.10.22.1.3.4
-- 1.3.6.1.4.1.37950.1.1.5.10.22.1.3.4
-- 1.3.6.1.4.1.37950.1.1.5.10.22.1.3.4
-- 1.3.6.1.4.1.37950.1.1.5.10.22.1.3.4
-- 1.3.6.1.4.1.37950.1.1.5.10.22.1.3.4
-- 1.3.6.1.4.1.37950.1.1.5.10.22.1.3.4
		-- 1.3.6.1.4.1.37950.1.1.5.10.22.1.3.4
		dhcpPoolExcludeAction OBJECT-TYPE
			SYNTAX INTEGER
				{
				del(0),
				add(1)
				}
			MAX-ACCESS read-write
			STATUS current
			DESCRIPTION
				"Description."
			::= { dhcpPoolExcludeAddr 4 }

		
--         1.3.6.1.4.1.37950.1.1.5.10.22.1.4
-- 1.3.6.1.4.1.37950.1.1.5.10.22.1.4
-- 1.3.6.1.4.1.37950.1.1.5.10.22.1.4
-- 1.3.6.1.4.1.37950.1.1.5.10.22.1.4
-- 1.3.6.1.4.1.37950.1.1.5.10.22.1.4
-- 1.3.6.1.4.1.37950.1.1.5.10.22.1.4
-- 1.3.6.1.4.1.37950.1.1.5.10.22.1.4
-- 1.3.6.1.4.1.37950.1.1.5.10.22.1.4
		-- 1.3.6.1.4.1.37950.1.1.5.10.22.1.4
		dhcpPoolInterfaceEnable OBJECT IDENTIFIER ::= { v3500DHCPServer 4 }

		
--         1.3.6.1.4.1.37950.1.1.5.10.22.1.4.1
-- 1.3.6.1.4.1.37950.1.1.5.10.22.1.4.1
-- 1.3.6.1.4.1.37950.1.1.5.10.22.1.4.1
-- 1.3.6.1.4.1.37950.1.1.5.10.22.1.4.1
-- 1.3.6.1.4.1.37950.1.1.5.10.22.1.4.1
-- 1.3.6.1.4.1.37950.1.1.5.10.22.1.4.1
-- 1.3.6.1.4.1.37950.1.1.5.10.22.1.4.1
-- 1.3.6.1.4.1.37950.1.1.5.10.22.1.4.1
		-- 1.3.6.1.4.1.37950.1.1.5.10.22.1.4.1
		dhcpPoolVlan OBJECT-TYPE
			SYNTAX Unsigned32 (1..4094)
			MAX-ACCESS read-write
			STATUS current
			DESCRIPTION
				"Description."
			::= { dhcpPoolInterfaceEnable 1 }

		
--         1.3.6.1.4.1.37950.1.1.5.10.22.1.4.2
-- 1.3.6.1.4.1.37950.1.1.5.10.22.1.4.2
-- 1.3.6.1.4.1.37950.1.1.5.10.22.1.4.2
-- 1.3.6.1.4.1.37950.1.1.5.10.22.1.4.2
-- 1.3.6.1.4.1.37950.1.1.5.10.22.1.4.2
-- 1.3.6.1.4.1.37950.1.1.5.10.22.1.4.2
-- 1.3.6.1.4.1.37950.1.1.5.10.22.1.4.2
-- 1.3.6.1.4.1.37950.1.1.5.10.22.1.4.2
		-- 1.3.6.1.4.1.37950.1.1.5.10.22.1.4.2
		dhcpServerPoolname OBJECT-TYPE
			SYNTAX OCTET STRING
			MAX-ACCESS read-write
			STATUS current
			DESCRIPTION
				"Description."
			::= { dhcpPoolInterfaceEnable 2 }

		
--         1.3.6.1.4.1.37950.1.1.5.10.22.1.4.3
-- 1.3.6.1.4.1.37950.1.1.5.10.22.1.4.3
-- 1.3.6.1.4.1.37950.1.1.5.10.22.1.4.3
-- 1.3.6.1.4.1.37950.1.1.5.10.22.1.4.3
-- 1.3.6.1.4.1.37950.1.1.5.10.22.1.4.3
-- 1.3.6.1.4.1.37950.1.1.5.10.22.1.4.3
-- 1.3.6.1.4.1.37950.1.1.5.10.22.1.4.3
-- 1.3.6.1.4.1.37950.1.1.5.10.22.1.4.3
		-- 1.3.6.1.4.1.37950.1.1.5.10.22.1.4.3
		dhcpPoolEnable OBJECT-TYPE
			SYNTAX INTEGER
				{
				disable(0),
				enable(1)
				}
			MAX-ACCESS read-write
			STATUS current
			DESCRIPTION
				"Description."
			::= { dhcpPoolInterfaceEnable 3 }

		
--         1.3.6.1.4.1.37950.1.1.5.10.22.1.5
-- 1.3.6.1.4.1.37950.1.1.5.10.22.1.5
-- 1.3.6.1.4.1.37950.1.1.5.10.22.1.5
-- 1.3.6.1.4.1.37950.1.1.5.10.22.1.5
-- 1.3.6.1.4.1.37950.1.1.5.10.22.1.5
-- 1.3.6.1.4.1.37950.1.1.5.10.22.1.5
-- 1.3.6.1.4.1.37950.1.1.5.10.22.1.5
-- 1.3.6.1.4.1.37950.1.1.5.10.22.1.5
		-- 1.3.6.1.4.1.37950.1.1.5.10.22.1.5
		dhcpPoolTable OBJECT-TYPE
			SYNTAX SEQUENCE OF DhcpPoolEntry
			MAX-ACCESS not-accessible
			STATUS current
			DESCRIPTION
				"Description."
			::= { v3500DHCPServer 5 }

		
--         1.3.6.1.4.1.37950.1.1.5.10.22.1.5.1
-- 1.3.6.1.4.1.37950.1.1.5.10.22.1.5.1
-- 1.3.6.1.4.1.37950.1.1.5.10.22.1.5.1
-- 1.3.6.1.4.1.37950.1.1.5.10.22.1.5.1
-- 1.3.6.1.4.1.37950.1.1.5.10.22.1.5.1
-- 1.3.6.1.4.1.37950.1.1.5.10.22.1.5.1
-- 1.3.6.1.4.1.37950.1.1.5.10.22.1.5.1
-- 1.3.6.1.4.1.37950.1.1.5.10.22.1.5.1
		-- 1.3.6.1.4.1.37950.1.1.5.10.22.1.5.1
		dhcpPoolEntry OBJECT-TYPE
			SYNTAX DhcpPoolEntry
			MAX-ACCESS not-accessible
			STATUS current
			DESCRIPTION
				"Description."
			INDEX { poolName }
			::= { dhcpPoolTable 1 }

		
		DhcpPoolEntry ::=
			SEQUENCE { 
				poolName
					OCTET STRING,
				poolLeaseTime
					Unsigned32,
				poolStartIP
					IpAddress,
				poolEndIP
					IpAddress,
				poolSubnet
					IpAddress,
				poolGateway
					IpAddress,
				poolDNS1
					IpAddress,
				poolDNS2
					IpAddress,
				poolDNS3
					IpAddress,
				poolWins
					IpAddress
			 }

--         1.3.6.1.4.1.37950.1.1.5.10.22.1.5.1.1
-- 1.3.6.1.4.1.37950.1.1.5.10.22.1.5.1.1
-- 1.3.6.1.4.1.37950.1.1.5.10.22.1.5.1.1
-- 1.3.6.1.4.1.37950.1.1.5.10.22.1.5.1.1
-- 1.3.6.1.4.1.37950.1.1.5.10.22.1.5.1.1
-- 1.3.6.1.4.1.37950.1.1.5.10.22.1.5.1.1
-- 1.3.6.1.4.1.37950.1.1.5.10.22.1.5.1.1
-- 1.3.6.1.4.1.37950.1.1.5.10.22.1.5.1.1
		-- 1.3.6.1.4.1.37950.1.1.5.10.22.1.5.1.1
		poolName OBJECT-TYPE
			SYNTAX OCTET STRING
			MAX-ACCESS read-only
			STATUS current
			DESCRIPTION
				"Description."
			::= { dhcpPoolEntry 1 }

		
--         1.3.6.1.4.1.37950.1.1.5.10.22.1.5.1.2
-- 1.3.6.1.4.1.37950.1.1.5.10.22.1.5.1.2
-- 1.3.6.1.4.1.37950.1.1.5.10.22.1.5.1.2
-- 1.3.6.1.4.1.37950.1.1.5.10.22.1.5.1.2
-- 1.3.6.1.4.1.37950.1.1.5.10.22.1.5.1.2
-- 1.3.6.1.4.1.37950.1.1.5.10.22.1.5.1.2
-- 1.3.6.1.4.1.37950.1.1.5.10.22.1.5.1.2
-- 1.3.6.1.4.1.37950.1.1.5.10.22.1.5.1.2
		-- 1.3.6.1.4.1.37950.1.1.5.10.22.1.5.1.2
		poolLeaseTime OBJECT-TYPE
			SYNTAX Unsigned32 (60..864000)
			MAX-ACCESS read-only
			STATUS current
			DESCRIPTION
				"Description."
			::= { dhcpPoolEntry 2 }

		
--         1.3.6.1.4.1.37950.1.1.5.10.22.1.5.1.3
-- 1.3.6.1.4.1.37950.1.1.5.10.22.1.5.1.3
-- 1.3.6.1.4.1.37950.1.1.5.10.22.1.5.1.3
-- 1.3.6.1.4.1.37950.1.1.5.10.22.1.5.1.3
-- 1.3.6.1.4.1.37950.1.1.5.10.22.1.5.1.3
-- 1.3.6.1.4.1.37950.1.1.5.10.22.1.5.1.3
-- 1.3.6.1.4.1.37950.1.1.5.10.22.1.5.1.3
-- 1.3.6.1.4.1.37950.1.1.5.10.22.1.5.1.3
		-- 1.3.6.1.4.1.37950.1.1.5.10.22.1.5.1.3
		poolStartIP OBJECT-TYPE
			SYNTAX IpAddress
			MAX-ACCESS read-only
			STATUS current
			DESCRIPTION
				"Description."
			::= { dhcpPoolEntry 3 }

		
--         1.3.6.1.4.1.37950.1.1.5.10.22.1.5.1.4
-- 1.3.6.1.4.1.37950.1.1.5.10.22.1.5.1.4
-- 1.3.6.1.4.1.37950.1.1.5.10.22.1.5.1.4
-- 1.3.6.1.4.1.37950.1.1.5.10.22.1.5.1.4
-- 1.3.6.1.4.1.37950.1.1.5.10.22.1.5.1.4
-- 1.3.6.1.4.1.37950.1.1.5.10.22.1.5.1.4
-- 1.3.6.1.4.1.37950.1.1.5.10.22.1.5.1.4
-- 1.3.6.1.4.1.37950.1.1.5.10.22.1.5.1.4
		-- 1.3.6.1.4.1.37950.1.1.5.10.22.1.5.1.4
		poolEndIP OBJECT-TYPE
			SYNTAX IpAddress
			MAX-ACCESS read-only
			STATUS current
			DESCRIPTION
				"Description."
			::= { dhcpPoolEntry 4 }

		
--         1.3.6.1.4.1.37950.1.1.5.10.22.1.5.1.5
-- 1.3.6.1.4.1.37950.1.1.5.10.22.1.5.1.5
-- 1.3.6.1.4.1.37950.1.1.5.10.22.1.5.1.5
-- 1.3.6.1.4.1.37950.1.1.5.10.22.1.5.1.5
-- 1.3.6.1.4.1.37950.1.1.5.10.22.1.5.1.5
-- 1.3.6.1.4.1.37950.1.1.5.10.22.1.5.1.5
-- 1.3.6.1.4.1.37950.1.1.5.10.22.1.5.1.5
-- 1.3.6.1.4.1.37950.1.1.5.10.22.1.5.1.5
		-- 1.3.6.1.4.1.37950.1.1.5.10.22.1.5.1.5
		poolSubnet OBJECT-TYPE
			SYNTAX IpAddress
			MAX-ACCESS read-only
			STATUS current
			DESCRIPTION
				"Description."
			::= { dhcpPoolEntry 5 }

		
--         1.3.6.1.4.1.37950.1.1.5.10.22.1.5.1.6
-- 1.3.6.1.4.1.37950.1.1.5.10.22.1.5.1.6
-- 1.3.6.1.4.1.37950.1.1.5.10.22.1.5.1.6
-- 1.3.6.1.4.1.37950.1.1.5.10.22.1.5.1.6
-- 1.3.6.1.4.1.37950.1.1.5.10.22.1.5.1.6
-- 1.3.6.1.4.1.37950.1.1.5.10.22.1.5.1.6
-- 1.3.6.1.4.1.37950.1.1.5.10.22.1.5.1.6
-- 1.3.6.1.4.1.37950.1.1.5.10.22.1.5.1.6
		-- 1.3.6.1.4.1.37950.1.1.5.10.22.1.5.1.6
		poolGateway OBJECT-TYPE
			SYNTAX IpAddress
			MAX-ACCESS read-only
			STATUS current
			DESCRIPTION
				"Description."
			::= { dhcpPoolEntry 6 }

		
--         1.3.6.1.4.1.37950.1.1.5.10.22.1.5.1.7
-- 1.3.6.1.4.1.37950.1.1.5.10.22.1.5.1.7
-- 1.3.6.1.4.1.37950.1.1.5.10.22.1.5.1.7
-- 1.3.6.1.4.1.37950.1.1.5.10.22.1.5.1.7
-- 1.3.6.1.4.1.37950.1.1.5.10.22.1.5.1.7
-- 1.3.6.1.4.1.37950.1.1.5.10.22.1.5.1.7
-- 1.3.6.1.4.1.37950.1.1.5.10.22.1.5.1.7
-- 1.3.6.1.4.1.37950.1.1.5.10.22.1.5.1.7
		-- 1.3.6.1.4.1.37950.1.1.5.10.22.1.5.1.7
		poolDNS1 OBJECT-TYPE
			SYNTAX IpAddress
			MAX-ACCESS read-only
			STATUS current
			DESCRIPTION
				"Description."
			::= { dhcpPoolEntry 7 }

		
--         1.3.6.1.4.1.37950.1.1.5.10.22.1.5.1.8
-- 1.3.6.1.4.1.37950.1.1.5.10.22.1.5.1.8
-- 1.3.6.1.4.1.37950.1.1.5.10.22.1.5.1.8
-- 1.3.6.1.4.1.37950.1.1.5.10.22.1.5.1.8
-- 1.3.6.1.4.1.37950.1.1.5.10.22.1.5.1.8
-- 1.3.6.1.4.1.37950.1.1.5.10.22.1.5.1.8
-- 1.3.6.1.4.1.37950.1.1.5.10.22.1.5.1.8
-- 1.3.6.1.4.1.37950.1.1.5.10.22.1.5.1.8
		-- 1.3.6.1.4.1.37950.1.1.5.10.22.1.5.1.8
		poolDNS2 OBJECT-TYPE
			SYNTAX IpAddress
			MAX-ACCESS read-only
			STATUS current
			DESCRIPTION
				"Description."
			::= { dhcpPoolEntry 8 }

		
--         1.3.6.1.4.1.37950.1.1.5.10.22.1.5.1.9
-- 1.3.6.1.4.1.37950.1.1.5.10.22.1.5.1.9
-- 1.3.6.1.4.1.37950.1.1.5.10.22.1.5.1.9
-- 1.3.6.1.4.1.37950.1.1.5.10.22.1.5.1.9
-- 1.3.6.1.4.1.37950.1.1.5.10.22.1.5.1.9
-- 1.3.6.1.4.1.37950.1.1.5.10.22.1.5.1.9
-- 1.3.6.1.4.1.37950.1.1.5.10.22.1.5.1.9
-- 1.3.6.1.4.1.37950.1.1.5.10.22.1.5.1.9
		-- 1.3.6.1.4.1.37950.1.1.5.10.22.1.5.1.9
		poolDNS3 OBJECT-TYPE
			SYNTAX IpAddress
			MAX-ACCESS read-only
			STATUS current
			DESCRIPTION
				"Description."
			::= { dhcpPoolEntry 9 }

		
--         1.3.6.1.4.1.37950.1.1.5.10.22.1.5.1.10
-- 1.3.6.1.4.1.37950.1.1.5.10.22.1.5.1.10
-- 1.3.6.1.4.1.37950.1.1.5.10.22.1.5.1.10
-- 1.3.6.1.4.1.37950.1.1.5.10.22.1.5.1.10
-- 1.3.6.1.4.1.37950.1.1.5.10.22.1.5.1.10
-- 1.3.6.1.4.1.37950.1.1.5.10.22.1.5.1.10
-- 1.3.6.1.4.1.37950.1.1.5.10.22.1.5.1.10
-- 1.3.6.1.4.1.37950.1.1.5.10.22.1.5.1.10
		-- 1.3.6.1.4.1.37950.1.1.5.10.22.1.5.1.10
		poolWins OBJECT-TYPE
			SYNTAX IpAddress
			MAX-ACCESS read-only
			STATUS current
			DESCRIPTION
				"Description."
			::= { dhcpPoolEntry 10 }

		
--         1.3.6.1.4.1.37950.1.1.5.10.22.1.6
-- 1.3.6.1.4.1.37950.1.1.5.10.22.1.6
-- 1.3.6.1.4.1.37950.1.1.5.10.22.1.6
-- 1.3.6.1.4.1.37950.1.1.5.10.22.1.6
-- 1.3.6.1.4.1.37950.1.1.5.10.22.1.6
-- 1.3.6.1.4.1.37950.1.1.5.10.22.1.6
-- 1.3.6.1.4.1.37950.1.1.5.10.22.1.6
-- 1.3.6.1.4.1.37950.1.1.5.10.22.1.6
		-- 1.3.6.1.4.1.37950.1.1.5.10.22.1.6
		dhcpPoolReservedAddrTable OBJECT-TYPE
			SYNTAX SEQUENCE OF DhcpPoolReservedAddrEntry
			MAX-ACCESS not-accessible
			STATUS current
			DESCRIPTION
				"Description."
			::= { v3500DHCPServer 6 }

		
--         1.3.6.1.4.1.37950.1.1.5.10.22.1.6.1
-- 1.3.6.1.4.1.37950.1.1.5.10.22.1.6.1
-- 1.3.6.1.4.1.37950.1.1.5.10.22.1.6.1
-- 1.3.6.1.4.1.37950.1.1.5.10.22.1.6.1
-- 1.3.6.1.4.1.37950.1.1.5.10.22.1.6.1
-- 1.3.6.1.4.1.37950.1.1.5.10.22.1.6.1
-- 1.3.6.1.4.1.37950.1.1.5.10.22.1.6.1
-- 1.3.6.1.4.1.37950.1.1.5.10.22.1.6.1
		-- 1.3.6.1.4.1.37950.1.1.5.10.22.1.6.1
		dhcpPoolReservedAddrEntry OBJECT-TYPE
			SYNTAX DhcpPoolReservedAddrEntry
			MAX-ACCESS not-accessible
			STATUS current
			DESCRIPTION
				"Description."
			INDEX { reservedIndex, reservedPoolName }
			::= { dhcpPoolReservedAddrTable 1 }

		
		DhcpPoolReservedAddrEntry ::=
			SEQUENCE { 
				reservedIndex
					Integer32,
				reservedPoolName
					OCTET STRING,
				reservedAddress
					IpAddress,
				clientMacAddr
					OCTET STRING
			 }

--         1.3.6.1.4.1.37950.1.1.5.10.22.1.6.1.1
-- 1.3.6.1.4.1.37950.1.1.5.10.22.1.6.1.1
-- 1.3.6.1.4.1.37950.1.1.5.10.22.1.6.1.1
-- 1.3.6.1.4.1.37950.1.1.5.10.22.1.6.1.1
-- 1.3.6.1.4.1.37950.1.1.5.10.22.1.6.1.1
-- 1.3.6.1.4.1.37950.1.1.5.10.22.1.6.1.1
-- 1.3.6.1.4.1.37950.1.1.5.10.22.1.6.1.1
-- 1.3.6.1.4.1.37950.1.1.5.10.22.1.6.1.1
		-- 1.3.6.1.4.1.37950.1.1.5.10.22.1.6.1.1
		reservedIndex OBJECT-TYPE
			SYNTAX Integer32
			MAX-ACCESS read-only
			STATUS current
			DESCRIPTION
				"Description."
			::= { dhcpPoolReservedAddrEntry 1 }

		
--         1.3.6.1.4.1.37950.1.1.5.10.22.1.6.1.2
-- 1.3.6.1.4.1.37950.1.1.5.10.22.1.6.1.2
-- 1.3.6.1.4.1.37950.1.1.5.10.22.1.6.1.2
-- 1.3.6.1.4.1.37950.1.1.5.10.22.1.6.1.2
-- 1.3.6.1.4.1.37950.1.1.5.10.22.1.6.1.2
-- 1.3.6.1.4.1.37950.1.1.5.10.22.1.6.1.2
-- 1.3.6.1.4.1.37950.1.1.5.10.22.1.6.1.2
-- 1.3.6.1.4.1.37950.1.1.5.10.22.1.6.1.2
		-- 1.3.6.1.4.1.37950.1.1.5.10.22.1.6.1.2
		reservedPoolName OBJECT-TYPE
			SYNTAX OCTET STRING
			MAX-ACCESS read-only
			STATUS current
			DESCRIPTION
				"Description."
			::= { dhcpPoolReservedAddrEntry 2 }

		
--         1.3.6.1.4.1.37950.1.1.5.10.22.1.6.1.3
-- 1.3.6.1.4.1.37950.1.1.5.10.22.1.6.1.3
-- 1.3.6.1.4.1.37950.1.1.5.10.22.1.6.1.3
-- 1.3.6.1.4.1.37950.1.1.5.10.22.1.6.1.3
-- 1.3.6.1.4.1.37950.1.1.5.10.22.1.6.1.3
-- 1.3.6.1.4.1.37950.1.1.5.10.22.1.6.1.3
-- 1.3.6.1.4.1.37950.1.1.5.10.22.1.6.1.3
-- 1.3.6.1.4.1.37950.1.1.5.10.22.1.6.1.3
		-- 1.3.6.1.4.1.37950.1.1.5.10.22.1.6.1.3
		reservedAddress OBJECT-TYPE
			SYNTAX IpAddress
			MAX-ACCESS read-only
			STATUS current
			DESCRIPTION
				"Description."
			::= { dhcpPoolReservedAddrEntry 3 }

		
--         1.3.6.1.4.1.37950.1.1.5.10.22.1.6.1.4
-- 1.3.6.1.4.1.37950.1.1.5.10.22.1.6.1.4
-- 1.3.6.1.4.1.37950.1.1.5.10.22.1.6.1.4
-- 1.3.6.1.4.1.37950.1.1.5.10.22.1.6.1.4
-- 1.3.6.1.4.1.37950.1.1.5.10.22.1.6.1.4
-- 1.3.6.1.4.1.37950.1.1.5.10.22.1.6.1.4
-- 1.3.6.1.4.1.37950.1.1.5.10.22.1.6.1.4
-- 1.3.6.1.4.1.37950.1.1.5.10.22.1.6.1.4
		-- 1.3.6.1.4.1.37950.1.1.5.10.22.1.6.1.4
		clientMacAddr OBJECT-TYPE
			SYNTAX OCTET STRING
			MAX-ACCESS read-only
			STATUS current
			DESCRIPTION
				"Description."
			::= { dhcpPoolReservedAddrEntry 4 }

		
--         1.3.6.1.4.1.37950.1.1.5.10.22.1.7
-- 1.3.6.1.4.1.37950.1.1.5.10.22.1.7
-- 1.3.6.1.4.1.37950.1.1.5.10.22.1.7
-- 1.3.6.1.4.1.37950.1.1.5.10.22.1.7
-- 1.3.6.1.4.1.37950.1.1.5.10.22.1.7
-- 1.3.6.1.4.1.37950.1.1.5.10.22.1.7
-- 1.3.6.1.4.1.37950.1.1.5.10.22.1.7
-- 1.3.6.1.4.1.37950.1.1.5.10.22.1.7
		-- 1.3.6.1.4.1.37950.1.1.5.10.22.1.7
		dhcpPoolExcludeAddrTable OBJECT-TYPE
			SYNTAX SEQUENCE OF DhcpPoolExcludeAddrEntry
			MAX-ACCESS not-accessible
			STATUS current
			DESCRIPTION
				"Description."
			::= { v3500DHCPServer 7 }

		
--         1.3.6.1.4.1.37950.1.1.5.10.22.1.7.1
-- 1.3.6.1.4.1.37950.1.1.5.10.22.1.7.1
-- 1.3.6.1.4.1.37950.1.1.5.10.22.1.7.1
-- 1.3.6.1.4.1.37950.1.1.5.10.22.1.7.1
-- 1.3.6.1.4.1.37950.1.1.5.10.22.1.7.1
-- 1.3.6.1.4.1.37950.1.1.5.10.22.1.7.1
-- 1.3.6.1.4.1.37950.1.1.5.10.22.1.7.1
-- 1.3.6.1.4.1.37950.1.1.5.10.22.1.7.1
		-- 1.3.6.1.4.1.37950.1.1.5.10.22.1.7.1
		dhcpPoolExcludeAddrEntry OBJECT-TYPE
			SYNTAX DhcpPoolExcludeAddrEntry
			MAX-ACCESS not-accessible
			STATUS current
			DESCRIPTION
				"Description."
			INDEX { excludeIndex, excludePoolName }
			::= { dhcpPoolExcludeAddrTable 1 }

		
		DhcpPoolExcludeAddrEntry ::=
			SEQUENCE { 
				excludePoolName
					OCTET STRING,
				excludeIndex
					Integer32,
				excludeLowAddress
					IpAddress,
				excludeHighAddress
					IpAddress
			 }

--         1.3.6.1.4.1.37950.1.1.5.10.22.1.7.1.1
-- 1.3.6.1.4.1.37950.1.1.5.10.22.1.7.1.1
-- 1.3.6.1.4.1.37950.1.1.5.10.22.1.7.1.1
-- 1.3.6.1.4.1.37950.1.1.5.10.22.1.7.1.1
-- 1.3.6.1.4.1.37950.1.1.5.10.22.1.7.1.1
-- 1.3.6.1.4.1.37950.1.1.5.10.22.1.7.1.1
-- 1.3.6.1.4.1.37950.1.1.5.10.22.1.7.1.1
-- 1.3.6.1.4.1.37950.1.1.5.10.22.1.7.1.1
		-- 1.3.6.1.4.1.37950.1.1.5.10.22.1.7.1.1
		excludePoolName OBJECT-TYPE
			SYNTAX OCTET STRING
			MAX-ACCESS read-only
			STATUS current
			DESCRIPTION
				"Description."
			::= { dhcpPoolExcludeAddrEntry 1 }

		
--         1.3.6.1.4.1.37950.1.1.5.10.22.1.7.1.2
-- 1.3.6.1.4.1.37950.1.1.5.10.22.1.7.1.2
-- 1.3.6.1.4.1.37950.1.1.5.10.22.1.7.1.2
-- 1.3.6.1.4.1.37950.1.1.5.10.22.1.7.1.2
-- 1.3.6.1.4.1.37950.1.1.5.10.22.1.7.1.2
-- 1.3.6.1.4.1.37950.1.1.5.10.22.1.7.1.2
-- 1.3.6.1.4.1.37950.1.1.5.10.22.1.7.1.2
-- 1.3.6.1.4.1.37950.1.1.5.10.22.1.7.1.2
		-- 1.3.6.1.4.1.37950.1.1.5.10.22.1.7.1.2
		excludeIndex OBJECT-TYPE
			SYNTAX Integer32
			MAX-ACCESS read-only
			STATUS current
			DESCRIPTION
				"Description."
			::= { dhcpPoolExcludeAddrEntry 2 }

		
--         1.3.6.1.4.1.37950.1.1.5.10.22.1.7.1.3
-- 1.3.6.1.4.1.37950.1.1.5.10.22.1.7.1.3
-- 1.3.6.1.4.1.37950.1.1.5.10.22.1.7.1.3
-- 1.3.6.1.4.1.37950.1.1.5.10.22.1.7.1.3
-- 1.3.6.1.4.1.37950.1.1.5.10.22.1.7.1.3
-- 1.3.6.1.4.1.37950.1.1.5.10.22.1.7.1.3
-- 1.3.6.1.4.1.37950.1.1.5.10.22.1.7.1.3
-- 1.3.6.1.4.1.37950.1.1.5.10.22.1.7.1.3
		-- 1.3.6.1.4.1.37950.1.1.5.10.22.1.7.1.3
		excludeLowAddress OBJECT-TYPE
			SYNTAX IpAddress
			MAX-ACCESS read-only
			STATUS current
			DESCRIPTION
				"Description."
			::= { dhcpPoolExcludeAddrEntry 3 }

		
--         1.3.6.1.4.1.37950.1.1.5.10.22.1.7.1.4
-- 1.3.6.1.4.1.37950.1.1.5.10.22.1.7.1.4
-- 1.3.6.1.4.1.37950.1.1.5.10.22.1.7.1.4
-- 1.3.6.1.4.1.37950.1.1.5.10.22.1.7.1.4
-- 1.3.6.1.4.1.37950.1.1.5.10.22.1.7.1.4
-- 1.3.6.1.4.1.37950.1.1.5.10.22.1.7.1.4
-- 1.3.6.1.4.1.37950.1.1.5.10.22.1.7.1.4
-- 1.3.6.1.4.1.37950.1.1.5.10.22.1.7.1.4
		-- 1.3.6.1.4.1.37950.1.1.5.10.22.1.7.1.4
		excludeHighAddress OBJECT-TYPE
			SYNTAX IpAddress
			MAX-ACCESS read-only
			STATUS current
			DESCRIPTION
				"Description."
			::= { dhcpPoolExcludeAddrEntry 4 }

		
--         1.3.6.1.4.1.37950.1.1.5.10.22.1.8
-- 1.3.6.1.4.1.37950.1.1.5.10.22.1.8
-- 1.3.6.1.4.1.37950.1.1.5.10.22.1.8
-- 1.3.6.1.4.1.37950.1.1.5.10.22.1.8
-- 1.3.6.1.4.1.37950.1.1.5.10.22.1.8
-- 1.3.6.1.4.1.37950.1.1.5.10.22.1.8
-- 1.3.6.1.4.1.37950.1.1.5.10.22.1.8
-- 1.3.6.1.4.1.37950.1.1.5.10.22.1.8
		-- 1.3.6.1.4.1.37950.1.1.5.10.22.1.8
		dhcpPoolInterfaceEnableTable OBJECT-TYPE
			SYNTAX SEQUENCE OF DhcpPoolInterfaceEnableEntry
			MAX-ACCESS not-accessible
			STATUS current
			DESCRIPTION
				"Description."
			::= { v3500DHCPServer 8 }

		
--         1.3.6.1.4.1.37950.1.1.5.10.22.1.8.1
-- 1.3.6.1.4.1.37950.1.1.5.10.22.1.8.1
-- 1.3.6.1.4.1.37950.1.1.5.10.22.1.8.1
-- 1.3.6.1.4.1.37950.1.1.5.10.22.1.8.1
-- 1.3.6.1.4.1.37950.1.1.5.10.22.1.8.1
-- 1.3.6.1.4.1.37950.1.1.5.10.22.1.8.1
-- 1.3.6.1.4.1.37950.1.1.5.10.22.1.8.1
-- 1.3.6.1.4.1.37950.1.1.5.10.22.1.8.1
		-- 1.3.6.1.4.1.37950.1.1.5.10.22.1.8.1
		dhcpPoolInterfaceEnableEntry OBJECT-TYPE
			SYNTAX DhcpPoolInterfaceEnableEntry
			MAX-ACCESS not-accessible
			STATUS current
			DESCRIPTION
				"Description."
			INDEX { dhcpPoolInterfaceVlan, enabledPoolName }
			::= { dhcpPoolInterfaceEnableTable 1 }

		
		DhcpPoolInterfaceEnableEntry ::=
			SEQUENCE { 
				dhcpPoolInterfaceVlan
					Unsigned32,
				enabledPoolName
					OCTET STRING
			 }

--         1.3.6.1.4.1.37950.1.1.5.10.22.1.8.1.1
-- 1.3.6.1.4.1.37950.1.1.5.10.22.1.8.1.1
-- 1.3.6.1.4.1.37950.1.1.5.10.22.1.8.1.1
-- 1.3.6.1.4.1.37950.1.1.5.10.22.1.8.1.1
-- 1.3.6.1.4.1.37950.1.1.5.10.22.1.8.1.1
-- 1.3.6.1.4.1.37950.1.1.5.10.22.1.8.1.1
-- 1.3.6.1.4.1.37950.1.1.5.10.22.1.8.1.1
-- 1.3.6.1.4.1.37950.1.1.5.10.22.1.8.1.1
		-- 1.3.6.1.4.1.37950.1.1.5.10.22.1.8.1.1
		dhcpPoolInterfaceVlan OBJECT-TYPE
			SYNTAX Unsigned32 (1..4094)
			MAX-ACCESS read-only
			STATUS current
			DESCRIPTION
				"Description."
			::= { dhcpPoolInterfaceEnableEntry 1 }

		
--         1.3.6.1.4.1.37950.1.1.5.10.22.1.8.1.2
-- 1.3.6.1.4.1.37950.1.1.5.10.22.1.8.1.2
-- 1.3.6.1.4.1.37950.1.1.5.10.22.1.8.1.2
-- 1.3.6.1.4.1.37950.1.1.5.10.22.1.8.1.2
-- 1.3.6.1.4.1.37950.1.1.5.10.22.1.8.1.2
-- 1.3.6.1.4.1.37950.1.1.5.10.22.1.8.1.2
-- 1.3.6.1.4.1.37950.1.1.5.10.22.1.8.1.2
-- 1.3.6.1.4.1.37950.1.1.5.10.22.1.8.1.2
		-- 1.3.6.1.4.1.37950.1.1.5.10.22.1.8.1.2
		enabledPoolName OBJECT-TYPE
			SYNTAX OCTET STRING
			MAX-ACCESS read-only
			STATUS current
			DESCRIPTION
				"Description."
			::= { dhcpPoolInterfaceEnableEntry 2 }

		
--         1.3.6.1.4.1.37950.1.1.5.10.22.1.9
-- 1.3.6.1.4.1.37950.1.1.5.10.22.1.9
-- 1.3.6.1.4.1.37950.1.1.5.10.22.1.9
-- 1.3.6.1.4.1.37950.1.1.5.10.22.1.9
-- 1.3.6.1.4.1.37950.1.1.5.10.22.1.9
-- 1.3.6.1.4.1.37950.1.1.5.10.22.1.9
-- 1.3.6.1.4.1.37950.1.1.5.10.22.1.9
-- 1.3.6.1.4.1.37950.1.1.5.10.22.1.9
		-- 1.3.6.1.4.1.37950.1.1.5.10.22.1.9
		dhcpBindingTable OBJECT-TYPE
			SYNTAX SEQUENCE OF DhcpBindingEntry
			MAX-ACCESS not-accessible
			STATUS current
			DESCRIPTION
				"Description."
			::= { v3500DHCPServer 9 }

		
--         1.3.6.1.4.1.37950.1.1.5.10.22.1.9.1
-- 1.3.6.1.4.1.37950.1.1.5.10.22.1.9.1
-- 1.3.6.1.4.1.37950.1.1.5.10.22.1.9.1
-- 1.3.6.1.4.1.37950.1.1.5.10.22.1.9.1
-- 1.3.6.1.4.1.37950.1.1.5.10.22.1.9.1
-- 1.3.6.1.4.1.37950.1.1.5.10.22.1.9.1
-- 1.3.6.1.4.1.37950.1.1.5.10.22.1.9.1
-- 1.3.6.1.4.1.37950.1.1.5.10.22.1.9.1
		-- 1.3.6.1.4.1.37950.1.1.5.10.22.1.9.1
		dhcpBindingEntry OBJECT-TYPE
			SYNTAX DhcpBindingEntry
			MAX-ACCESS not-accessible
			STATUS current
			DESCRIPTION
				"Description."
			INDEX { dhcpBindingClientMac }
			::= { dhcpBindingTable 1 }

		
		DhcpBindingEntry ::=
			SEQUENCE { 
				dhcpBindingIndex
					Integer32,
				dhcpBindingClientMac
					OCTET STRING,
				dhcpBindingnAddr
					IpAddress,
				dhcpBindingLeaseTime
					Unsigned32,
				dhcpBindingType
					INTEGER,
				dhcpBindingHostName
					OCTET STRING
			 }

--         1.3.6.1.4.1.37950.1.1.5.10.22.1.9.1.1
-- 1.3.6.1.4.1.37950.1.1.5.10.22.1.9.1.1
-- 1.3.6.1.4.1.37950.1.1.5.10.22.1.9.1.1
-- 1.3.6.1.4.1.37950.1.1.5.10.22.1.9.1.1
-- 1.3.6.1.4.1.37950.1.1.5.10.22.1.9.1.1
-- 1.3.6.1.4.1.37950.1.1.5.10.22.1.9.1.1
-- 1.3.6.1.4.1.37950.1.1.5.10.22.1.9.1.1
-- 1.3.6.1.4.1.37950.1.1.5.10.22.1.9.1.1
		-- 1.3.6.1.4.1.37950.1.1.5.10.22.1.9.1.1
		dhcpBindingIndex OBJECT-TYPE
			SYNTAX Integer32
			MAX-ACCESS read-only
			STATUS current
			DESCRIPTION
				"Description."
			::= { dhcpBindingEntry 1 }

		
--         1.3.6.1.4.1.37950.1.1.5.10.22.1.9.1.2
-- 1.3.6.1.4.1.37950.1.1.5.10.22.1.9.1.2
-- 1.3.6.1.4.1.37950.1.1.5.10.22.1.9.1.2
-- 1.3.6.1.4.1.37950.1.1.5.10.22.1.9.1.2
-- 1.3.6.1.4.1.37950.1.1.5.10.22.1.9.1.2
-- 1.3.6.1.4.1.37950.1.1.5.10.22.1.9.1.2
-- 1.3.6.1.4.1.37950.1.1.5.10.22.1.9.1.2
-- 1.3.6.1.4.1.37950.1.1.5.10.22.1.9.1.2
		-- 1.3.6.1.4.1.37950.1.1.5.10.22.1.9.1.2
		dhcpBindingClientMac OBJECT-TYPE
			SYNTAX OCTET STRING
			MAX-ACCESS read-only
			STATUS current
			DESCRIPTION
				"Description."
			::= { dhcpBindingEntry 2 }

		
--         1.3.6.1.4.1.37950.1.1.5.10.22.1.9.1.3
-- 1.3.6.1.4.1.37950.1.1.5.10.22.1.9.1.3
-- 1.3.6.1.4.1.37950.1.1.5.10.22.1.9.1.3
-- 1.3.6.1.4.1.37950.1.1.5.10.22.1.9.1.3
-- 1.3.6.1.4.1.37950.1.1.5.10.22.1.9.1.3
-- 1.3.6.1.4.1.37950.1.1.5.10.22.1.9.1.3
-- 1.3.6.1.4.1.37950.1.1.5.10.22.1.9.1.3
-- 1.3.6.1.4.1.37950.1.1.5.10.22.1.9.1.3
		-- 1.3.6.1.4.1.37950.1.1.5.10.22.1.9.1.3
		dhcpBindingnAddr OBJECT-TYPE
			SYNTAX IpAddress
			MAX-ACCESS read-only
			STATUS current
			DESCRIPTION
				"Description."
			::= { dhcpBindingEntry 3 }

		
--         1.3.6.1.4.1.37950.1.1.5.10.22.1.9.1.4
-- 1.3.6.1.4.1.37950.1.1.5.10.22.1.9.1.4
-- 1.3.6.1.4.1.37950.1.1.5.10.22.1.9.1.4
-- 1.3.6.1.4.1.37950.1.1.5.10.22.1.9.1.4
-- 1.3.6.1.4.1.37950.1.1.5.10.22.1.9.1.4
-- 1.3.6.1.4.1.37950.1.1.5.10.22.1.9.1.4
-- 1.3.6.1.4.1.37950.1.1.5.10.22.1.9.1.4
-- 1.3.6.1.4.1.37950.1.1.5.10.22.1.9.1.4
		-- 1.3.6.1.4.1.37950.1.1.5.10.22.1.9.1.4
		dhcpBindingLeaseTime OBJECT-TYPE
			SYNTAX Unsigned32 (60..86400)
			MAX-ACCESS read-only
			STATUS current
			DESCRIPTION
				"Description."
			::= { dhcpBindingEntry 4 }

		
--         1.3.6.1.4.1.37950.1.1.5.10.22.1.9.1.5
-- 1.3.6.1.4.1.37950.1.1.5.10.22.1.9.1.5
-- 1.3.6.1.4.1.37950.1.1.5.10.22.1.9.1.5
-- 1.3.6.1.4.1.37950.1.1.5.10.22.1.9.1.5
-- 1.3.6.1.4.1.37950.1.1.5.10.22.1.9.1.5
-- 1.3.6.1.4.1.37950.1.1.5.10.22.1.9.1.5
-- 1.3.6.1.4.1.37950.1.1.5.10.22.1.9.1.5
-- 1.3.6.1.4.1.37950.1.1.5.10.22.1.9.1.5
		-- 1.3.6.1.4.1.37950.1.1.5.10.22.1.9.1.5
		dhcpBindingType OBJECT-TYPE
			SYNTAX INTEGER
				{
				automatic(1),
				manual(2),
				ping(3)
				}
			MAX-ACCESS read-only
			STATUS current
			DESCRIPTION
				"Description."
			::= { dhcpBindingEntry 5 }

		
--         1.3.6.1.4.1.37950.1.1.5.10.22.1.9.1.6
-- 1.3.6.1.4.1.37950.1.1.5.10.22.1.9.1.6
-- 1.3.6.1.4.1.37950.1.1.5.10.22.1.9.1.6
-- 1.3.6.1.4.1.37950.1.1.5.10.22.1.9.1.6
-- 1.3.6.1.4.1.37950.1.1.5.10.22.1.9.1.6
-- 1.3.6.1.4.1.37950.1.1.5.10.22.1.9.1.6
-- 1.3.6.1.4.1.37950.1.1.5.10.22.1.9.1.6
-- 1.3.6.1.4.1.37950.1.1.5.10.22.1.9.1.6
		-- 1.3.6.1.4.1.37950.1.1.5.10.22.1.9.1.6
		dhcpBindingHostName OBJECT-TYPE
			SYNTAX OCTET STRING
			MAX-ACCESS read-only
			STATUS current
			DESCRIPTION
				"Description."
			::= { dhcpBindingEntry 6 }

		
--         1.3.6.1.4.1.37950.1.1.5.10.23
-- 1.3.6.1.4.1.37950.1.1.5.10.23
-- 1.3.6.1.4.1.37950.1.1.5.10.23
-- 1.3.6.1.4.1.37950.1.1.5.10.23
-- 1.3.6.1.4.1.37950.1.1.5.10.23
-- 1.3.6.1.4.1.37950.1.1.5.10.23
-- 1.3.6.1.4.1.37950.1.1.5.10.23
-- 1.3.6.1.4.1.37950.1.1.5.10.23
		-- 1.3.6.1.4.1.37950.1.1.5.10.23
		v1600RIPng OBJECT IDENTIFIER ::= { v1600dSwitch 23 }

		
--         1.3.6.1.4.1.37950.1.1.5.10.23.1
-- 1.3.6.1.4.1.37950.1.1.5.10.23.1
-- 1.3.6.1.4.1.37950.1.1.5.10.23.1
-- 1.3.6.1.4.1.37950.1.1.5.10.23.1
-- 1.3.6.1.4.1.37950.1.1.5.10.23.1
-- 1.3.6.1.4.1.37950.1.1.5.10.23.1
-- 1.3.6.1.4.1.37950.1.1.5.10.23.1
-- 1.3.6.1.4.1.37950.1.1.5.10.23.1
		-- 1.3.6.1.4.1.37950.1.1.5.10.23.1
		ripngGlobalCfg OBJECT IDENTIFIER ::= { v1600RIPng 1 }

		
--         1.3.6.1.4.1.37950.1.1.5.10.23.1.1
-- 1.3.6.1.4.1.37950.1.1.5.10.23.1.1
-- 1.3.6.1.4.1.37950.1.1.5.10.23.1.1
-- 1.3.6.1.4.1.37950.1.1.5.10.23.1.1
-- 1.3.6.1.4.1.37950.1.1.5.10.23.1.1
-- 1.3.6.1.4.1.37950.1.1.5.10.23.1.1
-- 1.3.6.1.4.1.37950.1.1.5.10.23.1.1
-- 1.3.6.1.4.1.37950.1.1.5.10.23.1.1
		-- 1.3.6.1.4.1.37950.1.1.5.10.23.1.1
		ripngRouteEn OBJECT-TYPE
			SYNTAX INTEGER
				{
				disable(0),
				enable(1)
				}
			MAX-ACCESS read-write
			STATUS current
			DESCRIPTION
				"Description."
			::= { ripngGlobalCfg 1 }

		
--         1.3.6.1.4.1.37950.1.1.5.10.23.1.2
-- 1.3.6.1.4.1.37950.1.1.5.10.23.1.2
-- 1.3.6.1.4.1.37950.1.1.5.10.23.1.2
-- 1.3.6.1.4.1.37950.1.1.5.10.23.1.2
-- 1.3.6.1.4.1.37950.1.1.5.10.23.1.2
-- 1.3.6.1.4.1.37950.1.1.5.10.23.1.2
-- 1.3.6.1.4.1.37950.1.1.5.10.23.1.2
-- 1.3.6.1.4.1.37950.1.1.5.10.23.1.2
		-- 1.3.6.1.4.1.37950.1.1.5.10.23.1.2
		ripngUpdateTime OBJECT-TYPE
			SYNTAX Integer32 (0..65535)
			MAX-ACCESS read-write
			STATUS current
			DESCRIPTION
				"Description."
			::= { ripngGlobalCfg 2 }

		
--         1.3.6.1.4.1.37950.1.1.5.10.23.1.3
-- 1.3.6.1.4.1.37950.1.1.5.10.23.1.3
-- 1.3.6.1.4.1.37950.1.1.5.10.23.1.3
-- 1.3.6.1.4.1.37950.1.1.5.10.23.1.3
-- 1.3.6.1.4.1.37950.1.1.5.10.23.1.3
-- 1.3.6.1.4.1.37950.1.1.5.10.23.1.3
-- 1.3.6.1.4.1.37950.1.1.5.10.23.1.3
-- 1.3.6.1.4.1.37950.1.1.5.10.23.1.3
		-- 1.3.6.1.4.1.37950.1.1.5.10.23.1.3
		ripngTimeout OBJECT-TYPE
			SYNTAX Integer32 (0..65535)
			MAX-ACCESS read-write
			STATUS current
			DESCRIPTION
				"Description."
			::= { ripngGlobalCfg 3 }

		
--         1.3.6.1.4.1.37950.1.1.5.10.23.1.4
-- 1.3.6.1.4.1.37950.1.1.5.10.23.1.4
-- 1.3.6.1.4.1.37950.1.1.5.10.23.1.4
-- 1.3.6.1.4.1.37950.1.1.5.10.23.1.4
-- 1.3.6.1.4.1.37950.1.1.5.10.23.1.4
-- 1.3.6.1.4.1.37950.1.1.5.10.23.1.4
-- 1.3.6.1.4.1.37950.1.1.5.10.23.1.4
-- 1.3.6.1.4.1.37950.1.1.5.10.23.1.4
		-- 1.3.6.1.4.1.37950.1.1.5.10.23.1.4
		ripngGarbageTime OBJECT-TYPE
			SYNTAX Integer32 (0..65535)
			MAX-ACCESS read-write
			STATUS current
			DESCRIPTION
				"Description."
			::= { ripngGlobalCfg 4 }

		
--         1.3.6.1.4.1.37950.1.1.5.10.23.1.5
-- 1.3.6.1.4.1.37950.1.1.5.10.23.1.5
-- 1.3.6.1.4.1.37950.1.1.5.10.23.1.5
-- 1.3.6.1.4.1.37950.1.1.5.10.23.1.5
-- 1.3.6.1.4.1.37950.1.1.5.10.23.1.5
-- 1.3.6.1.4.1.37950.1.1.5.10.23.1.5
-- 1.3.6.1.4.1.37950.1.1.5.10.23.1.5
-- 1.3.6.1.4.1.37950.1.1.5.10.23.1.5
		-- 1.3.6.1.4.1.37950.1.1.5.10.23.1.5
		ripngDefMetric OBJECT-TYPE
			SYNTAX Integer32 (1..16)
			MAX-ACCESS read-write
			STATUS current
			DESCRIPTION
				"Description."
			::= { ripngGlobalCfg 5 }

		
--         1.3.6.1.4.1.37950.1.1.5.10.23.1.6
-- 1.3.6.1.4.1.37950.1.1.5.10.23.1.6
-- 1.3.6.1.4.1.37950.1.1.5.10.23.1.6
-- 1.3.6.1.4.1.37950.1.1.5.10.23.1.6
-- 1.3.6.1.4.1.37950.1.1.5.10.23.1.6
-- 1.3.6.1.4.1.37950.1.1.5.10.23.1.6
-- 1.3.6.1.4.1.37950.1.1.5.10.23.1.6
-- 1.3.6.1.4.1.37950.1.1.5.10.23.1.6
		-- 1.3.6.1.4.1.37950.1.1.5.10.23.1.6
		ripngRouteNetworking OBJECT IDENTIFIER ::= { ripngGlobalCfg 6 }

		
--         1.3.6.1.4.1.37950.1.1.5.10.23.1.6.1
-- 1.3.6.1.4.1.37950.1.1.5.10.23.1.6.1
-- 1.3.6.1.4.1.37950.1.1.5.10.23.1.6.1
-- 1.3.6.1.4.1.37950.1.1.5.10.23.1.6.1
-- 1.3.6.1.4.1.37950.1.1.5.10.23.1.6.1
-- 1.3.6.1.4.1.37950.1.1.5.10.23.1.6.1
-- 1.3.6.1.4.1.37950.1.1.5.10.23.1.6.1
-- 1.3.6.1.4.1.37950.1.1.5.10.23.1.6.1
		-- 1.3.6.1.4.1.37950.1.1.5.10.23.1.6.1
		ripngVlanid OBJECT-TYPE
			SYNTAX Integer32 (1..4094)
			MAX-ACCESS read-write
			STATUS current
			DESCRIPTION
				"Description."
			::= { ripngRouteNetworking 1 }

		
--         1.3.6.1.4.1.37950.1.1.5.10.23.1.6.2
-- 1.3.6.1.4.1.37950.1.1.5.10.23.1.6.2
-- 1.3.6.1.4.1.37950.1.1.5.10.23.1.6.2
-- 1.3.6.1.4.1.37950.1.1.5.10.23.1.6.2
-- 1.3.6.1.4.1.37950.1.1.5.10.23.1.6.2
-- 1.3.6.1.4.1.37950.1.1.5.10.23.1.6.2
-- 1.3.6.1.4.1.37950.1.1.5.10.23.1.6.2
-- 1.3.6.1.4.1.37950.1.1.5.10.23.1.6.2
		-- 1.3.6.1.4.1.37950.1.1.5.10.23.1.6.2
		ripngIPv6Addr OBJECT-TYPE
			SYNTAX OCTET STRING
			MAX-ACCESS read-write
			STATUS current
			DESCRIPTION
				"Description."
			::= { ripngRouteNetworking 2 }

		
--         1.3.6.1.4.1.37950.1.1.5.10.23.1.6.3
-- 1.3.6.1.4.1.37950.1.1.5.10.23.1.6.3
-- 1.3.6.1.4.1.37950.1.1.5.10.23.1.6.3
-- 1.3.6.1.4.1.37950.1.1.5.10.23.1.6.3
-- 1.3.6.1.4.1.37950.1.1.5.10.23.1.6.3
-- 1.3.6.1.4.1.37950.1.1.5.10.23.1.6.3
-- 1.3.6.1.4.1.37950.1.1.5.10.23.1.6.3
-- 1.3.6.1.4.1.37950.1.1.5.10.23.1.6.3
		-- 1.3.6.1.4.1.37950.1.1.5.10.23.1.6.3
		ripngRouteAction OBJECT-TYPE
			SYNTAX INTEGER
				{
				add(1),
				del(2)
				}
			MAX-ACCESS read-write
			STATUS current
			DESCRIPTION
				"Description."
			::= { ripngRouteNetworking 3 }

		
--         1.3.6.1.4.1.37950.1.1.5.10.23.1.7
-- 1.3.6.1.4.1.37950.1.1.5.10.23.1.7
-- 1.3.6.1.4.1.37950.1.1.5.10.23.1.7
-- 1.3.6.1.4.1.37950.1.1.5.10.23.1.7
-- 1.3.6.1.4.1.37950.1.1.5.10.23.1.7
-- 1.3.6.1.4.1.37950.1.1.5.10.23.1.7
-- 1.3.6.1.4.1.37950.1.1.5.10.23.1.7
-- 1.3.6.1.4.1.37950.1.1.5.10.23.1.7
		-- 1.3.6.1.4.1.37950.1.1.5.10.23.1.7
		ripngRouteNetworkTable OBJECT-TYPE
			SYNTAX SEQUENCE OF RipngRouteNetworkEntry
			MAX-ACCESS not-accessible
			STATUS current
			DESCRIPTION
				"Description."
			::= { ripngGlobalCfg 7 }

		
--         1.3.6.1.4.1.37950.1.1.5.10.23.1.7.1
-- 1.3.6.1.4.1.37950.1.1.5.10.23.1.7.1
-- 1.3.6.1.4.1.37950.1.1.5.10.23.1.7.1
-- 1.3.6.1.4.1.37950.1.1.5.10.23.1.7.1
-- 1.3.6.1.4.1.37950.1.1.5.10.23.1.7.1
-- 1.3.6.1.4.1.37950.1.1.5.10.23.1.7.1
-- 1.3.6.1.4.1.37950.1.1.5.10.23.1.7.1
-- 1.3.6.1.4.1.37950.1.1.5.10.23.1.7.1
		-- 1.3.6.1.4.1.37950.1.1.5.10.23.1.7.1
		ripngRouteNetworkEntry OBJECT-TYPE
			SYNTAX RipngRouteNetworkEntry
			MAX-ACCESS not-accessible
			STATUS current
			DESCRIPTION
				"Description."
			INDEX { ripngRouteNetwork }
			::= { ripngRouteNetworkTable 1 }

		
		RipngRouteNetworkEntry ::=
			SEQUENCE { 
				ripngRouteNetwork
					OCTET STRING
			 }

--         1.3.6.1.4.1.37950.1.1.5.10.23.1.7.1.1
-- 1.3.6.1.4.1.37950.1.1.5.10.23.1.7.1.1
-- 1.3.6.1.4.1.37950.1.1.5.10.23.1.7.1.1
-- 1.3.6.1.4.1.37950.1.1.5.10.23.1.7.1.1
-- 1.3.6.1.4.1.37950.1.1.5.10.23.1.7.1.1
-- 1.3.6.1.4.1.37950.1.1.5.10.23.1.7.1.1
-- 1.3.6.1.4.1.37950.1.1.5.10.23.1.7.1.1
-- 1.3.6.1.4.1.37950.1.1.5.10.23.1.7.1.1
		-- 1.3.6.1.4.1.37950.1.1.5.10.23.1.7.1.1
		ripngRouteNetwork OBJECT-TYPE
			SYNTAX OCTET STRING
			MAX-ACCESS read-only
			STATUS current
			DESCRIPTION
				"Description."
			::= { ripngRouteNetworkEntry 1 }

		
--         1.3.6.1.4.1.37950.1.1.5.10.23.1.8
-- 1.3.6.1.4.1.37950.1.1.5.10.23.1.8
-- 1.3.6.1.4.1.37950.1.1.5.10.23.1.8
-- 1.3.6.1.4.1.37950.1.1.5.10.23.1.8
-- 1.3.6.1.4.1.37950.1.1.5.10.23.1.8
-- 1.3.6.1.4.1.37950.1.1.5.10.23.1.8
-- 1.3.6.1.4.1.37950.1.1.5.10.23.1.8
-- 1.3.6.1.4.1.37950.1.1.5.10.23.1.8
		-- 1.3.6.1.4.1.37950.1.1.5.10.23.1.8
		ripngAggregate OBJECT IDENTIFIER ::= { ripngGlobalCfg 8 }

		
--         1.3.6.1.4.1.37950.1.1.5.10.23.1.8.1
-- 1.3.6.1.4.1.37950.1.1.5.10.23.1.8.1
-- 1.3.6.1.4.1.37950.1.1.5.10.23.1.8.1
-- 1.3.6.1.4.1.37950.1.1.5.10.23.1.8.1
-- 1.3.6.1.4.1.37950.1.1.5.10.23.1.8.1
-- 1.3.6.1.4.1.37950.1.1.5.10.23.1.8.1
-- 1.3.6.1.4.1.37950.1.1.5.10.23.1.8.1
-- 1.3.6.1.4.1.37950.1.1.5.10.23.1.8.1
		-- 1.3.6.1.4.1.37950.1.1.5.10.23.1.8.1
		ripngAggreIPv6 OBJECT-TYPE
			SYNTAX OCTET STRING
			MAX-ACCESS read-write
			STATUS current
			DESCRIPTION
				"Description."
			::= { ripngAggregate 1 }

		
--         1.3.6.1.4.1.37950.1.1.5.10.23.1.8.2
-- 1.3.6.1.4.1.37950.1.1.5.10.23.1.8.2
-- 1.3.6.1.4.1.37950.1.1.5.10.23.1.8.2
-- 1.3.6.1.4.1.37950.1.1.5.10.23.1.8.2
-- 1.3.6.1.4.1.37950.1.1.5.10.23.1.8.2
-- 1.3.6.1.4.1.37950.1.1.5.10.23.1.8.2
-- 1.3.6.1.4.1.37950.1.1.5.10.23.1.8.2
-- 1.3.6.1.4.1.37950.1.1.5.10.23.1.8.2
		-- 1.3.6.1.4.1.37950.1.1.5.10.23.1.8.2
		ripngAggrePrefix OBJECT-TYPE
			SYNTAX Integer32 (0..128)
			MAX-ACCESS read-write
			STATUS current
			DESCRIPTION
				"Description."
			::= { ripngAggregate 2 }

		
--         1.3.6.1.4.1.37950.1.1.5.10.23.1.8.3
-- 1.3.6.1.4.1.37950.1.1.5.10.23.1.8.3
-- 1.3.6.1.4.1.37950.1.1.5.10.23.1.8.3
-- 1.3.6.1.4.1.37950.1.1.5.10.23.1.8.3
-- 1.3.6.1.4.1.37950.1.1.5.10.23.1.8.3
-- 1.3.6.1.4.1.37950.1.1.5.10.23.1.8.3
-- 1.3.6.1.4.1.37950.1.1.5.10.23.1.8.3
-- 1.3.6.1.4.1.37950.1.1.5.10.23.1.8.3
		-- 1.3.6.1.4.1.37950.1.1.5.10.23.1.8.3
		ripngAggreAction OBJECT-TYPE
			SYNTAX INTEGER
				{
				add(1),
				del(2)
				}
			MAX-ACCESS read-write
			STATUS current
			DESCRIPTION
				"Description."
			::= { ripngAggregate 3 }

		
--         1.3.6.1.4.1.37950.1.1.5.10.23.1.9
-- 1.3.6.1.4.1.37950.1.1.5.10.23.1.9
-- 1.3.6.1.4.1.37950.1.1.5.10.23.1.9
-- 1.3.6.1.4.1.37950.1.1.5.10.23.1.9
-- 1.3.6.1.4.1.37950.1.1.5.10.23.1.9
-- 1.3.6.1.4.1.37950.1.1.5.10.23.1.9
-- 1.3.6.1.4.1.37950.1.1.5.10.23.1.9
-- 1.3.6.1.4.1.37950.1.1.5.10.23.1.9
		-- 1.3.6.1.4.1.37950.1.1.5.10.23.1.9
		ripngAggregateTable OBJECT-TYPE
			SYNTAX SEQUENCE OF RipngAggregateEntry
			MAX-ACCESS not-accessible
			STATUS current
			DESCRIPTION
				"Description."
			::= { ripngGlobalCfg 9 }

		
--         1.3.6.1.4.1.37950.1.1.5.10.23.1.9.1
-- 1.3.6.1.4.1.37950.1.1.5.10.23.1.9.1
-- 1.3.6.1.4.1.37950.1.1.5.10.23.1.9.1
-- 1.3.6.1.4.1.37950.1.1.5.10.23.1.9.1
-- 1.3.6.1.4.1.37950.1.1.5.10.23.1.9.1
-- 1.3.6.1.4.1.37950.1.1.5.10.23.1.9.1
-- 1.3.6.1.4.1.37950.1.1.5.10.23.1.9.1
-- 1.3.6.1.4.1.37950.1.1.5.10.23.1.9.1
		-- 1.3.6.1.4.1.37950.1.1.5.10.23.1.9.1
		ripngAggregateEntry OBJECT-TYPE
			SYNTAX RipngAggregateEntry
			MAX-ACCESS not-accessible
			STATUS current
			DESCRIPTION
				"Description."
			INDEX { ripngAggreNetwork }
			::= { ripngAggregateTable 1 }

		
		RipngAggregateEntry ::=
			SEQUENCE { 
				ripngAggreNetwork
					OCTET STRING
			 }

--         1.3.6.1.4.1.37950.1.1.5.10.23.1.9.1.1
-- 1.3.6.1.4.1.37950.1.1.5.10.23.1.9.1.1
-- 1.3.6.1.4.1.37950.1.1.5.10.23.1.9.1.1
-- 1.3.6.1.4.1.37950.1.1.5.10.23.1.9.1.1
-- 1.3.6.1.4.1.37950.1.1.5.10.23.1.9.1.1
-- 1.3.6.1.4.1.37950.1.1.5.10.23.1.9.1.1
-- 1.3.6.1.4.1.37950.1.1.5.10.23.1.9.1.1
-- 1.3.6.1.4.1.37950.1.1.5.10.23.1.9.1.1
		-- 1.3.6.1.4.1.37950.1.1.5.10.23.1.9.1.1
		ripngAggreNetwork OBJECT-TYPE
			SYNTAX OCTET STRING
			MAX-ACCESS read-only
			STATUS current
			DESCRIPTION
				"Description."
			::= { ripngAggregateEntry 1 }

		
--         1.3.6.1.4.1.37950.1.1.5.10.23.1.10
-- 1.3.6.1.4.1.37950.1.1.5.10.23.1.10
-- 1.3.6.1.4.1.37950.1.1.5.10.23.1.10
-- 1.3.6.1.4.1.37950.1.1.5.10.23.1.10
-- 1.3.6.1.4.1.37950.1.1.5.10.23.1.10
-- 1.3.6.1.4.1.37950.1.1.5.10.23.1.10
-- 1.3.6.1.4.1.37950.1.1.5.10.23.1.10
-- 1.3.6.1.4.1.37950.1.1.5.10.23.1.10
		-- 1.3.6.1.4.1.37950.1.1.5.10.23.1.10
		ripngRedistribute OBJECT IDENTIFIER ::= { ripngGlobalCfg 10 }

		
--         1.3.6.1.4.1.37950.1.1.5.10.23.1.10.1
-- 1.3.6.1.4.1.37950.1.1.5.10.23.1.10.1
-- 1.3.6.1.4.1.37950.1.1.5.10.23.1.10.1
-- 1.3.6.1.4.1.37950.1.1.5.10.23.1.10.1
-- 1.3.6.1.4.1.37950.1.1.5.10.23.1.10.1
-- 1.3.6.1.4.1.37950.1.1.5.10.23.1.10.1
-- 1.3.6.1.4.1.37950.1.1.5.10.23.1.10.1
-- 1.3.6.1.4.1.37950.1.1.5.10.23.1.10.1
		-- 1.3.6.1.4.1.37950.1.1.5.10.23.1.10.1
		ripngDefRedisEn OBJECT-TYPE
			SYNTAX INTEGER
				{
				disable(0),
				enable(1)
				}
			MAX-ACCESS read-write
			STATUS current
			DESCRIPTION
				"Description."
			::= { ripngRedistribute 1 }

		
--         1.3.6.1.4.1.37950.1.1.5.10.23.1.10.2
-- 1.3.6.1.4.1.37950.1.1.5.10.23.1.10.2
-- 1.3.6.1.4.1.37950.1.1.5.10.23.1.10.2
-- 1.3.6.1.4.1.37950.1.1.5.10.23.1.10.2
-- 1.3.6.1.4.1.37950.1.1.5.10.23.1.10.2
-- 1.3.6.1.4.1.37950.1.1.5.10.23.1.10.2
-- 1.3.6.1.4.1.37950.1.1.5.10.23.1.10.2
-- 1.3.6.1.4.1.37950.1.1.5.10.23.1.10.2
		-- 1.3.6.1.4.1.37950.1.1.5.10.23.1.10.2
		ripngRedisType OBJECT-TYPE
			SYNTAX INTEGER
				{
				kernel(1),
				connected(2),
				static(3),
				ospf6(7)
				}
			MAX-ACCESS read-write
			STATUS current
			DESCRIPTION
				"Description."
			::= { ripngRedistribute 2 }

		
--         1.3.6.1.4.1.37950.1.1.5.10.23.1.10.3
-- 1.3.6.1.4.1.37950.1.1.5.10.23.1.10.3
-- 1.3.6.1.4.1.37950.1.1.5.10.23.1.10.3
-- 1.3.6.1.4.1.37950.1.1.5.10.23.1.10.3
-- 1.3.6.1.4.1.37950.1.1.5.10.23.1.10.3
-- 1.3.6.1.4.1.37950.1.1.5.10.23.1.10.3
-- 1.3.6.1.4.1.37950.1.1.5.10.23.1.10.3
-- 1.3.6.1.4.1.37950.1.1.5.10.23.1.10.3
		-- 1.3.6.1.4.1.37950.1.1.5.10.23.1.10.3
		ripngRedisMetric OBJECT-TYPE
			SYNTAX Integer32 (0..16)
			MAX-ACCESS read-write
			STATUS current
			DESCRIPTION
				"Description."
			::= { ripngRedistribute 3 }

		
--         1.3.6.1.4.1.37950.1.1.5.10.23.1.10.4
-- 1.3.6.1.4.1.37950.1.1.5.10.23.1.10.4
-- 1.3.6.1.4.1.37950.1.1.5.10.23.1.10.4
-- 1.3.6.1.4.1.37950.1.1.5.10.23.1.10.4
-- 1.3.6.1.4.1.37950.1.1.5.10.23.1.10.4
-- 1.3.6.1.4.1.37950.1.1.5.10.23.1.10.4
-- 1.3.6.1.4.1.37950.1.1.5.10.23.1.10.4
-- 1.3.6.1.4.1.37950.1.1.5.10.23.1.10.4
		-- 1.3.6.1.4.1.37950.1.1.5.10.23.1.10.4
		ripngRedisAction OBJECT-TYPE
			SYNTAX INTEGER
				{
				add(1),
				del(2)
				}
			MAX-ACCESS read-write
			STATUS current
			DESCRIPTION
				"Description."
			::= { ripngRedistribute 4 }

		
--         1.3.6.1.4.1.37950.1.1.5.10.23.1.11
-- 1.3.6.1.4.1.37950.1.1.5.10.23.1.11
-- 1.3.6.1.4.1.37950.1.1.5.10.23.1.11
-- 1.3.6.1.4.1.37950.1.1.5.10.23.1.11
-- 1.3.6.1.4.1.37950.1.1.5.10.23.1.11
-- 1.3.6.1.4.1.37950.1.1.5.10.23.1.11
-- 1.3.6.1.4.1.37950.1.1.5.10.23.1.11
-- 1.3.6.1.4.1.37950.1.1.5.10.23.1.11
		-- 1.3.6.1.4.1.37950.1.1.5.10.23.1.11
		ripngRedisTable OBJECT-TYPE
			SYNTAX SEQUENCE OF RipngRedisEntry
			MAX-ACCESS not-accessible
			STATUS current
			DESCRIPTION
				"Description."
			::= { ripngGlobalCfg 11 }

		
--         1.3.6.1.4.1.37950.1.1.5.10.23.1.11.1
-- 1.3.6.1.4.1.37950.1.1.5.10.23.1.11.1
-- 1.3.6.1.4.1.37950.1.1.5.10.23.1.11.1
-- 1.3.6.1.4.1.37950.1.1.5.10.23.1.11.1
-- 1.3.6.1.4.1.37950.1.1.5.10.23.1.11.1
-- 1.3.6.1.4.1.37950.1.1.5.10.23.1.11.1
-- 1.3.6.1.4.1.37950.1.1.5.10.23.1.11.1
-- 1.3.6.1.4.1.37950.1.1.5.10.23.1.11.1
		-- 1.3.6.1.4.1.37950.1.1.5.10.23.1.11.1
		ripngRedisEntry OBJECT-TYPE
			SYNTAX RipngRedisEntry
			MAX-ACCESS not-accessible
			STATUS current
			DESCRIPTION
				"Description."
			INDEX { ripngRedistributeType }
			::= { ripngRedisTable 1 }

		
		RipngRedisEntry ::=
			SEQUENCE { 
				ripngRedistributeType
					INTEGER,
				ripngRedistributeMetric
					Integer32
			 }

--         1.3.6.1.4.1.37950.1.1.5.10.23.1.11.1.1
-- 1.3.6.1.4.1.37950.1.1.5.10.23.1.11.1.1
-- 1.3.6.1.4.1.37950.1.1.5.10.23.1.11.1.1
-- 1.3.6.1.4.1.37950.1.1.5.10.23.1.11.1.1
-- 1.3.6.1.4.1.37950.1.1.5.10.23.1.11.1.1
-- 1.3.6.1.4.1.37950.1.1.5.10.23.1.11.1.1
-- 1.3.6.1.4.1.37950.1.1.5.10.23.1.11.1.1
-- 1.3.6.1.4.1.37950.1.1.5.10.23.1.11.1.1
		-- 1.3.6.1.4.1.37950.1.1.5.10.23.1.11.1.1
		ripngRedistributeType OBJECT-TYPE
			SYNTAX INTEGER
				{
				kernel(1),
				connect(2),
				static(3),
				ospf6(7)
				}
			MAX-ACCESS read-only
			STATUS current
			DESCRIPTION
				"Description."
			::= { ripngRedisEntry 1 }

		
--         1.3.6.1.4.1.37950.1.1.5.10.23.1.11.1.2
-- 1.3.6.1.4.1.37950.1.1.5.10.23.1.11.1.2
-- 1.3.6.1.4.1.37950.1.1.5.10.23.1.11.1.2
-- 1.3.6.1.4.1.37950.1.1.5.10.23.1.11.1.2
-- 1.3.6.1.4.1.37950.1.1.5.10.23.1.11.1.2
-- 1.3.6.1.4.1.37950.1.1.5.10.23.1.11.1.2
-- 1.3.6.1.4.1.37950.1.1.5.10.23.1.11.1.2
-- 1.3.6.1.4.1.37950.1.1.5.10.23.1.11.1.2
		-- 1.3.6.1.4.1.37950.1.1.5.10.23.1.11.1.2
		ripngRedistributeMetric OBJECT-TYPE
			SYNTAX Integer32 (0..16)
			MAX-ACCESS read-only
			STATUS current
			DESCRIPTION
				"Description."
			::= { ripngRedisEntry 2 }

		
--         1.3.6.1.4.1.37950.1.1.5.10.23.1.12
-- 1.3.6.1.4.1.37950.1.1.5.10.23.1.12
-- 1.3.6.1.4.1.37950.1.1.5.10.23.1.12
-- 1.3.6.1.4.1.37950.1.1.5.10.23.1.12
-- 1.3.6.1.4.1.37950.1.1.5.10.23.1.12
-- 1.3.6.1.4.1.37950.1.1.5.10.23.1.12
-- 1.3.6.1.4.1.37950.1.1.5.10.23.1.12
-- 1.3.6.1.4.1.37950.1.1.5.10.23.1.12
		-- 1.3.6.1.4.1.37950.1.1.5.10.23.1.12
		ripngInterfaceTable OBJECT-TYPE
			SYNTAX SEQUENCE OF RipngInterfaceEntry
			MAX-ACCESS not-accessible
			STATUS current
			DESCRIPTION
				"Description."
			::= { ripngGlobalCfg 12 }

		
--         1.3.6.1.4.1.37950.1.1.5.10.23.1.12.1
-- 1.3.6.1.4.1.37950.1.1.5.10.23.1.12.1
-- 1.3.6.1.4.1.37950.1.1.5.10.23.1.12.1
-- 1.3.6.1.4.1.37950.1.1.5.10.23.1.12.1
-- 1.3.6.1.4.1.37950.1.1.5.10.23.1.12.1
-- 1.3.6.1.4.1.37950.1.1.5.10.23.1.12.1
-- 1.3.6.1.4.1.37950.1.1.5.10.23.1.12.1
-- 1.3.6.1.4.1.37950.1.1.5.10.23.1.12.1
		-- 1.3.6.1.4.1.37950.1.1.5.10.23.1.12.1
		ripngInterfaceEntry OBJECT-TYPE
			SYNTAX RipngInterfaceEntry
			MAX-ACCESS not-accessible
			STATUS current
			DESCRIPTION
				"Description."
			INDEX { ripngInterfaceID }
			::= { ripngInterfaceTable 1 }

		
		RipngInterfaceEntry ::=
			SEQUENCE { 
				ripngInterfaceID
					OCTET STRING,
				ripngInterSplitHorizon
					INTEGER
			 }

--         1.3.6.1.4.1.37950.1.1.5.10.23.1.12.1.1
-- 1.3.6.1.4.1.37950.1.1.5.10.23.1.12.1.1
-- 1.3.6.1.4.1.37950.1.1.5.10.23.1.12.1.1
-- 1.3.6.1.4.1.37950.1.1.5.10.23.1.12.1.1
-- 1.3.6.1.4.1.37950.1.1.5.10.23.1.12.1.1
-- 1.3.6.1.4.1.37950.1.1.5.10.23.1.12.1.1
-- 1.3.6.1.4.1.37950.1.1.5.10.23.1.12.1.1
-- 1.3.6.1.4.1.37950.1.1.5.10.23.1.12.1.1
		-- 1.3.6.1.4.1.37950.1.1.5.10.23.1.12.1.1
		ripngInterfaceID OBJECT-TYPE
			SYNTAX OCTET STRING
			MAX-ACCESS read-only
			STATUS current
			DESCRIPTION
				"Description."
			::= { ripngInterfaceEntry 1 }

		
--         1.3.6.1.4.1.37950.1.1.5.10.23.1.12.1.2
-- 1.3.6.1.4.1.37950.1.1.5.10.23.1.12.1.2
-- 1.3.6.1.4.1.37950.1.1.5.10.23.1.12.1.2
-- 1.3.6.1.4.1.37950.1.1.5.10.23.1.12.1.2
-- 1.3.6.1.4.1.37950.1.1.5.10.23.1.12.1.2
-- 1.3.6.1.4.1.37950.1.1.5.10.23.1.12.1.2
-- 1.3.6.1.4.1.37950.1.1.5.10.23.1.12.1.2
-- 1.3.6.1.4.1.37950.1.1.5.10.23.1.12.1.2
		-- 1.3.6.1.4.1.37950.1.1.5.10.23.1.12.1.2
		ripngInterSplitHorizon OBJECT-TYPE
			SYNTAX INTEGER
				{
				disable(0),
				split-horizon(1),
				horizon-and-reverse(2)
				}
			MAX-ACCESS read-write
			STATUS current
			DESCRIPTION
				"Description."
			::= { ripngInterfaceEntry 2 }

		
--         1.3.6.1.4.1.37950.1.1.5.10.23.2
-- 1.3.6.1.4.1.37950.1.1.5.10.23.2
-- 1.3.6.1.4.1.37950.1.1.5.10.23.2
-- 1.3.6.1.4.1.37950.1.1.5.10.23.2
-- 1.3.6.1.4.1.37950.1.1.5.10.23.2
-- 1.3.6.1.4.1.37950.1.1.5.10.23.2
-- 1.3.6.1.4.1.37950.1.1.5.10.23.2
-- 1.3.6.1.4.1.37950.1.1.5.10.23.2
		-- 1.3.6.1.4.1.37950.1.1.5.10.23.2
		ripngRouteTable OBJECT-TYPE
			SYNTAX SEQUENCE OF RipngRouteEntry
			MAX-ACCESS not-accessible
			STATUS current
			DESCRIPTION
				"Description."
			::= { v1600RIPng 2 }

		
--         1.3.6.1.4.1.37950.1.1.5.10.23.2.1
-- 1.3.6.1.4.1.37950.1.1.5.10.23.2.1
-- 1.3.6.1.4.1.37950.1.1.5.10.23.2.1
-- 1.3.6.1.4.1.37950.1.1.5.10.23.2.1
-- 1.3.6.1.4.1.37950.1.1.5.10.23.2.1
-- 1.3.6.1.4.1.37950.1.1.5.10.23.2.1
-- 1.3.6.1.4.1.37950.1.1.5.10.23.2.1
-- 1.3.6.1.4.1.37950.1.1.5.10.23.2.1
		-- 1.3.6.1.4.1.37950.1.1.5.10.23.2.1
		ripngRouteEntry OBJECT-TYPE
			SYNTAX RipngRouteEntry
			MAX-ACCESS not-accessible
			STATUS current
			DESCRIPTION
				"Description."
			INDEX { ripngRouteType, ripngRouteNetworks }
			::= { ripngRouteTable 1 }

		
		RipngRouteEntry ::=
			SEQUENCE { 
				ripngRouteType
					OCTET STRING,
				ripngRouteNetworks
					OCTET STRING,
				ripngRouteNextHop
					OCTET STRING,
				ripngRouteVia
					OCTET STRING,
				ripngRouteMetric
					Integer32,
				ripngRouteTag
					Integer32,
				ripngRouteTime
					OCTET STRING
			 }

--         1.3.6.1.4.1.37950.1.1.5.10.23.2.1.1
-- 1.3.6.1.4.1.37950.1.1.5.10.23.2.1.1
-- 1.3.6.1.4.1.37950.1.1.5.10.23.2.1.1
-- 1.3.6.1.4.1.37950.1.1.5.10.23.2.1.1
-- 1.3.6.1.4.1.37950.1.1.5.10.23.2.1.1
-- 1.3.6.1.4.1.37950.1.1.5.10.23.2.1.1
-- 1.3.6.1.4.1.37950.1.1.5.10.23.2.1.1
-- 1.3.6.1.4.1.37950.1.1.5.10.23.2.1.1
		-- 1.3.6.1.4.1.37950.1.1.5.10.23.2.1.1
		ripngRouteType OBJECT-TYPE
			SYNTAX OCTET STRING
			MAX-ACCESS read-only
			STATUS current
			DESCRIPTION
				"Description."
			::= { ripngRouteEntry 1 }

		
--         1.3.6.1.4.1.37950.1.1.5.10.23.2.1.2
-- 1.3.6.1.4.1.37950.1.1.5.10.23.2.1.2
-- 1.3.6.1.4.1.37950.1.1.5.10.23.2.1.2
-- 1.3.6.1.4.1.37950.1.1.5.10.23.2.1.2
-- 1.3.6.1.4.1.37950.1.1.5.10.23.2.1.2
-- 1.3.6.1.4.1.37950.1.1.5.10.23.2.1.2
-- 1.3.6.1.4.1.37950.1.1.5.10.23.2.1.2
-- 1.3.6.1.4.1.37950.1.1.5.10.23.2.1.2
		-- 1.3.6.1.4.1.37950.1.1.5.10.23.2.1.2
		ripngRouteNetworks OBJECT-TYPE
			SYNTAX OCTET STRING
			MAX-ACCESS read-only
			STATUS current
			DESCRIPTION
				"Description."
			::= { ripngRouteEntry 2 }

		
--         1.3.6.1.4.1.37950.1.1.5.10.23.2.1.3
-- 1.3.6.1.4.1.37950.1.1.5.10.23.2.1.3
-- 1.3.6.1.4.1.37950.1.1.5.10.23.2.1.3
-- 1.3.6.1.4.1.37950.1.1.5.10.23.2.1.3
-- 1.3.6.1.4.1.37950.1.1.5.10.23.2.1.3
-- 1.3.6.1.4.1.37950.1.1.5.10.23.2.1.3
-- 1.3.6.1.4.1.37950.1.1.5.10.23.2.1.3
-- 1.3.6.1.4.1.37950.1.1.5.10.23.2.1.3
		-- 1.3.6.1.4.1.37950.1.1.5.10.23.2.1.3
		ripngRouteNextHop OBJECT-TYPE
			SYNTAX OCTET STRING
			MAX-ACCESS read-only
			STATUS current
			DESCRIPTION
				"Description."
			::= { ripngRouteEntry 3 }

		
--         1.3.6.1.4.1.37950.1.1.5.10.23.2.1.4
-- 1.3.6.1.4.1.37950.1.1.5.10.23.2.1.4
-- 1.3.6.1.4.1.37950.1.1.5.10.23.2.1.4
-- 1.3.6.1.4.1.37950.1.1.5.10.23.2.1.4
-- 1.3.6.1.4.1.37950.1.1.5.10.23.2.1.4
-- 1.3.6.1.4.1.37950.1.1.5.10.23.2.1.4
-- 1.3.6.1.4.1.37950.1.1.5.10.23.2.1.4
-- 1.3.6.1.4.1.37950.1.1.5.10.23.2.1.4
		-- 1.3.6.1.4.1.37950.1.1.5.10.23.2.1.4
		ripngRouteVia OBJECT-TYPE
			SYNTAX OCTET STRING
			MAX-ACCESS read-only
			STATUS current
			DESCRIPTION
				"Description."
			::= { ripngRouteEntry 4 }

		
--         1.3.6.1.4.1.37950.1.1.5.10.23.2.1.5
-- 1.3.6.1.4.1.37950.1.1.5.10.23.2.1.5
-- 1.3.6.1.4.1.37950.1.1.5.10.23.2.1.5
-- 1.3.6.1.4.1.37950.1.1.5.10.23.2.1.5
-- 1.3.6.1.4.1.37950.1.1.5.10.23.2.1.5
-- 1.3.6.1.4.1.37950.1.1.5.10.23.2.1.5
-- 1.3.6.1.4.1.37950.1.1.5.10.23.2.1.5
-- 1.3.6.1.4.1.37950.1.1.5.10.23.2.1.5
		-- 1.3.6.1.4.1.37950.1.1.5.10.23.2.1.5
		ripngRouteMetric OBJECT-TYPE
			SYNTAX Integer32
			MAX-ACCESS read-only
			STATUS current
			DESCRIPTION
				"Description."
			::= { ripngRouteEntry 5 }

		
--         1.3.6.1.4.1.37950.1.1.5.10.23.2.1.6
-- 1.3.6.1.4.1.37950.1.1.5.10.23.2.1.6
-- 1.3.6.1.4.1.37950.1.1.5.10.23.2.1.6
-- 1.3.6.1.4.1.37950.1.1.5.10.23.2.1.6
-- 1.3.6.1.4.1.37950.1.1.5.10.23.2.1.6
-- 1.3.6.1.4.1.37950.1.1.5.10.23.2.1.6
-- 1.3.6.1.4.1.37950.1.1.5.10.23.2.1.6
-- 1.3.6.1.4.1.37950.1.1.5.10.23.2.1.6
		-- 1.3.6.1.4.1.37950.1.1.5.10.23.2.1.6
		ripngRouteTag OBJECT-TYPE
			SYNTAX Integer32
			MAX-ACCESS read-only
			STATUS current
			DESCRIPTION
				"Description."
			::= { ripngRouteEntry 6 }

		
--         1.3.6.1.4.1.37950.1.1.5.10.23.2.1.7
-- 1.3.6.1.4.1.37950.1.1.5.10.23.2.1.7
-- 1.3.6.1.4.1.37950.1.1.5.10.23.2.1.7
-- 1.3.6.1.4.1.37950.1.1.5.10.23.2.1.7
-- 1.3.6.1.4.1.37950.1.1.5.10.23.2.1.7
-- 1.3.6.1.4.1.37950.1.1.5.10.23.2.1.7
-- 1.3.6.1.4.1.37950.1.1.5.10.23.2.1.7
-- 1.3.6.1.4.1.37950.1.1.5.10.23.2.1.7
		-- 1.3.6.1.4.1.37950.1.1.5.10.23.2.1.7
		ripngRouteTime OBJECT-TYPE
			SYNTAX OCTET STRING
			MAX-ACCESS read-only
			STATUS current
			DESCRIPTION
				"Description."
			::= { ripngRouteEntry 7 }

		
--         1.3.6.1.4.1.37950.1.1.5.10.23.3
-- 1.3.6.1.4.1.37950.1.1.5.10.23.3
-- 1.3.6.1.4.1.37950.1.1.5.10.23.3
-- 1.3.6.1.4.1.37950.1.1.5.10.23.3
-- 1.3.6.1.4.1.37950.1.1.5.10.23.3
-- 1.3.6.1.4.1.37950.1.1.5.10.23.3
-- 1.3.6.1.4.1.37950.1.1.5.10.23.3
-- 1.3.6.1.4.1.37950.1.1.5.10.23.3
		-- 1.3.6.1.4.1.37950.1.1.5.10.23.3
		ripngRouteInfoSrcTable OBJECT-TYPE
			SYNTAX SEQUENCE OF RipngRouteInfoSrcEntry
			MAX-ACCESS not-accessible
			STATUS current
			DESCRIPTION
				"Description."
			::= { v1600RIPng 3 }

		
--         1.3.6.1.4.1.37950.1.1.5.10.23.3.1
-- 1.3.6.1.4.1.37950.1.1.5.10.23.3.1
-- 1.3.6.1.4.1.37950.1.1.5.10.23.3.1
-- 1.3.6.1.4.1.37950.1.1.5.10.23.3.1
-- 1.3.6.1.4.1.37950.1.1.5.10.23.3.1
-- 1.3.6.1.4.1.37950.1.1.5.10.23.3.1
-- 1.3.6.1.4.1.37950.1.1.5.10.23.3.1
-- 1.3.6.1.4.1.37950.1.1.5.10.23.3.1
		-- 1.3.6.1.4.1.37950.1.1.5.10.23.3.1
		ripngRouteInfoSrcEntry OBJECT-TYPE
			SYNTAX RipngRouteInfoSrcEntry
			MAX-ACCESS not-accessible
			STATUS current
			DESCRIPTION
				"Description."
			INDEX { ripngGateway }
			::= { ripngRouteInfoSrcTable 1 }

		
		RipngRouteInfoSrcEntry ::=
			SEQUENCE { 
				ripngGateway
					OCTET STRING,
				ripngBadPackets
					Unsigned32,
				ripngBadRoutes
					Unsigned32,
				ripngDistance
					Unsigned32,
				ripngLastUpdate
					OCTET STRING
			 }

--         1.3.6.1.4.1.37950.1.1.5.10.23.3.1.1
-- 1.3.6.1.4.1.37950.1.1.5.10.23.3.1.1
-- 1.3.6.1.4.1.37950.1.1.5.10.23.3.1.1
-- 1.3.6.1.4.1.37950.1.1.5.10.23.3.1.1
-- 1.3.6.1.4.1.37950.1.1.5.10.23.3.1.1
-- 1.3.6.1.4.1.37950.1.1.5.10.23.3.1.1
-- 1.3.6.1.4.1.37950.1.1.5.10.23.3.1.1
-- 1.3.6.1.4.1.37950.1.1.5.10.23.3.1.1
		-- 1.3.6.1.4.1.37950.1.1.5.10.23.3.1.1
		ripngGateway OBJECT-TYPE
			SYNTAX OCTET STRING
			MAX-ACCESS read-only
			STATUS current
			DESCRIPTION
				"Description."
			::= { ripngRouteInfoSrcEntry 1 }

		
--         1.3.6.1.4.1.37950.1.1.5.10.23.3.1.2
-- 1.3.6.1.4.1.37950.1.1.5.10.23.3.1.2
-- 1.3.6.1.4.1.37950.1.1.5.10.23.3.1.2
-- 1.3.6.1.4.1.37950.1.1.5.10.23.3.1.2
-- 1.3.6.1.4.1.37950.1.1.5.10.23.3.1.2
-- 1.3.6.1.4.1.37950.1.1.5.10.23.3.1.2
-- 1.3.6.1.4.1.37950.1.1.5.10.23.3.1.2
-- 1.3.6.1.4.1.37950.1.1.5.10.23.3.1.2
		-- 1.3.6.1.4.1.37950.1.1.5.10.23.3.1.2
		ripngBadPackets OBJECT-TYPE
			SYNTAX Unsigned32
			MAX-ACCESS read-only
			STATUS current
			DESCRIPTION
				"Description."
			::= { ripngRouteInfoSrcEntry 2 }

		
--         1.3.6.1.4.1.37950.1.1.5.10.23.3.1.3
-- 1.3.6.1.4.1.37950.1.1.5.10.23.3.1.3
-- 1.3.6.1.4.1.37950.1.1.5.10.23.3.1.3
-- 1.3.6.1.4.1.37950.1.1.5.10.23.3.1.3
-- 1.3.6.1.4.1.37950.1.1.5.10.23.3.1.3
-- 1.3.6.1.4.1.37950.1.1.5.10.23.3.1.3
-- 1.3.6.1.4.1.37950.1.1.5.10.23.3.1.3
-- 1.3.6.1.4.1.37950.1.1.5.10.23.3.1.3
		-- 1.3.6.1.4.1.37950.1.1.5.10.23.3.1.3
		ripngBadRoutes OBJECT-TYPE
			SYNTAX Unsigned32
			MAX-ACCESS read-only
			STATUS current
			DESCRIPTION
				"Description."
			::= { ripngRouteInfoSrcEntry 3 }

		
--         1.3.6.1.4.1.37950.1.1.5.10.23.3.1.4
-- 1.3.6.1.4.1.37950.1.1.5.10.23.3.1.4
-- 1.3.6.1.4.1.37950.1.1.5.10.23.3.1.4
-- 1.3.6.1.4.1.37950.1.1.5.10.23.3.1.4
-- 1.3.6.1.4.1.37950.1.1.5.10.23.3.1.4
-- 1.3.6.1.4.1.37950.1.1.5.10.23.3.1.4
-- 1.3.6.1.4.1.37950.1.1.5.10.23.3.1.4
-- 1.3.6.1.4.1.37950.1.1.5.10.23.3.1.4
		-- 1.3.6.1.4.1.37950.1.1.5.10.23.3.1.4
		ripngDistance OBJECT-TYPE
			SYNTAX Unsigned32
			MAX-ACCESS read-only
			STATUS current
			DESCRIPTION
				"Description."
			::= { ripngRouteInfoSrcEntry 4 }

		
--         1.3.6.1.4.1.37950.1.1.5.10.23.3.1.5
-- 1.3.6.1.4.1.37950.1.1.5.10.23.3.1.5
-- 1.3.6.1.4.1.37950.1.1.5.10.23.3.1.5
-- 1.3.6.1.4.1.37950.1.1.5.10.23.3.1.5
-- 1.3.6.1.4.1.37950.1.1.5.10.23.3.1.5
-- 1.3.6.1.4.1.37950.1.1.5.10.23.3.1.5
-- 1.3.6.1.4.1.37950.1.1.5.10.23.3.1.5
-- 1.3.6.1.4.1.37950.1.1.5.10.23.3.1.5
		-- 1.3.6.1.4.1.37950.1.1.5.10.23.3.1.5
		ripngLastUpdate OBJECT-TYPE
			SYNTAX OCTET STRING
			MAX-ACCESS read-only
			STATUS current
			DESCRIPTION
				"Description."
			::= { ripngRouteInfoSrcEntry 5 }

		
--         1.3.6.1.4.1.37950.1.1.5.10.25
-- 1.3.6.1.4.1.37950.1.1.5.10.25
-- 1.3.6.1.4.1.37950.1.1.5.10.25
-- 1.3.6.1.4.1.37950.1.1.5.10.25
-- 1.3.6.1.4.1.37950.1.1.5.10.25
-- 1.3.6.1.4.1.37950.1.1.5.10.25
-- 1.3.6.1.4.1.37950.1.1.5.10.25
-- 1.3.6.1.4.1.37950.1.1.5.10.25
		-- 1.3.6.1.4.1.37950.1.1.5.10.25
		v1600Tacacs OBJECT IDENTIFIER ::= { v1600dSwitch 25 }

		
--         1.3.6.1.4.1.37950.1.1.5.10.25.1
-- 1.3.6.1.4.1.37950.1.1.5.10.25.1
-- 1.3.6.1.4.1.37950.1.1.5.10.25.1
-- 1.3.6.1.4.1.37950.1.1.5.10.25.1
-- 1.3.6.1.4.1.37950.1.1.5.10.25.1
-- 1.3.6.1.4.1.37950.1.1.5.10.25.1
-- 1.3.6.1.4.1.37950.1.1.5.10.25.1
-- 1.3.6.1.4.1.37950.1.1.5.10.25.1
		-- 1.3.6.1.4.1.37950.1.1.5.10.25.1
		tacplusCfg OBJECT IDENTIFIER ::= { v1600Tacacs 1 }

		
--         1.3.6.1.4.1.37950.1.1.5.10.25.1.1
-- 1.3.6.1.4.1.37950.1.1.5.10.25.1.1
-- 1.3.6.1.4.1.37950.1.1.5.10.25.1.1
-- 1.3.6.1.4.1.37950.1.1.5.10.25.1.1
-- 1.3.6.1.4.1.37950.1.1.5.10.25.1.1
-- 1.3.6.1.4.1.37950.1.1.5.10.25.1.1
-- 1.3.6.1.4.1.37950.1.1.5.10.25.1.1
-- 1.3.6.1.4.1.37950.1.1.5.10.25.1.1
		-- 1.3.6.1.4.1.37950.1.1.5.10.25.1.1
		tacAAAEnable OBJECT-TYPE
			SYNTAX INTEGER
				{
				enable(0),
				disable(1)
				}
			MAX-ACCESS read-write
			STATUS current
			DESCRIPTION
				"Description."
			::= { tacplusCfg 1 }

		
--         1.3.6.1.4.1.37950.1.1.5.10.25.1.2
-- 1.3.6.1.4.1.37950.1.1.5.10.25.1.2
-- 1.3.6.1.4.1.37950.1.1.5.10.25.1.2
-- 1.3.6.1.4.1.37950.1.1.5.10.25.1.2
-- 1.3.6.1.4.1.37950.1.1.5.10.25.1.2
-- 1.3.6.1.4.1.37950.1.1.5.10.25.1.2
-- 1.3.6.1.4.1.37950.1.1.5.10.25.1.2
-- 1.3.6.1.4.1.37950.1.1.5.10.25.1.2
		-- 1.3.6.1.4.1.37950.1.1.5.10.25.1.2
		tacAuthen OBJECT-TYPE
			SYNTAX INTEGER
				{
				enable(0),
				disable(1)
				}
			MAX-ACCESS read-write
			STATUS current
			DESCRIPTION
				"Description."
			::= { tacplusCfg 2 }

		
--         1.3.6.1.4.1.37950.1.1.5.10.25.1.3
-- 1.3.6.1.4.1.37950.1.1.5.10.25.1.3
-- 1.3.6.1.4.1.37950.1.1.5.10.25.1.3
-- 1.3.6.1.4.1.37950.1.1.5.10.25.1.3
-- 1.3.6.1.4.1.37950.1.1.5.10.25.1.3
-- 1.3.6.1.4.1.37950.1.1.5.10.25.1.3
-- 1.3.6.1.4.1.37950.1.1.5.10.25.1.3
-- 1.3.6.1.4.1.37950.1.1.5.10.25.1.3
		-- 1.3.6.1.4.1.37950.1.1.5.10.25.1.3
		tacAuthenLocal OBJECT-TYPE
			SYNTAX INTEGER
				{
				enable(0),
				disable(1)
				}
			MAX-ACCESS read-write
			STATUS current
			DESCRIPTION
				"Description."
			::= { tacplusCfg 3 }

		
--         1.3.6.1.4.1.37950.1.1.5.10.25.1.4
-- 1.3.6.1.4.1.37950.1.1.5.10.25.1.4
-- 1.3.6.1.4.1.37950.1.1.5.10.25.1.4
-- 1.3.6.1.4.1.37950.1.1.5.10.25.1.4
-- 1.3.6.1.4.1.37950.1.1.5.10.25.1.4
-- 1.3.6.1.4.1.37950.1.1.5.10.25.1.4
-- 1.3.6.1.4.1.37950.1.1.5.10.25.1.4
-- 1.3.6.1.4.1.37950.1.1.5.10.25.1.4
		-- 1.3.6.1.4.1.37950.1.1.5.10.25.1.4
		tacAuthenEnable OBJECT-TYPE
			SYNTAX INTEGER
				{
				enable(0),
				disable(1)
				}
			MAX-ACCESS read-write
			STATUS current
			DESCRIPTION
				"Description."
			::= { tacplusCfg 4 }

		
--         1.3.6.1.4.1.37950.1.1.5.10.25.1.5
-- 1.3.6.1.4.1.37950.1.1.5.10.25.1.5
-- 1.3.6.1.4.1.37950.1.1.5.10.25.1.5
-- 1.3.6.1.4.1.37950.1.1.5.10.25.1.5
-- 1.3.6.1.4.1.37950.1.1.5.10.25.1.5
-- 1.3.6.1.4.1.37950.1.1.5.10.25.1.5
-- 1.3.6.1.4.1.37950.1.1.5.10.25.1.5
-- 1.3.6.1.4.1.37950.1.1.5.10.25.1.5
		-- 1.3.6.1.4.1.37950.1.1.5.10.25.1.5
		tacAuthenEnableLocal OBJECT-TYPE
			SYNTAX INTEGER
				{
				enable(0),
				disable(1)
				}
			MAX-ACCESS read-write
			STATUS current
			DESCRIPTION
				"Description."
			::= { tacplusCfg 5 }

		
--         1.3.6.1.4.1.37950.1.1.5.10.25.1.6
-- 1.3.6.1.4.1.37950.1.1.5.10.25.1.6
-- 1.3.6.1.4.1.37950.1.1.5.10.25.1.6
-- 1.3.6.1.4.1.37950.1.1.5.10.25.1.6
-- 1.3.6.1.4.1.37950.1.1.5.10.25.1.6
-- 1.3.6.1.4.1.37950.1.1.5.10.25.1.6
-- 1.3.6.1.4.1.37950.1.1.5.10.25.1.6
-- 1.3.6.1.4.1.37950.1.1.5.10.25.1.6
		-- 1.3.6.1.4.1.37950.1.1.5.10.25.1.6
		tacAuthorExec OBJECT-TYPE
			SYNTAX INTEGER
				{
				enable(0),
				disable(1)
				}
			MAX-ACCESS read-write
			STATUS current
			DESCRIPTION
				"Description."
			::= { tacplusCfg 6 }

		
--         1.3.6.1.4.1.37950.1.1.5.10.25.1.7
-- 1.3.6.1.4.1.37950.1.1.5.10.25.1.7
-- 1.3.6.1.4.1.37950.1.1.5.10.25.1.7
-- 1.3.6.1.4.1.37950.1.1.5.10.25.1.7
-- 1.3.6.1.4.1.37950.1.1.5.10.25.1.7
-- 1.3.6.1.4.1.37950.1.1.5.10.25.1.7
-- 1.3.6.1.4.1.37950.1.1.5.10.25.1.7
-- 1.3.6.1.4.1.37950.1.1.5.10.25.1.7
		-- 1.3.6.1.4.1.37950.1.1.5.10.25.1.7
		tacAuthorExecLocal OBJECT-TYPE
			SYNTAX INTEGER
				{
				enable(0),
				disable(1)
				}
			MAX-ACCESS read-write
			STATUS current
			DESCRIPTION
				"Description."
			::= { tacplusCfg 7 }

		
--         1.3.6.1.4.1.37950.1.1.5.10.25.1.8
-- 1.3.6.1.4.1.37950.1.1.5.10.25.1.8
-- 1.3.6.1.4.1.37950.1.1.5.10.25.1.8
-- 1.3.6.1.4.1.37950.1.1.5.10.25.1.8
-- 1.3.6.1.4.1.37950.1.1.5.10.25.1.8
-- 1.3.6.1.4.1.37950.1.1.5.10.25.1.8
-- 1.3.6.1.4.1.37950.1.1.5.10.25.1.8
-- 1.3.6.1.4.1.37950.1.1.5.10.25.1.8
		-- 1.3.6.1.4.1.37950.1.1.5.10.25.1.8
		tacAuthorCmdLv OBJECT-TYPE
			SYNTAX INTEGER (0..15)
			MAX-ACCESS read-write
			STATUS current
			DESCRIPTION
				"Description."
			::= { tacplusCfg 8 }

		
--         1.3.6.1.4.1.37950.1.1.5.10.25.1.9
-- 1.3.6.1.4.1.37950.1.1.5.10.25.1.9
-- 1.3.6.1.4.1.37950.1.1.5.10.25.1.9
-- 1.3.6.1.4.1.37950.1.1.5.10.25.1.9
-- 1.3.6.1.4.1.37950.1.1.5.10.25.1.9
-- 1.3.6.1.4.1.37950.1.1.5.10.25.1.9
-- 1.3.6.1.4.1.37950.1.1.5.10.25.1.9
-- 1.3.6.1.4.1.37950.1.1.5.10.25.1.9
		-- 1.3.6.1.4.1.37950.1.1.5.10.25.1.9
		tacAuthorCmdLvLocal OBJECT-TYPE
			SYNTAX INTEGER (0..15)
			MAX-ACCESS read-write
			STATUS current
			DESCRIPTION
				"Description."
			::= { tacplusCfg 9 }

		
--         1.3.6.1.4.1.37950.1.1.5.10.25.1.10
-- 1.3.6.1.4.1.37950.1.1.5.10.25.1.10
-- 1.3.6.1.4.1.37950.1.1.5.10.25.1.10
-- 1.3.6.1.4.1.37950.1.1.5.10.25.1.10
-- 1.3.6.1.4.1.37950.1.1.5.10.25.1.10
-- 1.3.6.1.4.1.37950.1.1.5.10.25.1.10
-- 1.3.6.1.4.1.37950.1.1.5.10.25.1.10
-- 1.3.6.1.4.1.37950.1.1.5.10.25.1.10
		-- 1.3.6.1.4.1.37950.1.1.5.10.25.1.10
		tacAuthorCmdEnable OBJECT-TYPE
			SYNTAX INTEGER
				{
				enable(0),
				disable(1)
				}
			MAX-ACCESS read-write
			STATUS current
			DESCRIPTION
				"Description."
			::= { tacplusCfg 10 }

		
--         1.3.6.1.4.1.37950.1.1.5.10.25.1.11
-- 1.3.6.1.4.1.37950.1.1.5.10.25.1.11
-- 1.3.6.1.4.1.37950.1.1.5.10.25.1.11
-- 1.3.6.1.4.1.37950.1.1.5.10.25.1.11
-- 1.3.6.1.4.1.37950.1.1.5.10.25.1.11
-- 1.3.6.1.4.1.37950.1.1.5.10.25.1.11
-- 1.3.6.1.4.1.37950.1.1.5.10.25.1.11
-- 1.3.6.1.4.1.37950.1.1.5.10.25.1.11
		-- 1.3.6.1.4.1.37950.1.1.5.10.25.1.11
		tacAcctExec OBJECT-TYPE
			SYNTAX INTEGER
				{
				enable(0),
				disable(1)
				}
			MAX-ACCESS read-write
			STATUS current
			DESCRIPTION
				"Description."
			::= { tacplusCfg 11 }

		
--         1.3.6.1.4.1.37950.1.1.5.10.25.1.12
-- 1.3.6.1.4.1.37950.1.1.5.10.25.1.12
-- 1.3.6.1.4.1.37950.1.1.5.10.25.1.12
-- 1.3.6.1.4.1.37950.1.1.5.10.25.1.12
-- 1.3.6.1.4.1.37950.1.1.5.10.25.1.12
-- 1.3.6.1.4.1.37950.1.1.5.10.25.1.12
-- 1.3.6.1.4.1.37950.1.1.5.10.25.1.12
-- 1.3.6.1.4.1.37950.1.1.5.10.25.1.12
		-- 1.3.6.1.4.1.37950.1.1.5.10.25.1.12
		tacAcctCmdLv OBJECT-TYPE
			SYNTAX INTEGER (0..15)
			MAX-ACCESS read-write
			STATUS current
			DESCRIPTION
				"Description."
			::= { tacplusCfg 12 }

		
--         1.3.6.1.4.1.37950.1.1.5.10.25.1.13
-- 1.3.6.1.4.1.37950.1.1.5.10.25.1.13
-- 1.3.6.1.4.1.37950.1.1.5.10.25.1.13
-- 1.3.6.1.4.1.37950.1.1.5.10.25.1.13
-- 1.3.6.1.4.1.37950.1.1.5.10.25.1.13
-- 1.3.6.1.4.1.37950.1.1.5.10.25.1.13
-- 1.3.6.1.4.1.37950.1.1.5.10.25.1.13
-- 1.3.6.1.4.1.37950.1.1.5.10.25.1.13
		-- 1.3.6.1.4.1.37950.1.1.5.10.25.1.13
		tacAcctCmdEnable OBJECT-TYPE
			SYNTAX INTEGER
				{
				enable(0),
				disable(1)
				}
			MAX-ACCESS read-write
			STATUS current
			DESCRIPTION
				"Description."
			::= { tacplusCfg 13 }

		
--         1.3.6.1.4.1.37950.1.1.5.10.25.1.14
-- 1.3.6.1.4.1.37950.1.1.5.10.25.1.14
-- 1.3.6.1.4.1.37950.1.1.5.10.25.1.14
-- 1.3.6.1.4.1.37950.1.1.5.10.25.1.14
-- 1.3.6.1.4.1.37950.1.1.5.10.25.1.14
-- 1.3.6.1.4.1.37950.1.1.5.10.25.1.14
-- 1.3.6.1.4.1.37950.1.1.5.10.25.1.14
-- 1.3.6.1.4.1.37950.1.1.5.10.25.1.14
		-- 1.3.6.1.4.1.37950.1.1.5.10.25.1.14
		enableConsoleTac OBJECT-TYPE
			SYNTAX INTEGER
				{
				enable(0),
				disable(1)
				}
			MAX-ACCESS read-write
			STATUS current
			DESCRIPTION
				"Description."
			::= { tacplusCfg 14 }

		
--         1.3.6.1.4.1.37950.1.1.5.10.25.1.15
-- 1.3.6.1.4.1.37950.1.1.5.10.25.1.15
-- 1.3.6.1.4.1.37950.1.1.5.10.25.1.15
-- 1.3.6.1.4.1.37950.1.1.5.10.25.1.15
-- 1.3.6.1.4.1.37950.1.1.5.10.25.1.15
-- 1.3.6.1.4.1.37950.1.1.5.10.25.1.15
-- 1.3.6.1.4.1.37950.1.1.5.10.25.1.15
-- 1.3.6.1.4.1.37950.1.1.5.10.25.1.15
		-- 1.3.6.1.4.1.37950.1.1.5.10.25.1.15
		enableWebTac OBJECT-TYPE
			SYNTAX INTEGER
				{
				enable(0),
				disable(1)
				}
			MAX-ACCESS read-write
			STATUS current
			DESCRIPTION
				"Description."
			::= { tacplusCfg 15 }

		
--         1.3.6.1.4.1.37950.1.1.5.10.25.2
-- 1.3.6.1.4.1.37950.1.1.5.10.25.2
-- 1.3.6.1.4.1.37950.1.1.5.10.25.2
-- 1.3.6.1.4.1.37950.1.1.5.10.25.2
-- 1.3.6.1.4.1.37950.1.1.5.10.25.2
-- 1.3.6.1.4.1.37950.1.1.5.10.25.2
-- 1.3.6.1.4.1.37950.1.1.5.10.25.2
-- 1.3.6.1.4.1.37950.1.1.5.10.25.2
		-- 1.3.6.1.4.1.37950.1.1.5.10.25.2
		tacplusCfgTable OBJECT-TYPE
			SYNTAX SEQUENCE OF TacplusCfgEntry
			MAX-ACCESS not-accessible
			STATUS current
			DESCRIPTION
				"Description."
			::= { v1600Tacacs 2 }

		
--         1.3.6.1.4.1.37950.1.1.5.10.25.2.1
-- 1.3.6.1.4.1.37950.1.1.5.10.25.2.1
-- 1.3.6.1.4.1.37950.1.1.5.10.25.2.1
-- 1.3.6.1.4.1.37950.1.1.5.10.25.2.1
-- 1.3.6.1.4.1.37950.1.1.5.10.25.2.1
-- 1.3.6.1.4.1.37950.1.1.5.10.25.2.1
-- 1.3.6.1.4.1.37950.1.1.5.10.25.2.1
-- 1.3.6.1.4.1.37950.1.1.5.10.25.2.1
		-- 1.3.6.1.4.1.37950.1.1.5.10.25.2.1
		tacplusCfgEntry OBJECT-TYPE
			SYNTAX TacplusCfgEntry
			MAX-ACCESS not-accessible
			STATUS current
			DESCRIPTION
				"Description."
			INDEX { tacplusAAA }
			::= { tacplusCfgTable 1 }

		
		TacplusCfgEntry ::=
			SEQUENCE { 
				tacplusAAA
					INTEGER,
				tacplusAuthentication
					INTEGER,
				tacplusAuthenLocal
					INTEGER,
				tacplusAuthenEnable
					INTEGER,
				tacplusAuthenEnableLocal
					INTEGER,
				tacplusAuthorExec
					INTEGER,
				tacplusAuthorExecLocal
					INTEGER,
				tacplusAuthorCmdLv
					OCTET STRING,
				tacplusAcctExec
					INTEGER,
				tacplusAcctCmdLv
					OCTET STRING,
				tacplusConsoleStatus
					INTEGER,
				tacplusWebStatus
					INTEGER
			 }

--         1.3.6.1.4.1.37950.1.1.5.10.25.2.1.1
-- 1.3.6.1.4.1.37950.1.1.5.10.25.2.1.1
-- 1.3.6.1.4.1.37950.1.1.5.10.25.2.1.1
-- 1.3.6.1.4.1.37950.1.1.5.10.25.2.1.1
-- 1.3.6.1.4.1.37950.1.1.5.10.25.2.1.1
-- 1.3.6.1.4.1.37950.1.1.5.10.25.2.1.1
-- 1.3.6.1.4.1.37950.1.1.5.10.25.2.1.1
-- 1.3.6.1.4.1.37950.1.1.5.10.25.2.1.1
		-- 1.3.6.1.4.1.37950.1.1.5.10.25.2.1.1
		tacplusAAA OBJECT-TYPE
			SYNTAX INTEGER
				{
				enable(0),
				disable(1)
				}
			MAX-ACCESS read-only
			STATUS current
			DESCRIPTION
				"Description."
			::= { tacplusCfgEntry 1 }

		
--         1.3.6.1.4.1.37950.1.1.5.10.25.2.1.2
-- 1.3.6.1.4.1.37950.1.1.5.10.25.2.1.2
-- 1.3.6.1.4.1.37950.1.1.5.10.25.2.1.2
-- 1.3.6.1.4.1.37950.1.1.5.10.25.2.1.2
-- 1.3.6.1.4.1.37950.1.1.5.10.25.2.1.2
-- 1.3.6.1.4.1.37950.1.1.5.10.25.2.1.2
-- 1.3.6.1.4.1.37950.1.1.5.10.25.2.1.2
-- 1.3.6.1.4.1.37950.1.1.5.10.25.2.1.2
		-- 1.3.6.1.4.1.37950.1.1.5.10.25.2.1.2
		tacplusAuthentication OBJECT-TYPE
			SYNTAX INTEGER
				{
				enable(0),
				disable(1)
				}
			MAX-ACCESS read-only
			STATUS current
			DESCRIPTION
				"Description."
			::= { tacplusCfgEntry 2 }

		
--         1.3.6.1.4.1.37950.1.1.5.10.25.2.1.3
-- 1.3.6.1.4.1.37950.1.1.5.10.25.2.1.3
-- 1.3.6.1.4.1.37950.1.1.5.10.25.2.1.3
-- 1.3.6.1.4.1.37950.1.1.5.10.25.2.1.3
-- 1.3.6.1.4.1.37950.1.1.5.10.25.2.1.3
-- 1.3.6.1.4.1.37950.1.1.5.10.25.2.1.3
-- 1.3.6.1.4.1.37950.1.1.5.10.25.2.1.3
-- 1.3.6.1.4.1.37950.1.1.5.10.25.2.1.3
		-- 1.3.6.1.4.1.37950.1.1.5.10.25.2.1.3
		tacplusAuthenLocal OBJECT-TYPE
			SYNTAX INTEGER
				{
				enable(0),
				disable(1)
				}
			MAX-ACCESS read-only
			STATUS current
			DESCRIPTION
				"Description."
			::= { tacplusCfgEntry 3 }

		
--         1.3.6.1.4.1.37950.1.1.5.10.25.2.1.4
-- 1.3.6.1.4.1.37950.1.1.5.10.25.2.1.4
-- 1.3.6.1.4.1.37950.1.1.5.10.25.2.1.4
-- 1.3.6.1.4.1.37950.1.1.5.10.25.2.1.4
-- 1.3.6.1.4.1.37950.1.1.5.10.25.2.1.4
-- 1.3.6.1.4.1.37950.1.1.5.10.25.2.1.4
-- 1.3.6.1.4.1.37950.1.1.5.10.25.2.1.4
-- 1.3.6.1.4.1.37950.1.1.5.10.25.2.1.4
		-- 1.3.6.1.4.1.37950.1.1.5.10.25.2.1.4
		tacplusAuthenEnable OBJECT-TYPE
			SYNTAX INTEGER
				{
				enable(0),
				disable(1)
				}
			MAX-ACCESS read-only
			STATUS current
			DESCRIPTION
				"Description."
			::= { tacplusCfgEntry 4 }

		
--         1.3.6.1.4.1.37950.1.1.5.10.25.2.1.5
-- 1.3.6.1.4.1.37950.1.1.5.10.25.2.1.5
-- 1.3.6.1.4.1.37950.1.1.5.10.25.2.1.5
-- 1.3.6.1.4.1.37950.1.1.5.10.25.2.1.5
-- 1.3.6.1.4.1.37950.1.1.5.10.25.2.1.5
-- 1.3.6.1.4.1.37950.1.1.5.10.25.2.1.5
-- 1.3.6.1.4.1.37950.1.1.5.10.25.2.1.5
-- 1.3.6.1.4.1.37950.1.1.5.10.25.2.1.5
		-- 1.3.6.1.4.1.37950.1.1.5.10.25.2.1.5
		tacplusAuthenEnableLocal OBJECT-TYPE
			SYNTAX INTEGER
				{
				enable(0),
				disable(1)
				}
			MAX-ACCESS read-only
			STATUS current
			DESCRIPTION
				"Description."
			::= { tacplusCfgEntry 5 }

		
--         1.3.6.1.4.1.37950.1.1.5.10.25.2.1.6
-- 1.3.6.1.4.1.37950.1.1.5.10.25.2.1.6
-- 1.3.6.1.4.1.37950.1.1.5.10.25.2.1.6
-- 1.3.6.1.4.1.37950.1.1.5.10.25.2.1.6
-- 1.3.6.1.4.1.37950.1.1.5.10.25.2.1.6
-- 1.3.6.1.4.1.37950.1.1.5.10.25.2.1.6
-- 1.3.6.1.4.1.37950.1.1.5.10.25.2.1.6
-- 1.3.6.1.4.1.37950.1.1.5.10.25.2.1.6
		-- 1.3.6.1.4.1.37950.1.1.5.10.25.2.1.6
		tacplusAuthorExec OBJECT-TYPE
			SYNTAX INTEGER
				{
				enable(0),
				disable(1)
				}
			MAX-ACCESS read-only
			STATUS current
			DESCRIPTION
				"Description."
			::= { tacplusCfgEntry 6 }

		
--         1.3.6.1.4.1.37950.1.1.5.10.25.2.1.7
-- 1.3.6.1.4.1.37950.1.1.5.10.25.2.1.7
-- 1.3.6.1.4.1.37950.1.1.5.10.25.2.1.7
-- 1.3.6.1.4.1.37950.1.1.5.10.25.2.1.7
-- 1.3.6.1.4.1.37950.1.1.5.10.25.2.1.7
-- 1.3.6.1.4.1.37950.1.1.5.10.25.2.1.7
-- 1.3.6.1.4.1.37950.1.1.5.10.25.2.1.7
-- 1.3.6.1.4.1.37950.1.1.5.10.25.2.1.7
		-- 1.3.6.1.4.1.37950.1.1.5.10.25.2.1.7
		tacplusAuthorExecLocal OBJECT-TYPE
			SYNTAX INTEGER
				{
				enable(0),
				disable(1)
				}
			MAX-ACCESS read-only
			STATUS current
			DESCRIPTION
				"Description."
			::= { tacplusCfgEntry 7 }

		
--         1.3.6.1.4.1.37950.1.1.5.10.25.2.1.8
-- 1.3.6.1.4.1.37950.1.1.5.10.25.2.1.8
-- 1.3.6.1.4.1.37950.1.1.5.10.25.2.1.8
-- 1.3.6.1.4.1.37950.1.1.5.10.25.2.1.8
-- 1.3.6.1.4.1.37950.1.1.5.10.25.2.1.8
-- 1.3.6.1.4.1.37950.1.1.5.10.25.2.1.8
-- 1.3.6.1.4.1.37950.1.1.5.10.25.2.1.8
-- 1.3.6.1.4.1.37950.1.1.5.10.25.2.1.8
		-- 1.3.6.1.4.1.37950.1.1.5.10.25.2.1.8
		tacplusAuthorCmdLv OBJECT-TYPE
			SYNTAX OCTET STRING
			MAX-ACCESS read-only
			STATUS current
			DESCRIPTION
				"Description."
			::= { tacplusCfgEntry 8 }

		
--         1.3.6.1.4.1.37950.1.1.5.10.25.2.1.10
-- 1.3.6.1.4.1.37950.1.1.5.10.25.2.1.10
-- 1.3.6.1.4.1.37950.1.1.5.10.25.2.1.10
-- 1.3.6.1.4.1.37950.1.1.5.10.25.2.1.10
-- 1.3.6.1.4.1.37950.1.1.5.10.25.2.1.10
-- 1.3.6.1.4.1.37950.1.1.5.10.25.2.1.10
-- 1.3.6.1.4.1.37950.1.1.5.10.25.2.1.10
-- 1.3.6.1.4.1.37950.1.1.5.10.25.2.1.9
		-- 1.3.6.1.4.1.37950.1.1.5.10.25.2.1.9
		tacplusAcctExec OBJECT-TYPE
			SYNTAX INTEGER
				{
				enable(0),
				disable(1)
				}
			MAX-ACCESS read-only
			STATUS current
			DESCRIPTION
				"Description."
			::= { tacplusCfgEntry 9 }

		
--         1.3.6.1.4.1.37950.1.1.5.10.25.2.1.11
-- 1.3.6.1.4.1.37950.1.1.5.10.25.2.1.11
-- 1.3.6.1.4.1.37950.1.1.5.10.25.2.1.11
-- 1.3.6.1.4.1.37950.1.1.5.10.25.2.1.11
-- 1.3.6.1.4.1.37950.1.1.5.10.25.2.1.11
-- 1.3.6.1.4.1.37950.1.1.5.10.25.2.1.11
-- 1.3.6.1.4.1.37950.1.1.5.10.25.2.1.11
-- 1.3.6.1.4.1.37950.1.1.5.10.25.2.1.10
		-- 1.3.6.1.4.1.37950.1.1.5.10.25.2.1.10
		tacplusAcctCmdLv OBJECT-TYPE
			SYNTAX OCTET STRING
			MAX-ACCESS read-only
			STATUS current
			DESCRIPTION
				"Description."
			::= { tacplusCfgEntry 10 }

		
--         1.3.6.1.4.1.37950.1.1.5.10.25.2.1.12
-- 1.3.6.1.4.1.37950.1.1.5.10.25.2.1.12
-- 1.3.6.1.4.1.37950.1.1.5.10.25.2.1.12
-- 1.3.6.1.4.1.37950.1.1.5.10.25.2.1.12
-- 1.3.6.1.4.1.37950.1.1.5.10.25.2.1.12
-- 1.3.6.1.4.1.37950.1.1.5.10.25.2.1.12
-- 1.3.6.1.4.1.37950.1.1.5.10.25.2.1.12
-- 1.3.6.1.4.1.37950.1.1.5.10.25.2.1.11
		-- 1.3.6.1.4.1.37950.1.1.5.10.25.2.1.11
		tacplusConsoleStatus OBJECT-TYPE
			SYNTAX INTEGER
				{
				enable(0),
				disable(1)
				}
			MAX-ACCESS read-only
			STATUS current
			DESCRIPTION
				"Description."
			::= { tacplusCfgEntry 11 }

		
--  1.3.6.1.4.1.37950.1.1.5.10.25.2.1.12
		-- 1.3.6.1.4.1.37950.1.1.5.10.25.2.1.12
		tacplusWebStatus OBJECT-TYPE
			SYNTAX INTEGER
				{
				enable(0),
				disable(1)
				}
			MAX-ACCESS read-only
			STATUS current
			DESCRIPTION
				"Description."
			::= { tacplusCfgEntry 12 }

		
--         1.3.6.1.4.1.37950.1.1.5.10.25.3
-- 1.3.6.1.4.1.37950.1.1.5.10.25.3
-- 1.3.6.1.4.1.37950.1.1.5.10.25.3
-- 1.3.6.1.4.1.37950.1.1.5.10.25.3
-- 1.3.6.1.4.1.37950.1.1.5.10.25.3
-- 1.3.6.1.4.1.37950.1.1.5.10.25.3
-- 1.3.6.1.4.1.37950.1.1.5.10.25.3
-- 1.3.6.1.4.1.37950.1.1.5.10.25.3
		-- 1.3.6.1.4.1.37950.1.1.5.10.25.3
		tacplusServerCfg OBJECT IDENTIFIER ::= { v1600Tacacs 3 }

		
--         1.3.6.1.4.1.37950.1.1.5.10.25.3.1
-- 1.3.6.1.4.1.37950.1.1.5.10.25.3.1
-- 1.3.6.1.4.1.37950.1.1.5.10.25.3.1
-- 1.3.6.1.4.1.37950.1.1.5.10.25.3.1
-- 1.3.6.1.4.1.37950.1.1.5.10.25.3.1
-- 1.3.6.1.4.1.37950.1.1.5.10.25.3.1
-- 1.3.6.1.4.1.37950.1.1.5.10.25.3.1
-- 1.3.6.1.4.1.37950.1.1.5.10.25.3.1
		-- 1.3.6.1.4.1.37950.1.1.5.10.25.3.1
		tacServerHost OBJECT-TYPE
			SYNTAX OCTET STRING
			MAX-ACCESS read-write
			STATUS current
			DESCRIPTION
				"Description."
			::= { tacplusServerCfg 1 }

		
--         1.3.6.1.4.1.37950.1.1.5.10.25.3.2
-- 1.3.6.1.4.1.37950.1.1.5.10.25.3.2
-- 1.3.6.1.4.1.37950.1.1.5.10.25.3.2
-- 1.3.6.1.4.1.37950.1.1.5.10.25.3.2
-- 1.3.6.1.4.1.37950.1.1.5.10.25.3.2
-- 1.3.6.1.4.1.37950.1.1.5.10.25.3.2
-- 1.3.6.1.4.1.37950.1.1.5.10.25.3.2
-- 1.3.6.1.4.1.37950.1.1.5.10.25.3.2
		-- 1.3.6.1.4.1.37950.1.1.5.10.25.3.2
		tacAddServer OBJECT-TYPE
			SYNTAX INTEGER
				{
				add(0),
				del(1)
				}
			MAX-ACCESS read-write
			STATUS current
			DESCRIPTION
				"Description."
			::= { tacplusServerCfg 2 }

		
--         1.3.6.1.4.1.37950.1.1.5.10.25.3.3
-- 1.3.6.1.4.1.37950.1.1.5.10.25.3.3
-- 1.3.6.1.4.1.37950.1.1.5.10.25.3.3
-- 1.3.6.1.4.1.37950.1.1.5.10.25.3.3
-- 1.3.6.1.4.1.37950.1.1.5.10.25.3.3
-- 1.3.6.1.4.1.37950.1.1.5.10.25.3.3
-- 1.3.6.1.4.1.37950.1.1.5.10.25.3.3
-- 1.3.6.1.4.1.37950.1.1.5.10.25.3.3
		-- 1.3.6.1.4.1.37950.1.1.5.10.25.3.3
		tacSharedKey OBJECT-TYPE
			SYNTAX OCTET STRING
			MAX-ACCESS read-write
			STATUS current
			DESCRIPTION
				"Description."
			::= { tacplusServerCfg 3 }

		
--         1.3.6.1.4.1.37950.1.1.5.10.25.3.4
-- 1.3.6.1.4.1.37950.1.1.5.10.25.3.4
-- 1.3.6.1.4.1.37950.1.1.5.10.25.3.4
-- 1.3.6.1.4.1.37950.1.1.5.10.25.3.4
-- 1.3.6.1.4.1.37950.1.1.5.10.25.3.4
-- 1.3.6.1.4.1.37950.1.1.5.10.25.3.4
-- 1.3.6.1.4.1.37950.1.1.5.10.25.3.4
-- 1.3.6.1.4.1.37950.1.1.5.10.25.3.4
		-- 1.3.6.1.4.1.37950.1.1.5.10.25.3.4
		tacAddKey OBJECT-TYPE
			SYNTAX INTEGER
				{
				add(0),
				del(1)
				}
			MAX-ACCESS read-write
			STATUS current
			DESCRIPTION
				"Description."
			::= { tacplusServerCfg 4 }

		
--         1.3.6.1.4.1.37950.1.1.5.10.25.4
-- 1.3.6.1.4.1.37950.1.1.5.10.25.4
-- 1.3.6.1.4.1.37950.1.1.5.10.25.4
-- 1.3.6.1.4.1.37950.1.1.5.10.25.4
-- 1.3.6.1.4.1.37950.1.1.5.10.25.4
-- 1.3.6.1.4.1.37950.1.1.5.10.25.4
-- 1.3.6.1.4.1.37950.1.1.5.10.25.4
-- 1.3.6.1.4.1.37950.1.1.5.10.25.4
		-- 1.3.6.1.4.1.37950.1.1.5.10.25.4
		tacplusServerTable OBJECT-TYPE
			SYNTAX SEQUENCE OF TacplusServerEntry
			MAX-ACCESS not-accessible
			STATUS current
			DESCRIPTION
				"Description."
			::= { v1600Tacacs 4 }

		
--         1.3.6.1.4.1.37950.1.1.5.10.25.4.1
-- 1.3.6.1.4.1.37950.1.1.5.10.25.4.1
-- 1.3.6.1.4.1.37950.1.1.5.10.25.4.1
-- 1.3.6.1.4.1.37950.1.1.5.10.25.4.1
-- 1.3.6.1.4.1.37950.1.1.5.10.25.4.1
-- 1.3.6.1.4.1.37950.1.1.5.10.25.4.1
-- 1.3.6.1.4.1.37950.1.1.5.10.25.4.1
-- 1.3.6.1.4.1.37950.1.1.5.10.25.4.1
		-- 1.3.6.1.4.1.37950.1.1.5.10.25.4.1
		tacplusServerEntry OBJECT-TYPE
			SYNTAX TacplusServerEntry
			MAX-ACCESS not-accessible
			STATUS current
			DESCRIPTION
				"Description."
			INDEX { tacplusServer }
			::= { tacplusServerTable 1 }

		
		TacplusServerEntry ::=
			SEQUENCE { 
				tacplusServer
					OCTET STRING,
				tacplusKey
					OCTET STRING
			 }

--         1.3.6.1.4.1.37950.1.1.5.10.25.4.1.1
-- 1.3.6.1.4.1.37950.1.1.5.10.25.4.1.1
-- 1.3.6.1.4.1.37950.1.1.5.10.25.4.1.1
-- 1.3.6.1.4.1.37950.1.1.5.10.25.4.1.1
-- 1.3.6.1.4.1.37950.1.1.5.10.25.4.1.1
-- 1.3.6.1.4.1.37950.1.1.5.10.25.4.1.1
-- 1.3.6.1.4.1.37950.1.1.5.10.25.4.1.1
-- 1.3.6.1.4.1.37950.1.1.5.10.25.4.1.1
		-- 1.3.6.1.4.1.37950.1.1.5.10.25.4.1.1
		tacplusServer OBJECT-TYPE
			SYNTAX OCTET STRING
			MAX-ACCESS read-only
			STATUS current
			DESCRIPTION
				"Description."
			::= { tacplusServerEntry 1 }

		
--         1.3.6.1.4.1.37950.1.1.5.10.25.4.1.2
-- 1.3.6.1.4.1.37950.1.1.5.10.25.4.1.2
-- 1.3.6.1.4.1.37950.1.1.5.10.25.4.1.2
-- 1.3.6.1.4.1.37950.1.1.5.10.25.4.1.2
-- 1.3.6.1.4.1.37950.1.1.5.10.25.4.1.2
-- 1.3.6.1.4.1.37950.1.1.5.10.25.4.1.2
-- 1.3.6.1.4.1.37950.1.1.5.10.25.4.1.2
-- 1.3.6.1.4.1.37950.1.1.5.10.25.4.1.2
		-- 1.3.6.1.4.1.37950.1.1.5.10.25.4.1.2
		tacplusKey OBJECT-TYPE
			SYNTAX OCTET STRING
			MAX-ACCESS read-only
			STATUS current
			DESCRIPTION
				"Description."
			::= { tacplusServerEntry 2 }

		
--         1.3.6.1.4.1.37950.1.1.5.10.26
-- 1.3.6.1.4.1.37950.1.1.5.10.26
-- 1.3.6.1.4.1.37950.1.1.5.10.26
-- 1.3.6.1.4.1.37950.1.1.5.10.26
-- 1.3.6.1.4.1.37950.1.1.5.10.26
-- 1.3.6.1.4.1.37950.1.1.5.10.26
-- 1.3.6.1.4.1.37950.1.1.5.10.26
-- 1.3.6.1.4.1.37950.1.1.5.10.26
		-- 1.3.6.1.4.1.37950.1.1.5.10.26
		v1600Radius OBJECT IDENTIFIER ::= { v1600dSwitch 26 }

		
--         1.3.6.1.4.1.37950.1.1.5.10.26.1
-- 1.3.6.1.4.1.37950.1.1.5.10.26.1
-- 1.3.6.1.4.1.37950.1.1.5.10.26.1
-- 1.3.6.1.4.1.37950.1.1.5.10.26.1
-- 1.3.6.1.4.1.37950.1.1.5.10.26.1
-- 1.3.6.1.4.1.37950.1.1.5.10.26.1
-- 1.3.6.1.4.1.37950.1.1.5.10.26.1
-- 1.3.6.1.4.1.37950.1.1.5.10.26.1
		-- 1.3.6.1.4.1.37950.1.1.5.10.26.1
		radiusCfg OBJECT IDENTIFIER ::= { v1600Radius 1 }

		
--         1.3.6.1.4.1.37950.1.1.5.10.26.1.1
-- 1.3.6.1.4.1.37950.1.1.5.10.26.1.1
-- 1.3.6.1.4.1.37950.1.1.5.10.26.1.1
-- 1.3.6.1.4.1.37950.1.1.5.10.26.1.1
-- 1.3.6.1.4.1.37950.1.1.5.10.26.1.1
-- 1.3.6.1.4.1.37950.1.1.5.10.26.1.1
-- 1.3.6.1.4.1.37950.1.1.5.10.26.1.1
-- 1.3.6.1.4.1.37950.1.1.5.10.26.1.1
		-- 1.3.6.1.4.1.37950.1.1.5.10.26.1.1
		radAAAEnable OBJECT-TYPE
			SYNTAX INTEGER
				{
				enable(0),
				disable(1)
				}
			MAX-ACCESS read-write
			STATUS current
			DESCRIPTION
				"Description."
			::= { radiusCfg 1 }

		
--         1.3.6.1.4.1.37950.1.1.5.10.26.1.2
-- 1.3.6.1.4.1.37950.1.1.5.10.26.1.2
-- 1.3.6.1.4.1.37950.1.1.5.10.26.1.2
-- 1.3.6.1.4.1.37950.1.1.5.10.26.1.2
-- 1.3.6.1.4.1.37950.1.1.5.10.26.1.2
-- 1.3.6.1.4.1.37950.1.1.5.10.26.1.2
-- 1.3.6.1.4.1.37950.1.1.5.10.26.1.2
-- 1.3.6.1.4.1.37950.1.1.5.10.26.1.2
		-- 1.3.6.1.4.1.37950.1.1.5.10.26.1.2
		radAuthen OBJECT-TYPE
			SYNTAX INTEGER
				{
				enable(0),
				disable(1)
				}
			MAX-ACCESS read-write
			STATUS current
			DESCRIPTION
				"Description."
			::= { radiusCfg 2 }

		
--         1.3.6.1.4.1.37950.1.1.5.10.26.1.3
-- 1.3.6.1.4.1.37950.1.1.5.10.26.1.3
-- 1.3.6.1.4.1.37950.1.1.5.10.26.1.3
-- 1.3.6.1.4.1.37950.1.1.5.10.26.1.3
-- 1.3.6.1.4.1.37950.1.1.5.10.26.1.3
-- 1.3.6.1.4.1.37950.1.1.5.10.26.1.3
-- 1.3.6.1.4.1.37950.1.1.5.10.26.1.3
-- 1.3.6.1.4.1.37950.1.1.5.10.26.1.3
		-- 1.3.6.1.4.1.37950.1.1.5.10.26.1.3
		radAuthenLocal OBJECT-TYPE
			SYNTAX INTEGER
				{
				enable(0),
				disable(1)
				}
			MAX-ACCESS read-write
			STATUS current
			DESCRIPTION
				"Description."
			::= { radiusCfg 3 }

		
--         1.3.6.1.4.1.37950.1.1.5.10.26.1.4
-- 1.3.6.1.4.1.37950.1.1.5.10.26.1.4
-- 1.3.6.1.4.1.37950.1.1.5.10.26.1.4
-- 1.3.6.1.4.1.37950.1.1.5.10.26.1.4
-- 1.3.6.1.4.1.37950.1.1.5.10.26.1.4
-- 1.3.6.1.4.1.37950.1.1.5.10.26.1.4
-- 1.3.6.1.4.1.37950.1.1.5.10.26.1.4
-- 1.3.6.1.4.1.37950.1.1.5.10.26.1.4
		-- 1.3.6.1.4.1.37950.1.1.5.10.26.1.4
		radAuthenEnable OBJECT-TYPE
			SYNTAX INTEGER
				{
				enable(0),
				disable(1)
				}
			MAX-ACCESS read-write
			STATUS current
			DESCRIPTION
				"Description."
			::= { radiusCfg 4 }

		
--         1.3.6.1.4.1.37950.1.1.5.10.26.1.5
-- 1.3.6.1.4.1.37950.1.1.5.10.26.1.5
-- 1.3.6.1.4.1.37950.1.1.5.10.26.1.5
-- 1.3.6.1.4.1.37950.1.1.5.10.26.1.5
-- 1.3.6.1.4.1.37950.1.1.5.10.26.1.5
-- 1.3.6.1.4.1.37950.1.1.5.10.26.1.5
-- 1.3.6.1.4.1.37950.1.1.5.10.26.1.5
-- 1.3.6.1.4.1.37950.1.1.5.10.26.1.5
		-- 1.3.6.1.4.1.37950.1.1.5.10.26.1.5
		radAuthenEnableLocal OBJECT-TYPE
			SYNTAX INTEGER
				{
				enable(0),
				disable(1)
				}
			MAX-ACCESS read-write
			STATUS current
			DESCRIPTION
				"Description."
			::= { radiusCfg 5 }

		
--         1.3.6.1.4.1.37950.1.1.5.10.26.1.6
-- 1.3.6.1.4.1.37950.1.1.5.10.26.1.6
-- 1.3.6.1.4.1.37950.1.1.5.10.26.1.6
-- 1.3.6.1.4.1.37950.1.1.5.10.26.1.6
-- 1.3.6.1.4.1.37950.1.1.5.10.26.1.6
-- 1.3.6.1.4.1.37950.1.1.5.10.26.1.6
-- 1.3.6.1.4.1.37950.1.1.5.10.26.1.6
-- 1.3.6.1.4.1.37950.1.1.5.10.26.1.6
		-- 1.3.6.1.4.1.37950.1.1.5.10.26.1.6
		radAcctExec OBJECT-TYPE
			SYNTAX INTEGER
				{
				enable(0),
				disable(1)
				}
			MAX-ACCESS read-write
			STATUS current
			DESCRIPTION
				"Description."
			::= { radiusCfg 6 }

		
--         1.3.6.1.4.1.37950.1.1.5.10.26.1.7
-- 1.3.6.1.4.1.37950.1.1.5.10.26.1.7
-- 1.3.6.1.4.1.37950.1.1.5.10.26.1.7
-- 1.3.6.1.4.1.37950.1.1.5.10.26.1.7
-- 1.3.6.1.4.1.37950.1.1.5.10.26.1.7
-- 1.3.6.1.4.1.37950.1.1.5.10.26.1.7
-- 1.3.6.1.4.1.37950.1.1.5.10.26.1.7
-- 1.3.6.1.4.1.37950.1.1.5.10.26.1.7
		-- 1.3.6.1.4.1.37950.1.1.5.10.26.1.7
		enableConsoleRad OBJECT-TYPE
			SYNTAX INTEGER
				{
				enable(0),
				disable(1)
				}
			MAX-ACCESS read-write
			STATUS current
			DESCRIPTION
				"Description."
			::= { radiusCfg 7 }

		
--         1.3.6.1.4.1.37950.1.1.5.10.26.1.8
-- 1.3.6.1.4.1.37950.1.1.5.10.26.1.8
-- 1.3.6.1.4.1.37950.1.1.5.10.26.1.8
-- 1.3.6.1.4.1.37950.1.1.5.10.26.1.8
-- 1.3.6.1.4.1.37950.1.1.5.10.26.1.8
-- 1.3.6.1.4.1.37950.1.1.5.10.26.1.8
-- 1.3.6.1.4.1.37950.1.1.5.10.26.1.8
-- 1.3.6.1.4.1.37950.1.1.5.10.26.1.8
		-- 1.3.6.1.4.1.37950.1.1.5.10.26.1.8
		enableWebRad OBJECT-TYPE
			SYNTAX INTEGER
				{
				enable(0),
				disable(1)
				}
			MAX-ACCESS read-write
			STATUS current
			DESCRIPTION
				"Description."
			::= { radiusCfg 8 }

		
--         1.3.6.1.4.1.37950.1.1.5.10.26.1.9
-- 1.3.6.1.4.1.37950.1.1.5.10.26.1.9
-- 1.3.6.1.4.1.37950.1.1.5.10.26.1.9
-- 1.3.6.1.4.1.37950.1.1.5.10.26.1.9
-- 1.3.6.1.4.1.37950.1.1.5.10.26.1.9
-- 1.3.6.1.4.1.37950.1.1.5.10.26.1.9
-- 1.3.6.1.4.1.37950.1.1.5.10.26.1.9
-- 1.3.6.1.4.1.37950.1.1.5.10.26.1.9
		-- 1.3.6.1.4.1.37950.1.1.5.10.26.1.9
		radDot1xAuthen OBJECT-TYPE
			SYNTAX INTEGER
				{
				enable(0),
				disable(1)
				}
			MAX-ACCESS read-write
			STATUS current
			DESCRIPTION
				"Description."
			::= { radiusCfg 9 }

		
--         1.3.6.1.4.1.37950.1.1.5.10.26.1.10
-- 1.3.6.1.4.1.37950.1.1.5.10.26.1.10
-- 1.3.6.1.4.1.37950.1.1.5.10.26.1.10
-- 1.3.6.1.4.1.37950.1.1.5.10.26.1.10
-- 1.3.6.1.4.1.37950.1.1.5.10.26.1.10
-- 1.3.6.1.4.1.37950.1.1.5.10.26.1.10
-- 1.3.6.1.4.1.37950.1.1.5.10.26.1.10
-- 1.3.6.1.4.1.37950.1.1.5.10.26.1.10
		-- 1.3.6.1.4.1.37950.1.1.5.10.26.1.10
		radDot1xAuthenLocal OBJECT-TYPE
			SYNTAX INTEGER
				{
				enable(0),
				disable(1)
				}
			MAX-ACCESS read-write
			STATUS current
			DESCRIPTION
				"Description."
			::= { radiusCfg 10 }

		
--         1.3.6.1.4.1.37950.1.1.5.10.26.1.11
-- 1.3.6.1.4.1.37950.1.1.5.10.26.1.11
-- 1.3.6.1.4.1.37950.1.1.5.10.26.1.11
-- 1.3.6.1.4.1.37950.1.1.5.10.26.1.11
-- 1.3.6.1.4.1.37950.1.1.5.10.26.1.11
-- 1.3.6.1.4.1.37950.1.1.5.10.26.1.11
-- 1.3.6.1.4.1.37950.1.1.5.10.26.1.11
-- 1.3.6.1.4.1.37950.1.1.5.10.26.1.11
		-- 1.3.6.1.4.1.37950.1.1.5.10.26.1.11
		radDot1xAuthor OBJECT-TYPE
			SYNTAX INTEGER
				{
				enable(0),
				disable(1)
				}
			MAX-ACCESS read-write
			STATUS current
			DESCRIPTION
				"Description."
			::= { radiusCfg 11 }

		
--         1.3.6.1.4.1.37950.1.1.5.10.26.1.12
-- 1.3.6.1.4.1.37950.1.1.5.10.26.1.12
-- 1.3.6.1.4.1.37950.1.1.5.10.26.1.12
-- 1.3.6.1.4.1.37950.1.1.5.10.26.1.12
-- 1.3.6.1.4.1.37950.1.1.5.10.26.1.12
-- 1.3.6.1.4.1.37950.1.1.5.10.26.1.12
-- 1.3.6.1.4.1.37950.1.1.5.10.26.1.12
-- 1.3.6.1.4.1.37950.1.1.5.10.26.1.12
		-- 1.3.6.1.4.1.37950.1.1.5.10.26.1.12
		radDot1xAcct OBJECT-TYPE
			SYNTAX INTEGER
				{
				enable(0),
				disable(1)
				}
			MAX-ACCESS read-write
			STATUS current
			DESCRIPTION
				"Description."
			::= { radiusCfg 12 }

		
--         1.3.6.1.4.1.37950.1.1.5.10.26.2
-- 1.3.6.1.4.1.37950.1.1.5.10.26.2
-- 1.3.6.1.4.1.37950.1.1.5.10.26.2
-- 1.3.6.1.4.1.37950.1.1.5.10.26.2
-- 1.3.6.1.4.1.37950.1.1.5.10.26.2
-- 1.3.6.1.4.1.37950.1.1.5.10.26.2
-- 1.3.6.1.4.1.37950.1.1.5.10.26.2
-- 1.3.6.1.4.1.37950.1.1.5.10.26.2
		-- 1.3.6.1.4.1.37950.1.1.5.10.26.2
		radiusCfgTable OBJECT-TYPE
			SYNTAX SEQUENCE OF RadiusCfgEntry
			MAX-ACCESS not-accessible
			STATUS current
			DESCRIPTION
				"Description."
			::= { v1600Radius 2 }

		
--         1.3.6.1.4.1.37950.1.1.5.10.26.2.1
-- 1.3.6.1.4.1.37950.1.1.5.10.26.2.1
-- 1.3.6.1.4.1.37950.1.1.5.10.26.2.1
-- 1.3.6.1.4.1.37950.1.1.5.10.26.2.1
-- 1.3.6.1.4.1.37950.1.1.5.10.26.2.1
-- 1.3.6.1.4.1.37950.1.1.5.10.26.2.1
-- 1.3.6.1.4.1.37950.1.1.5.10.26.2.1
-- 1.3.6.1.4.1.37950.1.1.5.10.26.2.1
		-- 1.3.6.1.4.1.37950.1.1.5.10.26.2.1
		radiusCfgEntry OBJECT-TYPE
			SYNTAX RadiusCfgEntry
			MAX-ACCESS not-accessible
			STATUS current
			DESCRIPTION
				"Description."
			INDEX { radiusAAA }
			::= { radiusCfgTable 1 }

		
		RadiusCfgEntry ::=
			SEQUENCE { 
				radiusAAA
					INTEGER,
				radiusAuthentication
					INTEGER,
				radiusAuthenLocal
					INTEGER,
				radiusAuthenEnable
					INTEGER,
				radiusAuthenEnableLocal
					INTEGER,
				radiusAcctExec
					INTEGER,
				radiusConsoleStatus
					INTEGER,
				radiusWebStatus
					INTEGER,
				radiusDot1xAuthen
					INTEGER,
				radiusDot1xAuthenLocal
					INTEGER,
				radiusDot1xAuthor
					INTEGER,
				radiusDot1xAcct
					INTEGER
			 }

--         1.3.6.1.4.1.37950.1.1.5.10.26.2.1.1
-- 1.3.6.1.4.1.37950.1.1.5.10.26.2.1.1
-- 1.3.6.1.4.1.37950.1.1.5.10.26.2.1.1
-- 1.3.6.1.4.1.37950.1.1.5.10.26.2.1.1
-- 1.3.6.1.4.1.37950.1.1.5.10.26.2.1.1
-- 1.3.6.1.4.1.37950.1.1.5.10.26.2.1.1
-- 1.3.6.1.4.1.37950.1.1.5.10.26.2.1.1
-- 1.3.6.1.4.1.37950.1.1.5.10.26.2.1.1
		-- 1.3.6.1.4.1.37950.1.1.5.10.26.2.1.1
		radiusAAA OBJECT-TYPE
			SYNTAX INTEGER
				{
				enable(0),
				disable(1)
				}
			MAX-ACCESS read-only
			STATUS current
			DESCRIPTION
				"Description."
			::= { radiusCfgEntry 1 }

		
--         1.3.6.1.4.1.37950.1.1.5.10.26.2.1.2
-- 1.3.6.1.4.1.37950.1.1.5.10.26.2.1.2
-- 1.3.6.1.4.1.37950.1.1.5.10.26.2.1.2
-- 1.3.6.1.4.1.37950.1.1.5.10.26.2.1.2
-- 1.3.6.1.4.1.37950.1.1.5.10.26.2.1.2
-- 1.3.6.1.4.1.37950.1.1.5.10.26.2.1.2
-- 1.3.6.1.4.1.37950.1.1.5.10.26.2.1.2
-- 1.3.6.1.4.1.37950.1.1.5.10.26.2.1.2
		-- 1.3.6.1.4.1.37950.1.1.5.10.26.2.1.2
		radiusAuthentication OBJECT-TYPE
			SYNTAX INTEGER
				{
				enable(0),
				disable(1)
				}
			MAX-ACCESS read-only
			STATUS current
			DESCRIPTION
				"Description."
			::= { radiusCfgEntry 2 }

		
--         1.3.6.1.4.1.37950.1.1.5.10.26.2.1.3
-- 1.3.6.1.4.1.37950.1.1.5.10.26.2.1.3
-- 1.3.6.1.4.1.37950.1.1.5.10.26.2.1.3
-- 1.3.6.1.4.1.37950.1.1.5.10.26.2.1.3
-- 1.3.6.1.4.1.37950.1.1.5.10.26.2.1.3
-- 1.3.6.1.4.1.37950.1.1.5.10.26.2.1.3
-- 1.3.6.1.4.1.37950.1.1.5.10.26.2.1.3
-- 1.3.6.1.4.1.37950.1.1.5.10.26.2.1.3
		-- 1.3.6.1.4.1.37950.1.1.5.10.26.2.1.3
		radiusAuthenLocal OBJECT-TYPE
			SYNTAX INTEGER
				{
				enable(0),
				disable(1)
				}
			MAX-ACCESS read-only
			STATUS current
			DESCRIPTION
				"Description."
			::= { radiusCfgEntry 3 }

		
--         1.3.6.1.4.1.37950.1.1.5.10.26.2.1.4
-- 1.3.6.1.4.1.37950.1.1.5.10.26.2.1.4
-- 1.3.6.1.4.1.37950.1.1.5.10.26.2.1.4
-- 1.3.6.1.4.1.37950.1.1.5.10.26.2.1.4
-- 1.3.6.1.4.1.37950.1.1.5.10.26.2.1.4
-- 1.3.6.1.4.1.37950.1.1.5.10.26.2.1.4
-- 1.3.6.1.4.1.37950.1.1.5.10.26.2.1.4
-- 1.3.6.1.4.1.37950.1.1.5.10.26.2.1.4
		-- 1.3.6.1.4.1.37950.1.1.5.10.26.2.1.4
		radiusAuthenEnable OBJECT-TYPE
			SYNTAX INTEGER
				{
				enable(0),
				disable(1)
				}
			MAX-ACCESS read-only
			STATUS current
			DESCRIPTION
				"Description."
			::= { radiusCfgEntry 4 }

		
--         1.3.6.1.4.1.37950.1.1.5.10.26.2.1.5
-- 1.3.6.1.4.1.37950.1.1.5.10.26.2.1.5
-- 1.3.6.1.4.1.37950.1.1.5.10.26.2.1.5
-- 1.3.6.1.4.1.37950.1.1.5.10.26.2.1.5
-- 1.3.6.1.4.1.37950.1.1.5.10.26.2.1.5
-- 1.3.6.1.4.1.37950.1.1.5.10.26.2.1.5
-- 1.3.6.1.4.1.37950.1.1.5.10.26.2.1.5
-- 1.3.6.1.4.1.37950.1.1.5.10.26.2.1.5
		-- 1.3.6.1.4.1.37950.1.1.5.10.26.2.1.5
		radiusAuthenEnableLocal OBJECT-TYPE
			SYNTAX INTEGER
				{
				enable(0),
				disable(1)
				}
			MAX-ACCESS read-only
			STATUS current
			DESCRIPTION
				"Description."
			::= { radiusCfgEntry 5 }

		
--         1.3.6.1.4.1.37950.1.1.5.10.26.2.1.6
-- 1.3.6.1.4.1.37950.1.1.5.10.26.2.1.6
-- 1.3.6.1.4.1.37950.1.1.5.10.26.2.1.6
-- 1.3.6.1.4.1.37950.1.1.5.10.26.2.1.6
-- 1.3.6.1.4.1.37950.1.1.5.10.26.2.1.6
-- 1.3.6.1.4.1.37950.1.1.5.10.26.2.1.6
-- 1.3.6.1.4.1.37950.1.1.5.10.26.2.1.6
-- 1.3.6.1.4.1.37950.1.1.5.10.26.2.1.6
		-- 1.3.6.1.4.1.37950.1.1.5.10.26.2.1.6
		radiusAcctExec OBJECT-TYPE
			SYNTAX INTEGER
				{
				enable(0),
				disable(1)
				}
			MAX-ACCESS read-only
			STATUS current
			DESCRIPTION
				"Description."
			::= { radiusCfgEntry 6 }

		
--         1.3.6.1.4.1.37950.1.1.5.10.26.2.1.7
-- 1.3.6.1.4.1.37950.1.1.5.10.26.2.1.7
-- 1.3.6.1.4.1.37950.1.1.5.10.26.2.1.7
-- 1.3.6.1.4.1.37950.1.1.5.10.26.2.1.7
-- 1.3.6.1.4.1.37950.1.1.5.10.26.2.1.7
-- 1.3.6.1.4.1.37950.1.1.5.10.26.2.1.7
-- 1.3.6.1.4.1.37950.1.1.5.10.26.2.1.7
-- 1.3.6.1.4.1.37950.1.1.5.10.26.2.1.7
		-- 1.3.6.1.4.1.37950.1.1.5.10.26.2.1.7
		radiusConsoleStatus OBJECT-TYPE
			SYNTAX INTEGER
				{
				enable(0),
				disable(1)
				}
			MAX-ACCESS read-only
			STATUS current
			DESCRIPTION
				"Description."
			::= { radiusCfgEntry 7 }

		
--         1.3.6.1.4.1.37950.1.1.5.10.26.2.1.8
-- 1.3.6.1.4.1.37950.1.1.5.10.26.2.1.8
-- 1.3.6.1.4.1.37950.1.1.5.10.26.2.1.8
-- 1.3.6.1.4.1.37950.1.1.5.10.26.2.1.8
-- 1.3.6.1.4.1.37950.1.1.5.10.26.2.1.8
-- 1.3.6.1.4.1.37950.1.1.5.10.26.2.1.8
-- 1.3.6.1.4.1.37950.1.1.5.10.26.2.1.8
-- 1.3.6.1.4.1.37950.1.1.5.10.26.2.1.8
		-- 1.3.6.1.4.1.37950.1.1.5.10.26.2.1.8
		radiusWebStatus OBJECT-TYPE
			SYNTAX INTEGER
				{
				enable(0),
				disable(1)
				}
			MAX-ACCESS read-only
			STATUS current
			DESCRIPTION
				"Description."
			::= { radiusCfgEntry 8 }

		
--         1.3.6.1.4.1.37950.1.1.5.10.26.2.1.9
-- 1.3.6.1.4.1.37950.1.1.5.10.26.2.1.9
-- 1.3.6.1.4.1.37950.1.1.5.10.26.2.1.9
-- 1.3.6.1.4.1.37950.1.1.5.10.26.2.1.9
-- 1.3.6.1.4.1.37950.1.1.5.10.26.2.1.9
-- 1.3.6.1.4.1.37950.1.1.5.10.26.2.1.9
-- 1.3.6.1.4.1.37950.1.1.5.10.26.2.1.9
-- 1.3.6.1.4.1.37950.1.1.5.10.26.2.1.9
		-- 1.3.6.1.4.1.37950.1.1.5.10.26.2.1.9
		radiusDot1xAuthen OBJECT-TYPE
			SYNTAX INTEGER
				{
				enable(0),
				disable(1)
				}
			MAX-ACCESS read-only
			STATUS current
			DESCRIPTION
				"Description."
			::= { radiusCfgEntry 9 }

		
--         1.3.6.1.4.1.37950.1.1.5.10.26.2.1.10
-- 1.3.6.1.4.1.37950.1.1.5.10.26.2.1.10
-- 1.3.6.1.4.1.37950.1.1.5.10.26.2.1.10
-- 1.3.6.1.4.1.37950.1.1.5.10.26.2.1.10
-- 1.3.6.1.4.1.37950.1.1.5.10.26.2.1.10
-- 1.3.6.1.4.1.37950.1.1.5.10.26.2.1.10
-- 1.3.6.1.4.1.37950.1.1.5.10.26.2.1.10
-- 1.3.6.1.4.1.37950.1.1.5.10.26.2.1.10
		-- 1.3.6.1.4.1.37950.1.1.5.10.26.2.1.10
		radiusDot1xAuthenLocal OBJECT-TYPE
			SYNTAX INTEGER
				{
				enable(0),
				disable(1)
				}
			MAX-ACCESS read-only
			STATUS current
			DESCRIPTION
				"Description."
			::= { radiusCfgEntry 10 }

		
--         1.3.6.1.4.1.37950.1.1.5.10.26.2.1.11
-- 1.3.6.1.4.1.37950.1.1.5.10.26.2.1.11
-- 1.3.6.1.4.1.37950.1.1.5.10.26.2.1.11
-- 1.3.6.1.4.1.37950.1.1.5.10.26.2.1.11
-- 1.3.6.1.4.1.37950.1.1.5.10.26.2.1.11
-- 1.3.6.1.4.1.37950.1.1.5.10.26.2.1.11
-- 1.3.6.1.4.1.37950.1.1.5.10.26.2.1.11
-- 1.3.6.1.4.1.37950.1.1.5.10.26.2.1.11
		-- 1.3.6.1.4.1.37950.1.1.5.10.26.2.1.11
		radiusDot1xAuthor OBJECT-TYPE
			SYNTAX INTEGER
				{
				enable(0),
				disable(1)
				}
			MAX-ACCESS read-only
			STATUS current
			DESCRIPTION
				"Description."
			::= { radiusCfgEntry 11 }

		
--         1.3.6.1.4.1.37950.1.1.5.10.26.2.1.12
-- 1.3.6.1.4.1.37950.1.1.5.10.26.2.1.12
-- 1.3.6.1.4.1.37950.1.1.5.10.26.2.1.12
-- 1.3.6.1.4.1.37950.1.1.5.10.26.2.1.12
-- 1.3.6.1.4.1.37950.1.1.5.10.26.2.1.12
-- 1.3.6.1.4.1.37950.1.1.5.10.26.2.1.12
-- 1.3.6.1.4.1.37950.1.1.5.10.26.2.1.12
-- 1.3.6.1.4.1.37950.1.1.5.10.26.2.1.12
		-- 1.3.6.1.4.1.37950.1.1.5.10.26.2.1.12
		radiusDot1xAcct OBJECT-TYPE
			SYNTAX INTEGER
				{
				enable(0),
				disable(1)
				}
			MAX-ACCESS read-only
			STATUS current
			DESCRIPTION
				"Description."
			::= { radiusCfgEntry 12 }

		
--         1.3.6.1.4.1.37950.1.1.5.10.26.3
-- 1.3.6.1.4.1.37950.1.1.5.10.26.3
-- 1.3.6.1.4.1.37950.1.1.5.10.26.3
-- 1.3.6.1.4.1.37950.1.1.5.10.26.3
-- 1.3.6.1.4.1.37950.1.1.5.10.26.3
-- 1.3.6.1.4.1.37950.1.1.5.10.26.3
-- 1.3.6.1.4.1.37950.1.1.5.10.26.3
-- 1.3.6.1.4.1.37950.1.1.5.10.26.3
-- 1.3.6.1.4.1.37950.1.1.5.10.26.3
		-- 1.3.6.1.4.1.37950.1.1.5.10.26.3
		radiusServerCfg OBJECT IDENTIFIER ::= { v1600Radius 3 }

		
--         1.3.6.1.4.1.37950.1.1.5.10.26.3.1
-- 1.3.6.1.4.1.37950.1.1.5.10.26.3.1
-- 1.3.6.1.4.1.37950.1.1.5.10.26.3.1
-- 1.3.6.1.4.1.37950.1.1.5.10.26.3.1
-- 1.3.6.1.4.1.37950.1.1.5.10.26.3.1
-- 1.3.6.1.4.1.37950.1.1.5.10.26.3.1
-- 1.3.6.1.4.1.37950.1.1.5.10.26.3.1
-- 1.3.6.1.4.1.37950.1.1.5.10.26.3.1
		-- 1.3.6.1.4.1.37950.1.1.5.10.26.3.1
		radServerHost OBJECT-TYPE
			SYNTAX OCTET STRING
			MAX-ACCESS read-write
			STATUS current
			DESCRIPTION
				"Description."
			::= { radiusServerCfg 1 }

		
--         1.3.6.1.4.1.37950.1.1.5.10.26.3.2
-- 1.3.6.1.4.1.37950.1.1.5.10.26.3.2
-- 1.3.6.1.4.1.37950.1.1.5.10.26.3.2
-- 1.3.6.1.4.1.37950.1.1.5.10.26.3.2
-- 1.3.6.1.4.1.37950.1.1.5.10.26.3.2
-- 1.3.6.1.4.1.37950.1.1.5.10.26.3.2
-- 1.3.6.1.4.1.37950.1.1.5.10.26.3.2
-- 1.3.6.1.4.1.37950.1.1.5.10.26.3.2
		-- 1.3.6.1.4.1.37950.1.1.5.10.26.3.2
		radSharedKey OBJECT-TYPE
			SYNTAX OCTET STRING
			MAX-ACCESS read-write
			STATUS current
			DESCRIPTION
				"Description."
			::= { radiusServerCfg 2 }

		
--         1.3.6.1.4.1.37950.1.1.5.10.26.3.3
-- 1.3.6.1.4.1.37950.1.1.5.10.26.3.3
-- 1.3.6.1.4.1.37950.1.1.5.10.26.3.3
-- 1.3.6.1.4.1.37950.1.1.5.10.26.3.3
-- 1.3.6.1.4.1.37950.1.1.5.10.26.3.3
-- 1.3.6.1.4.1.37950.1.1.5.10.26.3.3
-- 1.3.6.1.4.1.37950.1.1.5.10.26.3.3
-- 1.3.6.1.4.1.37950.1.1.5.10.26.3.3
		-- 1.3.6.1.4.1.37950.1.1.5.10.26.3.3
		radAddAction OBJECT-TYPE
			SYNTAX INTEGER
				{
				add(0),
				del(1)
				}
			MAX-ACCESS read-write
			STATUS current
			DESCRIPTION
				"Description."
			::= { radiusServerCfg 3 }

		
--         1.3.6.1.4.1.37950.1.1.5.10.26.4
-- 1.3.6.1.4.1.37950.1.1.5.10.26.4
-- 1.3.6.1.4.1.37950.1.1.5.10.26.4
-- 1.3.6.1.4.1.37950.1.1.5.10.26.4
-- 1.3.6.1.4.1.37950.1.1.5.10.26.4
-- 1.3.6.1.4.1.37950.1.1.5.10.26.4
-- 1.3.6.1.4.1.37950.1.1.5.10.26.4
-- 1.3.6.1.4.1.37950.1.1.5.10.26.4
		-- 1.3.6.1.4.1.37950.1.1.5.10.26.4
		radiusServerTable OBJECT-TYPE
			SYNTAX SEQUENCE OF RadiusServerEntry
			MAX-ACCESS not-accessible
			STATUS current
			DESCRIPTION
				"Description."
			::= { v1600Radius 4 }

		
--         1.3.6.1.4.1.37950.1.1.5.10.26.4.1
-- 1.3.6.1.4.1.37950.1.1.5.10.26.4.1
-- 1.3.6.1.4.1.37950.1.1.5.10.26.4.1
-- 1.3.6.1.4.1.37950.1.1.5.10.26.4.1
-- 1.3.6.1.4.1.37950.1.1.5.10.26.4.1
-- 1.3.6.1.4.1.37950.1.1.5.10.26.4.1
-- 1.3.6.1.4.1.37950.1.1.5.10.26.4.1
-- 1.3.6.1.4.1.37950.1.1.5.10.26.4.1
		-- 1.3.6.1.4.1.37950.1.1.5.10.26.4.1
		radiusServerEntry OBJECT-TYPE
			SYNTAX RadiusServerEntry
			MAX-ACCESS not-accessible
			STATUS current
			DESCRIPTION
				"Description."
			INDEX { radiusServer }
			::= { radiusServerTable 1 }

		
		RadiusServerEntry ::=
			SEQUENCE { 
				radiusServer
					OCTET STRING,
				radiusKey
					OCTET STRING
			 }

--         1.3.6.1.4.1.37950.1.1.5.10.26.4.1.1
-- 1.3.6.1.4.1.37950.1.1.5.10.26.4.1.1
-- 1.3.6.1.4.1.37950.1.1.5.10.26.4.1.1
-- 1.3.6.1.4.1.37950.1.1.5.10.26.4.1.1
-- 1.3.6.1.4.1.37950.1.1.5.10.26.4.1.1
-- 1.3.6.1.4.1.37950.1.1.5.10.26.4.1.1
-- 1.3.6.1.4.1.37950.1.1.5.10.26.4.1.1
-- 1.3.6.1.4.1.37950.1.1.5.10.26.4.1.1
		-- 1.3.6.1.4.1.37950.1.1.5.10.26.4.1.1
		radiusServer OBJECT-TYPE
			SYNTAX OCTET STRING
			MAX-ACCESS read-only
			STATUS current
			DESCRIPTION
				"Description."
			::= { radiusServerEntry 1 }

		
--         1.3.6.1.4.1.37950.1.1.5.10.26.4.1.2
-- 1.3.6.1.4.1.37950.1.1.5.10.26.4.1.2
-- 1.3.6.1.4.1.37950.1.1.5.10.26.4.1.2
-- 1.3.6.1.4.1.37950.1.1.5.10.26.4.1.2
-- 1.3.6.1.4.1.37950.1.1.5.10.26.4.1.2
-- 1.3.6.1.4.1.37950.1.1.5.10.26.4.1.2
-- 1.3.6.1.4.1.37950.1.1.5.10.26.4.1.2
-- 1.3.6.1.4.1.37950.1.1.5.10.26.4.1.2
		-- 1.3.6.1.4.1.37950.1.1.5.10.26.4.1.2
		radiusKey OBJECT-TYPE
			SYNTAX OCTET STRING
			MAX-ACCESS read-only
			STATUS current
			DESCRIPTION
				"Description."
			DEFVAL { ''b }
			::= { radiusServerEntry 2 }

		
--           1.3.6.1.4.1.37950.1.1.5.10.23
-- 1.3.6.1.4.1.37950.1.1.5.10.23
-- 1.3.6.1.4.1.37950.1.1.5.10.27
-- 1.3.6.1.4.1.37950.1.1.5.10.27
-- 1.3.6.1.4.1.37950.1.1.5.10.27
-- 1.3.6.1.4.1.37950.1.1.5.10.27
-- 1.3.6.1.4.1.37950.1.1.5.10.27
-- 1.3.6.1.4.1.37950.1.1.5.10.27
-- 1.3.6.1.4.1.37950.1.1.5.10.27
-- 1.3.6.1.4.1.37950.1.1.5.10.27
		-- 1.3.6.1.4.1.37950.1.1.5.10.27
		v1600dMstp OBJECT IDENTIFIER ::= { v1600dSwitch 27 }

		
--           1.3.6.1.4.1.37950.1.1.5.10.23.1
-- 1.3.6.1.4.1.37950.1.1.5.10.23.1
-- 1.3.6.1.4.1.37950.1.1.5.10.27.1
-- 1.3.6.1.4.1.37950.1.1.5.10.27.1
-- 1.3.6.1.4.1.37950.1.1.5.10.27.1
-- 1.3.6.1.4.1.37950.1.1.5.10.27.1
-- 1.3.6.1.4.1.37950.1.1.5.10.27.1
-- 1.3.6.1.4.1.37950.1.1.5.10.27.1
-- 1.3.6.1.4.1.37950.1.1.5.10.27.1
-- 1.3.6.1.4.1.37950.1.1.5.10.27.1
		-- 1.3.6.1.4.1.37950.1.1.5.10.27.1
		mstpEn OBJECT-TYPE
			SYNTAX INTEGER
				{
				disable(0),
				enable(1)
				}
			MAX-ACCESS read-write
			STATUS current
			DESCRIPTION
				"Description."
			::= { v1600dMstp 1 }

		
--           1.3.6.1.4.1.37950.1.1.5.10.23.2
-- 1.3.6.1.4.1.37950.1.1.5.10.23.2
-- 1.3.6.1.4.1.37950.1.1.5.10.27.2
-- 1.3.6.1.4.1.37950.1.1.5.10.27.2
-- 1.3.6.1.4.1.37950.1.1.5.10.27.2
-- 1.3.6.1.4.1.37950.1.1.5.10.27.2
-- 1.3.6.1.4.1.37950.1.1.5.10.27.2
-- 1.3.6.1.4.1.37950.1.1.5.10.27.2
-- 1.3.6.1.4.1.37950.1.1.5.10.27.2
-- 1.3.6.1.4.1.37950.1.1.5.10.27.2
		-- 1.3.6.1.4.1.37950.1.1.5.10.27.2
		mstpCfg OBJECT IDENTIFIER ::= { v1600dMstp 2 }

		
--           1.3.6.1.4.1.37950.1.1.5.10.23.2.1
-- 1.3.6.1.4.1.37950.1.1.5.10.23.2.1
-- 1.3.6.1.4.1.37950.1.1.5.10.27.2.1
-- 1.3.6.1.4.1.37950.1.1.5.10.27.2.1
-- 1.3.6.1.4.1.37950.1.1.5.10.27.2.1
-- 1.3.6.1.4.1.37950.1.1.5.10.27.2.1
-- 1.3.6.1.4.1.37950.1.1.5.10.27.2.1
-- 1.3.6.1.4.1.37950.1.1.5.10.27.2.1
-- 1.3.6.1.4.1.37950.1.1.5.10.27.2.1
-- 1.3.6.1.4.1.37950.1.1.5.10.27.2.1
		-- 1.3.6.1.4.1.37950.1.1.5.10.27.2.1
		mstpHelloTime OBJECT-TYPE
			SYNTAX Integer32
			MAX-ACCESS read-write
			STATUS current
			DESCRIPTION
				"Description."
			DEFVAL { 2 }
			::= { mstpCfg 1 }

		
--           1.3.6.1.4.1.37950.1.1.5.10.23.2.2
-- 1.3.6.1.4.1.37950.1.1.5.10.23.2.2
-- 1.3.6.1.4.1.37950.1.1.5.10.27.2.2
-- 1.3.6.1.4.1.37950.1.1.5.10.27.2.2
-- 1.3.6.1.4.1.37950.1.1.5.10.27.2.2
-- 1.3.6.1.4.1.37950.1.1.5.10.27.2.2
-- 1.3.6.1.4.1.37950.1.1.5.10.27.2.2
-- 1.3.6.1.4.1.37950.1.1.5.10.27.2.2
-- 1.3.6.1.4.1.37950.1.1.5.10.27.2.2
-- 1.3.6.1.4.1.37950.1.1.5.10.27.2.2
		-- 1.3.6.1.4.1.37950.1.1.5.10.27.2.2
		mstpForwardDelay OBJECT-TYPE
			SYNTAX Integer32
			MAX-ACCESS read-write
			STATUS current
			DESCRIPTION
				"Description."
			DEFVAL { 15 }
			::= { mstpCfg 2 }

		
--           1.3.6.1.4.1.37950.1.1.5.10.23.2.3
-- 1.3.6.1.4.1.37950.1.1.5.10.23.2.3
-- 1.3.6.1.4.1.37950.1.1.5.10.27.2.3
-- 1.3.6.1.4.1.37950.1.1.5.10.27.2.3
-- 1.3.6.1.4.1.37950.1.1.5.10.27.2.3
-- 1.3.6.1.4.1.37950.1.1.5.10.27.2.3
-- 1.3.6.1.4.1.37950.1.1.5.10.27.2.3
-- 1.3.6.1.4.1.37950.1.1.5.10.27.2.3
-- 1.3.6.1.4.1.37950.1.1.5.10.27.2.3
-- 1.3.6.1.4.1.37950.1.1.5.10.27.2.3
		-- 1.3.6.1.4.1.37950.1.1.5.10.27.2.3
		mstpMaxAge OBJECT-TYPE
			SYNTAX Integer32
			MAX-ACCESS read-write
			STATUS current
			DESCRIPTION
				"Description."
			DEFVAL { 20 }
			::= { mstpCfg 3 }

		
--           1.3.6.1.4.1.37950.1.1.5.10.23.2.4
-- 1.3.6.1.4.1.37950.1.1.5.10.23.2.4
-- 1.3.6.1.4.1.37950.1.1.5.10.27.2.4
-- 1.3.6.1.4.1.37950.1.1.5.10.27.2.4
-- 1.3.6.1.4.1.37950.1.1.5.10.27.2.4
-- 1.3.6.1.4.1.37950.1.1.5.10.27.2.4
-- 1.3.6.1.4.1.37950.1.1.5.10.27.2.4
-- 1.3.6.1.4.1.37950.1.1.5.10.27.2.4
-- 1.3.6.1.4.1.37950.1.1.5.10.27.2.4
-- 1.3.6.1.4.1.37950.1.1.5.10.27.2.4
		-- 1.3.6.1.4.1.37950.1.1.5.10.27.2.4
		mstpMaxHops OBJECT-TYPE
			SYNTAX Integer32
			MAX-ACCESS read-write
			STATUS current
			DESCRIPTION
				"Description."
			DEFVAL { 20 }
			::= { mstpCfg 4 }

		
--           1.3.6.1.4.1.37950.1.1.5.10.23.2.5
-- 1.3.6.1.4.1.37950.1.1.5.10.23.2.5
-- 1.3.6.1.4.1.37950.1.1.5.10.27.2.5
-- 1.3.6.1.4.1.37950.1.1.5.10.27.2.5
-- 1.3.6.1.4.1.37950.1.1.5.10.27.2.5
-- 1.3.6.1.4.1.37950.1.1.5.10.27.2.5
-- 1.3.6.1.4.1.37950.1.1.5.10.27.2.5
-- 1.3.6.1.4.1.37950.1.1.5.10.27.2.5
-- 1.3.6.1.4.1.37950.1.1.5.10.27.2.5
-- 1.3.6.1.4.1.37950.1.1.5.10.27.2.5
		-- 1.3.6.1.4.1.37950.1.1.5.10.27.2.5
		mstpCfgAction OBJECT-TYPE
			SYNTAX INTEGER
				{
				add(1),
				del(2)
				}
			MAX-ACCESS read-write
			STATUS current
			DESCRIPTION
				"Description."
			::= { mstpCfg 5 }

		
--           1.3.6.1.4.1.37950.1.1.5.10.23.3
-- 1.3.6.1.4.1.37950.1.1.5.10.23.3
-- 1.3.6.1.4.1.37950.1.1.5.10.27.3
-- 1.3.6.1.4.1.37950.1.1.5.10.27.3
-- 1.3.6.1.4.1.37950.1.1.5.10.27.3
-- 1.3.6.1.4.1.37950.1.1.5.10.27.3
-- 1.3.6.1.4.1.37950.1.1.5.10.27.3
-- 1.3.6.1.4.1.37950.1.1.5.10.27.3
-- 1.3.6.1.4.1.37950.1.1.5.10.27.3
-- 1.3.6.1.4.1.37950.1.1.5.10.27.3
		-- 1.3.6.1.4.1.37950.1.1.5.10.27.3
		mstpRegionCfg OBJECT IDENTIFIER ::= { v1600dMstp 3 }

		
--           1.3.6.1.4.1.37950.1.1.5.10.23.3.1
-- 1.3.6.1.4.1.37950.1.1.5.10.23.3.1
-- 1.3.6.1.4.1.37950.1.1.5.10.27.3.1
-- 1.3.6.1.4.1.37950.1.1.5.10.27.3.1
-- 1.3.6.1.4.1.37950.1.1.5.10.27.3.1
-- 1.3.6.1.4.1.37950.1.1.5.10.27.3.1
-- 1.3.6.1.4.1.37950.1.1.5.10.27.3.1
-- 1.3.6.1.4.1.37950.1.1.5.10.27.3.1
-- 1.3.6.1.4.1.37950.1.1.5.10.27.3.1
-- 1.3.6.1.4.1.37950.1.1.5.10.27.3.1
		-- 1.3.6.1.4.1.37950.1.1.5.10.27.3.1
		mstpFormatID OBJECT-TYPE
			SYNTAX Integer32
			MAX-ACCESS read-only
			STATUS current
			DESCRIPTION
				"Description."
			DEFVAL { 0 }
			::= { mstpRegionCfg 1 }

		
--           1.3.6.1.4.1.37950.1.1.5.10.23.3.2
-- 1.3.6.1.4.1.37950.1.1.5.10.23.3.2
-- 1.3.6.1.4.1.37950.1.1.5.10.27.3.2
-- 1.3.6.1.4.1.37950.1.1.5.10.27.3.2
-- 1.3.6.1.4.1.37950.1.1.5.10.27.3.2
-- 1.3.6.1.4.1.37950.1.1.5.10.27.3.2
-- 1.3.6.1.4.1.37950.1.1.5.10.27.3.2
-- 1.3.6.1.4.1.37950.1.1.5.10.27.3.2
-- 1.3.6.1.4.1.37950.1.1.5.10.27.3.2
-- 1.3.6.1.4.1.37950.1.1.5.10.27.3.2
		-- 1.3.6.1.4.1.37950.1.1.5.10.27.3.2
		mstpRegionName OBJECT-TYPE
			SYNTAX OCTET STRING
			MAX-ACCESS read-write
			STATUS current
			DESCRIPTION
				"Description."
			::= { mstpRegionCfg 2 }

		
--           1.3.6.1.4.1.37950.1.1.5.10.23.3.3
-- 1.3.6.1.4.1.37950.1.1.5.10.23.3.3
-- 1.3.6.1.4.1.37950.1.1.5.10.27.3.3
-- 1.3.6.1.4.1.37950.1.1.5.10.27.3.3
-- 1.3.6.1.4.1.37950.1.1.5.10.27.3.3
-- 1.3.6.1.4.1.37950.1.1.5.10.27.3.3
-- 1.3.6.1.4.1.37950.1.1.5.10.27.3.3
-- 1.3.6.1.4.1.37950.1.1.5.10.27.3.3
-- 1.3.6.1.4.1.37950.1.1.5.10.27.3.3
-- 1.3.6.1.4.1.37950.1.1.5.10.27.3.3
		-- 1.3.6.1.4.1.37950.1.1.5.10.27.3.3
		mstpRevisionLevel OBJECT-TYPE
			SYNTAX Integer32
			MAX-ACCESS read-write
			STATUS current
			DESCRIPTION
				"Description."
			DEFVAL { 0 }
			::= { mstpRegionCfg 3 }

		
--           1.3.6.1.4.1.37950.1.1.5.10.23.3.4
-- 1.3.6.1.4.1.37950.1.1.5.10.23.3.4
-- 1.3.6.1.4.1.37950.1.1.5.10.27.3.4
-- 1.3.6.1.4.1.37950.1.1.5.10.27.3.4
-- 1.3.6.1.4.1.37950.1.1.5.10.27.3.4
-- 1.3.6.1.4.1.37950.1.1.5.10.27.3.4
-- 1.3.6.1.4.1.37950.1.1.5.10.27.3.4
-- 1.3.6.1.4.1.37950.1.1.5.10.27.3.4
-- 1.3.6.1.4.1.37950.1.1.5.10.27.3.4
-- 1.3.6.1.4.1.37950.1.1.5.10.27.3.4
		-- 1.3.6.1.4.1.37950.1.1.5.10.27.3.4
		mstpDigest OBJECT-TYPE
			SYNTAX OCTET STRING
			MAX-ACCESS read-only
			STATUS current
			DESCRIPTION
				"Description."
			::= { mstpRegionCfg 4 }

		
--           1.3.6.1.4.1.37950.1.1.5.10.23.3.5
-- 1.3.6.1.4.1.37950.1.1.5.10.23.3.5
-- 1.3.6.1.4.1.37950.1.1.5.10.27.3.5
-- 1.3.6.1.4.1.37950.1.1.5.10.27.3.5
-- 1.3.6.1.4.1.37950.1.1.5.10.27.3.5
-- 1.3.6.1.4.1.37950.1.1.5.10.27.3.5
-- 1.3.6.1.4.1.37950.1.1.5.10.27.3.5
-- 1.3.6.1.4.1.37950.1.1.5.10.27.3.5
-- 1.3.6.1.4.1.37950.1.1.5.10.27.3.5
-- 1.3.6.1.4.1.37950.1.1.5.10.27.3.5
		-- 1.3.6.1.4.1.37950.1.1.5.10.27.3.5
		mstpRegionCfgAction OBJECT-TYPE
			SYNTAX INTEGER
				{
				add(1),
				del(2)
				}
			MAX-ACCESS read-write
			STATUS current
			DESCRIPTION
				"Description."
			::= { mstpRegionCfg 5 }

		
--           1.3.6.1.4.1.37950.1.1.5.10.23.4
-- 1.3.6.1.4.1.37950.1.1.5.10.23.4
-- 1.3.6.1.4.1.37950.1.1.5.10.27.4
-- 1.3.6.1.4.1.37950.1.1.5.10.27.4
-- 1.3.6.1.4.1.37950.1.1.5.10.27.4
-- 1.3.6.1.4.1.37950.1.1.5.10.27.4
-- 1.3.6.1.4.1.37950.1.1.5.10.27.4
-- 1.3.6.1.4.1.37950.1.1.5.10.27.4
-- 1.3.6.1.4.1.37950.1.1.5.10.27.4
-- 1.3.6.1.4.1.37950.1.1.5.10.27.4
		-- 1.3.6.1.4.1.37950.1.1.5.10.27.4
		mstpGuard OBJECT IDENTIFIER ::= { v1600dMstp 4 }

		
--           1.3.6.1.4.1.37950.1.1.5.10.23.4.1
-- 1.3.6.1.4.1.37950.1.1.5.10.23.4.1
-- 1.3.6.1.4.1.37950.1.1.5.10.27.4.1
-- 1.3.6.1.4.1.37950.1.1.5.10.27.4.1
-- 1.3.6.1.4.1.37950.1.1.5.10.27.4.1
-- 1.3.6.1.4.1.37950.1.1.5.10.27.4.1
-- 1.3.6.1.4.1.37950.1.1.5.10.27.4.1
-- 1.3.6.1.4.1.37950.1.1.5.10.27.4.1
-- 1.3.6.1.4.1.37950.1.1.5.10.27.4.1
-- 1.3.6.1.4.1.37950.1.1.5.10.27.4.1
		-- 1.3.6.1.4.1.37950.1.1.5.10.27.4.1
		mstpBPDUFilter OBJECT-TYPE
			SYNTAX INTEGER
				{
				disable(0),
				enable(1)
				}
			MAX-ACCESS read-write
			STATUS current
			DESCRIPTION
				"Description."
			::= { mstpGuard 1 }

		
--           1.3.6.1.4.1.37950.1.1.5.10.23.4.2
-- 1.3.6.1.4.1.37950.1.1.5.10.23.4.2
-- 1.3.6.1.4.1.37950.1.1.5.10.27.4.2
-- 1.3.6.1.4.1.37950.1.1.5.10.27.4.2
-- 1.3.6.1.4.1.37950.1.1.5.10.27.4.2
-- 1.3.6.1.4.1.37950.1.1.5.10.27.4.2
-- 1.3.6.1.4.1.37950.1.1.5.10.27.4.2
-- 1.3.6.1.4.1.37950.1.1.5.10.27.4.2
-- 1.3.6.1.4.1.37950.1.1.5.10.27.4.2
-- 1.3.6.1.4.1.37950.1.1.5.10.27.4.2
		-- 1.3.6.1.4.1.37950.1.1.5.10.27.4.2
		mstpBPDUFilterRecovery OBJECT-TYPE
			SYNTAX INTEGER
				{
				disable(0),
				enable(1)
				}
			MAX-ACCESS read-write
			STATUS current
			DESCRIPTION
				"Description."
			::= { mstpGuard 2 }

		
--           1.3.6.1.4.1.37950.1.1.5.10.23.4.3
-- 1.3.6.1.4.1.37950.1.1.5.10.23.4.3
-- 1.3.6.1.4.1.37950.1.1.5.10.27.4.3
-- 1.3.6.1.4.1.37950.1.1.5.10.27.4.3
-- 1.3.6.1.4.1.37950.1.1.5.10.27.4.3
-- 1.3.6.1.4.1.37950.1.1.5.10.27.4.3
-- 1.3.6.1.4.1.37950.1.1.5.10.27.4.3
-- 1.3.6.1.4.1.37950.1.1.5.10.27.4.3
-- 1.3.6.1.4.1.37950.1.1.5.10.27.4.3
-- 1.3.6.1.4.1.37950.1.1.5.10.27.4.3
		-- 1.3.6.1.4.1.37950.1.1.5.10.27.4.3
		mstpBPDUGuard OBJECT-TYPE
			SYNTAX INTEGER
				{
				disable(0),
				enable(1)
				}
			MAX-ACCESS read-write
			STATUS current
			DESCRIPTION
				"Description."
			::= { mstpGuard 3 }

		
--           1.3.6.1.4.1.37950.1.1.5.10.23.4.4
-- 1.3.6.1.4.1.37950.1.1.5.10.23.4.4
-- 1.3.6.1.4.1.37950.1.1.5.10.27.4.4
-- 1.3.6.1.4.1.37950.1.1.5.10.27.4.4
-- 1.3.6.1.4.1.37950.1.1.5.10.27.4.4
-- 1.3.6.1.4.1.37950.1.1.5.10.27.4.4
-- 1.3.6.1.4.1.37950.1.1.5.10.27.4.4
-- 1.3.6.1.4.1.37950.1.1.5.10.27.4.4
-- 1.3.6.1.4.1.37950.1.1.5.10.27.4.4
-- 1.3.6.1.4.1.37950.1.1.5.10.27.4.4
		-- 1.3.6.1.4.1.37950.1.1.5.10.27.4.4
		mstpLoopGuard OBJECT-TYPE
			SYNTAX INTEGER
				{
				disable(0),
				enable(1)
				}
			MAX-ACCESS read-write
			STATUS current
			DESCRIPTION
				"Description."
			::= { mstpGuard 4 }

		
--           1.3.6.1.4.1.37950.1.1.5.10.23.4.5
-- 1.3.6.1.4.1.37950.1.1.5.10.23.4.5
-- 1.3.6.1.4.1.37950.1.1.5.10.27.4.5
-- 1.3.6.1.4.1.37950.1.1.5.10.27.4.5
-- 1.3.6.1.4.1.37950.1.1.5.10.27.4.5
-- 1.3.6.1.4.1.37950.1.1.5.10.27.4.5
-- 1.3.6.1.4.1.37950.1.1.5.10.27.4.5
-- 1.3.6.1.4.1.37950.1.1.5.10.27.4.5
-- 1.3.6.1.4.1.37950.1.1.5.10.27.4.5
-- 1.3.6.1.4.1.37950.1.1.5.10.27.4.5
		-- 1.3.6.1.4.1.37950.1.1.5.10.27.4.5
		mstpGuardAction OBJECT-TYPE
			SYNTAX INTEGER
				{
				add(1),
				del(2)
				}
			MAX-ACCESS read-write
			STATUS current
			DESCRIPTION
				"Description."
			::= { mstpGuard 5 }

		
--           1.3.6.1.4.1.37950.1.1.5.10.23.5
-- 1.3.6.1.4.1.37950.1.1.5.10.23.5
-- 1.3.6.1.4.1.37950.1.1.5.10.27.5
-- 1.3.6.1.4.1.37950.1.1.5.10.27.5
-- 1.3.6.1.4.1.37950.1.1.5.10.27.5
-- 1.3.6.1.4.1.37950.1.1.5.10.27.5
-- 1.3.6.1.4.1.37950.1.1.5.10.27.5
-- 1.3.6.1.4.1.37950.1.1.5.10.27.5
-- 1.3.6.1.4.1.37950.1.1.5.10.27.5
-- 1.3.6.1.4.1.37950.1.1.5.10.27.5
		-- 1.3.6.1.4.1.37950.1.1.5.10.27.5
		mstpInstance OBJECT IDENTIFIER ::= { v1600dMstp 5 }

		
--           1.3.6.1.4.1.37950.1.1.5.10.23.5.1
-- 1.3.6.1.4.1.37950.1.1.5.10.23.5.1
-- 1.3.6.1.4.1.37950.1.1.5.10.27.5.1
-- 1.3.6.1.4.1.37950.1.1.5.10.27.5.1
-- 1.3.6.1.4.1.37950.1.1.5.10.27.5.1
-- 1.3.6.1.4.1.37950.1.1.5.10.27.5.1
-- 1.3.6.1.4.1.37950.1.1.5.10.27.5.1
-- 1.3.6.1.4.1.37950.1.1.5.10.27.5.1
-- 1.3.6.1.4.1.37950.1.1.5.10.27.5.1
-- 1.3.6.1.4.1.37950.1.1.5.10.27.5.1
		-- 1.3.6.1.4.1.37950.1.1.5.10.27.5.1
		mstpInstanceID OBJECT-TYPE
			SYNTAX Integer32
			MAX-ACCESS read-write
			STATUS current
			DESCRIPTION
				"Description."
			::= { mstpInstance 1 }

		
--           1.3.6.1.4.1.37950.1.1.5.10.23.5.2
-- 1.3.6.1.4.1.37950.1.1.5.10.23.5.2
-- 1.3.6.1.4.1.37950.1.1.5.10.27.5.2
-- 1.3.6.1.4.1.37950.1.1.5.10.27.5.2
-- 1.3.6.1.4.1.37950.1.1.5.10.27.5.2
-- 1.3.6.1.4.1.37950.1.1.5.10.27.5.2
-- 1.3.6.1.4.1.37950.1.1.5.10.27.5.2
-- 1.3.6.1.4.1.37950.1.1.5.10.27.5.2
-- 1.3.6.1.4.1.37950.1.1.5.10.27.5.2
-- 1.3.6.1.4.1.37950.1.1.5.10.27.5.2
		-- 1.3.6.1.4.1.37950.1.1.5.10.27.5.2
		mstpInstancePriority OBJECT-TYPE
			SYNTAX Integer32
			MAX-ACCESS read-write
			STATUS current
			DESCRIPTION
				"Description."
			DEFVAL { 32768 }
			::= { mstpInstance 2 }

		
--           1.3.6.1.4.1.37950.1.1.5.10.23.5.3
-- 1.3.6.1.4.1.37950.1.1.5.10.23.5.3
-- 1.3.6.1.4.1.37950.1.1.5.10.27.5.3
-- 1.3.6.1.4.1.37950.1.1.5.10.27.5.3
-- 1.3.6.1.4.1.37950.1.1.5.10.27.5.3
-- 1.3.6.1.4.1.37950.1.1.5.10.27.5.3
-- 1.3.6.1.4.1.37950.1.1.5.10.27.5.3
-- 1.3.6.1.4.1.37950.1.1.5.10.27.5.3
-- 1.3.6.1.4.1.37950.1.1.5.10.27.5.3
-- 1.3.6.1.4.1.37950.1.1.5.10.27.5.3
		-- 1.3.6.1.4.1.37950.1.1.5.10.27.5.3
		mstpVLANMapped OBJECT-TYPE
			SYNTAX Integer32
			MAX-ACCESS read-write
			STATUS current
			DESCRIPTION
				"Description."
			::= { mstpInstance 3 }

		
--           1.3.6.1.4.1.37950.1.1.5.10.23.5.4
-- 1.3.6.1.4.1.37950.1.1.5.10.23.5.4
-- 1.3.6.1.4.1.37950.1.1.5.10.27.5.4
-- 1.3.6.1.4.1.37950.1.1.5.10.27.5.4
-- 1.3.6.1.4.1.37950.1.1.5.10.27.5.4
-- 1.3.6.1.4.1.37950.1.1.5.10.27.5.4
-- 1.3.6.1.4.1.37950.1.1.5.10.27.5.4
-- 1.3.6.1.4.1.37950.1.1.5.10.27.5.4
-- 1.3.6.1.4.1.37950.1.1.5.10.27.5.4
-- 1.3.6.1.4.1.37950.1.1.5.10.27.5.4
		-- 1.3.6.1.4.1.37950.1.1.5.10.27.5.4
		mstpInstanceAction OBJECT-TYPE
			SYNTAX INTEGER
				{
				add(1),
				del(2)
				}
			MAX-ACCESS read-write
			STATUS current
			DESCRIPTION
				"Description."
			::= { mstpInstance 4 }

		
--           1.3.6.1.4.1.37950.1.1.5.10.23.6
-- 1.3.6.1.4.1.37950.1.1.5.10.23.6
-- 1.3.6.1.4.1.37950.1.1.5.10.27.6
-- 1.3.6.1.4.1.37950.1.1.5.10.27.6
-- 1.3.6.1.4.1.37950.1.1.5.10.27.6
-- 1.3.6.1.4.1.37950.1.1.5.10.27.6
-- 1.3.6.1.4.1.37950.1.1.5.10.27.6
-- 1.3.6.1.4.1.37950.1.1.5.10.27.6
-- 1.3.6.1.4.1.37950.1.1.5.10.27.6
-- 1.3.6.1.4.1.37950.1.1.5.10.27.6
		-- 1.3.6.1.4.1.37950.1.1.5.10.27.6
		mstpInstanceTable OBJECT-TYPE
			SYNTAX SEQUENCE OF MstpInstanceEntry
			MAX-ACCESS not-accessible
			STATUS current
			DESCRIPTION
				"Description."
			::= { v1600dMstp 6 }

		
--           1.3.6.1.4.1.37950.1.1.5.10.23.6.1
-- 1.3.6.1.4.1.37950.1.1.5.10.23.6.1
-- 1.3.6.1.4.1.37950.1.1.5.10.27.6.1
-- 1.3.6.1.4.1.37950.1.1.5.10.27.6.1
-- 1.3.6.1.4.1.37950.1.1.5.10.27.6.1
-- 1.3.6.1.4.1.37950.1.1.5.10.27.6.1
-- 1.3.6.1.4.1.37950.1.1.5.10.27.6.1
-- 1.3.6.1.4.1.37950.1.1.5.10.27.6.1
-- 1.3.6.1.4.1.37950.1.1.5.10.27.6.1
-- 1.3.6.1.4.1.37950.1.1.5.10.27.6.1
		-- 1.3.6.1.4.1.37950.1.1.5.10.27.6.1
		mstpInstanceEntry OBJECT-TYPE
			SYNTAX MstpInstanceEntry
			MAX-ACCESS not-accessible
			STATUS current
			DESCRIPTION
				"Description."
			INDEX { mstpInstanceId }
			::= { mstpInstanceTable 1 }

		
		MstpInstanceEntry ::=
			SEQUENCE { 
				mstpInstanceId
					Integer32,
				mstpInstanceVLANMapped
					OCTET STRING
			 }

--           1.3.6.1.4.1.37950.1.1.5.10.23.6.1.1
-- 1.3.6.1.4.1.37950.1.1.5.10.23.6.1.1
-- 1.3.6.1.4.1.37950.1.1.5.10.27.6.1.1
-- 1.3.6.1.4.1.37950.1.1.5.10.27.6.1.1
-- 1.3.6.1.4.1.37950.1.1.5.10.27.6.1.1
-- 1.3.6.1.4.1.37950.1.1.5.10.27.6.1.1
-- 1.3.6.1.4.1.37950.1.1.5.10.27.6.1.1
-- 1.3.6.1.4.1.37950.1.1.5.10.27.6.1.1
-- 1.3.6.1.4.1.37950.1.1.5.10.27.6.1.1
-- 1.3.6.1.4.1.37950.1.1.5.10.27.6.1.1
		-- 1.3.6.1.4.1.37950.1.1.5.10.27.6.1.1
		mstpInstanceId OBJECT-TYPE
			SYNTAX Integer32
			MAX-ACCESS read-only
			STATUS current
			DESCRIPTION
				"Description."
			::= { mstpInstanceEntry 1 }

		
--           1.3.6.1.4.1.37950.1.1.5.10.23.6.1.2
-- 1.3.6.1.4.1.37950.1.1.5.10.23.6.1.2
-- 1.3.6.1.4.1.37950.1.1.5.10.27.6.1.2
-- 1.3.6.1.4.1.37950.1.1.5.10.27.6.1.2
-- 1.3.6.1.4.1.37950.1.1.5.10.27.6.1.2
-- 1.3.6.1.4.1.37950.1.1.5.10.27.6.1.2
-- 1.3.6.1.4.1.37950.1.1.5.10.27.6.1.2
-- 1.3.6.1.4.1.37950.1.1.5.10.27.6.1.2
-- 1.3.6.1.4.1.37950.1.1.5.10.27.6.1.2
-- 1.3.6.1.4.1.37950.1.1.5.10.27.6.1.2
		-- 1.3.6.1.4.1.37950.1.1.5.10.27.6.1.2
		mstpInstanceVLANMapped OBJECT-TYPE
			SYNTAX OCTET STRING
			MAX-ACCESS read-only
			STATUS current
			DESCRIPTION
				"Description."
			::= { mstpInstanceEntry 2 }

		
--           1.3.6.1.4.1.37950.1.1.5.10.23.7
-- 1.3.6.1.4.1.37950.1.1.5.10.23.7
-- 1.3.6.1.4.1.37950.1.1.5.10.27.7
-- 1.3.6.1.4.1.37950.1.1.5.10.27.7
-- 1.3.6.1.4.1.37950.1.1.5.10.27.7
-- 1.3.6.1.4.1.37950.1.1.5.10.27.7
-- 1.3.6.1.4.1.37950.1.1.5.10.27.7
-- 1.3.6.1.4.1.37950.1.1.5.10.27.7
-- 1.3.6.1.4.1.37950.1.1.5.10.27.7
-- 1.3.6.1.4.1.37950.1.1.5.10.27.7
		-- 1.3.6.1.4.1.37950.1.1.5.10.27.7
		mstpPortTable OBJECT-TYPE
			SYNTAX SEQUENCE OF MstpPortEntry
			MAX-ACCESS not-accessible
			STATUS current
			DESCRIPTION
				"Description."
			::= { v1600dMstp 7 }

		
--           1.3.6.1.4.1.37950.1.1.5.10.23.7.1
-- 1.3.6.1.4.1.37950.1.1.5.10.23.7.1
-- 1.3.6.1.4.1.37950.1.1.5.10.27.7.1
-- 1.3.6.1.4.1.37950.1.1.5.10.27.7.1
-- 1.3.6.1.4.1.37950.1.1.5.10.27.7.1
-- 1.3.6.1.4.1.37950.1.1.5.10.27.7.1
-- 1.3.6.1.4.1.37950.1.1.5.10.27.7.1
-- 1.3.6.1.4.1.37950.1.1.5.10.27.7.1
-- 1.3.6.1.4.1.37950.1.1.5.10.27.7.1
-- 1.3.6.1.4.1.37950.1.1.5.10.27.7.1
		-- 1.3.6.1.4.1.37950.1.1.5.10.27.7.1
		mstpPortEntry OBJECT-TYPE
			SYNTAX MstpPortEntry
			MAX-ACCESS not-accessible
			STATUS current
			DESCRIPTION
				"Description."
			INDEX { mstpPortInstanceID, mstpPortIfindex }
			::= { mstpPortTable 1 }

		
		MstpPortEntry ::=
			SEQUENCE { 
				mstpPortInstanceID
					Integer32,
				mstpPortIfindex
					Integer32,
				mstpPortstatus
					INTEGER,
				mstpPortPriority
					Integer32,
				mstpPortPathCost
					Integer32,
				mstpPortFast
					INTEGER,
				mstpPortP2P
					INTEGER,
				mstpPortBPDUFilter
					INTEGER,
				mstpPortBPDUGuard
					INTEGER,
				mstpPortGuard
					INTEGER
			 }

--           1.3.6.1.4.1.37950.1.1.5.10.23.7.1.1
-- 1.3.6.1.4.1.37950.1.1.5.10.23.7.1.1
-- 1.3.6.1.4.1.37950.1.1.5.10.27.7.1.1
-- 1.3.6.1.4.1.37950.1.1.5.10.27.7.1.1
-- 1.3.6.1.4.1.37950.1.1.5.10.27.7.1.1
-- 1.3.6.1.4.1.37950.1.1.5.10.27.7.1.1
-- 1.3.6.1.4.1.37950.1.1.5.10.27.7.1.1
-- 1.3.6.1.4.1.37950.1.1.5.10.27.7.1.1
-- 1.3.6.1.4.1.37950.1.1.5.10.27.7.1.1
-- 1.3.6.1.4.1.37950.1.1.5.10.27.7.1.1
		-- 1.3.6.1.4.1.37950.1.1.5.10.27.7.1.1
		mstpPortInstanceID OBJECT-TYPE
			SYNTAX Integer32
			MAX-ACCESS read-only
			STATUS current
			DESCRIPTION
				"Description."
			::= { mstpPortEntry 1 }

		
--           1.3.6.1.4.1.37950.1.1.5.10.23.7.1.2
-- 1.3.6.1.4.1.37950.1.1.5.10.23.7.1.2
-- 1.3.6.1.4.1.37950.1.1.5.10.27.7.1.2
-- 1.3.6.1.4.1.37950.1.1.5.10.27.7.1.2
-- 1.3.6.1.4.1.37950.1.1.5.10.27.7.1.2
-- 1.3.6.1.4.1.37950.1.1.5.10.27.7.1.2
-- 1.3.6.1.4.1.37950.1.1.5.10.27.7.1.2
-- 1.3.6.1.4.1.37950.1.1.5.10.27.7.1.2
-- 1.3.6.1.4.1.37950.1.1.5.10.27.7.1.2
-- 1.3.6.1.4.1.37950.1.1.5.10.27.7.1.2
		-- 1.3.6.1.4.1.37950.1.1.5.10.27.7.1.2
		mstpPortIfindex OBJECT-TYPE
			SYNTAX Integer32
			MAX-ACCESS read-only
			STATUS current
			DESCRIPTION
				"Description."
			::= { mstpPortEntry 2 }

		
--           1.3.6.1.4.1.37950.1.1.5.10.23.7.1.3
-- 1.3.6.1.4.1.37950.1.1.5.10.23.7.1.3
-- 1.3.6.1.4.1.37950.1.1.5.10.27.7.1.3
-- 1.3.6.1.4.1.37950.1.1.5.10.27.7.1.3
-- 1.3.6.1.4.1.37950.1.1.5.10.27.7.1.3
-- 1.3.6.1.4.1.37950.1.1.5.10.27.7.1.3
-- 1.3.6.1.4.1.37950.1.1.5.10.27.7.1.3
-- 1.3.6.1.4.1.37950.1.1.5.10.27.7.1.3
-- 1.3.6.1.4.1.37950.1.1.5.10.27.7.1.3
-- 1.3.6.1.4.1.37950.1.1.5.10.27.7.1.3
		-- 1.3.6.1.4.1.37950.1.1.5.10.27.7.1.3
		mstpPortstatus OBJECT-TYPE
			SYNTAX INTEGER { disable(0) }
			MAX-ACCESS read-write
			STATUS current
			DESCRIPTION
				"Description."
			::= { mstpPortEntry 3 }

		
--           1.3.6.1.4.1.37950.1.1.5.10.23.7.1.4
-- 1.3.6.1.4.1.37950.1.1.5.10.23.7.1.4
-- 1.3.6.1.4.1.37950.1.1.5.10.27.7.1.4
-- 1.3.6.1.4.1.37950.1.1.5.10.27.7.1.4
-- 1.3.6.1.4.1.37950.1.1.5.10.27.7.1.4
-- 1.3.6.1.4.1.37950.1.1.5.10.27.7.1.4
-- 1.3.6.1.4.1.37950.1.1.5.10.27.7.1.4
-- 1.3.6.1.4.1.37950.1.1.5.10.27.7.1.4
-- 1.3.6.1.4.1.37950.1.1.5.10.27.7.1.4
-- 1.3.6.1.4.1.37950.1.1.5.10.27.7.1.4
		-- 1.3.6.1.4.1.37950.1.1.5.10.27.7.1.4
		mstpPortPriority OBJECT-TYPE
			SYNTAX Integer32
			MAX-ACCESS read-write
			STATUS current
			DESCRIPTION
				"Description."
			::= { mstpPortEntry 4 }

		
--           1.3.6.1.4.1.37950.1.1.5.10.23.7.1.5
-- 1.3.6.1.4.1.37950.1.1.5.10.23.7.1.5
-- 1.3.6.1.4.1.37950.1.1.5.10.27.7.1.5
-- 1.3.6.1.4.1.37950.1.1.5.10.27.7.1.5
-- 1.3.6.1.4.1.37950.1.1.5.10.27.7.1.5
-- 1.3.6.1.4.1.37950.1.1.5.10.27.7.1.5
-- 1.3.6.1.4.1.37950.1.1.5.10.27.7.1.5
-- 1.3.6.1.4.1.37950.1.1.5.10.27.7.1.5
-- 1.3.6.1.4.1.37950.1.1.5.10.27.7.1.5
-- 1.3.6.1.4.1.37950.1.1.5.10.27.7.1.5
		-- 1.3.6.1.4.1.37950.1.1.5.10.27.7.1.5
		mstpPortPathCost OBJECT-TYPE
			SYNTAX Integer32
			MAX-ACCESS read-write
			STATUS current
			DESCRIPTION
				"Description."
			::= { mstpPortEntry 5 }

		
--           1.3.6.1.4.1.37950.1.1.5.10.23.7.1.6
-- 1.3.6.1.4.1.37950.1.1.5.10.23.7.1.6
-- 1.3.6.1.4.1.37950.1.1.5.10.27.7.1.6
-- 1.3.6.1.4.1.37950.1.1.5.10.27.7.1.6
-- 1.3.6.1.4.1.37950.1.1.5.10.27.7.1.6
-- 1.3.6.1.4.1.37950.1.1.5.10.27.7.1.6
-- 1.3.6.1.4.1.37950.1.1.5.10.27.7.1.6
-- 1.3.6.1.4.1.37950.1.1.5.10.27.7.1.6
-- 1.3.6.1.4.1.37950.1.1.5.10.27.7.1.6
-- 1.3.6.1.4.1.37950.1.1.5.10.27.7.1.6
		-- 1.3.6.1.4.1.37950.1.1.5.10.27.7.1.6
		mstpPortFast OBJECT-TYPE
			SYNTAX INTEGER
				{
				disable(0),
				enable(1)
				}
			MAX-ACCESS read-write
			STATUS current
			DESCRIPTION
				"Description."
			::= { mstpPortEntry 6 }

		
--           1.3.6.1.4.1.37950.1.1.5.10.23.7.1.7
-- 1.3.6.1.4.1.37950.1.1.5.10.23.7.1.7
-- 1.3.6.1.4.1.37950.1.1.5.10.27.7.1.7
-- 1.3.6.1.4.1.37950.1.1.5.10.27.7.1.7
-- 1.3.6.1.4.1.37950.1.1.5.10.27.7.1.7
-- 1.3.6.1.4.1.37950.1.1.5.10.27.7.1.7
-- 1.3.6.1.4.1.37950.1.1.5.10.27.7.1.7
-- 1.3.6.1.4.1.37950.1.1.5.10.27.7.1.7
-- 1.3.6.1.4.1.37950.1.1.5.10.27.7.1.7
-- 1.3.6.1.4.1.37950.1.1.5.10.27.7.1.7
		-- 1.3.6.1.4.1.37950.1.1.5.10.27.7.1.7
		mstpPortP2P OBJECT-TYPE
			SYNTAX INTEGER { disable(0) }
			MAX-ACCESS read-write
			STATUS current
			DESCRIPTION
				"Description."
			::= { mstpPortEntry 7 }

		
--           1.3.6.1.4.1.37950.1.1.5.10.23.7.1.8
-- 1.3.6.1.4.1.37950.1.1.5.10.23.7.1.8
-- 1.3.6.1.4.1.37950.1.1.5.10.27.7.1.8
-- 1.3.6.1.4.1.37950.1.1.5.10.27.7.1.8
-- 1.3.6.1.4.1.37950.1.1.5.10.27.7.1.8
-- 1.3.6.1.4.1.37950.1.1.5.10.27.7.1.8
-- 1.3.6.1.4.1.37950.1.1.5.10.27.7.1.8
-- 1.3.6.1.4.1.37950.1.1.5.10.27.7.1.8
-- 1.3.6.1.4.1.37950.1.1.5.10.27.7.1.8
-- 1.3.6.1.4.1.37950.1.1.5.10.27.7.1.8
		-- 1.3.6.1.4.1.37950.1.1.5.10.27.7.1.8
		mstpPortBPDUFilter OBJECT-TYPE
			SYNTAX INTEGER
				{
				disable(0),
				enable(1)
				}
			MAX-ACCESS read-write
			STATUS current
			DESCRIPTION
				"Description."
			::= { mstpPortEntry 8 }

		
--           1.3.6.1.4.1.37950.1.1.5.10.23.7.1.9
-- 1.3.6.1.4.1.37950.1.1.5.10.23.7.1.9
-- 1.3.6.1.4.1.37950.1.1.5.10.27.7.1.9
-- 1.3.6.1.4.1.37950.1.1.5.10.27.7.1.9
-- 1.3.6.1.4.1.37950.1.1.5.10.27.7.1.9
-- 1.3.6.1.4.1.37950.1.1.5.10.27.7.1.9
-- 1.3.6.1.4.1.37950.1.1.5.10.27.7.1.9
-- 1.3.6.1.4.1.37950.1.1.5.10.27.7.1.9
-- 1.3.6.1.4.1.37950.1.1.5.10.27.7.1.9
-- 1.3.6.1.4.1.37950.1.1.5.10.27.7.1.9
		-- 1.3.6.1.4.1.37950.1.1.5.10.27.7.1.9
		mstpPortBPDUGuard OBJECT-TYPE
			SYNTAX INTEGER
				{
				disable(0),
				enable(1)
				}
			MAX-ACCESS read-write
			STATUS current
			DESCRIPTION
				"Description."
			::= { mstpPortEntry 9 }

		
--           1.3.6.1.4.1.37950.1.1.5.10.23.7.1.10
-- 1.3.6.1.4.1.37950.1.1.5.10.23.7.1.10
-- 1.3.6.1.4.1.37950.1.1.5.10.27.7.1.10
-- 1.3.6.1.4.1.37950.1.1.5.10.27.7.1.10
-- 1.3.6.1.4.1.37950.1.1.5.10.27.7.1.10
-- 1.3.6.1.4.1.37950.1.1.5.10.27.7.1.10
-- 1.3.6.1.4.1.37950.1.1.5.10.27.7.1.10
-- 1.3.6.1.4.1.37950.1.1.5.10.27.7.1.10
-- 1.3.6.1.4.1.37950.1.1.5.10.27.7.1.10
-- 1.3.6.1.4.1.37950.1.1.5.10.27.7.1.10
		-- 1.3.6.1.4.1.37950.1.1.5.10.27.7.1.10
		mstpPortGuard OBJECT-TYPE
			SYNTAX INTEGER
				{
				none(0),
				root(1)
				}
			MAX-ACCESS read-write
			STATUS current
			DESCRIPTION
				"Description."
			::= { mstpPortEntry 10 }

		
--           1.3.6.1.4.1.37950.1.1.5.10.23.8
-- 1.3.6.1.4.1.37950.1.1.5.10.23.8
-- 1.3.6.1.4.1.37950.1.1.5.10.27.8
-- 1.3.6.1.4.1.37950.1.1.5.10.27.8
-- 1.3.6.1.4.1.37950.1.1.5.10.27.8
-- 1.3.6.1.4.1.37950.1.1.5.10.27.8
-- 1.3.6.1.4.1.37950.1.1.5.10.27.8
-- 1.3.6.1.4.1.37950.1.1.5.10.27.8
-- 1.3.6.1.4.1.37950.1.1.5.10.27.8
-- 1.3.6.1.4.1.37950.1.1.5.10.27.8
		-- 1.3.6.1.4.1.37950.1.1.5.10.27.8
		mstpInformation OBJECT IDENTIFIER ::= { v1600dMstp 8 }

		
--           1.3.6.1.4.1.37950.1.1.5.10.23.8.1
-- 1.3.6.1.4.1.37950.1.1.5.10.23.8.1
-- 1.3.6.1.4.1.37950.1.1.5.10.27.8.1
-- 1.3.6.1.4.1.37950.1.1.5.10.27.8.1
-- 1.3.6.1.4.1.37950.1.1.5.10.27.8.1
-- 1.3.6.1.4.1.37950.1.1.5.10.27.8.1
-- 1.3.6.1.4.1.37950.1.1.5.10.27.8.1
-- 1.3.6.1.4.1.37950.1.1.5.10.27.8.1
-- 1.3.6.1.4.1.37950.1.1.5.10.27.8.1
-- 1.3.6.1.4.1.37950.1.1.5.10.27.8.1
		-- 1.3.6.1.4.1.37950.1.1.5.10.27.8.1
		mstpInstanceInfoTable OBJECT-TYPE
			SYNTAX SEQUENCE OF MstpInstanceInfoEntry
			MAX-ACCESS not-accessible
			STATUS current
			DESCRIPTION
				"Description."
			::= { mstpInformation 1 }

		
--           1.3.6.1.4.1.37950.1.1.5.10.23.8.1.1
-- 1.3.6.1.4.1.37950.1.1.5.10.23.8.1.1
-- 1.3.6.1.4.1.37950.1.1.5.10.27.8.1.1
-- 1.3.6.1.4.1.37950.1.1.5.10.27.8.1.1
-- 1.3.6.1.4.1.37950.1.1.5.10.27.8.1.1
-- 1.3.6.1.4.1.37950.1.1.5.10.27.8.1.1
-- 1.3.6.1.4.1.37950.1.1.5.10.27.8.1.1
-- 1.3.6.1.4.1.37950.1.1.5.10.27.8.1.1
-- 1.3.6.1.4.1.37950.1.1.5.10.27.8.1.1
-- 1.3.6.1.4.1.37950.1.1.5.10.27.8.1.1
		-- 1.3.6.1.4.1.37950.1.1.5.10.27.8.1.1
		mstpInstanceInfoEntry OBJECT-TYPE
			SYNTAX MstpInstanceInfoEntry
			MAX-ACCESS not-accessible
			STATUS current
			DESCRIPTION
				"Description."
			INDEX { mstpInfoInstanceID }
			::= { mstpInstanceInfoTable 1 }

		
		MstpInstanceInfoEntry ::=
			SEQUENCE { 
				mstpInfoInstanceID
					Integer32,
				mstpInfoInstanceVlanMapped
					OCTET STRING,
				mstpBridgeAddress
					OCTET STRING,
				mstpBridgePriority
					Integer32,
				mstpRootAddress
					OCTET STRING,
				mstpRootPriority
					Integer32,
				mstpRegRootAddress
					OCTET STRING,
				mstpRegRootPriority
					Integer32,
				mstpBridgeHelloTime
					Integer32,
				mstpBridgeForwardDelay
					Integer32,
				mstpBridgeMaxAge
					Integer32,
				mstpBridgeMaxHops
					Integer32,
				mstpRootHelloTime
					Integer32,
				mstpRootForwardDelay
					Integer32,
				mstpRootMaxAge
					Integer32
			 }

--           1.3.6.1.4.1.37950.1.1.5.10.23.8.1.1.1
-- 1.3.6.1.4.1.37950.1.1.5.10.23.8.1.1.1
-- 1.3.6.1.4.1.37950.1.1.5.10.27.8.1.1.1
-- 1.3.6.1.4.1.37950.1.1.5.10.27.8.1.1.1
-- 1.3.6.1.4.1.37950.1.1.5.10.27.8.1.1.1
-- 1.3.6.1.4.1.37950.1.1.5.10.27.8.1.1.1
-- 1.3.6.1.4.1.37950.1.1.5.10.27.8.1.1.1
-- 1.3.6.1.4.1.37950.1.1.5.10.27.8.1.1.1
-- 1.3.6.1.4.1.37950.1.1.5.10.27.8.1.1.1
-- 1.3.6.1.4.1.37950.1.1.5.10.27.8.1.1.1
		-- 1.3.6.1.4.1.37950.1.1.5.10.27.8.1.1.1
		mstpInfoInstanceID OBJECT-TYPE
			SYNTAX Integer32
			MAX-ACCESS read-only
			STATUS current
			DESCRIPTION
				"Description."
			::= { mstpInstanceInfoEntry 1 }

		
--           1.3.6.1.4.1.37950.1.1.5.10.23.8.1.1.2
-- 1.3.6.1.4.1.37950.1.1.5.10.23.8.1.1.2
-- 1.3.6.1.4.1.37950.1.1.5.10.27.8.1.1.2
-- 1.3.6.1.4.1.37950.1.1.5.10.27.8.1.1.2
-- 1.3.6.1.4.1.37950.1.1.5.10.27.8.1.1.2
-- 1.3.6.1.4.1.37950.1.1.5.10.27.8.1.1.2
-- 1.3.6.1.4.1.37950.1.1.5.10.27.8.1.1.2
-- 1.3.6.1.4.1.37950.1.1.5.10.27.8.1.1.2
-- 1.3.6.1.4.1.37950.1.1.5.10.27.8.1.1.2
-- 1.3.6.1.4.1.37950.1.1.5.10.27.8.1.1.2
		-- 1.3.6.1.4.1.37950.1.1.5.10.27.8.1.1.2
		mstpInfoInstanceVlanMapped OBJECT-TYPE
			SYNTAX OCTET STRING
			MAX-ACCESS read-only
			STATUS current
			DESCRIPTION
				"Description."
			::= { mstpInstanceInfoEntry 2 }

		
--           1.3.6.1.4.1.37950.1.1.5.10.23.8.1.1.3
-- 1.3.6.1.4.1.37950.1.1.5.10.23.8.1.1.3
-- 1.3.6.1.4.1.37950.1.1.5.10.27.8.1.1.3
-- 1.3.6.1.4.1.37950.1.1.5.10.27.8.1.1.3
-- 1.3.6.1.4.1.37950.1.1.5.10.27.8.1.1.3
-- 1.3.6.1.4.1.37950.1.1.5.10.27.8.1.1.3
-- 1.3.6.1.4.1.37950.1.1.5.10.27.8.1.1.3
-- 1.3.6.1.4.1.37950.1.1.5.10.27.8.1.1.3
-- 1.3.6.1.4.1.37950.1.1.5.10.27.8.1.1.3
-- 1.3.6.1.4.1.37950.1.1.5.10.27.8.1.1.3
		-- 1.3.6.1.4.1.37950.1.1.5.10.27.8.1.1.3
		mstpBridgeAddress OBJECT-TYPE
			SYNTAX OCTET STRING
			MAX-ACCESS read-write
			STATUS current
			DESCRIPTION
				"Description."
			::= { mstpInstanceInfoEntry 3 }

		
--           1.3.6.1.4.1.37950.1.1.5.10.23.8.1.1.4
-- 1.3.6.1.4.1.37950.1.1.5.10.23.8.1.1.4
-- 1.3.6.1.4.1.37950.1.1.5.10.27.8.1.1.4
-- 1.3.6.1.4.1.37950.1.1.5.10.27.8.1.1.4
-- 1.3.6.1.4.1.37950.1.1.5.10.27.8.1.1.4
-- 1.3.6.1.4.1.37950.1.1.5.10.27.8.1.1.4
-- 1.3.6.1.4.1.37950.1.1.5.10.27.8.1.1.4
-- 1.3.6.1.4.1.37950.1.1.5.10.27.8.1.1.4
-- 1.3.6.1.4.1.37950.1.1.5.10.27.8.1.1.4
-- 1.3.6.1.4.1.37950.1.1.5.10.27.8.1.1.4
		-- 1.3.6.1.4.1.37950.1.1.5.10.27.8.1.1.4
		mstpBridgePriority OBJECT-TYPE
			SYNTAX Integer32
			MAX-ACCESS read-only
			STATUS current
			DESCRIPTION
				"Description."
			::= { mstpInstanceInfoEntry 4 }

		
--           1.3.6.1.4.1.37950.1.1.5.10.23.8.1.1.5
-- 1.3.6.1.4.1.37950.1.1.5.10.23.8.1.1.5
-- 1.3.6.1.4.1.37950.1.1.5.10.27.8.1.1.5
-- 1.3.6.1.4.1.37950.1.1.5.10.27.8.1.1.5
-- 1.3.6.1.4.1.37950.1.1.5.10.27.8.1.1.5
-- 1.3.6.1.4.1.37950.1.1.5.10.27.8.1.1.5
-- 1.3.6.1.4.1.37950.1.1.5.10.27.8.1.1.5
-- 1.3.6.1.4.1.37950.1.1.5.10.27.8.1.1.5
-- 1.3.6.1.4.1.37950.1.1.5.10.27.8.1.1.5
-- 1.3.6.1.4.1.37950.1.1.5.10.27.8.1.1.5
		-- 1.3.6.1.4.1.37950.1.1.5.10.27.8.1.1.5
		mstpRootAddress OBJECT-TYPE
			SYNTAX OCTET STRING
			MAX-ACCESS read-only
			STATUS current
			DESCRIPTION
				"Description."
			::= { mstpInstanceInfoEntry 5 }

		
--           1.3.6.1.4.1.37950.1.1.5.10.23.8.1.1.6
-- 1.3.6.1.4.1.37950.1.1.5.10.23.8.1.1.6
-- 1.3.6.1.4.1.37950.1.1.5.10.27.8.1.1.6
-- 1.3.6.1.4.1.37950.1.1.5.10.27.8.1.1.6
-- 1.3.6.1.4.1.37950.1.1.5.10.27.8.1.1.6
-- 1.3.6.1.4.1.37950.1.1.5.10.27.8.1.1.6
-- 1.3.6.1.4.1.37950.1.1.5.10.27.8.1.1.6
-- 1.3.6.1.4.1.37950.1.1.5.10.27.8.1.1.6
-- 1.3.6.1.4.1.37950.1.1.5.10.27.8.1.1.6
-- 1.3.6.1.4.1.37950.1.1.5.10.27.8.1.1.6
		-- 1.3.6.1.4.1.37950.1.1.5.10.27.8.1.1.6
		mstpRootPriority OBJECT-TYPE
			SYNTAX Integer32
			MAX-ACCESS read-only
			STATUS current
			DESCRIPTION
				"Description."
			::= { mstpInstanceInfoEntry 6 }

		
--           1.3.6.1.4.1.37950.1.1.5.10.23.8.1.1.7
-- 1.3.6.1.4.1.37950.1.1.5.10.23.8.1.1.7
-- 1.3.6.1.4.1.37950.1.1.5.10.27.8.1.1.7
-- 1.3.6.1.4.1.37950.1.1.5.10.27.8.1.1.7
-- 1.3.6.1.4.1.37950.1.1.5.10.27.8.1.1.7
-- 1.3.6.1.4.1.37950.1.1.5.10.27.8.1.1.7
-- 1.3.6.1.4.1.37950.1.1.5.10.27.8.1.1.7
-- 1.3.6.1.4.1.37950.1.1.5.10.27.8.1.1.7
-- 1.3.6.1.4.1.37950.1.1.5.10.27.8.1.1.7
-- 1.3.6.1.4.1.37950.1.1.5.10.27.8.1.1.7
		-- 1.3.6.1.4.1.37950.1.1.5.10.27.8.1.1.7
		mstpRegRootAddress OBJECT-TYPE
			SYNTAX OCTET STRING
			MAX-ACCESS read-only
			STATUS current
			DESCRIPTION
				"Description."
			::= { mstpInstanceInfoEntry 7 }

		
--           1.3.6.1.4.1.37950.1.1.5.10.23.8.1.1.8
-- 1.3.6.1.4.1.37950.1.1.5.10.23.8.1.1.8
-- 1.3.6.1.4.1.37950.1.1.5.10.27.8.1.1.8
-- 1.3.6.1.4.1.37950.1.1.5.10.27.8.1.1.8
-- 1.3.6.1.4.1.37950.1.1.5.10.27.8.1.1.8
-- 1.3.6.1.4.1.37950.1.1.5.10.27.8.1.1.8
-- 1.3.6.1.4.1.37950.1.1.5.10.27.8.1.1.8
-- 1.3.6.1.4.1.37950.1.1.5.10.27.8.1.1.8
-- 1.3.6.1.4.1.37950.1.1.5.10.27.8.1.1.8
-- 1.3.6.1.4.1.37950.1.1.5.10.27.8.1.1.8
		-- 1.3.6.1.4.1.37950.1.1.5.10.27.8.1.1.8
		mstpRegRootPriority OBJECT-TYPE
			SYNTAX Integer32
			MAX-ACCESS read-only
			STATUS current
			DESCRIPTION
				"Description."
			::= { mstpInstanceInfoEntry 8 }

		
--           1.3.6.1.4.1.37950.1.1.5.10.23.8.1.1.9
-- 1.3.6.1.4.1.37950.1.1.5.10.23.8.1.1.9
-- 1.3.6.1.4.1.37950.1.1.5.10.27.8.1.1.9
-- 1.3.6.1.4.1.37950.1.1.5.10.27.8.1.1.9
-- 1.3.6.1.4.1.37950.1.1.5.10.27.8.1.1.9
-- 1.3.6.1.4.1.37950.1.1.5.10.27.8.1.1.9
-- 1.3.6.1.4.1.37950.1.1.5.10.27.8.1.1.9
-- 1.3.6.1.4.1.37950.1.1.5.10.27.8.1.1.9
-- 1.3.6.1.4.1.37950.1.1.5.10.27.8.1.1.9
-- 1.3.6.1.4.1.37950.1.1.5.10.27.8.1.1.9
		-- 1.3.6.1.4.1.37950.1.1.5.10.27.8.1.1.9
		mstpBridgeHelloTime OBJECT-TYPE
			SYNTAX Integer32
			MAX-ACCESS read-only
			STATUS current
			DESCRIPTION
				"Description."
			::= { mstpInstanceInfoEntry 9 }

		
--           1.3.6.1.4.1.37950.1.1.5.10.23.8.1.1.10
-- 1.3.6.1.4.1.37950.1.1.5.10.23.8.1.1.10
-- 1.3.6.1.4.1.37950.1.1.5.10.27.8.1.1.10
-- 1.3.6.1.4.1.37950.1.1.5.10.27.8.1.1.10
-- 1.3.6.1.4.1.37950.1.1.5.10.27.8.1.1.10
-- 1.3.6.1.4.1.37950.1.1.5.10.27.8.1.1.10
-- 1.3.6.1.4.1.37950.1.1.5.10.27.8.1.1.10
-- 1.3.6.1.4.1.37950.1.1.5.10.27.8.1.1.10
-- 1.3.6.1.4.1.37950.1.1.5.10.27.8.1.1.10
-- 1.3.6.1.4.1.37950.1.1.5.10.27.8.1.1.10
		-- 1.3.6.1.4.1.37950.1.1.5.10.27.8.1.1.10
		mstpBridgeForwardDelay OBJECT-TYPE
			SYNTAX Integer32
			MAX-ACCESS read-only
			STATUS current
			DESCRIPTION
				"Description."
			::= { mstpInstanceInfoEntry 10 }

		
--           1.3.6.1.4.1.37950.1.1.5.10.23.8.1.1.11
-- 1.3.6.1.4.1.37950.1.1.5.10.23.8.1.1.11
-- 1.3.6.1.4.1.37950.1.1.5.10.27.8.1.1.11
-- 1.3.6.1.4.1.37950.1.1.5.10.27.8.1.1.11
-- 1.3.6.1.4.1.37950.1.1.5.10.27.8.1.1.11
-- 1.3.6.1.4.1.37950.1.1.5.10.27.8.1.1.11
-- 1.3.6.1.4.1.37950.1.1.5.10.27.8.1.1.11
-- 1.3.6.1.4.1.37950.1.1.5.10.27.8.1.1.11
-- 1.3.6.1.4.1.37950.1.1.5.10.27.8.1.1.11
-- 1.3.6.1.4.1.37950.1.1.5.10.27.8.1.1.11
		-- 1.3.6.1.4.1.37950.1.1.5.10.27.8.1.1.11
		mstpBridgeMaxAge OBJECT-TYPE
			SYNTAX Integer32
			MAX-ACCESS read-only
			STATUS current
			DESCRIPTION
				"Description."
			::= { mstpInstanceInfoEntry 11 }

		
--           1.3.6.1.4.1.37950.1.1.5.10.23.8.1.1.12
-- 1.3.6.1.4.1.37950.1.1.5.10.23.8.1.1.12
-- 1.3.6.1.4.1.37950.1.1.5.10.27.8.1.1.12
-- 1.3.6.1.4.1.37950.1.1.5.10.27.8.1.1.12
-- 1.3.6.1.4.1.37950.1.1.5.10.27.8.1.1.12
-- 1.3.6.1.4.1.37950.1.1.5.10.27.8.1.1.12
-- 1.3.6.1.4.1.37950.1.1.5.10.27.8.1.1.12
-- 1.3.6.1.4.1.37950.1.1.5.10.27.8.1.1.12
-- 1.3.6.1.4.1.37950.1.1.5.10.27.8.1.1.12
-- 1.3.6.1.4.1.37950.1.1.5.10.27.8.1.1.12
		-- 1.3.6.1.4.1.37950.1.1.5.10.27.8.1.1.12
		mstpBridgeMaxHops OBJECT-TYPE
			SYNTAX Integer32
			MAX-ACCESS read-only
			STATUS current
			DESCRIPTION
				"Description."
			::= { mstpInstanceInfoEntry 12 }

		
--           1.3.6.1.4.1.37950.1.1.5.10.23.8.1.1.13
-- 1.3.6.1.4.1.37950.1.1.5.10.23.8.1.1.13
-- 1.3.6.1.4.1.37950.1.1.5.10.27.8.1.1.13
-- 1.3.6.1.4.1.37950.1.1.5.10.27.8.1.1.13
-- 1.3.6.1.4.1.37950.1.1.5.10.27.8.1.1.13
-- 1.3.6.1.4.1.37950.1.1.5.10.27.8.1.1.13
-- 1.3.6.1.4.1.37950.1.1.5.10.27.8.1.1.13
-- 1.3.6.1.4.1.37950.1.1.5.10.27.8.1.1.13
-- 1.3.6.1.4.1.37950.1.1.5.10.27.8.1.1.13
-- 1.3.6.1.4.1.37950.1.1.5.10.27.8.1.1.13
		-- 1.3.6.1.4.1.37950.1.1.5.10.27.8.1.1.13
		mstpRootHelloTime OBJECT-TYPE
			SYNTAX Integer32
			MAX-ACCESS read-only
			STATUS current
			DESCRIPTION
				"Description."
			::= { mstpInstanceInfoEntry 13 }

		
--           1.3.6.1.4.1.37950.1.1.5.10.23.8.1.1.14
-- 1.3.6.1.4.1.37950.1.1.5.10.23.8.1.1.14
-- 1.3.6.1.4.1.37950.1.1.5.10.27.8.1.1.14
-- 1.3.6.1.4.1.37950.1.1.5.10.27.8.1.1.14
-- 1.3.6.1.4.1.37950.1.1.5.10.27.8.1.1.14
-- 1.3.6.1.4.1.37950.1.1.5.10.27.8.1.1.14
-- 1.3.6.1.4.1.37950.1.1.5.10.27.8.1.1.14
-- 1.3.6.1.4.1.37950.1.1.5.10.27.8.1.1.14
-- 1.3.6.1.4.1.37950.1.1.5.10.27.8.1.1.14
-- 1.3.6.1.4.1.37950.1.1.5.10.27.8.1.1.14
		-- 1.3.6.1.4.1.37950.1.1.5.10.27.8.1.1.14
		mstpRootForwardDelay OBJECT-TYPE
			SYNTAX Integer32
			MAX-ACCESS read-only
			STATUS current
			DESCRIPTION
				"Description."
			::= { mstpInstanceInfoEntry 14 }

		
--           1.3.6.1.4.1.37950.1.1.5.10.23.8.1.1.15
-- 1.3.6.1.4.1.37950.1.1.5.10.23.8.1.1.15
-- 1.3.6.1.4.1.37950.1.1.5.10.27.8.1.1.15
-- 1.3.6.1.4.1.37950.1.1.5.10.27.8.1.1.15
-- 1.3.6.1.4.1.37950.1.1.5.10.27.8.1.1.15
-- 1.3.6.1.4.1.37950.1.1.5.10.27.8.1.1.15
-- 1.3.6.1.4.1.37950.1.1.5.10.27.8.1.1.15
-- 1.3.6.1.4.1.37950.1.1.5.10.27.8.1.1.15
-- 1.3.6.1.4.1.37950.1.1.5.10.27.8.1.1.15
-- 1.3.6.1.4.1.37950.1.1.5.10.27.8.1.1.15
		-- 1.3.6.1.4.1.37950.1.1.5.10.27.8.1.1.15
		mstpRootMaxAge OBJECT-TYPE
			SYNTAX Integer32
			MAX-ACCESS read-only
			STATUS current
			DESCRIPTION
				"Description."
			::= { mstpInstanceInfoEntry 15 }

		
--           1.3.6.1.4.1.37950.1.1.5.10.23.8.2
-- 1.3.6.1.4.1.37950.1.1.5.10.23.8.2
-- 1.3.6.1.4.1.37950.1.1.5.10.27.8.2
-- 1.3.6.1.4.1.37950.1.1.5.10.27.8.2
-- 1.3.6.1.4.1.37950.1.1.5.10.27.8.2
-- 1.3.6.1.4.1.37950.1.1.5.10.27.8.2
-- 1.3.6.1.4.1.37950.1.1.5.10.27.8.2
-- 1.3.6.1.4.1.37950.1.1.5.10.27.8.2
-- 1.3.6.1.4.1.37950.1.1.5.10.27.8.2
-- 1.3.6.1.4.1.37950.1.1.5.10.27.8.2
		-- 1.3.6.1.4.1.37950.1.1.5.10.27.8.2
		mstpInstancePortTable OBJECT-TYPE
			SYNTAX SEQUENCE OF MstpInstancePortEntry
			MAX-ACCESS not-accessible
			STATUS current
			DESCRIPTION
				"Description."
			::= { mstpInformation 2 }

		
--           1.3.6.1.4.1.37950.1.1.5.10.23.8.2.1
-- 1.3.6.1.4.1.37950.1.1.5.10.23.8.2.1
-- 1.3.6.1.4.1.37950.1.1.5.10.27.8.2.1
-- 1.3.6.1.4.1.37950.1.1.5.10.27.8.2.1
-- 1.3.6.1.4.1.37950.1.1.5.10.27.8.2.1
-- 1.3.6.1.4.1.37950.1.1.5.10.27.8.2.1
-- 1.3.6.1.4.1.37950.1.1.5.10.27.8.2.1
-- 1.3.6.1.4.1.37950.1.1.5.10.27.8.2.1
-- 1.3.6.1.4.1.37950.1.1.5.10.27.8.2.1
-- 1.3.6.1.4.1.37950.1.1.5.10.27.8.2.1
		-- 1.3.6.1.4.1.37950.1.1.5.10.27.8.2.1
		mstpInstancePortEntry OBJECT-TYPE
			SYNTAX MstpInstancePortEntry
			MAX-ACCESS not-accessible
			STATUS current
			DESCRIPTION
				"Description."
			INDEX { mstpPortInstanceID, mstpPortIfindex }
			::= { mstpInstancePortTable 1 }

		
		MstpInstancePortEntry ::=
			SEQUENCE { 
				mstpInterfaceName
					OCTET STRING,
				mstpInstancePortRole
					OCTET STRING,
				mstpInstancePortState
					OCTET STRING,
				mstpInstancePortPathCost
					Integer32,
				mstpInstancePortPriority
					Integer32,
				mstpInstancePortNumber
					Integer32,
				mstpInstancePortLinkType
					OCTET STRING
			 }

--           1.3.6.1.4.1.37950.1.1.5.10.23.8.2.1.1
-- 1.3.6.1.4.1.37950.1.1.5.10.23.8.2.1.1
-- 1.3.6.1.4.1.37950.1.1.5.10.27.8.2.1.1
-- 1.3.6.1.4.1.37950.1.1.5.10.27.8.2.1.1
-- 1.3.6.1.4.1.37950.1.1.5.10.27.8.2.1.1
-- 1.3.6.1.4.1.37950.1.1.5.10.27.8.2.1.1
-- 1.3.6.1.4.1.37950.1.1.5.10.27.8.2.1.1
-- 1.3.6.1.4.1.37950.1.1.5.10.27.8.2.1.1
-- 1.3.6.1.4.1.37950.1.1.5.10.27.8.2.1.1
-- 1.3.6.1.4.1.37950.1.1.5.10.27.8.2.1.1
		-- 1.3.6.1.4.1.37950.1.1.5.10.27.8.2.1.1
		mstpInterfaceName OBJECT-TYPE
			SYNTAX OCTET STRING
			MAX-ACCESS read-only
			STATUS obsolete
			DESCRIPTION
				"Description."
			::= { mstpInstancePortEntry 1 }

		
--           1.3.6.1.4.1.37950.1.1.5.10.23.8.2.1.2
-- 1.3.6.1.4.1.37950.1.1.5.10.23.8.2.1.2
-- 1.3.6.1.4.1.37950.1.1.5.10.27.8.2.1.2
-- 1.3.6.1.4.1.37950.1.1.5.10.27.8.2.1.2
-- 1.3.6.1.4.1.37950.1.1.5.10.27.8.2.1.2
-- 1.3.6.1.4.1.37950.1.1.5.10.27.8.2.1.2
-- 1.3.6.1.4.1.37950.1.1.5.10.27.8.2.1.2
-- 1.3.6.1.4.1.37950.1.1.5.10.27.8.2.1.2
-- 1.3.6.1.4.1.37950.1.1.5.10.27.8.2.1.2
-- 1.3.6.1.4.1.37950.1.1.5.10.27.8.2.1.2
		-- 1.3.6.1.4.1.37950.1.1.5.10.27.8.2.1.2
		mstpInstancePortRole OBJECT-TYPE
			SYNTAX OCTET STRING
			MAX-ACCESS read-write
			STATUS current
			DESCRIPTION
				"Description."
			::= { mstpInstancePortEntry 2 }

		
--           1.3.6.1.4.1.37950.1.1.5.10.23.8.2.1.3
-- 1.3.6.1.4.1.37950.1.1.5.10.23.8.2.1.3
-- 1.3.6.1.4.1.37950.1.1.5.10.27.8.2.1.3
-- 1.3.6.1.4.1.37950.1.1.5.10.27.8.2.1.3
-- 1.3.6.1.4.1.37950.1.1.5.10.27.8.2.1.3
-- 1.3.6.1.4.1.37950.1.1.5.10.27.8.2.1.3
-- 1.3.6.1.4.1.37950.1.1.5.10.27.8.2.1.3
-- 1.3.6.1.4.1.37950.1.1.5.10.27.8.2.1.3
-- 1.3.6.1.4.1.37950.1.1.5.10.27.8.2.1.3
-- 1.3.6.1.4.1.37950.1.1.5.10.27.8.2.1.3
		-- 1.3.6.1.4.1.37950.1.1.5.10.27.8.2.1.3
		mstpInstancePortState OBJECT-TYPE
			SYNTAX OCTET STRING
			MAX-ACCESS read-write
			STATUS current
			DESCRIPTION
				"Description."
			::= { mstpInstancePortEntry 3 }

		
--           1.3.6.1.4.1.37950.1.1.5.10.23.8.2.1.4
-- 1.3.6.1.4.1.37950.1.1.5.10.23.8.2.1.4
-- 1.3.6.1.4.1.37950.1.1.5.10.27.8.2.1.4
-- 1.3.6.1.4.1.37950.1.1.5.10.27.8.2.1.4
-- 1.3.6.1.4.1.37950.1.1.5.10.27.8.2.1.4
-- 1.3.6.1.4.1.37950.1.1.5.10.27.8.2.1.4
-- 1.3.6.1.4.1.37950.1.1.5.10.27.8.2.1.4
-- 1.3.6.1.4.1.37950.1.1.5.10.27.8.2.1.4
-- 1.3.6.1.4.1.37950.1.1.5.10.27.8.2.1.4
-- 1.3.6.1.4.1.37950.1.1.5.10.27.8.2.1.4
		-- 1.3.6.1.4.1.37950.1.1.5.10.27.8.2.1.4
		mstpInstancePortPathCost OBJECT-TYPE
			SYNTAX Integer32
			MAX-ACCESS read-write
			STATUS current
			DESCRIPTION
				"Description."
			::= { mstpInstancePortEntry 4 }

		
--           1.3.6.1.4.1.37950.1.1.5.10.23.8.2.1.5
-- 1.3.6.1.4.1.37950.1.1.5.10.23.8.2.1.5
-- 1.3.6.1.4.1.37950.1.1.5.10.27.8.2.1.5
-- 1.3.6.1.4.1.37950.1.1.5.10.27.8.2.1.5
-- 1.3.6.1.4.1.37950.1.1.5.10.27.8.2.1.5
-- 1.3.6.1.4.1.37950.1.1.5.10.27.8.2.1.5
-- 1.3.6.1.4.1.37950.1.1.5.10.27.8.2.1.5
-- 1.3.6.1.4.1.37950.1.1.5.10.27.8.2.1.5
-- 1.3.6.1.4.1.37950.1.1.5.10.27.8.2.1.5
-- 1.3.6.1.4.1.37950.1.1.5.10.27.8.2.1.5
		-- 1.3.6.1.4.1.37950.1.1.5.10.27.8.2.1.5
		mstpInstancePortPriority OBJECT-TYPE
			SYNTAX Integer32
			MAX-ACCESS read-write
			STATUS current
			DESCRIPTION
				"Description."
			::= { mstpInstancePortEntry 5 }

		
--           1.3.6.1.4.1.37950.1.1.5.10.23.8.2.1.6
-- 1.3.6.1.4.1.37950.1.1.5.10.23.8.2.1.6
-- 1.3.6.1.4.1.37950.1.1.5.10.27.8.2.1.6
-- 1.3.6.1.4.1.37950.1.1.5.10.27.8.2.1.6
-- 1.3.6.1.4.1.37950.1.1.5.10.27.8.2.1.6
-- 1.3.6.1.4.1.37950.1.1.5.10.27.8.2.1.6
-- 1.3.6.1.4.1.37950.1.1.5.10.27.8.2.1.6
-- 1.3.6.1.4.1.37950.1.1.5.10.27.8.2.1.6
-- 1.3.6.1.4.1.37950.1.1.5.10.27.8.2.1.6
-- 1.3.6.1.4.1.37950.1.1.5.10.27.8.2.1.6
		-- 1.3.6.1.4.1.37950.1.1.5.10.27.8.2.1.6
		mstpInstancePortNumber OBJECT-TYPE
			SYNTAX Integer32
			MAX-ACCESS read-write
			STATUS current
			DESCRIPTION
				"Description."
			::= { mstpInstancePortEntry 6 }

		
--           1.3.6.1.4.1.37950.1.1.5.10.23.8.2.1.7
-- 1.3.6.1.4.1.37950.1.1.5.10.23.8.2.1.7
-- 1.3.6.1.4.1.37950.1.1.5.10.27.8.2.1.7
-- 1.3.6.1.4.1.37950.1.1.5.10.27.8.2.1.7
-- 1.3.6.1.4.1.37950.1.1.5.10.27.8.2.1.7
-- 1.3.6.1.4.1.37950.1.1.5.10.27.8.2.1.7
-- 1.3.6.1.4.1.37950.1.1.5.10.27.8.2.1.7
-- 1.3.6.1.4.1.37950.1.1.5.10.27.8.2.1.7
-- 1.3.6.1.4.1.37950.1.1.5.10.27.8.2.1.7
-- 1.3.6.1.4.1.37950.1.1.5.10.27.8.2.1.7
		-- 1.3.6.1.4.1.37950.1.1.5.10.27.8.2.1.7
		mstpInstancePortLinkType OBJECT-TYPE
			SYNTAX OCTET STRING
			MAX-ACCESS read-write
			STATUS current
			DESCRIPTION
				"Description."
			::= { mstpInstancePortEntry 7 }

		
--          1.3.6.1.4.1.37950.1.1.5.10.24
-- 1.3.6.1.4.1.37950.1.1.5.10.28
-- 1.3.6.1.4.1.37950.1.1.5.10.28
-- 1.3.6.1.4.1.37950.1.1.5.10.28
-- 1.3.6.1.4.1.37950.1.1.5.10.28
-- 1.3.6.1.4.1.37950.1.1.5.10.28
-- 1.3.6.1.4.1.37950.1.1.5.10.28
-- 1.3.6.1.4.1.37950.1.1.5.10.28
-- 1.3.6.1.4.1.37950.1.1.5.10.28
		-- 1.3.6.1.4.1.37950.1.1.5.10.28
		v1600dNdSnooping OBJECT IDENTIFIER ::= { v1600dSwitch 28 }

		
--          1.3.6.1.4.1.37950.1.1.5.10.24.1
-- 1.3.6.1.4.1.37950.1.1.5.10.28.1
-- 1.3.6.1.4.1.37950.1.1.5.10.28.1
-- 1.3.6.1.4.1.37950.1.1.5.10.28.1
-- 1.3.6.1.4.1.37950.1.1.5.10.28.1
-- 1.3.6.1.4.1.37950.1.1.5.10.28.1
-- 1.3.6.1.4.1.37950.1.1.5.10.28.1
-- 1.3.6.1.4.1.37950.1.1.5.10.28.1
-- 1.3.6.1.4.1.37950.1.1.5.10.28.1
		-- 1.3.6.1.4.1.37950.1.1.5.10.28.1
		ndSnoopingCfg OBJECT IDENTIFIER ::= { v1600dNdSnooping 1 }

		
--          1.3.6.1.4.1.37950.1.1.5.10.24.1.1
-- 1.3.6.1.4.1.37950.1.1.5.10.28.1.1
-- 1.3.6.1.4.1.37950.1.1.5.10.28.1.1
-- 1.3.6.1.4.1.37950.1.1.5.10.28.1.1
-- 1.3.6.1.4.1.37950.1.1.5.10.28.1.1
-- 1.3.6.1.4.1.37950.1.1.5.10.28.1.1
-- 1.3.6.1.4.1.37950.1.1.5.10.28.1.1
-- 1.3.6.1.4.1.37950.1.1.5.10.28.1.1
-- 1.3.6.1.4.1.37950.1.1.5.10.28.1.1
		-- 1.3.6.1.4.1.37950.1.1.5.10.28.1.1
		ndSnoopingEnable OBJECT-TYPE
			SYNTAX INTEGER
				{
				disable(0),
				enable(1)
				}
			MAX-ACCESS read-write
			STATUS current
			DESCRIPTION
				"Description."
			::= { ndSnoopingCfg 1 }

		
--          1.3.6.1.4.1.37950.1.1.5.10.24.1.2
-- 1.3.6.1.4.1.37950.1.1.5.10.28.1.2
-- 1.3.6.1.4.1.37950.1.1.5.10.28.1.2
-- 1.3.6.1.4.1.37950.1.1.5.10.28.1.2
-- 1.3.6.1.4.1.37950.1.1.5.10.28.1.2
-- 1.3.6.1.4.1.37950.1.1.5.10.28.1.2
-- 1.3.6.1.4.1.37950.1.1.5.10.28.1.2
-- 1.3.6.1.4.1.37950.1.1.5.10.28.1.2
-- 1.3.6.1.4.1.37950.1.1.5.10.28.1.2
		-- 1.3.6.1.4.1.37950.1.1.5.10.28.1.2
		ndSnoopingDetect OBJECT-TYPE
			SYNTAX INTEGER
				{
				disable(0),
				enable(1)
				}
			MAX-ACCESS read-write
			STATUS current
			DESCRIPTION
				"Description."
			::= { ndSnoopingCfg 2 }

		
--          1.3.6.1.4.1.37950.1.1.5.10.24.1.3
-- 1.3.6.1.4.1.37950.1.1.5.10.28.1.3
-- 1.3.6.1.4.1.37950.1.1.5.10.28.1.3
-- 1.3.6.1.4.1.37950.1.1.5.10.28.1.3
-- 1.3.6.1.4.1.37950.1.1.5.10.28.1.3
-- 1.3.6.1.4.1.37950.1.1.5.10.28.1.3
-- 1.3.6.1.4.1.37950.1.1.5.10.28.1.3
-- 1.3.6.1.4.1.37950.1.1.5.10.28.1.3
-- 1.3.6.1.4.1.37950.1.1.5.10.28.1.3
		-- 1.3.6.1.4.1.37950.1.1.5.10.28.1.3
		ndSnoopingRetransmit OBJECT-TYPE
			SYNTAX Integer32 (1..8)
			MAX-ACCESS read-write
			STATUS current
			DESCRIPTION
				"Description."
			::= { ndSnoopingCfg 3 }

		
--          1.3.6.1.4.1.37950.1.1.5.10.24.1.4
-- 1.3.6.1.4.1.37950.1.1.5.10.28.1.4
-- 1.3.6.1.4.1.37950.1.1.5.10.28.1.4
-- 1.3.6.1.4.1.37950.1.1.5.10.28.1.4
-- 1.3.6.1.4.1.37950.1.1.5.10.28.1.4
-- 1.3.6.1.4.1.37950.1.1.5.10.28.1.4
-- 1.3.6.1.4.1.37950.1.1.5.10.28.1.4
-- 1.3.6.1.4.1.37950.1.1.5.10.28.1.4
-- 1.3.6.1.4.1.37950.1.1.5.10.28.1.4
		-- 1.3.6.1.4.1.37950.1.1.5.10.28.1.4
		ndSnoopingInterval OBJECT-TYPE
			SYNTAX Integer32 (1..10000)
			MAX-ACCESS read-write
			STATUS current
			DESCRIPTION
				"Description."
			::= { ndSnoopingCfg 4 }

		
--          1.3.6.1.4.1.37950.1.1.5.10.24.2
-- 1.3.6.1.4.1.37950.1.1.5.10.28.2
-- 1.3.6.1.4.1.37950.1.1.5.10.28.2
-- 1.3.6.1.4.1.37950.1.1.5.10.28.2
-- 1.3.6.1.4.1.37950.1.1.5.10.28.2
-- 1.3.6.1.4.1.37950.1.1.5.10.28.2
-- 1.3.6.1.4.1.37950.1.1.5.10.28.2
-- 1.3.6.1.4.1.37950.1.1.5.10.28.2
-- 1.3.6.1.4.1.37950.1.1.5.10.28.2
		-- 1.3.6.1.4.1.37950.1.1.5.10.28.2
		ndSnoopingVLAN OBJECT IDENTIFIER ::= { v1600dNdSnooping 2 }

		
--          1.3.6.1.4.1.37950.1.1.5.10.24.2.1
-- 1.3.6.1.4.1.37950.1.1.5.10.28.2.1
-- 1.3.6.1.4.1.37950.1.1.5.10.28.2.1
-- 1.3.6.1.4.1.37950.1.1.5.10.28.2.1
-- 1.3.6.1.4.1.37950.1.1.5.10.28.2.1
-- 1.3.6.1.4.1.37950.1.1.5.10.28.2.1
-- 1.3.6.1.4.1.37950.1.1.5.10.28.2.1
-- 1.3.6.1.4.1.37950.1.1.5.10.28.2.1
-- 1.3.6.1.4.1.37950.1.1.5.10.28.2.1
		-- 1.3.6.1.4.1.37950.1.1.5.10.28.2.1
		ndSnoopingVLANID OBJECT-TYPE
			SYNTAX Integer32 (1..4094)
			MAX-ACCESS read-write
			STATUS current
			DESCRIPTION
				"Description."
			::= { ndSnoopingVLAN 1 }

		
--          1.3.6.1.4.1.37950.1.1.5.10.24.2.2
-- 1.3.6.1.4.1.37950.1.1.5.10.28.2.2
-- 1.3.6.1.4.1.37950.1.1.5.10.28.2.2
-- 1.3.6.1.4.1.37950.1.1.5.10.28.2.2
-- 1.3.6.1.4.1.37950.1.1.5.10.28.2.2
-- 1.3.6.1.4.1.37950.1.1.5.10.28.2.2
-- 1.3.6.1.4.1.37950.1.1.5.10.28.2.2
-- 1.3.6.1.4.1.37950.1.1.5.10.28.2.2
-- 1.3.6.1.4.1.37950.1.1.5.10.28.2.2
		-- 1.3.6.1.4.1.37950.1.1.5.10.28.2.2
		ndSnoopingVLANAction OBJECT-TYPE
			SYNTAX INTEGER
				{
				del(0),
				add(1)
				}
			MAX-ACCESS read-write
			STATUS current
			DESCRIPTION
				"Description."
			::= { ndSnoopingVLAN 2 }

		
--          1.3.6.1.4.1.37950.1.1.5.10.24.2.3
-- 1.3.6.1.4.1.37950.1.1.5.10.28.2.3
-- 1.3.6.1.4.1.37950.1.1.5.10.28.2.3
-- 1.3.6.1.4.1.37950.1.1.5.10.28.2.3
-- 1.3.6.1.4.1.37950.1.1.5.10.28.2.3
-- 1.3.6.1.4.1.37950.1.1.5.10.28.2.3
-- 1.3.6.1.4.1.37950.1.1.5.10.28.2.3
-- 1.3.6.1.4.1.37950.1.1.5.10.28.2.3
-- 1.3.6.1.4.1.37950.1.1.5.10.28.2.3
		-- 1.3.6.1.4.1.37950.1.1.5.10.28.2.3
		ndSnoopingVLANList OBJECT-TYPE
			SYNTAX OCTET STRING
			MAX-ACCESS read-only
			STATUS current
			DESCRIPTION
				"Description."
			::= { ndSnoopingVLAN 3 }

		
--          1.3.6.1.4.1.37950.1.1.5.10.24.3
-- 1.3.6.1.4.1.37950.1.1.5.10.28.3
-- 1.3.6.1.4.1.37950.1.1.5.10.28.3
-- 1.3.6.1.4.1.37950.1.1.5.10.28.3
-- 1.3.6.1.4.1.37950.1.1.5.10.28.3
-- 1.3.6.1.4.1.37950.1.1.5.10.28.3
-- 1.3.6.1.4.1.37950.1.1.5.10.28.3
-- 1.3.6.1.4.1.37950.1.1.5.10.28.3
-- 1.3.6.1.4.1.37950.1.1.5.10.28.3
		-- 1.3.6.1.4.1.37950.1.1.5.10.28.3
		ndSnoopingPortCfgTable OBJECT-TYPE
			SYNTAX SEQUENCE OF NdSnoopingPortCfgEntry
			MAX-ACCESS not-accessible
			STATUS current
			DESCRIPTION
				"Description."
			::= { v1600dNdSnooping 3 }

		
--          1.3.6.1.4.1.37950.1.1.5.10.24.3.1
-- 1.3.6.1.4.1.37950.1.1.5.10.28.3.1
-- 1.3.6.1.4.1.37950.1.1.5.10.28.3.1
-- 1.3.6.1.4.1.37950.1.1.5.10.28.3.1
-- 1.3.6.1.4.1.37950.1.1.5.10.28.3.1
-- 1.3.6.1.4.1.37950.1.1.5.10.28.3.1
-- 1.3.6.1.4.1.37950.1.1.5.10.28.3.1
-- 1.3.6.1.4.1.37950.1.1.5.10.28.3.1
-- 1.3.6.1.4.1.37950.1.1.5.10.28.3.1
		-- 1.3.6.1.4.1.37950.1.1.5.10.28.3.1
		ndSnoopingPortCfgEntry OBJECT-TYPE
			SYNTAX NdSnoopingPortCfgEntry
			MAX-ACCESS not-accessible
			STATUS current
			DESCRIPTION
				"Description."
			INDEX { ndSnoopingPortIndex }
			::= { ndSnoopingPortCfgTable 1 }

		
		NdSnoopingPortCfgEntry ::=
			SEQUENCE { 
				ndSnoopingPortIndex
					Integer32,
				ndSnoopingPortType
					INTEGER,
				ndSnoopingPortCfgNaCheck
					INTEGER,
				ndSnoopingPortCfgNsCheck
					INTEGER,
				ndSnoopingPortCfgRsCheck
					INTEGER
			 }

--          1.3.6.1.4.1.37950.1.1.5.10.24.3.1.1
-- 1.3.6.1.4.1.37950.1.1.5.10.28.3.1.1
-- 1.3.6.1.4.1.37950.1.1.5.10.28.3.1.1
-- 1.3.6.1.4.1.37950.1.1.5.10.28.3.1.1
-- 1.3.6.1.4.1.37950.1.1.5.10.28.3.1.1
-- 1.3.6.1.4.1.37950.1.1.5.10.28.3.1.1
-- 1.3.6.1.4.1.37950.1.1.5.10.28.3.1.1
-- 1.3.6.1.4.1.37950.1.1.5.10.28.3.1.1
-- 1.3.6.1.4.1.37950.1.1.5.10.28.3.1.1
		-- 1.3.6.1.4.1.37950.1.1.5.10.28.3.1.1
		ndSnoopingPortIndex OBJECT-TYPE
			SYNTAX Integer32
			MAX-ACCESS read-only
			STATUS current
			DESCRIPTION
				"Description."
			::= { ndSnoopingPortCfgEntry 1 }

		
--          1.3.6.1.4.1.37950.1.1.5.10.24.3.1.2
-- 1.3.6.1.4.1.37950.1.1.5.10.28.3.1.2
-- 1.3.6.1.4.1.37950.1.1.5.10.28.3.1.2
-- 1.3.6.1.4.1.37950.1.1.5.10.28.3.1.2
-- 1.3.6.1.4.1.37950.1.1.5.10.28.3.1.2
-- 1.3.6.1.4.1.37950.1.1.5.10.28.3.1.2
-- 1.3.6.1.4.1.37950.1.1.5.10.28.3.1.2
-- 1.3.6.1.4.1.37950.1.1.5.10.28.3.1.2
-- 1.3.6.1.4.1.37950.1.1.5.10.28.3.1.2
		-- 1.3.6.1.4.1.37950.1.1.5.10.28.3.1.2
		ndSnoopingPortType OBJECT-TYPE
			SYNTAX INTEGER
				{
				untrust(0),
				trust(1)
				}
			MAX-ACCESS read-write
			STATUS current
			DESCRIPTION
				"Description."
			::= { ndSnoopingPortCfgEntry 2 }

		
--          1.3.6.1.4.1.37950.1.1.5.10.24.3.1.3
-- 1.3.6.1.4.1.37950.1.1.5.10.28.3.1.3
-- 1.3.6.1.4.1.37950.1.1.5.10.28.3.1.3
-- 1.3.6.1.4.1.37950.1.1.5.10.28.3.1.3
-- 1.3.6.1.4.1.37950.1.1.5.10.28.3.1.3
-- 1.3.6.1.4.1.37950.1.1.5.10.28.3.1.3
-- 1.3.6.1.4.1.37950.1.1.5.10.28.3.1.3
-- 1.3.6.1.4.1.37950.1.1.5.10.28.3.1.3
-- 1.3.6.1.4.1.37950.1.1.5.10.28.3.1.3
		-- 1.3.6.1.4.1.37950.1.1.5.10.28.3.1.3
		ndSnoopingPortCfgNaCheck OBJECT-TYPE
			SYNTAX INTEGER
				{
				disable(0),
				enable(1)
				}
			MAX-ACCESS read-write
			STATUS current
			DESCRIPTION
				"Description."
			::= { ndSnoopingPortCfgEntry 3 }

		
--          1.3.6.1.4.1.37950.1.1.5.10.24.3.1.4
-- 1.3.6.1.4.1.37950.1.1.5.10.28.3.1.4
-- 1.3.6.1.4.1.37950.1.1.5.10.28.3.1.4
-- 1.3.6.1.4.1.37950.1.1.5.10.28.3.1.4
-- 1.3.6.1.4.1.37950.1.1.5.10.28.3.1.4
-- 1.3.6.1.4.1.37950.1.1.5.10.28.3.1.4
-- 1.3.6.1.4.1.37950.1.1.5.10.28.3.1.4
-- 1.3.6.1.4.1.37950.1.1.5.10.28.3.1.4
-- 1.3.6.1.4.1.37950.1.1.5.10.28.3.1.4
		-- 1.3.6.1.4.1.37950.1.1.5.10.28.3.1.4
		ndSnoopingPortCfgNsCheck OBJECT-TYPE
			SYNTAX INTEGER
				{
				disable(0),
				enable(1)
				}
			MAX-ACCESS read-write
			STATUS current
			DESCRIPTION
				"Description."
			::= { ndSnoopingPortCfgEntry 4 }

		
--          1.3.6.1.4.1.37950.1.1.5.10.24.3.1.5
-- 1.3.6.1.4.1.37950.1.1.5.10.28.3.1.5
-- 1.3.6.1.4.1.37950.1.1.5.10.28.3.1.5
-- 1.3.6.1.4.1.37950.1.1.5.10.28.3.1.5
-- 1.3.6.1.4.1.37950.1.1.5.10.28.3.1.5
-- 1.3.6.1.4.1.37950.1.1.5.10.28.3.1.5
-- 1.3.6.1.4.1.37950.1.1.5.10.28.3.1.5
-- 1.3.6.1.4.1.37950.1.1.5.10.28.3.1.5
-- 1.3.6.1.4.1.37950.1.1.5.10.28.3.1.5
		-- 1.3.6.1.4.1.37950.1.1.5.10.28.3.1.5
		ndSnoopingPortCfgRsCheck OBJECT-TYPE
			SYNTAX INTEGER
				{
				disable(0),
				enable(1)
				}
			MAX-ACCESS read-write
			STATUS current
			DESCRIPTION
				"Description."
			::= { ndSnoopingPortCfgEntry 5 }

		
--          1.3.6.1.4.1.37950.1.1.5.10.24.4
-- 1.3.6.1.4.1.37950.1.1.5.10.28.4
-- 1.3.6.1.4.1.37950.1.1.5.10.28.4
-- 1.3.6.1.4.1.37950.1.1.5.10.28.4
-- 1.3.6.1.4.1.37950.1.1.5.10.28.4
-- 1.3.6.1.4.1.37950.1.1.5.10.28.4
-- 1.3.6.1.4.1.37950.1.1.5.10.28.4
-- 1.3.6.1.4.1.37950.1.1.5.10.28.4
-- 1.3.6.1.4.1.37950.1.1.5.10.28.4
		-- 1.3.6.1.4.1.37950.1.1.5.10.28.4
		ndSnoopingEntry OBJECT IDENTIFIER ::= { v1600dNdSnooping 4 }

		
--          1.3.6.1.4.1.37950.1.1.5.10.24.4.1
-- 1.3.6.1.4.1.37950.1.1.5.10.28.4.1
-- 1.3.6.1.4.1.37950.1.1.5.10.28.4.1
-- 1.3.6.1.4.1.37950.1.1.5.10.28.4.1
-- 1.3.6.1.4.1.37950.1.1.5.10.28.4.1
-- 1.3.6.1.4.1.37950.1.1.5.10.28.4.1
-- 1.3.6.1.4.1.37950.1.1.5.10.28.4.1
-- 1.3.6.1.4.1.37950.1.1.5.10.28.4.1
-- 1.3.6.1.4.1.37950.1.1.5.10.28.4.1
		-- 1.3.6.1.4.1.37950.1.1.5.10.28.4.1
		ndSnoopingPrefixEntryTable OBJECT-TYPE
			SYNTAX SEQUENCE OF NdSnoopingPrefixEntryEntry
			MAX-ACCESS not-accessible
			STATUS current
			DESCRIPTION
				"Description."
			::= { ndSnoopingEntry 1 }

		
--          1.3.6.1.4.1.37950.1.1.5.10.24.4.1.1
-- 1.3.6.1.4.1.37950.1.1.5.10.28.4.1.1
-- 1.3.6.1.4.1.37950.1.1.5.10.28.4.1.1
-- 1.3.6.1.4.1.37950.1.1.5.10.28.4.1.1
-- 1.3.6.1.4.1.37950.1.1.5.10.28.4.1.1
-- 1.3.6.1.4.1.37950.1.1.5.10.28.4.1.1
-- 1.3.6.1.4.1.37950.1.1.5.10.28.4.1.1
-- 1.3.6.1.4.1.37950.1.1.5.10.28.4.1.1
-- 1.3.6.1.4.1.37950.1.1.5.10.28.4.1.1
		-- 1.3.6.1.4.1.37950.1.1.5.10.28.4.1.1
		ndSnoopingPrefixEntryEntry OBJECT-TYPE
			SYNTAX NdSnoopingPrefixEntryEntry
			MAX-ACCESS not-accessible
			STATUS current
			DESCRIPTION
				"Description."
			INDEX { ndSnoopingPrefixEntryID }
			::= { ndSnoopingPrefixEntryTable 1 }

		
		NdSnoopingPrefixEntryEntry ::=
			SEQUENCE { 
				ndSnoopingPrefixEntryID
					Integer32,
				ndSnoopingPrefixEntryPrefix
					OCTET STRING,
				ndSnoopingPrefixEntryPrefixlen
					Integer32,
				ndSnoopingPrefixEntryValidLifetime
					Integer32,
				ndSnoopingPrefixEntryPreferredLifetime
					Integer32,
				ndSnoopingPrefixEntryVlan
					Integer32,
				ndSnoopingPrefixEntryInterface
					OCTET STRING
			 }

--          1.3.6.1.4.1.37950.1.1.5.10.24.4.1.1.1
-- 1.3.6.1.4.1.37950.1.1.5.10.28.4.1.1.1
-- 1.3.6.1.4.1.37950.1.1.5.10.28.4.1.1.1
-- 1.3.6.1.4.1.37950.1.1.5.10.28.4.1.1.1
-- 1.3.6.1.4.1.37950.1.1.5.10.28.4.1.1.1
-- 1.3.6.1.4.1.37950.1.1.5.10.28.4.1.1.1
-- 1.3.6.1.4.1.37950.1.1.5.10.28.4.1.1.1
-- 1.3.6.1.4.1.37950.1.1.5.10.28.4.1.1.1
-- 1.3.6.1.4.1.37950.1.1.5.10.28.4.1.1.1
		-- 1.3.6.1.4.1.37950.1.1.5.10.28.4.1.1.1
		ndSnoopingPrefixEntryID OBJECT-TYPE
			SYNTAX Integer32
			MAX-ACCESS read-only
			STATUS current
			DESCRIPTION
				"Description."
			::= { ndSnoopingPrefixEntryEntry 1 }

		
--          1.3.6.1.4.1.37950.1.1.5.10.24.4.1.1.2
-- 1.3.6.1.4.1.37950.1.1.5.10.28.4.1.1.2
-- 1.3.6.1.4.1.37950.1.1.5.10.28.4.1.1.2
-- 1.3.6.1.4.1.37950.1.1.5.10.28.4.1.1.2
-- 1.3.6.1.4.1.37950.1.1.5.10.28.4.1.1.2
-- 1.3.6.1.4.1.37950.1.1.5.10.28.4.1.1.2
-- 1.3.6.1.4.1.37950.1.1.5.10.28.4.1.1.2
-- 1.3.6.1.4.1.37950.1.1.5.10.28.4.1.1.2
-- 1.3.6.1.4.1.37950.1.1.5.10.28.4.1.1.2
		-- 1.3.6.1.4.1.37950.1.1.5.10.28.4.1.1.2
		ndSnoopingPrefixEntryPrefix OBJECT-TYPE
			SYNTAX OCTET STRING
			MAX-ACCESS read-only
			STATUS current
			DESCRIPTION
				"Description."
			::= { ndSnoopingPrefixEntryEntry 2 }

		
--          1.3.6.1.4.1.37950.1.1.5.10.24.4.1.1.3
-- 1.3.6.1.4.1.37950.1.1.5.10.28.4.1.1.3
-- 1.3.6.1.4.1.37950.1.1.5.10.28.4.1.1.3
-- 1.3.6.1.4.1.37950.1.1.5.10.28.4.1.1.3
-- 1.3.6.1.4.1.37950.1.1.5.10.28.4.1.1.3
-- 1.3.6.1.4.1.37950.1.1.5.10.28.4.1.1.3
-- 1.3.6.1.4.1.37950.1.1.5.10.28.4.1.1.3
-- 1.3.6.1.4.1.37950.1.1.5.10.28.4.1.1.3
-- 1.3.6.1.4.1.37950.1.1.5.10.28.4.1.1.3
		-- 1.3.6.1.4.1.37950.1.1.5.10.28.4.1.1.3
		ndSnoopingPrefixEntryPrefixlen OBJECT-TYPE
			SYNTAX Integer32
			MAX-ACCESS read-only
			STATUS current
			DESCRIPTION
				"Description."
			::= { ndSnoopingPrefixEntryEntry 3 }

		
--          1.3.6.1.4.1.37950.1.1.5.10.24.4.1.1.4
-- 1.3.6.1.4.1.37950.1.1.5.10.28.4.1.1.4
-- 1.3.6.1.4.1.37950.1.1.5.10.28.4.1.1.4
-- 1.3.6.1.4.1.37950.1.1.5.10.28.4.1.1.4
-- 1.3.6.1.4.1.37950.1.1.5.10.28.4.1.1.4
-- 1.3.6.1.4.1.37950.1.1.5.10.28.4.1.1.4
-- 1.3.6.1.4.1.37950.1.1.5.10.28.4.1.1.4
-- 1.3.6.1.4.1.37950.1.1.5.10.28.4.1.1.4
-- 1.3.6.1.4.1.37950.1.1.5.10.28.4.1.1.4
		-- 1.3.6.1.4.1.37950.1.1.5.10.28.4.1.1.4
		ndSnoopingPrefixEntryValidLifetime OBJECT-TYPE
			SYNTAX Integer32
			MAX-ACCESS read-only
			STATUS current
			DESCRIPTION
				"Description."
			::= { ndSnoopingPrefixEntryEntry 4 }

		
--          1.3.6.1.4.1.37950.1.1.5.10.24.4.1.1.5
-- 1.3.6.1.4.1.37950.1.1.5.10.28.4.1.1.5
-- 1.3.6.1.4.1.37950.1.1.5.10.28.4.1.1.5
-- 1.3.6.1.4.1.37950.1.1.5.10.28.4.1.1.5
-- 1.3.6.1.4.1.37950.1.1.5.10.28.4.1.1.5
-- 1.3.6.1.4.1.37950.1.1.5.10.28.4.1.1.5
-- 1.3.6.1.4.1.37950.1.1.5.10.28.4.1.1.5
-- 1.3.6.1.4.1.37950.1.1.5.10.28.4.1.1.5
-- 1.3.6.1.4.1.37950.1.1.5.10.28.4.1.1.5
		-- 1.3.6.1.4.1.37950.1.1.5.10.28.4.1.1.5
		ndSnoopingPrefixEntryPreferredLifetime OBJECT-TYPE
			SYNTAX Integer32
			MAX-ACCESS read-only
			STATUS current
			DESCRIPTION
				"Description."
			::= { ndSnoopingPrefixEntryEntry 5 }

		
--          1.3.6.1.4.1.37950.1.1.5.10.24.4.1.1.6
-- 1.3.6.1.4.1.37950.1.1.5.10.28.4.1.1.6
-- 1.3.6.1.4.1.37950.1.1.5.10.28.4.1.1.6
-- 1.3.6.1.4.1.37950.1.1.5.10.28.4.1.1.6
-- 1.3.6.1.4.1.37950.1.1.5.10.28.4.1.1.6
-- 1.3.6.1.4.1.37950.1.1.5.10.28.4.1.1.6
-- 1.3.6.1.4.1.37950.1.1.5.10.28.4.1.1.6
-- 1.3.6.1.4.1.37950.1.1.5.10.28.4.1.1.6
-- 1.3.6.1.4.1.37950.1.1.5.10.28.4.1.1.6
		-- 1.3.6.1.4.1.37950.1.1.5.10.28.4.1.1.6
		ndSnoopingPrefixEntryVlan OBJECT-TYPE
			SYNTAX Integer32
			MAX-ACCESS read-only
			STATUS current
			DESCRIPTION
				"Description."
			::= { ndSnoopingPrefixEntryEntry 6 }

		
--          1.3.6.1.4.1.37950.1.1.5.10.24.4.1.1.7
-- 1.3.6.1.4.1.37950.1.1.5.10.28.4.1.1.7
-- 1.3.6.1.4.1.37950.1.1.5.10.28.4.1.1.7
-- 1.3.6.1.4.1.37950.1.1.5.10.28.4.1.1.7
-- 1.3.6.1.4.1.37950.1.1.5.10.28.4.1.1.7
-- 1.3.6.1.4.1.37950.1.1.5.10.28.4.1.1.7
-- 1.3.6.1.4.1.37950.1.1.5.10.28.4.1.1.7
-- 1.3.6.1.4.1.37950.1.1.5.10.28.4.1.1.7
-- 1.3.6.1.4.1.37950.1.1.5.10.28.4.1.1.7
		-- 1.3.6.1.4.1.37950.1.1.5.10.28.4.1.1.7
		ndSnoopingPrefixEntryInterface OBJECT-TYPE
			SYNTAX OCTET STRING
			MAX-ACCESS read-only
			STATUS current
			DESCRIPTION
				"Description."
			::= { ndSnoopingPrefixEntryEntry 7 }

		
--          1.3.6.1.4.1.37950.1.1.5.10.24.4.2
-- 1.3.6.1.4.1.37950.1.1.5.10.28.4.2
-- 1.3.6.1.4.1.37950.1.1.5.10.28.4.2
-- 1.3.6.1.4.1.37950.1.1.5.10.28.4.2
-- 1.3.6.1.4.1.37950.1.1.5.10.28.4.2
-- 1.3.6.1.4.1.37950.1.1.5.10.28.4.2
-- 1.3.6.1.4.1.37950.1.1.5.10.28.4.2
-- 1.3.6.1.4.1.37950.1.1.5.10.28.4.2
-- 1.3.6.1.4.1.37950.1.1.5.10.28.4.2
		-- 1.3.6.1.4.1.37950.1.1.5.10.28.4.2
		ndSnoopingBindingEntryTable OBJECT-TYPE
			SYNTAX SEQUENCE OF NdSnoopingBindingEntryEntry
			MAX-ACCESS not-accessible
			STATUS current
			DESCRIPTION
				"Description."
			::= { ndSnoopingEntry 2 }

		
--          1.3.6.1.4.1.37950.1.1.5.10.24.4.2.1
-- 1.3.6.1.4.1.37950.1.1.5.10.28.4.2.1
-- 1.3.6.1.4.1.37950.1.1.5.10.28.4.2.1
-- 1.3.6.1.4.1.37950.1.1.5.10.28.4.2.1
-- 1.3.6.1.4.1.37950.1.1.5.10.28.4.2.1
-- 1.3.6.1.4.1.37950.1.1.5.10.28.4.2.1
-- 1.3.6.1.4.1.37950.1.1.5.10.28.4.2.1
-- 1.3.6.1.4.1.37950.1.1.5.10.28.4.2.1
-- 1.3.6.1.4.1.37950.1.1.5.10.28.4.2.1
		-- 1.3.6.1.4.1.37950.1.1.5.10.28.4.2.1
		ndSnoopingBindingEntryEntry OBJECT-TYPE
			SYNTAX NdSnoopingBindingEntryEntry
			MAX-ACCESS not-accessible
			STATUS current
			DESCRIPTION
				"Description."
			INDEX { ndSnoopingBindingEntryID }
			::= { ndSnoopingBindingEntryTable 1 }

		
		NdSnoopingBindingEntryEntry ::=
			SEQUENCE { 
				ndSnoopingBindingEntryID
					Integer32,
				ndSnoopingBindingEntryMac
					OCTET STRING,
				ndSnoopingBindingEntryIPv6
					OCTET STRING,
				ndSnoopingBindingEntryVlan
					Integer32,
				ndSnoopingBindingEntryInterface
					OCTET STRING
			 }

--          1.3.6.1.4.1.37950.1.1.5.10.24.4.2.1.1
-- 1.3.6.1.4.1.37950.1.1.5.10.28.4.2.1.1
-- 1.3.6.1.4.1.37950.1.1.5.10.28.4.2.1.1
-- 1.3.6.1.4.1.37950.1.1.5.10.28.4.2.1.1
-- 1.3.6.1.4.1.37950.1.1.5.10.28.4.2.1.1
-- 1.3.6.1.4.1.37950.1.1.5.10.28.4.2.1.1
-- 1.3.6.1.4.1.37950.1.1.5.10.28.4.2.1.1
-- 1.3.6.1.4.1.37950.1.1.5.10.28.4.2.1.1
-- 1.3.6.1.4.1.37950.1.1.5.10.28.4.2.1.1
		-- 1.3.6.1.4.1.37950.1.1.5.10.28.4.2.1.1
		ndSnoopingBindingEntryID OBJECT-TYPE
			SYNTAX Integer32
			MAX-ACCESS read-only
			STATUS current
			DESCRIPTION
				"Description."
			::= { ndSnoopingBindingEntryEntry 1 }

		
--          1.3.6.1.4.1.37950.1.1.5.10.24.4.2.1.2
-- 1.3.6.1.4.1.37950.1.1.5.10.28.4.2.1.2
-- 1.3.6.1.4.1.37950.1.1.5.10.28.4.2.1.2
-- 1.3.6.1.4.1.37950.1.1.5.10.28.4.2.1.2
-- 1.3.6.1.4.1.37950.1.1.5.10.28.4.2.1.2
-- 1.3.6.1.4.1.37950.1.1.5.10.28.4.2.1.2
-- 1.3.6.1.4.1.37950.1.1.5.10.28.4.2.1.2
-- 1.3.6.1.4.1.37950.1.1.5.10.28.4.2.1.2
-- 1.3.6.1.4.1.37950.1.1.5.10.28.4.2.1.2
		-- 1.3.6.1.4.1.37950.1.1.5.10.28.4.2.1.2
		ndSnoopingBindingEntryMac OBJECT-TYPE
			SYNTAX OCTET STRING
			MAX-ACCESS read-only
			STATUS current
			DESCRIPTION
				"Description."
			::= { ndSnoopingBindingEntryEntry 2 }

		
--          1.3.6.1.4.1.37950.1.1.5.10.24.4.2.1.3
-- 1.3.6.1.4.1.37950.1.1.5.10.28.4.2.1.3
-- 1.3.6.1.4.1.37950.1.1.5.10.28.4.2.1.3
-- 1.3.6.1.4.1.37950.1.1.5.10.28.4.2.1.3
-- 1.3.6.1.4.1.37950.1.1.5.10.28.4.2.1.3
-- 1.3.6.1.4.1.37950.1.1.5.10.28.4.2.1.3
-- 1.3.6.1.4.1.37950.1.1.5.10.28.4.2.1.3
-- 1.3.6.1.4.1.37950.1.1.5.10.28.4.2.1.3
-- 1.3.6.1.4.1.37950.1.1.5.10.28.4.2.1.3
		-- 1.3.6.1.4.1.37950.1.1.5.10.28.4.2.1.3
		ndSnoopingBindingEntryIPv6 OBJECT-TYPE
			SYNTAX OCTET STRING
			MAX-ACCESS read-only
			STATUS current
			DESCRIPTION
				"Description."
			::= { ndSnoopingBindingEntryEntry 3 }

		
--          1.3.6.1.4.1.37950.1.1.5.10.24.4.2.1.4
-- 1.3.6.1.4.1.37950.1.1.5.10.28.4.2.1.4
-- 1.3.6.1.4.1.37950.1.1.5.10.28.4.2.1.4
-- 1.3.6.1.4.1.37950.1.1.5.10.28.4.2.1.4
-- 1.3.6.1.4.1.37950.1.1.5.10.28.4.2.1.4
-- 1.3.6.1.4.1.37950.1.1.5.10.28.4.2.1.4
-- 1.3.6.1.4.1.37950.1.1.5.10.28.4.2.1.4
-- 1.3.6.1.4.1.37950.1.1.5.10.28.4.2.1.4
-- 1.3.6.1.4.1.37950.1.1.5.10.28.4.2.1.4
		-- 1.3.6.1.4.1.37950.1.1.5.10.28.4.2.1.4
		ndSnoopingBindingEntryVlan OBJECT-TYPE
			SYNTAX Integer32
			MAX-ACCESS read-only
			STATUS current
			DESCRIPTION
				"Description."
			::= { ndSnoopingBindingEntryEntry 4 }

		
--          1.3.6.1.4.1.37950.1.1.5.10.24.4.2.1.5
-- 1.3.6.1.4.1.37950.1.1.5.10.28.4.2.1.5
-- 1.3.6.1.4.1.37950.1.1.5.10.28.4.2.1.5
-- 1.3.6.1.4.1.37950.1.1.5.10.28.4.2.1.5
-- 1.3.6.1.4.1.37950.1.1.5.10.28.4.2.1.5
-- 1.3.6.1.4.1.37950.1.1.5.10.28.4.2.1.5
-- 1.3.6.1.4.1.37950.1.1.5.10.28.4.2.1.5
-- 1.3.6.1.4.1.37950.1.1.5.10.28.4.2.1.5
-- 1.3.6.1.4.1.37950.1.1.5.10.28.4.2.1.5
		-- 1.3.6.1.4.1.37950.1.1.5.10.28.4.2.1.5
		ndSnoopingBindingEntryInterface OBJECT-TYPE
			SYNTAX OCTET STRING
			MAX-ACCESS read-only
			STATUS current
			DESCRIPTION
				"Description."
			::= { ndSnoopingBindingEntryEntry 5 }

		
--          1.3.6.1.4.1.37950.1.1.5.10.29
-- 1.3.6.1.4.1.37950.1.1.5.10.29
-- 1.3.6.1.4.1.37950.1.1.5.10.29
-- 1.3.6.1.4.1.37950.1.1.5.10.29
-- 1.3.6.1.4.1.37950.1.1.5.10.29
-- 1.3.6.1.4.1.37950.1.1.5.10.29
-- 1.3.6.1.4.1.37950.1.1.5.10.29
-- 1.3.6.1.4.1.37950.1.1.5.10.29
-- 1.3.6.1.4.1.37950.1.1.5.10.29
		-- 1.3.6.1.4.1.37950.1.1.5.10.29
		v1600dDot1x OBJECT IDENTIFIER ::= { v1600dSwitch 29 }

		
--          1.3.6.1.4.1.37950.1.1.5.10.29.1
-- 1.3.6.1.4.1.37950.1.1.5.10.29.1
-- 1.3.6.1.4.1.37950.1.1.5.10.29.1
-- 1.3.6.1.4.1.37950.1.1.5.10.29.1
-- 1.3.6.1.4.1.37950.1.1.5.10.29.1
-- 1.3.6.1.4.1.37950.1.1.5.10.29.1
-- 1.3.6.1.4.1.37950.1.1.5.10.29.1
-- 1.3.6.1.4.1.37950.1.1.5.10.29.1
-- 1.3.6.1.4.1.37950.1.1.5.10.29.1
		-- 1.3.6.1.4.1.37950.1.1.5.10.29.1
		dot1xGlobalEn OBJECT-TYPE
			SYNTAX INTEGER
				{
				disable(0),
				enable(1)
				}
			MAX-ACCESS read-write
			STATUS current
			DESCRIPTION
				"Description."
			::= { v1600dDot1x 1 }

		
--          1.3.6.1.4.1.37950.1.1.5.10.29.2
-- 1.3.6.1.4.1.37950.1.1.5.10.29.2
-- 1.3.6.1.4.1.37950.1.1.5.10.29.2
-- 1.3.6.1.4.1.37950.1.1.5.10.29.2
-- 1.3.6.1.4.1.37950.1.1.5.10.29.2
-- 1.3.6.1.4.1.37950.1.1.5.10.29.2
-- 1.3.6.1.4.1.37950.1.1.5.10.29.2
-- 1.3.6.1.4.1.37950.1.1.5.10.29.2
-- 1.3.6.1.4.1.37950.1.1.5.10.29.2
		-- 1.3.6.1.4.1.37950.1.1.5.10.29.2
		dot1xPortEn OBJECT IDENTIFIER ::= { v1600dDot1x 2 }

		
--          1.3.6.1.4.1.37950.1.1.5.10.29.2.1
-- 1.3.6.1.4.1.37950.1.1.5.10.29.2.1
-- 1.3.6.1.4.1.37950.1.1.5.10.29.2.1
-- 1.3.6.1.4.1.37950.1.1.5.10.29.2.1
-- 1.3.6.1.4.1.37950.1.1.5.10.29.2.1
-- 1.3.6.1.4.1.37950.1.1.5.10.29.2.1
-- 1.3.6.1.4.1.37950.1.1.5.10.29.2.1
-- 1.3.6.1.4.1.37950.1.1.5.10.29.2.1
-- 1.3.6.1.4.1.37950.1.1.5.10.29.2.1
		-- 1.3.6.1.4.1.37950.1.1.5.10.29.2.1
		dot1xPortId OBJECT-TYPE
			SYNTAX Integer32 (1..28)
			MAX-ACCESS read-write
			STATUS current
			DESCRIPTION
				"Description."
			::= { dot1xPortEn 1 }

		
--          1.3.6.1.4.1.37950.1.1.5.10.29.2.2
-- 1.3.6.1.4.1.37950.1.1.5.10.29.2.2
-- 1.3.6.1.4.1.37950.1.1.5.10.29.2.2
-- 1.3.6.1.4.1.37950.1.1.5.10.29.2.2
-- 1.3.6.1.4.1.37950.1.1.5.10.29.2.2
-- 1.3.6.1.4.1.37950.1.1.5.10.29.2.2
-- 1.3.6.1.4.1.37950.1.1.5.10.29.2.2
-- 1.3.6.1.4.1.37950.1.1.5.10.29.2.2
-- 1.3.6.1.4.1.37950.1.1.5.10.29.2.2
		-- 1.3.6.1.4.1.37950.1.1.5.10.29.2.2
		dot1xPortAction OBJECT-TYPE
			SYNTAX INTEGER
				{
				disable(0),
				enable(1)
				}
			MAX-ACCESS read-write
			STATUS current
			DESCRIPTION
				"Description."
			::= { dot1xPortEn 2 }

		
--          1.3.6.1.4.1.37950.1.1.5.10.29.3
-- 1.3.6.1.4.1.37950.1.1.5.10.29.3
-- 1.3.6.1.4.1.37950.1.1.5.10.29.3
-- 1.3.6.1.4.1.37950.1.1.5.10.29.3
-- 1.3.6.1.4.1.37950.1.1.5.10.29.3
-- 1.3.6.1.4.1.37950.1.1.5.10.29.3
-- 1.3.6.1.4.1.37950.1.1.5.10.29.3
-- 1.3.6.1.4.1.37950.1.1.5.10.29.3
-- 1.3.6.1.4.1.37950.1.1.5.10.29.3
		-- 1.3.6.1.4.1.37950.1.1.5.10.29.3
		dot1xPortConfigTable OBJECT-TYPE
			SYNTAX SEQUENCE OF Dot1xPortConfigEntry
			MAX-ACCESS not-accessible
			STATUS current
			DESCRIPTION
				"Description."
			::= { v1600dDot1x 3 }

		
--          1.3.6.1.4.1.37950.1.1.5.10.29.3.1
-- 1.3.6.1.4.1.37950.1.1.5.10.29.3.1
-- 1.3.6.1.4.1.37950.1.1.5.10.29.3.1
-- 1.3.6.1.4.1.37950.1.1.5.10.29.3.1
-- 1.3.6.1.4.1.37950.1.1.5.10.29.3.1
-- 1.3.6.1.4.1.37950.1.1.5.10.29.3.1
-- 1.3.6.1.4.1.37950.1.1.5.10.29.3.1
-- 1.3.6.1.4.1.37950.1.1.5.10.29.3.1
-- 1.3.6.1.4.1.37950.1.1.5.10.29.3.1
		-- 1.3.6.1.4.1.37950.1.1.5.10.29.3.1
		dot1xPortConfigEntry OBJECT-TYPE
			SYNTAX Dot1xPortConfigEntry
			MAX-ACCESS not-accessible
			STATUS current
			DESCRIPTION
				"Description."
			INDEX { dot1xPort }
			::= { dot1xPortConfigTable 1 }

		
		Dot1xPortConfigEntry ::=
			SEQUENCE { 
				dot1xPort
					Integer32,
				dot1xAuthenType
					INTEGER,
				dot1xPortControl
					INTEGER,
				dot1xMethodType
					INTEGER,
				dot1xMaxUser
					Integer32,
				dot1xGuestVlan
					Integer32,
				dot1xAuthFailVlan
					Integer32,
				dot1xTxTimer
					Integer32,
				dot1xSuppTimer
					Integer32,
				dot1xHandshakeEnable
					INTEGER,
				dot1xHandshakeTimer
					Integer32
			 }

--          1.3.6.1.4.1.37950.1.1.5.10.29.3.1.1
-- 1.3.6.1.4.1.37950.1.1.5.10.29.3.1.1
-- 1.3.6.1.4.1.37950.1.1.5.10.29.3.1.1
-- 1.3.6.1.4.1.37950.1.1.5.10.29.3.1.1
-- 1.3.6.1.4.1.37950.1.1.5.10.29.3.1.1
-- 1.3.6.1.4.1.37950.1.1.5.10.29.3.1.1
-- 1.3.6.1.4.1.37950.1.1.5.10.29.3.1.1
-- 1.3.6.1.4.1.37950.1.1.5.10.29.3.1.1
-- 1.3.6.1.4.1.37950.1.1.5.10.29.3.1.1
		-- 1.3.6.1.4.1.37950.1.1.5.10.29.3.1.1
		dot1xPort OBJECT-TYPE
			SYNTAX Integer32 (1..28)
			MAX-ACCESS read-only
			STATUS current
			DESCRIPTION
				"Description."
			::= { dot1xPortConfigEntry 1 }

		
--          1.3.6.1.4.1.37950.1.1.5.10.29.3.1.2
-- 1.3.6.1.4.1.37950.1.1.5.10.29.3.1.2
-- 1.3.6.1.4.1.37950.1.1.5.10.29.3.1.2
-- 1.3.6.1.4.1.37950.1.1.5.10.29.3.1.2
-- 1.3.6.1.4.1.37950.1.1.5.10.29.3.1.2
-- 1.3.6.1.4.1.37950.1.1.5.10.29.3.1.2
-- 1.3.6.1.4.1.37950.1.1.5.10.29.3.1.2
-- 1.3.6.1.4.1.37950.1.1.5.10.29.3.1.2
-- 1.3.6.1.4.1.37950.1.1.5.10.29.3.1.2
		-- 1.3.6.1.4.1.37950.1.1.5.10.29.3.1.2
		dot1xAuthenType OBJECT-TYPE
			SYNTAX INTEGER
				{
				chap(1),
				pap(2),
				eap(3)
				}
			MAX-ACCESS read-write
			STATUS current
			DESCRIPTION
				"Description."
			::= { dot1xPortConfigEntry 2 }

		
--          1.3.6.1.4.1.37950.1.1.5.10.29.3.1.3
-- 1.3.6.1.4.1.37950.1.1.5.10.29.3.1.3
-- 1.3.6.1.4.1.37950.1.1.5.10.29.3.1.3
-- 1.3.6.1.4.1.37950.1.1.5.10.29.3.1.3
-- 1.3.6.1.4.1.37950.1.1.5.10.29.3.1.3
-- 1.3.6.1.4.1.37950.1.1.5.10.29.3.1.3
-- 1.3.6.1.4.1.37950.1.1.5.10.29.3.1.3
-- 1.3.6.1.4.1.37950.1.1.5.10.29.3.1.3
-- 1.3.6.1.4.1.37950.1.1.5.10.29.3.1.3
		-- 1.3.6.1.4.1.37950.1.1.5.10.29.3.1.3
		dot1xPortControl OBJECT-TYPE
			SYNTAX INTEGER
				{
				auto(0),
				authorized-force(1),
				unauthorized-force(2)
				}
			MAX-ACCESS read-write
			STATUS current
			DESCRIPTION
				"Description."
			::= { dot1xPortConfigEntry 3 }

		
--          1.3.6.1.4.1.37950.1.1.5.10.29.3.1.4
-- 1.3.6.1.4.1.37950.1.1.5.10.29.3.1.4
-- 1.3.6.1.4.1.37950.1.1.5.10.29.3.1.4
-- 1.3.6.1.4.1.37950.1.1.5.10.29.3.1.4
-- 1.3.6.1.4.1.37950.1.1.5.10.29.3.1.4
-- 1.3.6.1.4.1.37950.1.1.5.10.29.3.1.4
-- 1.3.6.1.4.1.37950.1.1.5.10.29.3.1.4
-- 1.3.6.1.4.1.37950.1.1.5.10.29.3.1.4
-- 1.3.6.1.4.1.37950.1.1.5.10.29.3.1.4
		-- 1.3.6.1.4.1.37950.1.1.5.10.29.3.1.4
		dot1xMethodType OBJECT-TYPE
			SYNTAX INTEGER
				{
				macbased(1),
				portbased(2)
				}
			MAX-ACCESS read-write
			STATUS current
			DESCRIPTION
				"Description."
			::= { dot1xPortConfigEntry 4 }

		
--          1.3.6.1.4.1.37950.1.1.5.10.29.3.1.5
-- 1.3.6.1.4.1.37950.1.1.5.10.29.3.1.5
-- 1.3.6.1.4.1.37950.1.1.5.10.29.3.1.5
-- 1.3.6.1.4.1.37950.1.1.5.10.29.3.1.5
-- 1.3.6.1.4.1.37950.1.1.5.10.29.3.1.5
-- 1.3.6.1.4.1.37950.1.1.5.10.29.3.1.5
-- 1.3.6.1.4.1.37950.1.1.5.10.29.3.1.5
-- 1.3.6.1.4.1.37950.1.1.5.10.29.3.1.5
-- 1.3.6.1.4.1.37950.1.1.5.10.29.3.1.5
		-- 1.3.6.1.4.1.37950.1.1.5.10.29.3.1.5
		dot1xMaxUser OBJECT-TYPE
			SYNTAX Integer32 (1..256)
			MAX-ACCESS read-write
			STATUS current
			DESCRIPTION
				"Description."
			::= { dot1xPortConfigEntry 5 }

		
--          1.3.6.1.4.1.37950.1.1.5.10.29.3.1.6
-- 1.3.6.1.4.1.37950.1.1.5.10.29.3.1.6
-- 1.3.6.1.4.1.37950.1.1.5.10.29.3.1.6
-- 1.3.6.1.4.1.37950.1.1.5.10.29.3.1.6
-- 1.3.6.1.4.1.37950.1.1.5.10.29.3.1.6
-- 1.3.6.1.4.1.37950.1.1.5.10.29.3.1.6
-- 1.3.6.1.4.1.37950.1.1.5.10.29.3.1.6
-- 1.3.6.1.4.1.37950.1.1.5.10.29.3.1.6
-- 1.3.6.1.4.1.37950.1.1.5.10.29.3.1.6
		-- 1.3.6.1.4.1.37950.1.1.5.10.29.3.1.6
		dot1xGuestVlan OBJECT-TYPE
			SYNTAX Integer32 (1..4094)
			MAX-ACCESS read-write
			STATUS current
			DESCRIPTION
				"Description."
			::= { dot1xPortConfigEntry 6 }

		
--          1.3.6.1.4.1.37950.1.1.5.10.29.3.1.7
-- 1.3.6.1.4.1.37950.1.1.5.10.29.3.1.7
-- 1.3.6.1.4.1.37950.1.1.5.10.29.3.1.7
-- 1.3.6.1.4.1.37950.1.1.5.10.29.3.1.7
-- 1.3.6.1.4.1.37950.1.1.5.10.29.3.1.7
-- 1.3.6.1.4.1.37950.1.1.5.10.29.3.1.7
-- 1.3.6.1.4.1.37950.1.1.5.10.29.3.1.7
-- 1.3.6.1.4.1.37950.1.1.5.10.29.3.1.7
-- 1.3.6.1.4.1.37950.1.1.5.10.29.3.1.7
		-- 1.3.6.1.4.1.37950.1.1.5.10.29.3.1.7
		dot1xAuthFailVlan OBJECT-TYPE
			SYNTAX Integer32 (1..4094)
			MAX-ACCESS read-write
			STATUS current
			DESCRIPTION
				"Description."
			::= { dot1xPortConfigEntry 7 }

		
--          1.3.6.1.4.1.37950.1.1.5.10.29.3.1.8
-- 1.3.6.1.4.1.37950.1.1.5.10.29.3.1.8
-- 1.3.6.1.4.1.37950.1.1.5.10.29.3.1.8
-- 1.3.6.1.4.1.37950.1.1.5.10.29.3.1.8
-- 1.3.6.1.4.1.37950.1.1.5.10.29.3.1.8
-- 1.3.6.1.4.1.37950.1.1.5.10.29.3.1.8
-- 1.3.6.1.4.1.37950.1.1.5.10.29.3.1.8
-- 1.3.6.1.4.1.37950.1.1.5.10.29.3.1.8
-- 1.3.6.1.4.1.37950.1.1.5.10.29.3.1.8
		-- 1.3.6.1.4.1.37950.1.1.5.10.29.3.1.8
		dot1xTxTimer OBJECT-TYPE
			SYNTAX Integer32 (10..120)
			MAX-ACCESS read-write
			STATUS current
			DESCRIPTION
				"Description."
			::= { dot1xPortConfigEntry 8 }

		
--          1.3.6.1.4.1.37950.1.1.5.10.29.3.1.9
-- 1.3.6.1.4.1.37950.1.1.5.10.29.3.1.9
-- 1.3.6.1.4.1.37950.1.1.5.10.29.3.1.9
-- 1.3.6.1.4.1.37950.1.1.5.10.29.3.1.9
-- 1.3.6.1.4.1.37950.1.1.5.10.29.3.1.9
-- 1.3.6.1.4.1.37950.1.1.5.10.29.3.1.9
-- 1.3.6.1.4.1.37950.1.1.5.10.29.3.1.9
-- 1.3.6.1.4.1.37950.1.1.5.10.29.3.1.9
-- 1.3.6.1.4.1.37950.1.1.5.10.29.3.1.9
		-- 1.3.6.1.4.1.37950.1.1.5.10.29.3.1.9
		dot1xSuppTimer OBJECT-TYPE
			SYNTAX Integer32 (10..120)
			MAX-ACCESS read-write
			STATUS current
			DESCRIPTION
				"Description."
			::= { dot1xPortConfigEntry 9 }

		
--          1.3.6.1.4.1.37950.1.1.5.10.29.3.1.10
-- 1.3.6.1.4.1.37950.1.1.5.10.29.3.1.10
-- 1.3.6.1.4.1.37950.1.1.5.10.29.3.1.10
-- 1.3.6.1.4.1.37950.1.1.5.10.29.3.1.10
-- 1.3.6.1.4.1.37950.1.1.5.10.29.3.1.10
-- 1.3.6.1.4.1.37950.1.1.5.10.29.3.1.10
-- 1.3.6.1.4.1.37950.1.1.5.10.29.3.1.10
-- 1.3.6.1.4.1.37950.1.1.5.10.29.3.1.10
-- 1.3.6.1.4.1.37950.1.1.5.10.29.3.1.10
		-- 1.3.6.1.4.1.37950.1.1.5.10.29.3.1.10
		dot1xHandshakeEnable OBJECT-TYPE
			SYNTAX INTEGER
				{
				disable(0),
				enable(1)
				}
			MAX-ACCESS read-write
			STATUS current
			DESCRIPTION
				"Description."
			::= { dot1xPortConfigEntry 10 }

		
--          1.3.6.1.4.1.37950.1.1.5.10.29.3.1.11
-- 1.3.6.1.4.1.37950.1.1.5.10.29.3.1.11
-- 1.3.6.1.4.1.37950.1.1.5.10.29.3.1.11
-- 1.3.6.1.4.1.37950.1.1.5.10.29.3.1.11
-- 1.3.6.1.4.1.37950.1.1.5.10.29.3.1.11
-- 1.3.6.1.4.1.37950.1.1.5.10.29.3.1.11
-- 1.3.6.1.4.1.37950.1.1.5.10.29.3.1.11
-- 1.3.6.1.4.1.37950.1.1.5.10.29.3.1.11
-- 1.3.6.1.4.1.37950.1.1.5.10.29.3.1.11
		-- 1.3.6.1.4.1.37950.1.1.5.10.29.3.1.11
		dot1xHandshakeTimer OBJECT-TYPE
			SYNTAX Integer32 (5..1024)
			MAX-ACCESS read-write
			STATUS current
			DESCRIPTION
				"Description."
			::= { dot1xPortConfigEntry 11 }

		
--          1.3.6.1.4.1.37950.1.1.5.10.29.4
-- 1.3.6.1.4.1.37950.1.1.5.10.29.4
-- 1.3.6.1.4.1.37950.1.1.5.10.29.4
-- 1.3.6.1.4.1.37950.1.1.5.10.29.4
-- 1.3.6.1.4.1.37950.1.1.5.10.29.4
-- 1.3.6.1.4.1.37950.1.1.5.10.29.4
-- 1.3.6.1.4.1.37950.1.1.5.10.29.4
-- 1.3.6.1.4.1.37950.1.1.5.10.29.4
-- 1.3.6.1.4.1.37950.1.1.5.10.29.4
		-- 1.3.6.1.4.1.37950.1.1.5.10.29.4
		radiusDot1xCfg OBJECT IDENTIFIER ::= { v1600dDot1x 4 }

		
--          1.3.6.1.4.1.37950.1.1.5.10.29.4.1
-- 1.3.6.1.4.1.37950.1.1.5.10.29.4.1
-- 1.3.6.1.4.1.37950.1.1.5.10.29.4.1
-- 1.3.6.1.4.1.37950.1.1.5.10.29.4.1
-- 1.3.6.1.4.1.37950.1.1.5.10.29.4.1
-- 1.3.6.1.4.1.37950.1.1.5.10.29.4.1
-- 1.3.6.1.4.1.37950.1.1.5.10.29.4.1
-- 1.3.6.1.4.1.37950.1.1.5.10.29.4.1
-- 1.3.6.1.4.1.37950.1.1.5.10.29.4.1
-- 1.3.6.1.4.1.37950.1.1.5.10.29.4.1
		-- 1.3.6.1.4.1.37950.1.1.5.10.29.4.1
		radDot1xAuthen1 OBJECT-TYPE
			SYNTAX INTEGER
				{
				enable(0),
				disable(1)
				}
			MAX-ACCESS read-write
			STATUS current
			DESCRIPTION
				"Description."
			DEFVAL { 1 }
			::= { radiusDot1xCfg 1 }

		
--          1.3.6.1.4.1.37950.1.1.5.10.29.4.2
-- 1.3.6.1.4.1.37950.1.1.5.10.29.4.2
-- 1.3.6.1.4.1.37950.1.1.5.10.29.4.2
-- 1.3.6.1.4.1.37950.1.1.5.10.29.4.2
-- 1.3.6.1.4.1.37950.1.1.5.10.29.4.2
-- 1.3.6.1.4.1.37950.1.1.5.10.29.4.2
-- 1.3.6.1.4.1.37950.1.1.5.10.29.4.2
-- 1.3.6.1.4.1.37950.1.1.5.10.29.4.2
-- 1.3.6.1.4.1.37950.1.1.5.10.29.4.2
-- 1.3.6.1.4.1.37950.1.1.5.10.29.4.2
		-- 1.3.6.1.4.1.37950.1.1.5.10.29.4.2
		radDot1xAuthenLocal1 OBJECT-TYPE
			SYNTAX INTEGER
				{
				enable(0),
				disable(1)
				}
			MAX-ACCESS read-write
			STATUS current
			DESCRIPTION
				"Description."
			DEFVAL { 1 }
			::= { radiusDot1xCfg 2 }

		
--          1.3.6.1.4.1.37950.1.1.5.10.29.4.3
-- 1.3.6.1.4.1.37950.1.1.5.10.29.4.3
-- 1.3.6.1.4.1.37950.1.1.5.10.29.4.3
-- 1.3.6.1.4.1.37950.1.1.5.10.29.4.3
-- 1.3.6.1.4.1.37950.1.1.5.10.29.4.3
-- 1.3.6.1.4.1.37950.1.1.5.10.29.4.3
-- 1.3.6.1.4.1.37950.1.1.5.10.29.4.3
-- 1.3.6.1.4.1.37950.1.1.5.10.29.4.3
-- 1.3.6.1.4.1.37950.1.1.5.10.29.4.3
-- 1.3.6.1.4.1.37950.1.1.5.10.29.4.3
		-- 1.3.6.1.4.1.37950.1.1.5.10.29.4.3
		radDot1xAuthor1 OBJECT-TYPE
			SYNTAX INTEGER
				{
				enable(0),
				disable(1)
				}
			MAX-ACCESS read-write
			STATUS current
			DESCRIPTION
				"Description."
			DEFVAL { 1 }
			::= { radiusDot1xCfg 3 }

		
--          1.3.6.1.4.1.37950.1.1.5.10.29.4.4
-- 1.3.6.1.4.1.37950.1.1.5.10.29.4.4
-- 1.3.6.1.4.1.37950.1.1.5.10.29.4.4
-- 1.3.6.1.4.1.37950.1.1.5.10.29.4.4
-- 1.3.6.1.4.1.37950.1.1.5.10.29.4.4
-- 1.3.6.1.4.1.37950.1.1.5.10.29.4.4
-- 1.3.6.1.4.1.37950.1.1.5.10.29.4.4
-- 1.3.6.1.4.1.37950.1.1.5.10.29.4.4
-- 1.3.6.1.4.1.37950.1.1.5.10.29.4.4
-- 1.3.6.1.4.1.37950.1.1.5.10.29.4.4
		-- 1.3.6.1.4.1.37950.1.1.5.10.29.4.4
		radDot1xAcct1 OBJECT-TYPE
			SYNTAX INTEGER
				{
				enable(0),
				disable(1)
				}
			MAX-ACCESS read-write
			STATUS current
			DESCRIPTION
				"Description."
			DEFVAL { 1 }
			::= { radiusDot1xCfg 4 }

		
--          1.3.6.1.4.1.37950.1.1.5.10.30
-- 1.3.6.1.4.1.37950.1.1.5.10.30
-- 1.3.6.1.4.1.37950.1.1.5.10.30
-- 1.3.6.1.4.1.37950.1.1.5.10.30
-- 1.3.6.1.4.1.37950.1.1.5.10.30
-- 1.3.6.1.4.1.37950.1.1.5.10.30
-- 1.3.6.1.4.1.37950.1.1.5.10.30
-- 1.3.6.1.4.1.37950.1.1.5.10.30
-- 1.3.6.1.4.1.37950.1.1.5.10.30
		-- 1.3.6.1.4.1.37950.1.1.5.10.30
		v1600dPim OBJECT IDENTIFIER ::= { v1600dSwitch 30 }

		
--          1.3.6.1.4.1.37950.1.1.5.10.30.1
-- 1.3.6.1.4.1.37950.1.1.5.10.30.1
-- 1.3.6.1.4.1.37950.1.1.5.10.30.1
-- 1.3.6.1.4.1.37950.1.1.5.10.30.1
-- 1.3.6.1.4.1.37950.1.1.5.10.30.1
-- 1.3.6.1.4.1.37950.1.1.5.10.30.1
-- 1.3.6.1.4.1.37950.1.1.5.10.30.1
-- 1.3.6.1.4.1.37950.1.1.5.10.30.1
-- 1.3.6.1.4.1.37950.1.1.5.10.30.1
		-- 1.3.6.1.4.1.37950.1.1.5.10.30.1
		pimMulticastRoutingEn OBJECT-TYPE
			SYNTAX INTEGER
				{
				disable(0),
				enable(1)
				}
			MAX-ACCESS read-write
			STATUS current
			DESCRIPTION
				"Description."
			::= { v1600dPim 1 }

		
--          1.3.6.1.4.1.37950.1.1.5.10.30.2
-- 1.3.6.1.4.1.37950.1.1.5.10.30.2
-- 1.3.6.1.4.1.37950.1.1.5.10.30.2
-- 1.3.6.1.4.1.37950.1.1.5.10.30.2
-- 1.3.6.1.4.1.37950.1.1.5.10.30.2
-- 1.3.6.1.4.1.37950.1.1.5.10.30.2
-- 1.3.6.1.4.1.37950.1.1.5.10.30.2
-- 1.3.6.1.4.1.37950.1.1.5.10.30.2
-- 1.3.6.1.4.1.37950.1.1.5.10.30.2
		-- 1.3.6.1.4.1.37950.1.1.5.10.30.2
		pimIgmpCfg OBJECT IDENTIFIER ::= { v1600dPim 2 }

		
--          1.3.6.1.4.1.37950.1.1.5.10.30.2.1
-- 1.3.6.1.4.1.37950.1.1.5.10.30.2.1
-- 1.3.6.1.4.1.37950.1.1.5.10.30.2.1
-- 1.3.6.1.4.1.37950.1.1.5.10.30.2.1
-- 1.3.6.1.4.1.37950.1.1.5.10.30.2.1
-- 1.3.6.1.4.1.37950.1.1.5.10.30.2.1
-- 1.3.6.1.4.1.37950.1.1.5.10.30.2.1
-- 1.3.6.1.4.1.37950.1.1.5.10.30.2.1
-- 1.3.6.1.4.1.37950.1.1.5.10.30.2.1
		-- 1.3.6.1.4.1.37950.1.1.5.10.30.2.1
		pimIgmpQueryInterval OBJECT-TYPE
			SYNTAX Integer32 (1..65535)
			MAX-ACCESS read-write
			STATUS current
			DESCRIPTION
				"Description."
			::= { pimIgmpCfg 1 }

		
--          1.3.6.1.4.1.37950.1.1.5.10.30.2.2
-- 1.3.6.1.4.1.37950.1.1.5.10.30.2.2
-- 1.3.6.1.4.1.37950.1.1.5.10.30.2.2
-- 1.3.6.1.4.1.37950.1.1.5.10.30.2.2
-- 1.3.6.1.4.1.37950.1.1.5.10.30.2.2
-- 1.3.6.1.4.1.37950.1.1.5.10.30.2.2
-- 1.3.6.1.4.1.37950.1.1.5.10.30.2.2
-- 1.3.6.1.4.1.37950.1.1.5.10.30.2.2
-- 1.3.6.1.4.1.37950.1.1.5.10.30.2.2
		-- 1.3.6.1.4.1.37950.1.1.5.10.30.2.2
		pimIgmpQueryMaxResTime OBJECT-TYPE
			SYNTAX Integer32 (1..25)
			MAX-ACCESS read-write
			STATUS current
			DESCRIPTION
				"Description."
			::= { pimIgmpCfg 2 }

		
--          1.3.6.1.4.1.37950.1.1.5.10.30.2.3
-- 1.3.6.1.4.1.37950.1.1.5.10.30.2.3
-- 1.3.6.1.4.1.37950.1.1.5.10.30.2.3
-- 1.3.6.1.4.1.37950.1.1.5.10.30.2.3
-- 1.3.6.1.4.1.37950.1.1.5.10.30.2.3
-- 1.3.6.1.4.1.37950.1.1.5.10.30.2.3
-- 1.3.6.1.4.1.37950.1.1.5.10.30.2.3
-- 1.3.6.1.4.1.37950.1.1.5.10.30.2.3
-- 1.3.6.1.4.1.37950.1.1.5.10.30.2.3
		-- 1.3.6.1.4.1.37950.1.1.5.10.30.2.3
		pimIgmpQuerierTimeout OBJECT-TYPE
			SYNTAX Integer32 (60..300)
			MAX-ACCESS read-write
			STATUS current
			DESCRIPTION
				"Description."
			::= { pimIgmpCfg 3 }

		
--          1.3.6.1.4.1.37950.1.1.5.10.30.2.4
-- 1.3.6.1.4.1.37950.1.1.5.10.30.2.4
-- 1.3.6.1.4.1.37950.1.1.5.10.30.2.4
-- 1.3.6.1.4.1.37950.1.1.5.10.30.2.4
-- 1.3.6.1.4.1.37950.1.1.5.10.30.2.4
-- 1.3.6.1.4.1.37950.1.1.5.10.30.2.4
-- 1.3.6.1.4.1.37950.1.1.5.10.30.2.4
-- 1.3.6.1.4.1.37950.1.1.5.10.30.2.4
-- 1.3.6.1.4.1.37950.1.1.5.10.30.2.4
		-- 1.3.6.1.4.1.37950.1.1.5.10.30.2.4
		pmIgmpLastMenberInterval OBJECT-TYPE
			SYNTAX Integer32 (1..65)
			MAX-ACCESS read-write
			STATUS current
			DESCRIPTION
				"Description."
			::= { pimIgmpCfg 4 }

		
--          1.3.6.1.4.1.37950.1.1.5.10.30.2.5
-- 1.3.6.1.4.1.37950.1.1.5.10.30.2.5
-- 1.3.6.1.4.1.37950.1.1.5.10.30.2.5
-- 1.3.6.1.4.1.37950.1.1.5.10.30.2.5
-- 1.3.6.1.4.1.37950.1.1.5.10.30.2.5
-- 1.3.6.1.4.1.37950.1.1.5.10.30.2.5
-- 1.3.6.1.4.1.37950.1.1.5.10.30.2.5
-- 1.3.6.1.4.1.37950.1.1.5.10.30.2.5
-- 1.3.6.1.4.1.37950.1.1.5.10.30.2.5
		-- 1.3.6.1.4.1.37950.1.1.5.10.30.2.5
		pimIgmpRobustness OBJECT-TYPE
			SYNTAX Integer32 (1..5)
			MAX-ACCESS read-write
			STATUS current
			DESCRIPTION
				"Description."
			::= { pimIgmpCfg 5 }

		
--          1.3.6.1.4.1.37950.1.1.5.10.30.3
-- 1.3.6.1.4.1.37950.1.1.5.10.30.3
-- 1.3.6.1.4.1.37950.1.1.5.10.30.3
-- 1.3.6.1.4.1.37950.1.1.5.10.30.3
-- 1.3.6.1.4.1.37950.1.1.5.10.30.3
-- 1.3.6.1.4.1.37950.1.1.5.10.30.3
-- 1.3.6.1.4.1.37950.1.1.5.10.30.3
-- 1.3.6.1.4.1.37950.1.1.5.10.30.3
-- 1.3.6.1.4.1.37950.1.1.5.10.30.3
		-- 1.3.6.1.4.1.37950.1.1.5.10.30.3
		pimIgmpGroupCfg OBJECT IDENTIFIER ::= { v1600dPim 3 }

		
--          1.3.6.1.4.1.37950.1.1.5.10.30.3.1
-- 1.3.6.1.4.1.37950.1.1.5.10.30.3.1
-- 1.3.6.1.4.1.37950.1.1.5.10.30.3.1
-- 1.3.6.1.4.1.37950.1.1.5.10.30.3.1
-- 1.3.6.1.4.1.37950.1.1.5.10.30.3.1
-- 1.3.6.1.4.1.37950.1.1.5.10.30.3.1
-- 1.3.6.1.4.1.37950.1.1.5.10.30.3.1
-- 1.3.6.1.4.1.37950.1.1.5.10.30.3.1
-- 1.3.6.1.4.1.37950.1.1.5.10.30.3.1
		-- 1.3.6.1.4.1.37950.1.1.5.10.30.3.1
		igmpInterface OBJECT-TYPE
			SYNTAX Integer32 (1..4094)
			MAX-ACCESS read-write
			STATUS current
			DESCRIPTION
				"Description."
			::= { pimIgmpGroupCfg 1 }

		
--          1.3.6.1.4.1.37950.1.1.5.10.30.3.2
-- 1.3.6.1.4.1.37950.1.1.5.10.30.3.2
-- 1.3.6.1.4.1.37950.1.1.5.10.30.3.2
-- 1.3.6.1.4.1.37950.1.1.5.10.30.3.2
-- 1.3.6.1.4.1.37950.1.1.5.10.30.3.2
-- 1.3.6.1.4.1.37950.1.1.5.10.30.3.2
-- 1.3.6.1.4.1.37950.1.1.5.10.30.3.2
-- 1.3.6.1.4.1.37950.1.1.5.10.30.3.2
-- 1.3.6.1.4.1.37950.1.1.5.10.30.3.2
		-- 1.3.6.1.4.1.37950.1.1.5.10.30.3.2
		igmpGroupAddress OBJECT-TYPE
			SYNTAX IpAddress
			MAX-ACCESS read-write
			STATUS current
			DESCRIPTION
				"Description."
			::= { pimIgmpGroupCfg 2 }

		
--          1.3.6.1.4.1.37950.1.1.5.10.30.3.3
-- 1.3.6.1.4.1.37950.1.1.5.10.30.3.3
-- 1.3.6.1.4.1.37950.1.1.5.10.30.3.3
-- 1.3.6.1.4.1.37950.1.1.5.10.30.3.3
-- 1.3.6.1.4.1.37950.1.1.5.10.30.3.3
-- 1.3.6.1.4.1.37950.1.1.5.10.30.3.3
-- 1.3.6.1.4.1.37950.1.1.5.10.30.3.3
-- 1.3.6.1.4.1.37950.1.1.5.10.30.3.3
-- 1.3.6.1.4.1.37950.1.1.5.10.30.3.3
		-- 1.3.6.1.4.1.37950.1.1.5.10.30.3.3
		igmpAddressMode OBJECT-TYPE
			SYNTAX INTEGER
				{
				static(1),
				dynamic(2)
				}
			MAX-ACCESS read-write
			STATUS current
			DESCRIPTION
				"Description."
			::= { pimIgmpGroupCfg 3 }

		
--          1.3.6.1.4.1.37950.1.1.5.10.30.3.4
-- 1.3.6.1.4.1.37950.1.1.5.10.30.3.4
-- 1.3.6.1.4.1.37950.1.1.5.10.30.3.4
-- 1.3.6.1.4.1.37950.1.1.5.10.30.3.4
-- 1.3.6.1.4.1.37950.1.1.5.10.30.3.4
-- 1.3.6.1.4.1.37950.1.1.5.10.30.3.4
-- 1.3.6.1.4.1.37950.1.1.5.10.30.3.4
-- 1.3.6.1.4.1.37950.1.1.5.10.30.3.4
-- 1.3.6.1.4.1.37950.1.1.5.10.30.3.4
		-- 1.3.6.1.4.1.37950.1.1.5.10.30.3.4
		pimIgmpAction OBJECT-TYPE
			SYNTAX INTEGER
				{
				del(0),
				add(1)
				}
			MAX-ACCESS read-write
			STATUS current
			DESCRIPTION
				"Description."
			::= { pimIgmpGroupCfg 4 }

		
--          1.3.6.1.4.1.37950.1.1.5.10.30.4
-- 1.3.6.1.4.1.37950.1.1.5.10.30.4
-- 1.3.6.1.4.1.37950.1.1.5.10.30.4
-- 1.3.6.1.4.1.37950.1.1.5.10.30.4
-- 1.3.6.1.4.1.37950.1.1.5.10.30.4
-- 1.3.6.1.4.1.37950.1.1.5.10.30.4
-- 1.3.6.1.4.1.37950.1.1.5.10.30.4
-- 1.3.6.1.4.1.37950.1.1.5.10.30.4
-- 1.3.6.1.4.1.37950.1.1.5.10.30.4
		-- 1.3.6.1.4.1.37950.1.1.5.10.30.4
		pimGlobalCfg OBJECT IDENTIFIER ::= { v1600dPim 4 }

		
--          1.3.6.1.4.1.37950.1.1.5.10.30.4.1
-- 1.3.6.1.4.1.37950.1.1.5.10.30.4.1
-- 1.3.6.1.4.1.37950.1.1.5.10.30.4.1
-- 1.3.6.1.4.1.37950.1.1.5.10.30.4.1
-- 1.3.6.1.4.1.37950.1.1.5.10.30.4.1
-- 1.3.6.1.4.1.37950.1.1.5.10.30.4.1
-- 1.3.6.1.4.1.37950.1.1.5.10.30.4.1
-- 1.3.6.1.4.1.37950.1.1.5.10.30.4.1
-- 1.3.6.1.4.1.37950.1.1.5.10.30.4.1
		-- 1.3.6.1.4.1.37950.1.1.5.10.30.4.1
		pimQueryInterval OBJECT-TYPE
			SYNTAX Integer32 (0..65535)
			MAX-ACCESS read-write
			STATUS current
			DESCRIPTION
				"Description."
			::= { pimGlobalCfg 1 }

		
--          1.3.6.1.4.1.37950.1.1.5.10.30.4.2
-- 1.3.6.1.4.1.37950.1.1.5.10.30.4.2
-- 1.3.6.1.4.1.37950.1.1.5.10.30.4.2
-- 1.3.6.1.4.1.37950.1.1.5.10.30.4.2
-- 1.3.6.1.4.1.37950.1.1.5.10.30.4.2
-- 1.3.6.1.4.1.37950.1.1.5.10.30.4.2
-- 1.3.6.1.4.1.37950.1.1.5.10.30.4.2
-- 1.3.6.1.4.1.37950.1.1.5.10.30.4.2
-- 1.3.6.1.4.1.37950.1.1.5.10.30.4.2
		-- 1.3.6.1.4.1.37950.1.1.5.10.30.4.2
		pimSPTThresholdInfinity OBJECT-TYPE
			SYNTAX INTEGER
				{
				enable(0),
				disable(1)
				}
			MAX-ACCESS read-write
			STATUS current
			DESCRIPTION
				"Description."
			::= { pimGlobalCfg 2 }

		
--          1.3.6.1.4.1.37950.1.1.5.10.30.5
-- 1.3.6.1.4.1.37950.1.1.5.10.30.5
-- 1.3.6.1.4.1.37950.1.1.5.10.30.5
-- 1.3.6.1.4.1.37950.1.1.5.10.30.5
-- 1.3.6.1.4.1.37950.1.1.5.10.30.5
-- 1.3.6.1.4.1.37950.1.1.5.10.30.5
-- 1.3.6.1.4.1.37950.1.1.5.10.30.5
-- 1.3.6.1.4.1.37950.1.1.5.10.30.5
-- 1.3.6.1.4.1.37950.1.1.5.10.30.5
		-- 1.3.6.1.4.1.37950.1.1.5.10.30.5
		pimInterfaceCfg OBJECT IDENTIFIER ::= { v1600dPim 5 }

		
--          1.3.6.1.4.1.37950.1.1.5.10.30.5.1
-- 1.3.6.1.4.1.37950.1.1.5.10.30.5.1
-- 1.3.6.1.4.1.37950.1.1.5.10.30.5.1
-- 1.3.6.1.4.1.37950.1.1.5.10.30.5.1
-- 1.3.6.1.4.1.37950.1.1.5.10.30.5.1
-- 1.3.6.1.4.1.37950.1.1.5.10.30.5.1
-- 1.3.6.1.4.1.37950.1.1.5.10.30.5.1
-- 1.3.6.1.4.1.37950.1.1.5.10.30.5.1
-- 1.3.6.1.4.1.37950.1.1.5.10.30.5.1
		-- 1.3.6.1.4.1.37950.1.1.5.10.30.5.1
		pimInterface OBJECT-TYPE
			SYNTAX Integer32 (1..4094)
			MAX-ACCESS read-write
			STATUS current
			DESCRIPTION
				"Description."
			::= { pimInterfaceCfg 1 }

		
--          1.3.6.1.4.1.37950.1.1.5.10.30.5.2
-- 1.3.6.1.4.1.37950.1.1.5.10.30.5.2
-- 1.3.6.1.4.1.37950.1.1.5.10.30.5.2
-- 1.3.6.1.4.1.37950.1.1.5.10.30.5.2
-- 1.3.6.1.4.1.37950.1.1.5.10.30.5.2
-- 1.3.6.1.4.1.37950.1.1.5.10.30.5.2
-- 1.3.6.1.4.1.37950.1.1.5.10.30.5.2
-- 1.3.6.1.4.1.37950.1.1.5.10.30.5.2
-- 1.3.6.1.4.1.37950.1.1.5.10.30.5.2
		-- 1.3.6.1.4.1.37950.1.1.5.10.30.5.2
		pimMode OBJECT-TYPE
			SYNTAX INTEGER
				{
				disable(0),
				sparse-mode(1)
				}
			MAX-ACCESS read-write
			STATUS current
			DESCRIPTION
				"Description."
			::= { pimInterfaceCfg 2 }

		
--          1.3.6.1.4.1.37950.1.1.5.10.30.5.3
-- 1.3.6.1.4.1.37950.1.1.5.10.30.5.3
-- 1.3.6.1.4.1.37950.1.1.5.10.30.5.3
-- 1.3.6.1.4.1.37950.1.1.5.10.30.5.3
-- 1.3.6.1.4.1.37950.1.1.5.10.30.5.3
-- 1.3.6.1.4.1.37950.1.1.5.10.30.5.3
-- 1.3.6.1.4.1.37950.1.1.5.10.30.5.3
-- 1.3.6.1.4.1.37950.1.1.5.10.30.5.3
-- 1.3.6.1.4.1.37950.1.1.5.10.30.5.3
		-- 1.3.6.1.4.1.37950.1.1.5.10.30.5.3
		pimDRPriority OBJECT-TYPE
			SYNTAX Unsigned32 (0..4294967294)
			MAX-ACCESS read-write
			STATUS current
			DESCRIPTION
				"Description."
			::= { pimInterfaceCfg 3 }

		
--          1.3.6.1.4.1.37950.1.1.5.10.30.5.4
-- 1.3.6.1.4.1.37950.1.1.5.10.30.5.4
-- 1.3.6.1.4.1.37950.1.1.5.10.30.5.4
-- 1.3.6.1.4.1.37950.1.1.5.10.30.5.4
-- 1.3.6.1.4.1.37950.1.1.5.10.30.5.4
-- 1.3.6.1.4.1.37950.1.1.5.10.30.5.4
-- 1.3.6.1.4.1.37950.1.1.5.10.30.5.4
-- 1.3.6.1.4.1.37950.1.1.5.10.30.5.4
-- 1.3.6.1.4.1.37950.1.1.5.10.30.5.4
		-- 1.3.6.1.4.1.37950.1.1.5.10.30.5.4
		pimBSRBorder OBJECT-TYPE
			SYNTAX INTEGER
				{
				disable(0),
				enable(1)
				}
			MAX-ACCESS read-write
			STATUS current
			DESCRIPTION
				"Description."
			::= { pimInterfaceCfg 4 }

		
--          1.3.6.1.4.1.37950.1.1.5.10.30.5.5
-- 1.3.6.1.4.1.37950.1.1.5.10.30.5.5
-- 1.3.6.1.4.1.37950.1.1.5.10.30.5.5
-- 1.3.6.1.4.1.37950.1.1.5.10.30.5.5
-- 1.3.6.1.4.1.37950.1.1.5.10.30.5.5
-- 1.3.6.1.4.1.37950.1.1.5.10.30.5.5
-- 1.3.6.1.4.1.37950.1.1.5.10.30.5.5
-- 1.3.6.1.4.1.37950.1.1.5.10.30.5.5
-- 1.3.6.1.4.1.37950.1.1.5.10.30.5.5
		-- 1.3.6.1.4.1.37950.1.1.5.10.30.5.5
		pimInterfaceAction OBJECT-TYPE
			SYNTAX INTEGER { action(1) }
			MAX-ACCESS read-write
			STATUS current
			DESCRIPTION
				"Description."
			::= { pimInterfaceCfg 5 }

		
--          1.3.6.1.4.1.37950.1.1.5.10.30.6
-- 1.3.6.1.4.1.37950.1.1.5.10.30.6
-- 1.3.6.1.4.1.37950.1.1.5.10.30.6
-- 1.3.6.1.4.1.37950.1.1.5.10.30.6
-- 1.3.6.1.4.1.37950.1.1.5.10.30.6
-- 1.3.6.1.4.1.37950.1.1.5.10.30.6
-- 1.3.6.1.4.1.37950.1.1.5.10.30.6
-- 1.3.6.1.4.1.37950.1.1.5.10.30.6
-- 1.3.6.1.4.1.37950.1.1.5.10.30.6
		-- 1.3.6.1.4.1.37950.1.1.5.10.30.6
		pimRPsCfg OBJECT IDENTIFIER ::= { v1600dPim 6 }

		
--          1.3.6.1.4.1.37950.1.1.5.10.30.6.1
-- 1.3.6.1.4.1.37950.1.1.5.10.30.6.1
-- 1.3.6.1.4.1.37950.1.1.5.10.30.6.1
-- 1.3.6.1.4.1.37950.1.1.5.10.30.6.1
-- 1.3.6.1.4.1.37950.1.1.5.10.30.6.1
-- 1.3.6.1.4.1.37950.1.1.5.10.30.6.1
-- 1.3.6.1.4.1.37950.1.1.5.10.30.6.1
-- 1.3.6.1.4.1.37950.1.1.5.10.30.6.1
-- 1.3.6.1.4.1.37950.1.1.5.10.30.6.1
		-- 1.3.6.1.4.1.37950.1.1.5.10.30.6.1
		pimRPsAddress OBJECT-TYPE
			SYNTAX IpAddress
			MAX-ACCESS read-write
			STATUS current
			DESCRIPTION
				"Description."
			::= { pimRPsCfg 1 }

		
--          1.3.6.1.4.1.37950.1.1.5.10.30.6.2
-- 1.3.6.1.4.1.37950.1.1.5.10.30.6.2
-- 1.3.6.1.4.1.37950.1.1.5.10.30.6.2
-- 1.3.6.1.4.1.37950.1.1.5.10.30.6.2
-- 1.3.6.1.4.1.37950.1.1.5.10.30.6.2
-- 1.3.6.1.4.1.37950.1.1.5.10.30.6.2
-- 1.3.6.1.4.1.37950.1.1.5.10.30.6.2
-- 1.3.6.1.4.1.37950.1.1.5.10.30.6.2
-- 1.3.6.1.4.1.37950.1.1.5.10.30.6.2
		-- 1.3.6.1.4.1.37950.1.1.5.10.30.6.2
		pimRPsAction OBJECT-TYPE
			SYNTAX INTEGER
				{
				del(0),
				add(1)
				}
			MAX-ACCESS read-write
			STATUS current
			DESCRIPTION
				"Description."
			::= { pimRPsCfg 2 }

		
--          1.3.6.1.4.1.37950.1.1.5.10.30.7
-- 1.3.6.1.4.1.37950.1.1.5.10.30.7
-- 1.3.6.1.4.1.37950.1.1.5.10.30.7
-- 1.3.6.1.4.1.37950.1.1.5.10.30.7
-- 1.3.6.1.4.1.37950.1.1.5.10.30.7
-- 1.3.6.1.4.1.37950.1.1.5.10.30.7
-- 1.3.6.1.4.1.37950.1.1.5.10.30.7
-- 1.3.6.1.4.1.37950.1.1.5.10.30.7
-- 1.3.6.1.4.1.37950.1.1.5.10.30.7
		-- 1.3.6.1.4.1.37950.1.1.5.10.30.7
		pimCandidateRPCfg OBJECT IDENTIFIER ::= { v1600dPim 7 }

		
--          1.3.6.1.4.1.37950.1.1.5.10.30.7.1
-- 1.3.6.1.4.1.37950.1.1.5.10.30.7.1
-- 1.3.6.1.4.1.37950.1.1.5.10.30.7.1
-- 1.3.6.1.4.1.37950.1.1.5.10.30.7.1
-- 1.3.6.1.4.1.37950.1.1.5.10.30.7.1
-- 1.3.6.1.4.1.37950.1.1.5.10.30.7.1
-- 1.3.6.1.4.1.37950.1.1.5.10.30.7.1
-- 1.3.6.1.4.1.37950.1.1.5.10.30.7.1
-- 1.3.6.1.4.1.37950.1.1.5.10.30.7.1
		-- 1.3.6.1.4.1.37950.1.1.5.10.30.7.1
		pimCRPInterface OBJECT-TYPE
			SYNTAX Integer32 (1..4094)
			MAX-ACCESS read-write
			STATUS current
			DESCRIPTION
				"Description."
			::= { pimCandidateRPCfg 1 }

		
--          1.3.6.1.4.1.37950.1.1.5.10.30.7.2
-- 1.3.6.1.4.1.37950.1.1.5.10.30.7.2
-- 1.3.6.1.4.1.37950.1.1.5.10.30.7.2
-- 1.3.6.1.4.1.37950.1.1.5.10.30.7.2
-- 1.3.6.1.4.1.37950.1.1.5.10.30.7.2
-- 1.3.6.1.4.1.37950.1.1.5.10.30.7.2
-- 1.3.6.1.4.1.37950.1.1.5.10.30.7.2
-- 1.3.6.1.4.1.37950.1.1.5.10.30.7.2
-- 1.3.6.1.4.1.37950.1.1.5.10.30.7.2
		-- 1.3.6.1.4.1.37950.1.1.5.10.30.7.2
		pimCRPPriority OBJECT-TYPE
			SYNTAX Integer32 (0..255)
			MAX-ACCESS read-write
			STATUS current
			DESCRIPTION
				"Description."
			::= { pimCandidateRPCfg 2 }

		
--          1.3.6.1.4.1.37950.1.1.5.10.30.7.3
-- 1.3.6.1.4.1.37950.1.1.5.10.30.7.3
-- 1.3.6.1.4.1.37950.1.1.5.10.30.7.3
-- 1.3.6.1.4.1.37950.1.1.5.10.30.7.3
-- 1.3.6.1.4.1.37950.1.1.5.10.30.7.3
-- 1.3.6.1.4.1.37950.1.1.5.10.30.7.3
-- 1.3.6.1.4.1.37950.1.1.5.10.30.7.3
-- 1.3.6.1.4.1.37950.1.1.5.10.30.7.3
-- 1.3.6.1.4.1.37950.1.1.5.10.30.7.3
		-- 1.3.6.1.4.1.37950.1.1.5.10.30.7.3
		pimCRPAction OBJECT-TYPE
			SYNTAX INTEGER
				{
				del(0),
				add(1)
				}
			MAX-ACCESS read-write
			STATUS current
			DESCRIPTION
				"Description."
			::= { pimCandidateRPCfg 3 }

		
--          1.3.6.1.4.1.37950.1.1.5.10.30.8
-- 1.3.6.1.4.1.37950.1.1.5.10.30.8
-- 1.3.6.1.4.1.37950.1.1.5.10.30.8
-- 1.3.6.1.4.1.37950.1.1.5.10.30.8
-- 1.3.6.1.4.1.37950.1.1.5.10.30.8
-- 1.3.6.1.4.1.37950.1.1.5.10.30.8
-- 1.3.6.1.4.1.37950.1.1.5.10.30.8
-- 1.3.6.1.4.1.37950.1.1.5.10.30.8
-- 1.3.6.1.4.1.37950.1.1.5.10.30.8
		-- 1.3.6.1.4.1.37950.1.1.5.10.30.8
		pimCandidateBSRCfg OBJECT IDENTIFIER ::= { v1600dPim 8 }

		
--          1.3.6.1.4.1.37950.1.1.5.10.30.8.1
-- 1.3.6.1.4.1.37950.1.1.5.10.30.8.1
-- 1.3.6.1.4.1.37950.1.1.5.10.30.8.1
-- 1.3.6.1.4.1.37950.1.1.5.10.30.8.1
-- 1.3.6.1.4.1.37950.1.1.5.10.30.8.1
-- 1.3.6.1.4.1.37950.1.1.5.10.30.8.1
-- 1.3.6.1.4.1.37950.1.1.5.10.30.8.1
-- 1.3.6.1.4.1.37950.1.1.5.10.30.8.1
-- 1.3.6.1.4.1.37950.1.1.5.10.30.8.1
		-- 1.3.6.1.4.1.37950.1.1.5.10.30.8.1
		pimCBSRInterface OBJECT-TYPE
			SYNTAX Integer32 (1..4094)
			MAX-ACCESS read-write
			STATUS current
			DESCRIPTION
				"Description."
			::= { pimCandidateBSRCfg 1 }

		
--          1.3.6.1.4.1.37950.1.1.5.10.30.8.2
-- 1.3.6.1.4.1.37950.1.1.5.10.30.8.2
-- 1.3.6.1.4.1.37950.1.1.5.10.30.8.2
-- 1.3.6.1.4.1.37950.1.1.5.10.30.8.2
-- 1.3.6.1.4.1.37950.1.1.5.10.30.8.2
-- 1.3.6.1.4.1.37950.1.1.5.10.30.8.2
-- 1.3.6.1.4.1.37950.1.1.5.10.30.8.2
-- 1.3.6.1.4.1.37950.1.1.5.10.30.8.2
-- 1.3.6.1.4.1.37950.1.1.5.10.30.8.2
		-- 1.3.6.1.4.1.37950.1.1.5.10.30.8.2
		pimCBSRPriority OBJECT-TYPE
			SYNTAX Integer32 (0..255)
			MAX-ACCESS read-write
			STATUS current
			DESCRIPTION
				"Description."
			::= { pimCandidateBSRCfg 2 }

		
--          1.3.6.1.4.1.37950.1.1.5.10.30.8.3
-- 1.3.6.1.4.1.37950.1.1.5.10.30.8.3
-- 1.3.6.1.4.1.37950.1.1.5.10.30.8.3
-- 1.3.6.1.4.1.37950.1.1.5.10.30.8.3
-- 1.3.6.1.4.1.37950.1.1.5.10.30.8.3
-- 1.3.6.1.4.1.37950.1.1.5.10.30.8.3
-- 1.3.6.1.4.1.37950.1.1.5.10.30.8.3
-- 1.3.6.1.4.1.37950.1.1.5.10.30.8.3
-- 1.3.6.1.4.1.37950.1.1.5.10.30.8.3
		-- 1.3.6.1.4.1.37950.1.1.5.10.30.8.3
		pimCBSRHashMaskLen OBJECT-TYPE
			SYNTAX Integer32 (0..32)
			MAX-ACCESS read-write
			STATUS current
			DESCRIPTION
				"Description."
			::= { pimCandidateBSRCfg 3 }

		
--          1.3.6.1.4.1.37950.1.1.5.10.30.8.4
-- 1.3.6.1.4.1.37950.1.1.5.10.30.8.4
-- 1.3.6.1.4.1.37950.1.1.5.10.30.8.4
-- 1.3.6.1.4.1.37950.1.1.5.10.30.8.4
-- 1.3.6.1.4.1.37950.1.1.5.10.30.8.4
-- 1.3.6.1.4.1.37950.1.1.5.10.30.8.4
-- 1.3.6.1.4.1.37950.1.1.5.10.30.8.4
-- 1.3.6.1.4.1.37950.1.1.5.10.30.8.4
-- 1.3.6.1.4.1.37950.1.1.5.10.30.8.4
		-- 1.3.6.1.4.1.37950.1.1.5.10.30.8.4
		pimCBSRAction OBJECT-TYPE
			SYNTAX INTEGER
				{
				del(0),
				add(1)
				}
			MAX-ACCESS read-write
			STATUS current
			DESCRIPTION
				"Description."
			::= { pimCandidateBSRCfg 4 }

		
--          1.3.6.1.4.1.37950.1.1.5.10.30.9
-- 1.3.6.1.4.1.37950.1.1.5.10.30.9
-- 1.3.6.1.4.1.37950.1.1.5.10.30.9
-- 1.3.6.1.4.1.37950.1.1.5.10.30.9
-- 1.3.6.1.4.1.37950.1.1.5.10.30.9
-- 1.3.6.1.4.1.37950.1.1.5.10.30.9
-- 1.3.6.1.4.1.37950.1.1.5.10.30.9
-- 1.3.6.1.4.1.37950.1.1.5.10.30.9
-- 1.3.6.1.4.1.37950.1.1.5.10.30.9
		-- 1.3.6.1.4.1.37950.1.1.5.10.30.9
		pimMRouteTable OBJECT-TYPE
			SYNTAX SEQUENCE OF PimMRouteEntry
			MAX-ACCESS not-accessible
			STATUS current
			DESCRIPTION
				"Description."
			::= { v1600dPim 9 }

		
--          1.3.6.1.4.1.37950.1.1.5.10.30.9.1
-- 1.3.6.1.4.1.37950.1.1.5.10.30.9.1
-- 1.3.6.1.4.1.37950.1.1.5.10.30.9.1
-- 1.3.6.1.4.1.37950.1.1.5.10.30.9.1
-- 1.3.6.1.4.1.37950.1.1.5.10.30.9.1
-- 1.3.6.1.4.1.37950.1.1.5.10.30.9.1
-- 1.3.6.1.4.1.37950.1.1.5.10.30.9.1
-- 1.3.6.1.4.1.37950.1.1.5.10.30.9.1
-- 1.3.6.1.4.1.37950.1.1.5.10.30.9.1
		-- 1.3.6.1.4.1.37950.1.1.5.10.30.9.1
		pimMRouteEntry OBJECT-TYPE
			SYNTAX PimMRouteEntry
			MAX-ACCESS not-accessible
			STATUS current
			DESCRIPTION
				"Description."
			INDEX { pimMRouteSource, pimMRouteGroup, pimMRouteCRP }
			::= { pimMRouteTable 1 }

		
		PimMRouteEntry ::=
			SEQUENCE { 
				pimMRouteSource
					IpAddress,
				pimMRouteGroup
					IpAddress,
				pimMRouteCRP
					IpAddress,
				pimMRouteUptime
					TimeTicks,
				pimMRouteExpires
					TimeTicks,
				pimMRouteRP
					IpAddress,
				pimMRouteMode
					INTEGER,
				pimMRouteIncomingInf
					OCTET STRING,
				pimMRouteRPFNbr
					IpAddress,
				pimMRouteOutgoingList
					OCTET STRING
			 }

--          1.3.6.1.4.1.37950.1.1.5.10.30.9.1.1
-- 1.3.6.1.4.1.37950.1.1.5.10.30.9.1.1
-- 1.3.6.1.4.1.37950.1.1.5.10.30.9.1.1
-- 1.3.6.1.4.1.37950.1.1.5.10.30.9.1.1
-- 1.3.6.1.4.1.37950.1.1.5.10.30.9.1.1
-- 1.3.6.1.4.1.37950.1.1.5.10.30.9.1.1
-- 1.3.6.1.4.1.37950.1.1.5.10.30.9.1.1
-- 1.3.6.1.4.1.37950.1.1.5.10.30.9.1.1
-- 1.3.6.1.4.1.37950.1.1.5.10.30.9.1.1
		-- 1.3.6.1.4.1.37950.1.1.5.10.30.9.1.1
		pimMRouteSource OBJECT-TYPE
			SYNTAX IpAddress
			MAX-ACCESS read-only
			STATUS current
			DESCRIPTION
				"Description."
			::= { pimMRouteEntry 1 }

		
--          1.3.6.1.4.1.37950.1.1.5.10.30.9.1.2
-- 1.3.6.1.4.1.37950.1.1.5.10.30.9.1.2
-- 1.3.6.1.4.1.37950.1.1.5.10.30.9.1.2
-- 1.3.6.1.4.1.37950.1.1.5.10.30.9.1.2
-- 1.3.6.1.4.1.37950.1.1.5.10.30.9.1.2
-- 1.3.6.1.4.1.37950.1.1.5.10.30.9.1.2
-- 1.3.6.1.4.1.37950.1.1.5.10.30.9.1.2
-- 1.3.6.1.4.1.37950.1.1.5.10.30.9.1.2
-- 1.3.6.1.4.1.37950.1.1.5.10.30.9.1.2
		-- 1.3.6.1.4.1.37950.1.1.5.10.30.9.1.2
		pimMRouteGroup OBJECT-TYPE
			SYNTAX IpAddress
			MAX-ACCESS read-only
			STATUS current
			DESCRIPTION
				"Description."
			::= { pimMRouteEntry 2 }

		
--          1.3.6.1.4.1.37950.1.1.5.10.30.9.1.3
-- 1.3.6.1.4.1.37950.1.1.5.10.30.9.1.3
-- 1.3.6.1.4.1.37950.1.1.5.10.30.9.1.3
-- 1.3.6.1.4.1.37950.1.1.5.10.30.9.1.3
-- 1.3.6.1.4.1.37950.1.1.5.10.30.9.1.3
-- 1.3.6.1.4.1.37950.1.1.5.10.30.9.1.3
-- 1.3.6.1.4.1.37950.1.1.5.10.30.9.1.3
-- 1.3.6.1.4.1.37950.1.1.5.10.30.9.1.3
-- 1.3.6.1.4.1.37950.1.1.5.10.30.9.1.3
		-- 1.3.6.1.4.1.37950.1.1.5.10.30.9.1.3
		pimMRouteCRP OBJECT-TYPE
			SYNTAX IpAddress
			MAX-ACCESS read-only
			STATUS current
			DESCRIPTION
				"Description."
			::= { pimMRouteEntry 3 }

		
--          1.3.6.1.4.1.37950.1.1.5.10.30.9.1.4
-- 1.3.6.1.4.1.37950.1.1.5.10.30.9.1.4
-- 1.3.6.1.4.1.37950.1.1.5.10.30.9.1.4
-- 1.3.6.1.4.1.37950.1.1.5.10.30.9.1.4
-- 1.3.6.1.4.1.37950.1.1.5.10.30.9.1.4
-- 1.3.6.1.4.1.37950.1.1.5.10.30.9.1.4
-- 1.3.6.1.4.1.37950.1.1.5.10.30.9.1.4
-- 1.3.6.1.4.1.37950.1.1.5.10.30.9.1.4
-- 1.3.6.1.4.1.37950.1.1.5.10.30.9.1.4
		-- 1.3.6.1.4.1.37950.1.1.5.10.30.9.1.4
		pimMRouteUptime OBJECT-TYPE
			SYNTAX TimeTicks
			MAX-ACCESS read-only
			STATUS current
			DESCRIPTION
				"Description."
			::= { pimMRouteEntry 4 }

		
--          1.3.6.1.4.1.37950.1.1.5.10.30.9.1.5
-- 1.3.6.1.4.1.37950.1.1.5.10.30.9.1.5
-- 1.3.6.1.4.1.37950.1.1.5.10.30.9.1.5
-- 1.3.6.1.4.1.37950.1.1.5.10.30.9.1.5
-- 1.3.6.1.4.1.37950.1.1.5.10.30.9.1.5
-- 1.3.6.1.4.1.37950.1.1.5.10.30.9.1.5
-- 1.3.6.1.4.1.37950.1.1.5.10.30.9.1.5
-- 1.3.6.1.4.1.37950.1.1.5.10.30.9.1.5
-- 1.3.6.1.4.1.37950.1.1.5.10.30.9.1.5
		-- 1.3.6.1.4.1.37950.1.1.5.10.30.9.1.5
		pimMRouteExpires OBJECT-TYPE
			SYNTAX TimeTicks
			MAX-ACCESS read-only
			STATUS current
			DESCRIPTION
				"Description."
			::= { pimMRouteEntry 5 }

		
--          1.3.6.1.4.1.37950.1.1.5.10.30.9.1.6
-- 1.3.6.1.4.1.37950.1.1.5.10.30.9.1.6
-- 1.3.6.1.4.1.37950.1.1.5.10.30.9.1.6
-- 1.3.6.1.4.1.37950.1.1.5.10.30.9.1.6
-- 1.3.6.1.4.1.37950.1.1.5.10.30.9.1.6
-- 1.3.6.1.4.1.37950.1.1.5.10.30.9.1.6
-- 1.3.6.1.4.1.37950.1.1.5.10.30.9.1.6
-- 1.3.6.1.4.1.37950.1.1.5.10.30.9.1.6
-- 1.3.6.1.4.1.37950.1.1.5.10.30.9.1.6
		-- 1.3.6.1.4.1.37950.1.1.5.10.30.9.1.6
		pimMRouteRP OBJECT-TYPE
			SYNTAX IpAddress
			MAX-ACCESS read-only
			STATUS current
			DESCRIPTION
				"Description."
			::= { pimMRouteEntry 6 }

		
--          1.3.6.1.4.1.37950.1.1.5.10.30.9.1.7
-- 1.3.6.1.4.1.37950.1.1.5.10.30.9.1.7
-- 1.3.6.1.4.1.37950.1.1.5.10.30.9.1.7
-- 1.3.6.1.4.1.37950.1.1.5.10.30.9.1.7
-- 1.3.6.1.4.1.37950.1.1.5.10.30.9.1.7
-- 1.3.6.1.4.1.37950.1.1.5.10.30.9.1.7
-- 1.3.6.1.4.1.37950.1.1.5.10.30.9.1.7
-- 1.3.6.1.4.1.37950.1.1.5.10.30.9.1.7
-- 1.3.6.1.4.1.37950.1.1.5.10.30.9.1.7
		-- 1.3.6.1.4.1.37950.1.1.5.10.30.9.1.7
		pimMRouteMode OBJECT-TYPE
			SYNTAX INTEGER { sprase-mode(1) }
			MAX-ACCESS read-only
			STATUS current
			DESCRIPTION
				"Description."
			::= { pimMRouteEntry 7 }

		
--          1.3.6.1.4.1.37950.1.1.5.10.30.9.1.8
-- 1.3.6.1.4.1.37950.1.1.5.10.30.9.1.8
-- 1.3.6.1.4.1.37950.1.1.5.10.30.9.1.8
-- 1.3.6.1.4.1.37950.1.1.5.10.30.9.1.8
-- 1.3.6.1.4.1.37950.1.1.5.10.30.9.1.8
-- 1.3.6.1.4.1.37950.1.1.5.10.30.9.1.8
-- 1.3.6.1.4.1.37950.1.1.5.10.30.9.1.8
-- 1.3.6.1.4.1.37950.1.1.5.10.30.9.1.8
-- 1.3.6.1.4.1.37950.1.1.5.10.30.9.1.8
		-- 1.3.6.1.4.1.37950.1.1.5.10.30.9.1.8
		pimMRouteIncomingInf OBJECT-TYPE
			SYNTAX OCTET STRING
			MAX-ACCESS read-only
			STATUS current
			DESCRIPTION
				"Description."
			::= { pimMRouteEntry 8 }

		
--          1.3.6.1.4.1.37950.1.1.5.10.30.9.1.9
-- 1.3.6.1.4.1.37950.1.1.5.10.30.9.1.9
-- 1.3.6.1.4.1.37950.1.1.5.10.30.9.1.9
-- 1.3.6.1.4.1.37950.1.1.5.10.30.9.1.9
-- 1.3.6.1.4.1.37950.1.1.5.10.30.9.1.9
-- 1.3.6.1.4.1.37950.1.1.5.10.30.9.1.9
-- 1.3.6.1.4.1.37950.1.1.5.10.30.9.1.9
-- 1.3.6.1.4.1.37950.1.1.5.10.30.9.1.9
-- 1.3.6.1.4.1.37950.1.1.5.10.30.9.1.9
		-- 1.3.6.1.4.1.37950.1.1.5.10.30.9.1.9
		pimMRouteRPFNbr OBJECT-TYPE
			SYNTAX IpAddress
			MAX-ACCESS read-only
			STATUS current
			DESCRIPTION
				"Description."
			::= { pimMRouteEntry 9 }

		
--          1.3.6.1.4.1.37950.1.1.5.10.30.9.1.10
-- 1.3.6.1.4.1.37950.1.1.5.10.30.9.1.10
-- 1.3.6.1.4.1.37950.1.1.5.10.30.9.1.10
-- 1.3.6.1.4.1.37950.1.1.5.10.30.9.1.10
-- 1.3.6.1.4.1.37950.1.1.5.10.30.9.1.10
-- 1.3.6.1.4.1.37950.1.1.5.10.30.9.1.10
-- 1.3.6.1.4.1.37950.1.1.5.10.30.9.1.10
-- 1.3.6.1.4.1.37950.1.1.5.10.30.9.1.10
-- 1.3.6.1.4.1.37950.1.1.5.10.30.9.1.10
		-- 1.3.6.1.4.1.37950.1.1.5.10.30.9.1.10
		pimMRouteOutgoingList OBJECT-TYPE
			SYNTAX OCTET STRING
			MAX-ACCESS read-only
			STATUS current
			DESCRIPTION
				"Description."
			::= { pimMRouteEntry 10 }

		
--          1.3.6.1.4.1.37950.1.1.5.10.30.10
-- 1.3.6.1.4.1.37950.1.1.5.10.30.10
-- 1.3.6.1.4.1.37950.1.1.5.10.30.10
-- 1.3.6.1.4.1.37950.1.1.5.10.30.10
-- 1.3.6.1.4.1.37950.1.1.5.10.30.10
-- 1.3.6.1.4.1.37950.1.1.5.10.30.10
-- 1.3.6.1.4.1.37950.1.1.5.10.30.10
-- 1.3.6.1.4.1.37950.1.1.5.10.30.10
-- 1.3.6.1.4.1.37950.1.1.5.10.30.10
		-- 1.3.6.1.4.1.37950.1.1.5.10.30.10
		pimIpIgmpGroupTable OBJECT-TYPE
			SYNTAX SEQUENCE OF PimIpIgmpGroupEntry
			MAX-ACCESS not-accessible
			STATUS current
			DESCRIPTION
				"Description."
			::= { v1600dPim 10 }

		
--          1.3.6.1.4.1.37950.1.1.5.10.30.10.1
-- 1.3.6.1.4.1.37950.1.1.5.10.30.10.1
-- 1.3.6.1.4.1.37950.1.1.5.10.30.10.1
-- 1.3.6.1.4.1.37950.1.1.5.10.30.10.1
-- 1.3.6.1.4.1.37950.1.1.5.10.30.10.1
-- 1.3.6.1.4.1.37950.1.1.5.10.30.10.1
-- 1.3.6.1.4.1.37950.1.1.5.10.30.10.1
-- 1.3.6.1.4.1.37950.1.1.5.10.30.10.1
-- 1.3.6.1.4.1.37950.1.1.5.10.30.10.1
		-- 1.3.6.1.4.1.37950.1.1.5.10.30.10.1
		pimIpIgmpGroupEntry OBJECT-TYPE
			SYNTAX PimIpIgmpGroupEntry
			MAX-ACCESS not-accessible
			STATUS current
			DESCRIPTION
				"Description."
			INDEX { pimIpIgmpGroupAddress, pimIpIgmpGroupInterface }
			::= { pimIpIgmpGroupTable 1 }

		
		PimIpIgmpGroupEntry ::=
			SEQUENCE { 
				pimIpIgmpGroupAddress
					IpAddress,
				pimIpIgmpGroupInterface
					Integer32,
				pimIpIgmpGroupUptime
					TimeTicks,
				pimIpIgmpGroupExpires
					TimeTicks,
				pimIpIgmpGroupLastReporter
					IpAddress
			 }

--          1.3.6.1.4.1.37950.1.1.5.10.30.10.1.1
-- 1.3.6.1.4.1.37950.1.1.5.10.30.10.1.1
-- 1.3.6.1.4.1.37950.1.1.5.10.30.10.1.1
-- 1.3.6.1.4.1.37950.1.1.5.10.30.10.1.1
-- 1.3.6.1.4.1.37950.1.1.5.10.30.10.1.1
-- 1.3.6.1.4.1.37950.1.1.5.10.30.10.1.1
-- 1.3.6.1.4.1.37950.1.1.5.10.30.10.1.1
-- 1.3.6.1.4.1.37950.1.1.5.10.30.10.1.1
-- 1.3.6.1.4.1.37950.1.1.5.10.30.10.1.1
		-- 1.3.6.1.4.1.37950.1.1.5.10.30.10.1.1
		pimIpIgmpGroupAddress OBJECT-TYPE
			SYNTAX IpAddress
			MAX-ACCESS read-only
			STATUS current
			DESCRIPTION
				"Description."
			::= { pimIpIgmpGroupEntry 1 }

		
--          1.3.6.1.4.1.37950.1.1.5.10.30.10.1.2
-- 1.3.6.1.4.1.37950.1.1.5.10.30.10.1.2
-- 1.3.6.1.4.1.37950.1.1.5.10.30.10.1.2
-- 1.3.6.1.4.1.37950.1.1.5.10.30.10.1.2
-- 1.3.6.1.4.1.37950.1.1.5.10.30.10.1.2
-- 1.3.6.1.4.1.37950.1.1.5.10.30.10.1.2
-- 1.3.6.1.4.1.37950.1.1.5.10.30.10.1.2
-- 1.3.6.1.4.1.37950.1.1.5.10.30.10.1.2
-- 1.3.6.1.4.1.37950.1.1.5.10.30.10.1.2
		-- 1.3.6.1.4.1.37950.1.1.5.10.30.10.1.2
		pimIpIgmpGroupInterface OBJECT-TYPE
			SYNTAX Integer32
			MAX-ACCESS read-only
			STATUS current
			DESCRIPTION
				"Description."
			::= { pimIpIgmpGroupEntry 2 }

		
--          1.3.6.1.4.1.37950.1.1.5.10.30.10.1.3
-- 1.3.6.1.4.1.37950.1.1.5.10.30.10.1.3
-- 1.3.6.1.4.1.37950.1.1.5.10.30.10.1.3
-- 1.3.6.1.4.1.37950.1.1.5.10.30.10.1.3
-- 1.3.6.1.4.1.37950.1.1.5.10.30.10.1.3
-- 1.3.6.1.4.1.37950.1.1.5.10.30.10.1.3
-- 1.3.6.1.4.1.37950.1.1.5.10.30.10.1.3
-- 1.3.6.1.4.1.37950.1.1.5.10.30.10.1.3
-- 1.3.6.1.4.1.37950.1.1.5.10.30.10.1.3
		-- 1.3.6.1.4.1.37950.1.1.5.10.30.10.1.3
		pimIpIgmpGroupUptime OBJECT-TYPE
			SYNTAX TimeTicks
			MAX-ACCESS read-only
			STATUS current
			DESCRIPTION
				"Description."
			::= { pimIpIgmpGroupEntry 3 }

		
--          1.3.6.1.4.1.37950.1.1.5.10.30.10.1.4
-- 1.3.6.1.4.1.37950.1.1.5.10.30.10.1.4
-- 1.3.6.1.4.1.37950.1.1.5.10.30.10.1.4
-- 1.3.6.1.4.1.37950.1.1.5.10.30.10.1.4
-- 1.3.6.1.4.1.37950.1.1.5.10.30.10.1.4
-- 1.3.6.1.4.1.37950.1.1.5.10.30.10.1.4
-- 1.3.6.1.4.1.37950.1.1.5.10.30.10.1.4
-- 1.3.6.1.4.1.37950.1.1.5.10.30.10.1.4
-- 1.3.6.1.4.1.37950.1.1.5.10.30.10.1.4
		-- 1.3.6.1.4.1.37950.1.1.5.10.30.10.1.4
		pimIpIgmpGroupExpires OBJECT-TYPE
			SYNTAX TimeTicks
			MAX-ACCESS read-only
			STATUS current
			DESCRIPTION
				"Description."
			::= { pimIpIgmpGroupEntry 4 }

		
--          1.3.6.1.4.1.37950.1.1.5.10.30.10.1.5
-- 1.3.6.1.4.1.37950.1.1.5.10.30.10.1.5
-- 1.3.6.1.4.1.37950.1.1.5.10.30.10.1.5
-- 1.3.6.1.4.1.37950.1.1.5.10.30.10.1.5
-- 1.3.6.1.4.1.37950.1.1.5.10.30.10.1.5
-- 1.3.6.1.4.1.37950.1.1.5.10.30.10.1.5
-- 1.3.6.1.4.1.37950.1.1.5.10.30.10.1.5
-- 1.3.6.1.4.1.37950.1.1.5.10.30.10.1.5
-- 1.3.6.1.4.1.37950.1.1.5.10.30.10.1.5
		-- 1.3.6.1.4.1.37950.1.1.5.10.30.10.1.5
		pimIpIgmpGroupLastReporter OBJECT-TYPE
			SYNTAX IpAddress
			MAX-ACCESS read-only
			STATUS current
			DESCRIPTION
				"Description."
			::= { pimIpIgmpGroupEntry 5 }

		
--          1.3.6.1.4.1.37950.1.1.5.10.30.11
-- 1.3.6.1.4.1.37950.1.1.5.10.30.11
-- 1.3.6.1.4.1.37950.1.1.5.10.30.11
-- 1.3.6.1.4.1.37950.1.1.5.10.30.11
-- 1.3.6.1.4.1.37950.1.1.5.10.30.11
-- 1.3.6.1.4.1.37950.1.1.5.10.30.11
-- 1.3.6.1.4.1.37950.1.1.5.10.30.11
-- 1.3.6.1.4.1.37950.1.1.5.10.30.11
-- 1.3.6.1.4.1.37950.1.1.5.10.30.11
		-- 1.3.6.1.4.1.37950.1.1.5.10.30.11
		pimIpIgmpInterfaceTable OBJECT-TYPE
			SYNTAX SEQUENCE OF PimIpIgmpInterfaceEntry
			MAX-ACCESS not-accessible
			STATUS current
			DESCRIPTION
				"Description."
			::= { v1600dPim 11 }

		
--          1.3.6.1.4.1.37950.1.1.5.10.30.11.1
-- 1.3.6.1.4.1.37950.1.1.5.10.30.11.1
-- 1.3.6.1.4.1.37950.1.1.5.10.30.11.1
-- 1.3.6.1.4.1.37950.1.1.5.10.30.11.1
-- 1.3.6.1.4.1.37950.1.1.5.10.30.11.1
-- 1.3.6.1.4.1.37950.1.1.5.10.30.11.1
-- 1.3.6.1.4.1.37950.1.1.5.10.30.11.1
-- 1.3.6.1.4.1.37950.1.1.5.10.30.11.1
-- 1.3.6.1.4.1.37950.1.1.5.10.30.11.1
		-- 1.3.6.1.4.1.37950.1.1.5.10.30.11.1
		pimIpIgmpInterfaceEntry OBJECT-TYPE
			SYNTAX PimIpIgmpInterfaceEntry
			MAX-ACCESS not-accessible
			STATUS current
			DESCRIPTION
				"Description."
			INDEX { pimIgmpInterfaceID }
			::= { pimIpIgmpInterfaceTable 1 }

		
		PimIpIgmpInterfaceEntry ::=
			SEQUENCE { 
				pimIgmpInterfaceID
					Integer32,
				pimIgmpInterfaceAddress
					IpAddress,
				pimIgmpInterfaceVersion
					INTEGER,
				pimIgmpInterfaceQueryInterval
					Integer32,
				pimIgmpInterfaceQuerierTimeout
					Integer32,
				pimIgmpInterfaceMaxResponseTime
					Integer32,
				pimIgmpInterfaceLastRespInterval
					Integer32,
				pimIgmpInterfaceTtl
					Integer32,
				pimIgmpInterfaceDR
					IpAddress,
				pimIgmpInterfaceQueryRouter
					IpAddress,
				pimIgmpInterfaceGroup
					IpAddress
			 }

--          1.3.6.1.4.1.37950.1.1.5.10.30.11.1.1
-- 1.3.6.1.4.1.37950.1.1.5.10.30.11.1.1
-- 1.3.6.1.4.1.37950.1.1.5.10.30.11.1.1
-- 1.3.6.1.4.1.37950.1.1.5.10.30.11.1.1
-- 1.3.6.1.4.1.37950.1.1.5.10.30.11.1.1
-- 1.3.6.1.4.1.37950.1.1.5.10.30.11.1.1
-- 1.3.6.1.4.1.37950.1.1.5.10.30.11.1.1
-- 1.3.6.1.4.1.37950.1.1.5.10.30.11.1.1
-- 1.3.6.1.4.1.37950.1.1.5.10.30.11.1.1
		-- 1.3.6.1.4.1.37950.1.1.5.10.30.11.1.1
		pimIgmpInterfaceID OBJECT-TYPE
			SYNTAX Integer32 (1..4094)
			MAX-ACCESS read-only
			STATUS current
			DESCRIPTION
				"Description."
			::= { pimIpIgmpInterfaceEntry 1 }

		
--          1.3.6.1.4.1.37950.1.1.5.10.30.11.1.2
-- 1.3.6.1.4.1.37950.1.1.5.10.30.11.1.2
-- 1.3.6.1.4.1.37950.1.1.5.10.30.11.1.2
-- 1.3.6.1.4.1.37950.1.1.5.10.30.11.1.2
-- 1.3.6.1.4.1.37950.1.1.5.10.30.11.1.2
-- 1.3.6.1.4.1.37950.1.1.5.10.30.11.1.2
-- 1.3.6.1.4.1.37950.1.1.5.10.30.11.1.2
-- 1.3.6.1.4.1.37950.1.1.5.10.30.11.1.2
-- 1.3.6.1.4.1.37950.1.1.5.10.30.11.1.2
		-- 1.3.6.1.4.1.37950.1.1.5.10.30.11.1.2
		pimIgmpInterfaceAddress OBJECT-TYPE
			SYNTAX IpAddress
			MAX-ACCESS read-only
			STATUS current
			DESCRIPTION
				"Description."
			::= { pimIpIgmpInterfaceEntry 2 }

		
--          1.3.6.1.4.1.37950.1.1.5.10.30.11.1.3
-- 1.3.6.1.4.1.37950.1.1.5.10.30.11.1.3
-- 1.3.6.1.4.1.37950.1.1.5.10.30.11.1.3
-- 1.3.6.1.4.1.37950.1.1.5.10.30.11.1.3
-- 1.3.6.1.4.1.37950.1.1.5.10.30.11.1.3
-- 1.3.6.1.4.1.37950.1.1.5.10.30.11.1.3
-- 1.3.6.1.4.1.37950.1.1.5.10.30.11.1.3
-- 1.3.6.1.4.1.37950.1.1.5.10.30.11.1.3
-- 1.3.6.1.4.1.37950.1.1.5.10.30.11.1.3
		-- 1.3.6.1.4.1.37950.1.1.5.10.30.11.1.3
		pimIgmpInterfaceVersion OBJECT-TYPE
			SYNTAX INTEGER
				{
				igmpv1(1),
				igmpv2(2),
				igmpv3(3)
				}
			MAX-ACCESS read-only
			STATUS current
			DESCRIPTION
				"Description."
			::= { pimIpIgmpInterfaceEntry 3 }

		
--          1.3.6.1.4.1.37950.1.1.5.10.30.11.1.4
-- 1.3.6.1.4.1.37950.1.1.5.10.30.11.1.4
-- 1.3.6.1.4.1.37950.1.1.5.10.30.11.1.4
-- 1.3.6.1.4.1.37950.1.1.5.10.30.11.1.4
-- 1.3.6.1.4.1.37950.1.1.5.10.30.11.1.4
-- 1.3.6.1.4.1.37950.1.1.5.10.30.11.1.4
-- 1.3.6.1.4.1.37950.1.1.5.10.30.11.1.4
-- 1.3.6.1.4.1.37950.1.1.5.10.30.11.1.4
-- 1.3.6.1.4.1.37950.1.1.5.10.30.11.1.4
		-- 1.3.6.1.4.1.37950.1.1.5.10.30.11.1.4
		pimIgmpInterfaceQueryInterval OBJECT-TYPE
			SYNTAX Integer32
			MAX-ACCESS read-only
			STATUS current
			DESCRIPTION
				"Description."
			::= { pimIpIgmpInterfaceEntry 4 }

		
--          1.3.6.1.4.1.37950.1.1.5.10.30.11.1.5
-- 1.3.6.1.4.1.37950.1.1.5.10.30.11.1.5
-- 1.3.6.1.4.1.37950.1.1.5.10.30.11.1.5
-- 1.3.6.1.4.1.37950.1.1.5.10.30.11.1.5
-- 1.3.6.1.4.1.37950.1.1.5.10.30.11.1.5
-- 1.3.6.1.4.1.37950.1.1.5.10.30.11.1.5
-- 1.3.6.1.4.1.37950.1.1.5.10.30.11.1.5
-- 1.3.6.1.4.1.37950.1.1.5.10.30.11.1.5
-- 1.3.6.1.4.1.37950.1.1.5.10.30.11.1.5
		-- 1.3.6.1.4.1.37950.1.1.5.10.30.11.1.5
		pimIgmpInterfaceQuerierTimeout OBJECT-TYPE
			SYNTAX Integer32
			MAX-ACCESS read-only
			STATUS current
			DESCRIPTION
				"Description."
			::= { pimIpIgmpInterfaceEntry 5 }

		
--          1.3.6.1.4.1.37950.1.1.5.10.30.11.1.6
-- 1.3.6.1.4.1.37950.1.1.5.10.30.11.1.6
-- 1.3.6.1.4.1.37950.1.1.5.10.30.11.1.6
-- 1.3.6.1.4.1.37950.1.1.5.10.30.11.1.6
-- 1.3.6.1.4.1.37950.1.1.5.10.30.11.1.6
-- 1.3.6.1.4.1.37950.1.1.5.10.30.11.1.6
-- 1.3.6.1.4.1.37950.1.1.5.10.30.11.1.6
-- 1.3.6.1.4.1.37950.1.1.5.10.30.11.1.6
-- 1.3.6.1.4.1.37950.1.1.5.10.30.11.1.6
		-- 1.3.6.1.4.1.37950.1.1.5.10.30.11.1.6
		pimIgmpInterfaceMaxResponseTime OBJECT-TYPE
			SYNTAX Integer32
			MAX-ACCESS read-only
			STATUS current
			DESCRIPTION
				"Description."
			::= { pimIpIgmpInterfaceEntry 6 }

		
--          1.3.6.1.4.1.37950.1.1.5.10.30.11.1.7
-- 1.3.6.1.4.1.37950.1.1.5.10.30.11.1.7
-- 1.3.6.1.4.1.37950.1.1.5.10.30.11.1.7
-- 1.3.6.1.4.1.37950.1.1.5.10.30.11.1.7
-- 1.3.6.1.4.1.37950.1.1.5.10.30.11.1.7
-- 1.3.6.1.4.1.37950.1.1.5.10.30.11.1.7
-- 1.3.6.1.4.1.37950.1.1.5.10.30.11.1.7
-- 1.3.6.1.4.1.37950.1.1.5.10.30.11.1.7
-- 1.3.6.1.4.1.37950.1.1.5.10.30.11.1.7
		-- 1.3.6.1.4.1.37950.1.1.5.10.30.11.1.7
		pimIgmpInterfaceLastRespInterval OBJECT-TYPE
			SYNTAX Integer32
			MAX-ACCESS read-write
			STATUS current
			DESCRIPTION
				"Description."
			::= { pimIpIgmpInterfaceEntry 7 }

		
--          1.3.6.1.4.1.37950.1.1.5.10.30.11.1.8
-- 1.3.6.1.4.1.37950.1.1.5.10.30.11.1.8
-- 1.3.6.1.4.1.37950.1.1.5.10.30.11.1.8
-- 1.3.6.1.4.1.37950.1.1.5.10.30.11.1.8
-- 1.3.6.1.4.1.37950.1.1.5.10.30.11.1.8
-- 1.3.6.1.4.1.37950.1.1.5.10.30.11.1.8
-- 1.3.6.1.4.1.37950.1.1.5.10.30.11.1.8
-- 1.3.6.1.4.1.37950.1.1.5.10.30.11.1.8
-- 1.3.6.1.4.1.37950.1.1.5.10.30.11.1.8
		-- 1.3.6.1.4.1.37950.1.1.5.10.30.11.1.8
		pimIgmpInterfaceTtl OBJECT-TYPE
			SYNTAX Integer32
			MAX-ACCESS read-only
			STATUS current
			DESCRIPTION
				"Description."
			::= { pimIpIgmpInterfaceEntry 8 }

		
--          1.3.6.1.4.1.37950.1.1.5.10.30.11.1.9
-- 1.3.6.1.4.1.37950.1.1.5.10.30.11.1.9
-- 1.3.6.1.4.1.37950.1.1.5.10.30.11.1.9
-- 1.3.6.1.4.1.37950.1.1.5.10.30.11.1.9
-- 1.3.6.1.4.1.37950.1.1.5.10.30.11.1.9
-- 1.3.6.1.4.1.37950.1.1.5.10.30.11.1.9
-- 1.3.6.1.4.1.37950.1.1.5.10.30.11.1.9
-- 1.3.6.1.4.1.37950.1.1.5.10.30.11.1.9
-- 1.3.6.1.4.1.37950.1.1.5.10.30.11.1.9
		-- 1.3.6.1.4.1.37950.1.1.5.10.30.11.1.9
		pimIgmpInterfaceDR OBJECT-TYPE
			SYNTAX IpAddress
			MAX-ACCESS read-only
			STATUS current
			DESCRIPTION
				"Description."
			::= { pimIpIgmpInterfaceEntry 9 }

		
--          1.3.6.1.4.1.37950.1.1.5.10.30.11.1.10
-- 1.3.6.1.4.1.37950.1.1.5.10.30.11.1.10
-- 1.3.6.1.4.1.37950.1.1.5.10.30.11.1.10
-- 1.3.6.1.4.1.37950.1.1.5.10.30.11.1.10
-- 1.3.6.1.4.1.37950.1.1.5.10.30.11.1.10
-- 1.3.6.1.4.1.37950.1.1.5.10.30.11.1.10
-- 1.3.6.1.4.1.37950.1.1.5.10.30.11.1.10
-- 1.3.6.1.4.1.37950.1.1.5.10.30.11.1.10
-- 1.3.6.1.4.1.37950.1.1.5.10.30.11.1.10
		-- 1.3.6.1.4.1.37950.1.1.5.10.30.11.1.10
		pimIgmpInterfaceQueryRouter OBJECT-TYPE
			SYNTAX IpAddress
			MAX-ACCESS read-only
			STATUS current
			DESCRIPTION
				"Description."
			::= { pimIpIgmpInterfaceEntry 10 }

		
--          1.3.6.1.4.1.37950.1.1.5.10.30.11.1.11
-- 1.3.6.1.4.1.37950.1.1.5.10.30.11.1.11
-- 1.3.6.1.4.1.37950.1.1.5.10.30.11.1.11
-- 1.3.6.1.4.1.37950.1.1.5.10.30.11.1.11
-- 1.3.6.1.4.1.37950.1.1.5.10.30.11.1.11
-- 1.3.6.1.4.1.37950.1.1.5.10.30.11.1.11
-- 1.3.6.1.4.1.37950.1.1.5.10.30.11.1.11
-- 1.3.6.1.4.1.37950.1.1.5.10.30.11.1.11
-- 1.3.6.1.4.1.37950.1.1.5.10.30.11.1.11
		-- 1.3.6.1.4.1.37950.1.1.5.10.30.11.1.11
		pimIgmpInterfaceGroup OBJECT-TYPE
			SYNTAX IpAddress
			MAX-ACCESS read-only
			STATUS current
			DESCRIPTION
				"Description."
			::= { pimIpIgmpInterfaceEntry 11 }

		
--          1.3.6.1.4.1.37950.1.1.5.10.30.12
-- 1.3.6.1.4.1.37950.1.1.5.10.30.12
-- 1.3.6.1.4.1.37950.1.1.5.10.30.12
-- 1.3.6.1.4.1.37950.1.1.5.10.30.12
-- 1.3.6.1.4.1.37950.1.1.5.10.30.12
-- 1.3.6.1.4.1.37950.1.1.5.10.30.12
-- 1.3.6.1.4.1.37950.1.1.5.10.30.12
-- 1.3.6.1.4.1.37950.1.1.5.10.30.12
-- 1.3.6.1.4.1.37950.1.1.5.10.30.12
		-- 1.3.6.1.4.1.37950.1.1.5.10.30.12
		pimInfTable OBJECT-TYPE
			SYNTAX SEQUENCE OF PimInfEntry
			MAX-ACCESS not-accessible
			STATUS current
			DESCRIPTION
				"Description."
			::= { v1600dPim 12 }

		
--          1.3.6.1.4.1.37950.1.1.5.10.30.12.1
-- 1.3.6.1.4.1.37950.1.1.5.10.30.12.1
-- 1.3.6.1.4.1.37950.1.1.5.10.30.12.1
-- 1.3.6.1.4.1.37950.1.1.5.10.30.12.1
-- 1.3.6.1.4.1.37950.1.1.5.10.30.12.1
-- 1.3.6.1.4.1.37950.1.1.5.10.30.12.1
-- 1.3.6.1.4.1.37950.1.1.5.10.30.12.1
-- 1.3.6.1.4.1.37950.1.1.5.10.30.12.1
-- 1.3.6.1.4.1.37950.1.1.5.10.30.12.1
		-- 1.3.6.1.4.1.37950.1.1.5.10.30.12.1
		pimInfEntry OBJECT-TYPE
			SYNTAX PimInfEntry
			MAX-ACCESS not-accessible
			STATUS current
			DESCRIPTION
				"Description."
			INDEX { pimInfID }
			::= { pimInfTable 1 }

		
		PimInfEntry ::=
			SEQUENCE { 
				pimInfAddress
					IpAddress,
				pimInfID
					Integer32,
				pimInfVersion
					INTEGER,
				pimInfMode
					INTEGER,
				pimInfNbrCount
					Integer32,
				pimInfQueryIntvl
					Integer32,
				pimInfDRPriority
					Unsigned32,
				pimInfDR
					IpAddress
			 }

--          1.3.6.1.4.1.37950.1.1.5.10.30.12.1.1
-- 1.3.6.1.4.1.37950.1.1.5.10.30.12.1.1
-- 1.3.6.1.4.1.37950.1.1.5.10.30.12.1.1
-- 1.3.6.1.4.1.37950.1.1.5.10.30.12.1.1
-- 1.3.6.1.4.1.37950.1.1.5.10.30.12.1.1
-- 1.3.6.1.4.1.37950.1.1.5.10.30.12.1.1
-- 1.3.6.1.4.1.37950.1.1.5.10.30.12.1.1
-- 1.3.6.1.4.1.37950.1.1.5.10.30.12.1.1
-- 1.3.6.1.4.1.37950.1.1.5.10.30.12.1.1
		-- 1.3.6.1.4.1.37950.1.1.5.10.30.12.1.1
		pimInfAddress OBJECT-TYPE
			SYNTAX IpAddress
			MAX-ACCESS read-only
			STATUS current
			DESCRIPTION
				"Description."
			::= { pimInfEntry 1 }

		
--          1.3.6.1.4.1.37950.1.1.5.10.30.12.1.2
-- 1.3.6.1.4.1.37950.1.1.5.10.30.12.1.2
-- 1.3.6.1.4.1.37950.1.1.5.10.30.12.1.2
-- 1.3.6.1.4.1.37950.1.1.5.10.30.12.1.2
-- 1.3.6.1.4.1.37950.1.1.5.10.30.12.1.2
-- 1.3.6.1.4.1.37950.1.1.5.10.30.12.1.2
-- 1.3.6.1.4.1.37950.1.1.5.10.30.12.1.2
-- 1.3.6.1.4.1.37950.1.1.5.10.30.12.1.2
-- 1.3.6.1.4.1.37950.1.1.5.10.30.12.1.2
		-- 1.3.6.1.4.1.37950.1.1.5.10.30.12.1.2
		pimInfID OBJECT-TYPE
			SYNTAX Integer32
			MAX-ACCESS read-only
			STATUS current
			DESCRIPTION
				"Description."
			::= { pimInfEntry 2 }

		
--          1.3.6.1.4.1.37950.1.1.5.10.30.12.1.3
-- 1.3.6.1.4.1.37950.1.1.5.10.30.12.1.3
-- 1.3.6.1.4.1.37950.1.1.5.10.30.12.1.3
-- 1.3.6.1.4.1.37950.1.1.5.10.30.12.1.3
-- 1.3.6.1.4.1.37950.1.1.5.10.30.12.1.3
-- 1.3.6.1.4.1.37950.1.1.5.10.30.12.1.3
-- 1.3.6.1.4.1.37950.1.1.5.10.30.12.1.3
-- 1.3.6.1.4.1.37950.1.1.5.10.30.12.1.3
-- 1.3.6.1.4.1.37950.1.1.5.10.30.12.1.3
		-- 1.3.6.1.4.1.37950.1.1.5.10.30.12.1.3
		pimInfVersion OBJECT-TYPE
			SYNTAX INTEGER { v2(2) }
			MAX-ACCESS read-only
			STATUS current
			DESCRIPTION
				"Description."
			::= { pimInfEntry 3 }

		
--          1.3.6.1.4.1.37950.1.1.5.10.30.12.1.4
-- 1.3.6.1.4.1.37950.1.1.5.10.30.12.1.4
-- 1.3.6.1.4.1.37950.1.1.5.10.30.12.1.4
-- 1.3.6.1.4.1.37950.1.1.5.10.30.12.1.4
-- 1.3.6.1.4.1.37950.1.1.5.10.30.12.1.4
-- 1.3.6.1.4.1.37950.1.1.5.10.30.12.1.4
-- 1.3.6.1.4.1.37950.1.1.5.10.30.12.1.4
-- 1.3.6.1.4.1.37950.1.1.5.10.30.12.1.4
-- 1.3.6.1.4.1.37950.1.1.5.10.30.12.1.4
		-- 1.3.6.1.4.1.37950.1.1.5.10.30.12.1.4
		pimInfMode OBJECT-TYPE
			SYNTAX INTEGER { sprase-mode(1) }
			MAX-ACCESS read-only
			STATUS current
			DESCRIPTION
				"Description."
			::= { pimInfEntry 4 }

		
--          1.3.6.1.4.1.37950.1.1.5.10.30.12.1.5
-- 1.3.6.1.4.1.37950.1.1.5.10.30.12.1.5
-- 1.3.6.1.4.1.37950.1.1.5.10.30.12.1.5
-- 1.3.6.1.4.1.37950.1.1.5.10.30.12.1.5
-- 1.3.6.1.4.1.37950.1.1.5.10.30.12.1.5
-- 1.3.6.1.4.1.37950.1.1.5.10.30.12.1.5
-- 1.3.6.1.4.1.37950.1.1.5.10.30.12.1.5
-- 1.3.6.1.4.1.37950.1.1.5.10.30.12.1.5
-- 1.3.6.1.4.1.37950.1.1.5.10.30.12.1.5
		-- 1.3.6.1.4.1.37950.1.1.5.10.30.12.1.5
		pimInfNbrCount OBJECT-TYPE
			SYNTAX Integer32
			MAX-ACCESS read-only
			STATUS current
			DESCRIPTION
				"Description."
			::= { pimInfEntry 5 }

		
--          1.3.6.1.4.1.37950.1.1.5.10.30.12.1.6
-- 1.3.6.1.4.1.37950.1.1.5.10.30.12.1.6
-- 1.3.6.1.4.1.37950.1.1.5.10.30.12.1.6
-- 1.3.6.1.4.1.37950.1.1.5.10.30.12.1.6
-- 1.3.6.1.4.1.37950.1.1.5.10.30.12.1.6
-- 1.3.6.1.4.1.37950.1.1.5.10.30.12.1.6
-- 1.3.6.1.4.1.37950.1.1.5.10.30.12.1.6
-- 1.3.6.1.4.1.37950.1.1.5.10.30.12.1.6
-- 1.3.6.1.4.1.37950.1.1.5.10.30.12.1.6
		-- 1.3.6.1.4.1.37950.1.1.5.10.30.12.1.6
		pimInfQueryIntvl OBJECT-TYPE
			SYNTAX Integer32
			MAX-ACCESS read-only
			STATUS current
			DESCRIPTION
				"Description."
			::= { pimInfEntry 6 }

		
--          1.3.6.1.4.1.37950.1.1.5.10.30.12.1.7
-- 1.3.6.1.4.1.37950.1.1.5.10.30.12.1.7
-- 1.3.6.1.4.1.37950.1.1.5.10.30.12.1.7
-- 1.3.6.1.4.1.37950.1.1.5.10.30.12.1.7
-- 1.3.6.1.4.1.37950.1.1.5.10.30.12.1.7
-- 1.3.6.1.4.1.37950.1.1.5.10.30.12.1.7
-- 1.3.6.1.4.1.37950.1.1.5.10.30.12.1.7
-- 1.3.6.1.4.1.37950.1.1.5.10.30.12.1.7
-- 1.3.6.1.4.1.37950.1.1.5.10.30.12.1.7
		-- 1.3.6.1.4.1.37950.1.1.5.10.30.12.1.7
		pimInfDRPriority OBJECT-TYPE
			SYNTAX Unsigned32
			MAX-ACCESS read-only
			STATUS current
			DESCRIPTION
				"Description."
			::= { pimInfEntry 7 }

		
--          1.3.6.1.4.1.37950.1.1.5.10.30.12.1.8
-- 1.3.6.1.4.1.37950.1.1.5.10.30.12.1.8
-- 1.3.6.1.4.1.37950.1.1.5.10.30.12.1.8
-- 1.3.6.1.4.1.37950.1.1.5.10.30.12.1.8
-- 1.3.6.1.4.1.37950.1.1.5.10.30.12.1.8
-- 1.3.6.1.4.1.37950.1.1.5.10.30.12.1.8
-- 1.3.6.1.4.1.37950.1.1.5.10.30.12.1.8
-- 1.3.6.1.4.1.37950.1.1.5.10.30.12.1.8
-- 1.3.6.1.4.1.37950.1.1.5.10.30.12.1.8
		-- 1.3.6.1.4.1.37950.1.1.5.10.30.12.1.8
		pimInfDR OBJECT-TYPE
			SYNTAX IpAddress
			MAX-ACCESS read-only
			STATUS current
			DESCRIPTION
				"Description."
			::= { pimInfEntry 8 }

		
--          1.3.6.1.4.1.37950.1.1.5.10.30.13
-- 1.3.6.1.4.1.37950.1.1.5.10.30.13
-- 1.3.6.1.4.1.37950.1.1.5.10.30.13
-- 1.3.6.1.4.1.37950.1.1.5.10.30.13
-- 1.3.6.1.4.1.37950.1.1.5.10.30.13
-- 1.3.6.1.4.1.37950.1.1.5.10.30.13
-- 1.3.6.1.4.1.37950.1.1.5.10.30.13
-- 1.3.6.1.4.1.37950.1.1.5.10.30.13
-- 1.3.6.1.4.1.37950.1.1.5.10.30.13
		-- 1.3.6.1.4.1.37950.1.1.5.10.30.13
		pimRPsTable OBJECT-TYPE
			SYNTAX SEQUENCE OF PimRPsEntry
			MAX-ACCESS not-accessible
			STATUS current
			DESCRIPTION
				"Description."
			::= { v1600dPim 13 }

		
--          1.3.6.1.4.1.37950.1.1.5.10.30.13.1
-- 1.3.6.1.4.1.37950.1.1.5.10.30.13.1
-- 1.3.6.1.4.1.37950.1.1.5.10.30.13.1
-- 1.3.6.1.4.1.37950.1.1.5.10.30.13.1
-- 1.3.6.1.4.1.37950.1.1.5.10.30.13.1
-- 1.3.6.1.4.1.37950.1.1.5.10.30.13.1
-- 1.3.6.1.4.1.37950.1.1.5.10.30.13.1
-- 1.3.6.1.4.1.37950.1.1.5.10.30.13.1
-- 1.3.6.1.4.1.37950.1.1.5.10.30.13.1
		-- 1.3.6.1.4.1.37950.1.1.5.10.30.13.1
		pimRPsEntry OBJECT-TYPE
			SYNTAX PimRPsEntry
			MAX-ACCESS not-accessible
			STATUS current
			DESCRIPTION
				"Description."
			INDEX { pimRPsIndex }
			::= { pimRPsTable 1 }

		
		PimRPsEntry ::=
			SEQUENCE { 
				pimRPsIndex
					Integer32,
				pimRPGroup
					IpAddress,
				pimRPGroupMaskLen
					Integer32,
				pimRPAddr
					IpAddress,
				pimRPIncoming
					OCTET STRING,
				pimRPPriority
					Integer32,
				pimRPHoldtime
					Integer32,
				pimRPType
					INTEGER
			 }

--          1.3.6.1.4.1.37950.1.1.5.10.30.13.1.1
-- 1.3.6.1.4.1.37950.1.1.5.10.30.13.1.1
-- 1.3.6.1.4.1.37950.1.1.5.10.30.13.1.1
-- 1.3.6.1.4.1.37950.1.1.5.10.30.13.1.1
-- 1.3.6.1.4.1.37950.1.1.5.10.30.13.1.1
-- 1.3.6.1.4.1.37950.1.1.5.10.30.13.1.1
-- 1.3.6.1.4.1.37950.1.1.5.10.30.13.1.1
-- 1.3.6.1.4.1.37950.1.1.5.10.30.13.1.1
-- 1.3.6.1.4.1.37950.1.1.5.10.30.13.1.1
		-- 1.3.6.1.4.1.37950.1.1.5.10.30.13.1.1
		pimRPsIndex OBJECT-TYPE
			SYNTAX Integer32
			MAX-ACCESS not-accessible
			STATUS current
			DESCRIPTION
				"Description."
			::= { pimRPsEntry 1 }

		
--          1.3.6.1.4.1.37950.1.1.5.10.30.13.1.2
-- 1.3.6.1.4.1.37950.1.1.5.10.30.13.1.2
-- 1.3.6.1.4.1.37950.1.1.5.10.30.13.1.2
-- 1.3.6.1.4.1.37950.1.1.5.10.30.13.1.2
-- 1.3.6.1.4.1.37950.1.1.5.10.30.13.1.2
-- 1.3.6.1.4.1.37950.1.1.5.10.30.13.1.2
-- 1.3.6.1.4.1.37950.1.1.5.10.30.13.1.2
-- 1.3.6.1.4.1.37950.1.1.5.10.30.13.1.2
-- 1.3.6.1.4.1.37950.1.1.5.10.30.13.1.2
		-- 1.3.6.1.4.1.37950.1.1.5.10.30.13.1.2
		pimRPGroup OBJECT-TYPE
			SYNTAX IpAddress
			MAX-ACCESS read-only
			STATUS current
			DESCRIPTION
				"Description."
			::= { pimRPsEntry 2 }

		
--          1.3.6.1.4.1.37950.1.1.5.10.30.13.1.2
-- 1.3.6.1.4.1.37950.1.1.5.10.30.13.1.3
-- 1.3.6.1.4.1.37950.1.1.5.10.30.13.1.3
-- 1.3.6.1.4.1.37950.1.1.5.10.30.13.1.3
-- 1.3.6.1.4.1.37950.1.1.5.10.30.13.1.3
-- 1.3.6.1.4.1.37950.1.1.5.10.30.13.1.3
-- 1.3.6.1.4.1.37950.1.1.5.10.30.13.1.3
-- 1.3.6.1.4.1.37950.1.1.5.10.30.13.1.3
-- 1.3.6.1.4.1.37950.1.1.5.10.30.13.1.3
		-- 1.3.6.1.4.1.37950.1.1.5.10.30.13.1.3
		pimRPGroupMaskLen OBJECT-TYPE
			SYNTAX Integer32
			MAX-ACCESS read-only
			STATUS current
			DESCRIPTION
				"Description."
			::= { pimRPsEntry 3 }

		
--          1.3.6.1.4.1.37950.1.1.5.10.30.13.1.3
-- 1.3.6.1.4.1.37950.1.1.5.10.30.13.1.4
-- 1.3.6.1.4.1.37950.1.1.5.10.30.13.1.4
-- 1.3.6.1.4.1.37950.1.1.5.10.30.13.1.4
-- 1.3.6.1.4.1.37950.1.1.5.10.30.13.1.4
-- 1.3.6.1.4.1.37950.1.1.5.10.30.13.1.4
-- 1.3.6.1.4.1.37950.1.1.5.10.30.13.1.4
-- 1.3.6.1.4.1.37950.1.1.5.10.30.13.1.4
-- 1.3.6.1.4.1.37950.1.1.5.10.30.13.1.4
		-- 1.3.6.1.4.1.37950.1.1.5.10.30.13.1.4
		pimRPAddr OBJECT-TYPE
			SYNTAX IpAddress
			MAX-ACCESS read-only
			STATUS current
			DESCRIPTION
				"Description."
			::= { pimRPsEntry 4 }

		
--          1.3.6.1.4.1.37950.1.1.5.10.30.13.1.4
-- 1.3.6.1.4.1.37950.1.1.5.10.30.13.1.5
-- 1.3.6.1.4.1.37950.1.1.5.10.30.13.1.5
-- 1.3.6.1.4.1.37950.1.1.5.10.30.13.1.5
-- 1.3.6.1.4.1.37950.1.1.5.10.30.13.1.5
-- 1.3.6.1.4.1.37950.1.1.5.10.30.13.1.5
-- 1.3.6.1.4.1.37950.1.1.5.10.30.13.1.5
-- 1.3.6.1.4.1.37950.1.1.5.10.30.13.1.5
-- 1.3.6.1.4.1.37950.1.1.5.10.30.13.1.5
		-- 1.3.6.1.4.1.37950.1.1.5.10.30.13.1.5
		pimRPIncoming OBJECT-TYPE
			SYNTAX OCTET STRING
			MAX-ACCESS read-only
			STATUS current
			DESCRIPTION
				"Description."
			::= { pimRPsEntry 5 }

		
--          1.3.6.1.4.1.37950.1.1.5.10.30.13.1.5
-- 1.3.6.1.4.1.37950.1.1.5.10.30.13.1.6
-- 1.3.6.1.4.1.37950.1.1.5.10.30.13.1.6
-- 1.3.6.1.4.1.37950.1.1.5.10.30.13.1.6
-- 1.3.6.1.4.1.37950.1.1.5.10.30.13.1.6
-- 1.3.6.1.4.1.37950.1.1.5.10.30.13.1.6
-- 1.3.6.1.4.1.37950.1.1.5.10.30.13.1.6
-- 1.3.6.1.4.1.37950.1.1.5.10.30.13.1.6
-- 1.3.6.1.4.1.37950.1.1.5.10.30.13.1.6
		-- 1.3.6.1.4.1.37950.1.1.5.10.30.13.1.6
		pimRPPriority OBJECT-TYPE
			SYNTAX Integer32
			MAX-ACCESS read-only
			STATUS current
			DESCRIPTION
				"Description."
			::= { pimRPsEntry 6 }

		
--          1.3.6.1.4.1.37950.1.1.5.10.30.13.1.6
-- 1.3.6.1.4.1.37950.1.1.5.10.30.13.1.7
-- 1.3.6.1.4.1.37950.1.1.5.10.30.13.1.7
-- 1.3.6.1.4.1.37950.1.1.5.10.30.13.1.7
-- 1.3.6.1.4.1.37950.1.1.5.10.30.13.1.7
-- 1.3.6.1.4.1.37950.1.1.5.10.30.13.1.7
-- 1.3.6.1.4.1.37950.1.1.5.10.30.13.1.7
-- 1.3.6.1.4.1.37950.1.1.5.10.30.13.1.7
-- 1.3.6.1.4.1.37950.1.1.5.10.30.13.1.7
		-- 1.3.6.1.4.1.37950.1.1.5.10.30.13.1.7
		pimRPHoldtime OBJECT-TYPE
			SYNTAX Integer32
			MAX-ACCESS read-only
			STATUS current
			DESCRIPTION
				"Description."
			::= { pimRPsEntry 7 }

		
--          1.3.6.1.4.1.37950.1.1.5.10.30.13.1.7
-- 1.3.6.1.4.1.37950.1.1.5.10.30.13.1.8
-- 1.3.6.1.4.1.37950.1.1.5.10.30.13.1.8
-- 1.3.6.1.4.1.37950.1.1.5.10.30.13.1.8
-- 1.3.6.1.4.1.37950.1.1.5.10.30.13.1.8
-- 1.3.6.1.4.1.37950.1.1.5.10.30.13.1.8
-- 1.3.6.1.4.1.37950.1.1.5.10.30.13.1.8
-- 1.3.6.1.4.1.37950.1.1.5.10.30.13.1.8
-- 1.3.6.1.4.1.37950.1.1.5.10.30.13.1.8
		-- 1.3.6.1.4.1.37950.1.1.5.10.30.13.1.8
		pimRPType OBJECT-TYPE
			SYNTAX INTEGER
				{
				static(1),
				dynamic(2)
				}
			MAX-ACCESS read-only
			STATUS current
			DESCRIPTION
				"Description."
			::= { pimRPsEntry 8 }

		
--          1.3.6.1.4.1.37950.1.1.5.10.30.14
-- 1.3.6.1.4.1.37950.1.1.5.10.30.14
-- 1.3.6.1.4.1.37950.1.1.5.10.30.14
-- 1.3.6.1.4.1.37950.1.1.5.10.30.14
-- 1.3.6.1.4.1.37950.1.1.5.10.30.14
-- 1.3.6.1.4.1.37950.1.1.5.10.30.14
-- 1.3.6.1.4.1.37950.1.1.5.10.30.14
-- 1.3.6.1.4.1.37950.1.1.5.10.30.14
-- 1.3.6.1.4.1.37950.1.1.5.10.30.14
		-- 1.3.6.1.4.1.37950.1.1.5.10.30.14
		pimNbrTable OBJECT-TYPE
			SYNTAX SEQUENCE OF PimNbrEntry
			MAX-ACCESS not-accessible
			STATUS current
			DESCRIPTION
				"Description."
			::= { v1600dPim 14 }

		
--          1.3.6.1.4.1.37950.1.1.5.10.30.14.1
-- 1.3.6.1.4.1.37950.1.1.5.10.30.14.1
-- 1.3.6.1.4.1.37950.1.1.5.10.30.14.1
-- 1.3.6.1.4.1.37950.1.1.5.10.30.14.1
-- 1.3.6.1.4.1.37950.1.1.5.10.30.14.1
-- 1.3.6.1.4.1.37950.1.1.5.10.30.14.1
-- 1.3.6.1.4.1.37950.1.1.5.10.30.14.1
-- 1.3.6.1.4.1.37950.1.1.5.10.30.14.1
-- 1.3.6.1.4.1.37950.1.1.5.10.30.14.1
		-- 1.3.6.1.4.1.37950.1.1.5.10.30.14.1
		pimNbrEntry OBJECT-TYPE
			SYNTAX PimNbrEntry
			MAX-ACCESS not-accessible
			STATUS current
			DESCRIPTION
				"Description."
			INDEX { pimNbrAddress, pimNbrInterface }
			::= { pimNbrTable 1 }

		
		PimNbrEntry ::=
			SEQUENCE { 
				pimNbrAddress
					IpAddress,
				pimNbrInterface
					Integer32,
				pimNbrExpires
					TimeTicks,
				pimNbrVersion
					INTEGER,
				pimNbrDRPrio
					Unsigned32,
				pimNbrMode
					OCTET STRING
			 }

--          1.3.6.1.4.1.37950.1.1.5.10.30.14.1.1
-- 1.3.6.1.4.1.37950.1.1.5.10.30.14.1.1
-- 1.3.6.1.4.1.37950.1.1.5.10.30.14.1.1
-- 1.3.6.1.4.1.37950.1.1.5.10.30.14.1.1
-- 1.3.6.1.4.1.37950.1.1.5.10.30.14.1.1
-- 1.3.6.1.4.1.37950.1.1.5.10.30.14.1.1
-- 1.3.6.1.4.1.37950.1.1.5.10.30.14.1.1
-- 1.3.6.1.4.1.37950.1.1.5.10.30.14.1.1
-- 1.3.6.1.4.1.37950.1.1.5.10.30.14.1.1
		-- 1.3.6.1.4.1.37950.1.1.5.10.30.14.1.1
		pimNbrAddress OBJECT-TYPE
			SYNTAX IpAddress
			MAX-ACCESS read-only
			STATUS current
			DESCRIPTION
				"Description."
			::= { pimNbrEntry 1 }

		
--          1.3.6.1.4.1.37950.1.1.5.10.30.14.1.2
-- 1.3.6.1.4.1.37950.1.1.5.10.30.14.1.2
-- 1.3.6.1.4.1.37950.1.1.5.10.30.14.1.2
-- 1.3.6.1.4.1.37950.1.1.5.10.30.14.1.2
-- 1.3.6.1.4.1.37950.1.1.5.10.30.14.1.2
-- 1.3.6.1.4.1.37950.1.1.5.10.30.14.1.2
-- 1.3.6.1.4.1.37950.1.1.5.10.30.14.1.2
-- 1.3.6.1.4.1.37950.1.1.5.10.30.14.1.2
-- 1.3.6.1.4.1.37950.1.1.5.10.30.14.1.2
		-- 1.3.6.1.4.1.37950.1.1.5.10.30.14.1.2
		pimNbrInterface OBJECT-TYPE
			SYNTAX Integer32
			MAX-ACCESS read-only
			STATUS current
			DESCRIPTION
				"Description."
			::= { pimNbrEntry 2 }

		
--          1.3.6.1.4.1.37950.1.1.5.10.30.14.1.3
-- 1.3.6.1.4.1.37950.1.1.5.10.30.14.1.3
-- 1.3.6.1.4.1.37950.1.1.5.10.30.14.1.3
-- 1.3.6.1.4.1.37950.1.1.5.10.30.14.1.3
-- 1.3.6.1.4.1.37950.1.1.5.10.30.14.1.3
-- 1.3.6.1.4.1.37950.1.1.5.10.30.14.1.3
-- 1.3.6.1.4.1.37950.1.1.5.10.30.14.1.3
-- 1.3.6.1.4.1.37950.1.1.5.10.30.14.1.3
-- 1.3.6.1.4.1.37950.1.1.5.10.30.14.1.3
		-- 1.3.6.1.4.1.37950.1.1.5.10.30.14.1.3
		pimNbrExpires OBJECT-TYPE
			SYNTAX TimeTicks
			MAX-ACCESS read-only
			STATUS current
			DESCRIPTION
				"Description."
			::= { pimNbrEntry 3 }

		
--          1.3.6.1.4.1.37950.1.1.5.10.30.14.1.4
-- 1.3.6.1.4.1.37950.1.1.5.10.30.14.1.4
-- 1.3.6.1.4.1.37950.1.1.5.10.30.14.1.4
-- 1.3.6.1.4.1.37950.1.1.5.10.30.14.1.4
-- 1.3.6.1.4.1.37950.1.1.5.10.30.14.1.4
-- 1.3.6.1.4.1.37950.1.1.5.10.30.14.1.4
-- 1.3.6.1.4.1.37950.1.1.5.10.30.14.1.4
-- 1.3.6.1.4.1.37950.1.1.5.10.30.14.1.4
-- 1.3.6.1.4.1.37950.1.1.5.10.30.14.1.4
		-- 1.3.6.1.4.1.37950.1.1.5.10.30.14.1.4
		pimNbrVersion OBJECT-TYPE
			SYNTAX INTEGER
				{
				v1(1),
				v2(2)
				}
			MAX-ACCESS read-only
			STATUS current
			DESCRIPTION
				"Description."
			::= { pimNbrEntry 4 }

		
--          1.3.6.1.4.1.37950.1.1.5.10.30.14.1.5
-- 1.3.6.1.4.1.37950.1.1.5.10.30.14.1.5
-- 1.3.6.1.4.1.37950.1.1.5.10.30.14.1.5
-- 1.3.6.1.4.1.37950.1.1.5.10.30.14.1.5
-- 1.3.6.1.4.1.37950.1.1.5.10.30.14.1.5
-- 1.3.6.1.4.1.37950.1.1.5.10.30.14.1.5
-- 1.3.6.1.4.1.37950.1.1.5.10.30.14.1.5
-- 1.3.6.1.4.1.37950.1.1.5.10.30.14.1.5
-- 1.3.6.1.4.1.37950.1.1.5.10.30.14.1.5
		-- 1.3.6.1.4.1.37950.1.1.5.10.30.14.1.5
		pimNbrDRPrio OBJECT-TYPE
			SYNTAX Unsigned32
			MAX-ACCESS read-only
			STATUS current
			DESCRIPTION
				"Description."
			::= { pimNbrEntry 5 }

		
--          1.3.6.1.4.1.37950.1.1.5.10.30.14.1.6
-- 1.3.6.1.4.1.37950.1.1.5.10.30.14.1.6
-- 1.3.6.1.4.1.37950.1.1.5.10.30.14.1.6
-- 1.3.6.1.4.1.37950.1.1.5.10.30.14.1.6
-- 1.3.6.1.4.1.37950.1.1.5.10.30.14.1.6
-- 1.3.6.1.4.1.37950.1.1.5.10.30.14.1.6
-- 1.3.6.1.4.1.37950.1.1.5.10.30.14.1.6
-- 1.3.6.1.4.1.37950.1.1.5.10.30.14.1.6
-- 1.3.6.1.4.1.37950.1.1.5.10.30.14.1.6
		-- 1.3.6.1.4.1.37950.1.1.5.10.30.14.1.6
		pimNbrMode OBJECT-TYPE
			SYNTAX OCTET STRING
			MAX-ACCESS read-only
			STATUS current
			DESCRIPTION
				"Description."
			::= { pimNbrEntry 6 }

		
--          1.3.6.1.4.1.37950.1.1.5.10.30.15
-- 1.3.6.1.4.1.37950.1.1.5.10.30.15
-- 1.3.6.1.4.1.37950.1.1.5.10.30.15
-- 1.3.6.1.4.1.37950.1.1.5.10.30.15
-- 1.3.6.1.4.1.37950.1.1.5.10.30.15
-- 1.3.6.1.4.1.37950.1.1.5.10.30.15
-- 1.3.6.1.4.1.37950.1.1.5.10.30.15
-- 1.3.6.1.4.1.37950.1.1.5.10.30.15
-- 1.3.6.1.4.1.37950.1.1.5.10.30.15
		-- 1.3.6.1.4.1.37950.1.1.5.10.30.15
		pimBSRRouterTable OBJECT-TYPE
			SYNTAX SEQUENCE OF PimBSRRouterEntry
			MAX-ACCESS not-accessible
			STATUS current
			DESCRIPTION
				"Description."
			::= { v1600dPim 15 }

		
--          1.3.6.1.4.1.37950.1.1.5.10.30.15.1
-- 1.3.6.1.4.1.37950.1.1.5.10.30.15.1
-- 1.3.6.1.4.1.37950.1.1.5.10.30.15.1
-- 1.3.6.1.4.1.37950.1.1.5.10.30.15.1
-- 1.3.6.1.4.1.37950.1.1.5.10.30.15.1
-- 1.3.6.1.4.1.37950.1.1.5.10.30.15.1
-- 1.3.6.1.4.1.37950.1.1.5.10.30.15.1
-- 1.3.6.1.4.1.37950.1.1.5.10.30.15.1
-- 1.3.6.1.4.1.37950.1.1.5.10.30.15.1
		-- 1.3.6.1.4.1.37950.1.1.5.10.30.15.1
		pimBSRRouterEntry OBJECT-TYPE
			SYNTAX PimBSRRouterEntry
			MAX-ACCESS not-accessible
			STATUS current
			DESCRIPTION
				"Description."
			INDEX { pimBSRAddress }
			::= { pimBSRRouterTable 1 }

		
		PimBSRRouterEntry ::=
			SEQUENCE { 
				pimBSRAddress
					IpAddress,
				pimBSRPriority
					Unsigned32,
				pimBSRMaskLen
					Integer32,
				pimBSRCandidateAddr
					IpAddress,
				pimBSRCandidatePriority
					Unsigned32,
				pimBSRCandidateMaskLen
					Integer32
			 }

--          1.3.6.1.4.1.37950.1.1.5.10.30.15.1.1
-- 1.3.6.1.4.1.37950.1.1.5.10.30.15.1.1
-- 1.3.6.1.4.1.37950.1.1.5.10.30.15.1.1
-- 1.3.6.1.4.1.37950.1.1.5.10.30.15.1.1
-- 1.3.6.1.4.1.37950.1.1.5.10.30.15.1.1
-- 1.3.6.1.4.1.37950.1.1.5.10.30.15.1.1
-- 1.3.6.1.4.1.37950.1.1.5.10.30.15.1.1
-- 1.3.6.1.4.1.37950.1.1.5.10.30.15.1.1
-- 1.3.6.1.4.1.37950.1.1.5.10.30.15.1.1
		-- 1.3.6.1.4.1.37950.1.1.5.10.30.15.1.1
		pimBSRAddress OBJECT-TYPE
			SYNTAX IpAddress
			MAX-ACCESS read-only
			STATUS current
			DESCRIPTION
				"Description."
			::= { pimBSRRouterEntry 1 }

		
--          1.3.6.1.4.1.37950.1.1.5.10.30.15.1.2
-- 1.3.6.1.4.1.37950.1.1.5.10.30.15.1.2
-- 1.3.6.1.4.1.37950.1.1.5.10.30.15.1.2
-- 1.3.6.1.4.1.37950.1.1.5.10.30.15.1.2
-- 1.3.6.1.4.1.37950.1.1.5.10.30.15.1.2
-- 1.3.6.1.4.1.37950.1.1.5.10.30.15.1.2
-- 1.3.6.1.4.1.37950.1.1.5.10.30.15.1.2
-- 1.3.6.1.4.1.37950.1.1.5.10.30.15.1.2
-- 1.3.6.1.4.1.37950.1.1.5.10.30.15.1.2
		-- 1.3.6.1.4.1.37950.1.1.5.10.30.15.1.2
		pimBSRPriority OBJECT-TYPE
			SYNTAX Unsigned32
			MAX-ACCESS read-only
			STATUS current
			DESCRIPTION
				"Description."
			::= { pimBSRRouterEntry 2 }

		
--          1.3.6.1.4.1.37950.1.1.5.10.30.15.1.3
-- 1.3.6.1.4.1.37950.1.1.5.10.30.15.1.3
-- 1.3.6.1.4.1.37950.1.1.5.10.30.15.1.3
-- 1.3.6.1.4.1.37950.1.1.5.10.30.15.1.3
-- 1.3.6.1.4.1.37950.1.1.5.10.30.15.1.3
-- 1.3.6.1.4.1.37950.1.1.5.10.30.15.1.3
-- 1.3.6.1.4.1.37950.1.1.5.10.30.15.1.3
-- 1.3.6.1.4.1.37950.1.1.5.10.30.15.1.3
-- 1.3.6.1.4.1.37950.1.1.5.10.30.15.1.3
		-- 1.3.6.1.4.1.37950.1.1.5.10.30.15.1.3
		pimBSRMaskLen OBJECT-TYPE
			SYNTAX Integer32
			MAX-ACCESS read-only
			STATUS current
			DESCRIPTION
				"Description."
			::= { pimBSRRouterEntry 3 }

		
--          1.3.6.1.4.1.37950.1.1.5.10.30.15.1.4
-- 1.3.6.1.4.1.37950.1.1.5.10.30.15.1.4
-- 1.3.6.1.4.1.37950.1.1.5.10.30.15.1.4
-- 1.3.6.1.4.1.37950.1.1.5.10.30.15.1.4
-- 1.3.6.1.4.1.37950.1.1.5.10.30.15.1.4
-- 1.3.6.1.4.1.37950.1.1.5.10.30.15.1.4
-- 1.3.6.1.4.1.37950.1.1.5.10.30.15.1.4
-- 1.3.6.1.4.1.37950.1.1.5.10.30.15.1.4
-- 1.3.6.1.4.1.37950.1.1.5.10.30.15.1.4
		-- 1.3.6.1.4.1.37950.1.1.5.10.30.15.1.4
		pimBSRCandidateAddr OBJECT-TYPE
			SYNTAX IpAddress
			MAX-ACCESS read-only
			STATUS current
			DESCRIPTION
				"Description."
			::= { pimBSRRouterEntry 4 }

		
--          1.3.6.1.4.1.37950.1.1.5.10.30.15.1.5
-- 1.3.6.1.4.1.37950.1.1.5.10.30.15.1.5
-- 1.3.6.1.4.1.37950.1.1.5.10.30.15.1.5
-- 1.3.6.1.4.1.37950.1.1.5.10.30.15.1.5
-- 1.3.6.1.4.1.37950.1.1.5.10.30.15.1.5
-- 1.3.6.1.4.1.37950.1.1.5.10.30.15.1.5
-- 1.3.6.1.4.1.37950.1.1.5.10.30.15.1.5
-- 1.3.6.1.4.1.37950.1.1.5.10.30.15.1.5
-- 1.3.6.1.4.1.37950.1.1.5.10.30.15.1.5
		-- 1.3.6.1.4.1.37950.1.1.5.10.30.15.1.5
		pimBSRCandidatePriority OBJECT-TYPE
			SYNTAX Unsigned32
			MAX-ACCESS read-only
			STATUS current
			DESCRIPTION
				"Description."
			::= { pimBSRRouterEntry 5 }

		
--          1.3.6.1.4.1.37950.1.1.5.10.30.15.1.6
-- 1.3.6.1.4.1.37950.1.1.5.10.30.15.1.6
-- 1.3.6.1.4.1.37950.1.1.5.10.30.15.1.6
-- 1.3.6.1.4.1.37950.1.1.5.10.30.15.1.6
-- 1.3.6.1.4.1.37950.1.1.5.10.30.15.1.6
-- 1.3.6.1.4.1.37950.1.1.5.10.30.15.1.6
-- 1.3.6.1.4.1.37950.1.1.5.10.30.15.1.6
-- 1.3.6.1.4.1.37950.1.1.5.10.30.15.1.6
-- 1.3.6.1.4.1.37950.1.1.5.10.30.15.1.6
		-- 1.3.6.1.4.1.37950.1.1.5.10.30.15.1.6
		pimBSRCandidateMaskLen OBJECT-TYPE
			SYNTAX Integer32
			MAX-ACCESS read-only
			STATUS current
			DESCRIPTION
				"Description."
			::= { pimBSRRouterEntry 6 }

		
--           1.3.6.1.4.1.37950.1.1.5.10.30
-- 1.3.6.1.4.1.37950.1.1.5.10.30
-- 1.3.6.1.4.1.37950.1.1.5.10.31
-- 1.3.6.1.4.1.37950.1.1.5.10.31
-- 1.3.6.1.4.1.37950.1.1.5.10.31
-- 1.3.6.1.4.1.37950.1.1.5.10.31
-- 1.3.6.1.4.1.37950.1.1.5.10.31
-- 1.3.6.1.4.1.37950.1.1.5.10.31
-- 1.3.6.1.4.1.37950.1.1.5.10.31
-- 1.3.6.1.4.1.37950.1.1.5.10.31
		-- 1.3.6.1.4.1.37950.1.1.5.10.31
		v1600dPPPoE OBJECT IDENTIFIER ::= { v1600dSwitch 31 }

		
--           1.3.6.1.4.1.37950.1.1.5.10.30.1
-- 1.3.6.1.4.1.37950.1.1.5.10.30.1
-- 1.3.6.1.4.1.37950.1.1.5.10.31.1
-- 1.3.6.1.4.1.37950.1.1.5.10.31.1
-- 1.3.6.1.4.1.37950.1.1.5.10.31.1
-- 1.3.6.1.4.1.37950.1.1.5.10.31.1
-- 1.3.6.1.4.1.37950.1.1.5.10.31.1
-- 1.3.6.1.4.1.37950.1.1.5.10.31.1
-- 1.3.6.1.4.1.37950.1.1.5.10.31.1
-- 1.3.6.1.4.1.37950.1.1.5.10.31.1
		-- 1.3.6.1.4.1.37950.1.1.5.10.31.1
		pppoeIaCfg OBJECT IDENTIFIER ::= { v1600dPPPoE 1 }

		
--           1.3.6.1.4.1.37950.1.1.5.10.30.1.1
-- 1.3.6.1.4.1.37950.1.1.5.10.30.1.1
-- 1.3.6.1.4.1.37950.1.1.5.10.31.1.1
-- 1.3.6.1.4.1.37950.1.1.5.10.31.1.1
-- 1.3.6.1.4.1.37950.1.1.5.10.31.1.1
-- 1.3.6.1.4.1.37950.1.1.5.10.31.1.1
-- 1.3.6.1.4.1.37950.1.1.5.10.31.1.1
-- 1.3.6.1.4.1.37950.1.1.5.10.31.1.1
-- 1.3.6.1.4.1.37950.1.1.5.10.31.1.1
-- 1.3.6.1.4.1.37950.1.1.5.10.31.1.1
		-- 1.3.6.1.4.1.37950.1.1.5.10.31.1.1
		pppoeIaEnable OBJECT-TYPE
			SYNTAX INTEGER
				{
				disable(0),
				enable(1)
				}
			MAX-ACCESS read-write
			STATUS current
			DESCRIPTION
				"Description."
			::= { pppoeIaCfg 1 }

		
--           1.3.6.1.4.1.37950.1.1.5.10.30.1.2
-- 1.3.6.1.4.1.37950.1.1.5.10.30.1.2
-- 1.3.6.1.4.1.37950.1.1.5.10.31.1.2
-- 1.3.6.1.4.1.37950.1.1.5.10.31.1.2
-- 1.3.6.1.4.1.37950.1.1.5.10.31.1.2
-- 1.3.6.1.4.1.37950.1.1.5.10.31.1.2
-- 1.3.6.1.4.1.37950.1.1.5.10.31.1.2
-- 1.3.6.1.4.1.37950.1.1.5.10.31.1.2
-- 1.3.6.1.4.1.37950.1.1.5.10.31.1.2
-- 1.3.6.1.4.1.37950.1.1.5.10.31.1.2
		-- 1.3.6.1.4.1.37950.1.1.5.10.31.1.2
		pppoeIaVendorId OBJECT-TYPE
			SYNTAX Unsigned32
			MAX-ACCESS read-write
			STATUS current
			DESCRIPTION
				"Description."
			::= { pppoeIaCfg 2 }

		
--           1.3.6.1.4.1.37950.1.1.5.10.30.1.3
-- 1.3.6.1.4.1.37950.1.1.5.10.30.1.3
-- 1.3.6.1.4.1.37950.1.1.5.10.31.1.3
-- 1.3.6.1.4.1.37950.1.1.5.10.31.1.3
-- 1.3.6.1.4.1.37950.1.1.5.10.31.1.3
-- 1.3.6.1.4.1.37950.1.1.5.10.31.1.3
-- 1.3.6.1.4.1.37950.1.1.5.10.31.1.3
-- 1.3.6.1.4.1.37950.1.1.5.10.31.1.3
-- 1.3.6.1.4.1.37950.1.1.5.10.31.1.3
-- 1.3.6.1.4.1.37950.1.1.5.10.31.1.3
		-- 1.3.6.1.4.1.37950.1.1.5.10.31.1.3
		pppoeIaEncapsulation OBJECT-TYPE
			SYNTAX INTEGER
				{
				null(0),
				circuit(1),
				remote(2),
				circuitremote(3)
				}
			MAX-ACCESS read-write
			STATUS current
			DESCRIPTION
				"Description."
			::= { pppoeIaCfg 3 }

		
--           1.3.6.1.4.1.37950.1.1.5.10.30.1.4
-- 1.3.6.1.4.1.37950.1.1.5.10.30.1.4
-- 1.3.6.1.4.1.37950.1.1.5.10.31.1.4
-- 1.3.6.1.4.1.37950.1.1.5.10.31.1.4
-- 1.3.6.1.4.1.37950.1.1.5.10.31.1.4
-- 1.3.6.1.4.1.37950.1.1.5.10.31.1.4
-- 1.3.6.1.4.1.37950.1.1.5.10.31.1.4
-- 1.3.6.1.4.1.37950.1.1.5.10.31.1.4
-- 1.3.6.1.4.1.37950.1.1.5.10.31.1.4
-- 1.3.6.1.4.1.37950.1.1.5.10.31.1.4
		-- 1.3.6.1.4.1.37950.1.1.5.10.31.1.4
		pppoeIaPolicy OBJECT-TYPE
			SYNTAX INTEGER
				{
				drop(0),
				keep(1),
				replace(2)
				}
			MAX-ACCESS read-write
			STATUS current
			DESCRIPTION
				"Description."
			::= { pppoeIaCfg 4 }

		
--           1.3.6.1.4.1.37950.1.1.5.10.30.1.5
-- 1.3.6.1.4.1.37950.1.1.5.10.30.1.5
-- 1.3.6.1.4.1.37950.1.1.5.10.31.1.5
-- 1.3.6.1.4.1.37950.1.1.5.10.31.1.5
-- 1.3.6.1.4.1.37950.1.1.5.10.31.1.5
-- 1.3.6.1.4.1.37950.1.1.5.10.31.1.5
-- 1.3.6.1.4.1.37950.1.1.5.10.31.1.5
-- 1.3.6.1.4.1.37950.1.1.5.10.31.1.5
-- 1.3.6.1.4.1.37950.1.1.5.10.31.1.5
-- 1.3.6.1.4.1.37950.1.1.5.10.31.1.5
		-- 1.3.6.1.4.1.37950.1.1.5.10.31.1.5
		pppoeIaIgnoreReply OBJECT-TYPE
			SYNTAX INTEGER
				{
				disable(0),
				enable(1)
				}
			MAX-ACCESS read-write
			STATUS current
			DESCRIPTION
				"Description."
			::= { pppoeIaCfg 5 }

		
--          1.3.6.1.4.1.37950.1.1.5.10.30.1.6
-- 1.3.6.1.4.1.37950.1.1.5.10.31.1.6
-- 1.3.6.1.4.1.37950.1.1.5.10.31.1.6
-- 1.3.6.1.4.1.37950.1.1.5.10.31.1.6
-- 1.3.6.1.4.1.37950.1.1.5.10.31.1.6
-- 1.3.6.1.4.1.37950.1.1.5.10.31.1.6
-- 1.3.6.1.4.1.37950.1.1.5.10.31.1.6
-- 1.3.6.1.4.1.37950.1.1.5.10.31.1.6
-- 1.3.6.1.4.1.37950.1.1.5.10.31.1.6
		-- 1.3.6.1.4.1.37950.1.1.5.10.31.1.6
		pppoeIaCfgAction OBJECT-TYPE
			SYNTAX INTEGER { submit(1) }
			MAX-ACCESS read-write
			STATUS current
			DESCRIPTION
				"Description."
			::= { pppoeIaCfg 6 }

		
--           1.3.6.1.4.1.37950.1.1.5.10.30.2
-- 1.3.6.1.4.1.37950.1.1.5.10.30.2
-- 1.3.6.1.4.1.37950.1.1.5.10.31.2
-- 1.3.6.1.4.1.37950.1.1.5.10.31.2
-- 1.3.6.1.4.1.37950.1.1.5.10.31.2
-- 1.3.6.1.4.1.37950.1.1.5.10.31.2
-- 1.3.6.1.4.1.37950.1.1.5.10.31.2
-- 1.3.6.1.4.1.37950.1.1.5.10.31.2
-- 1.3.6.1.4.1.37950.1.1.5.10.31.2
-- 1.3.6.1.4.1.37950.1.1.5.10.31.2
		-- 1.3.6.1.4.1.37950.1.1.5.10.31.2
		pppoeIaVlan OBJECT IDENTIFIER ::= { v1600dPPPoE 2 }

		
--           1.3.6.1.4.1.37950.1.1.5.10.30.2.1
-- 1.3.6.1.4.1.37950.1.1.5.10.30.2.1
-- 1.3.6.1.4.1.37950.1.1.5.10.31.2.1
-- 1.3.6.1.4.1.37950.1.1.5.10.31.2.1
-- 1.3.6.1.4.1.37950.1.1.5.10.31.2.1
-- 1.3.6.1.4.1.37950.1.1.5.10.31.2.1
-- 1.3.6.1.4.1.37950.1.1.5.10.31.2.1
-- 1.3.6.1.4.1.37950.1.1.5.10.31.2.1
-- 1.3.6.1.4.1.37950.1.1.5.10.31.2.1
-- 1.3.6.1.4.1.37950.1.1.5.10.31.2.1
		-- 1.3.6.1.4.1.37950.1.1.5.10.31.2.1
		pppoeIaVlanId OBJECT-TYPE
			SYNTAX Unsigned32
			MAX-ACCESS read-write
			STATUS current
			DESCRIPTION
				"Description."
			::= { pppoeIaVlan 1 }

		
--           1.3.6.1.4.1.37950.1.1.5.10.30.2.2
-- 1.3.6.1.4.1.37950.1.1.5.10.30.2.2
-- 1.3.6.1.4.1.37950.1.1.5.10.31.2.2
-- 1.3.6.1.4.1.37950.1.1.5.10.31.2.2
-- 1.3.6.1.4.1.37950.1.1.5.10.31.2.2
-- 1.3.6.1.4.1.37950.1.1.5.10.31.2.2
-- 1.3.6.1.4.1.37950.1.1.5.10.31.2.2
-- 1.3.6.1.4.1.37950.1.1.5.10.31.2.2
-- 1.3.6.1.4.1.37950.1.1.5.10.31.2.2
-- 1.3.6.1.4.1.37950.1.1.5.10.31.2.2
		-- 1.3.6.1.4.1.37950.1.1.5.10.31.2.2
		pppoeIaVlanAction OBJECT-TYPE
			SYNTAX INTEGER
				{
				del(0),
				add(1)
				}
			MAX-ACCESS read-write
			STATUS current
			DESCRIPTION
				"Description."
			::= { pppoeIaVlan 2 }

		
--           1.3.6.1.4.1.37950.1.1.5.10.30.2.3
-- 1.3.6.1.4.1.37950.1.1.5.10.30.2.3
-- 1.3.6.1.4.1.37950.1.1.5.10.31.2.3
-- 1.3.6.1.4.1.37950.1.1.5.10.31.2.3
-- 1.3.6.1.4.1.37950.1.1.5.10.31.2.3
-- 1.3.6.1.4.1.37950.1.1.5.10.31.2.3
-- 1.3.6.1.4.1.37950.1.1.5.10.31.2.3
-- 1.3.6.1.4.1.37950.1.1.5.10.31.2.3
-- 1.3.6.1.4.1.37950.1.1.5.10.31.2.3
-- 1.3.6.1.4.1.37950.1.1.5.10.31.2.3
		-- 1.3.6.1.4.1.37950.1.1.5.10.31.2.3
		pppoeIaVlanList OBJECT-TYPE
			SYNTAX OCTET STRING
			MAX-ACCESS read-only
			STATUS current
			DESCRIPTION
				"Description."
			::= { pppoeIaVlan 3 }

		
--           1.3.6.1.4.1.37950.1.1.5.10.30.3
-- 1.3.6.1.4.1.37950.1.1.5.10.30.3
-- 1.3.6.1.4.1.37950.1.1.5.10.31.3
-- 1.3.6.1.4.1.37950.1.1.5.10.31.3
-- 1.3.6.1.4.1.37950.1.1.5.10.31.3
-- 1.3.6.1.4.1.37950.1.1.5.10.31.3
-- 1.3.6.1.4.1.37950.1.1.5.10.31.3
-- 1.3.6.1.4.1.37950.1.1.5.10.31.3
-- 1.3.6.1.4.1.37950.1.1.5.10.31.3
-- 1.3.6.1.4.1.37950.1.1.5.10.31.3
		-- 1.3.6.1.4.1.37950.1.1.5.10.31.3
		pppoeIaPortCfgTable OBJECT-TYPE
			SYNTAX SEQUENCE OF PppoeIaPortCfgEntry
			MAX-ACCESS not-accessible
			STATUS current
			DESCRIPTION
				"Description."
			::= { v1600dPPPoE 3 }

		
--           1.3.6.1.4.1.37950.1.1.5.10.30.3.1
-- 1.3.6.1.4.1.37950.1.1.5.10.30.3.1
-- 1.3.6.1.4.1.37950.1.1.5.10.31.3.1
-- 1.3.6.1.4.1.37950.1.1.5.10.31.3.1
-- 1.3.6.1.4.1.37950.1.1.5.10.31.3.1
-- 1.3.6.1.4.1.37950.1.1.5.10.31.3.1
-- 1.3.6.1.4.1.37950.1.1.5.10.31.3.1
-- 1.3.6.1.4.1.37950.1.1.5.10.31.3.1
-- 1.3.6.1.4.1.37950.1.1.5.10.31.3.1
-- 1.3.6.1.4.1.37950.1.1.5.10.31.3.1
		-- 1.3.6.1.4.1.37950.1.1.5.10.31.3.1
		pppoeIaPortCfgEntry OBJECT-TYPE
			SYNTAX PppoeIaPortCfgEntry
			MAX-ACCESS not-accessible
			STATUS current
			DESCRIPTION
				"Description."
			INDEX { pppoeIaPortIndex }
			::= { pppoeIaPortCfgTable 1 }

		
		PppoeIaPortCfgEntry ::=
			SEQUENCE { 
				pppoeIaPortIndex
					Unsigned32,
				pppoeIaPortType
					INTEGER,
				pppoeIaPortCircuitFormat
					INTEGER,
				pppoeIaPortCircuit
					OCTET STRING,
				pppoeIaPortRemoteFormat
					INTEGER,
				pppoeIaPortRemote
					OCTET STRING
			 }

--           1.3.6.1.4.1.37950.1.1.5.10.30.3.1.1
-- 1.3.6.1.4.1.37950.1.1.5.10.30.3.1.1
-- 1.3.6.1.4.1.37950.1.1.5.10.31.3.1.1
-- 1.3.6.1.4.1.37950.1.1.5.10.31.3.1.1
-- 1.3.6.1.4.1.37950.1.1.5.10.31.3.1.1
-- 1.3.6.1.4.1.37950.1.1.5.10.31.3.1.1
-- 1.3.6.1.4.1.37950.1.1.5.10.31.3.1.1
-- 1.3.6.1.4.1.37950.1.1.5.10.31.3.1.1
-- 1.3.6.1.4.1.37950.1.1.5.10.31.3.1.1
-- 1.3.6.1.4.1.37950.1.1.5.10.31.3.1.1
		-- 1.3.6.1.4.1.37950.1.1.5.10.31.3.1.1
		pppoeIaPortIndex OBJECT-TYPE
			SYNTAX Unsigned32
			MAX-ACCESS read-only
			STATUS current
			DESCRIPTION
				"Description."
			::= { pppoeIaPortCfgEntry 1 }

		
--           1.3.6.1.4.1.37950.1.1.5.10.30.3.1.2
-- 1.3.6.1.4.1.37950.1.1.5.10.30.3.1.2
-- 1.3.6.1.4.1.37950.1.1.5.10.31.3.1.2
-- 1.3.6.1.4.1.37950.1.1.5.10.31.3.1.2
-- 1.3.6.1.4.1.37950.1.1.5.10.31.3.1.2
-- 1.3.6.1.4.1.37950.1.1.5.10.31.3.1.2
-- 1.3.6.1.4.1.37950.1.1.5.10.31.3.1.2
-- 1.3.6.1.4.1.37950.1.1.5.10.31.3.1.2
-- 1.3.6.1.4.1.37950.1.1.5.10.31.3.1.2
-- 1.3.6.1.4.1.37950.1.1.5.10.31.3.1.2
		-- 1.3.6.1.4.1.37950.1.1.5.10.31.3.1.2
		pppoeIaPortType OBJECT-TYPE
			SYNTAX INTEGER
				{
				untrust(0),
				trust(1)
				}
			MAX-ACCESS read-write
			STATUS current
			DESCRIPTION
				"Description."
			::= { pppoeIaPortCfgEntry 2 }

		
--           1.3.6.1.4.1.37950.1.1.5.10.30.3.1.3
-- 1.3.6.1.4.1.37950.1.1.5.10.30.3.1.3
-- 1.3.6.1.4.1.37950.1.1.5.10.31.3.1.3
-- 1.3.6.1.4.1.37950.1.1.5.10.31.3.1.3
-- 1.3.6.1.4.1.37950.1.1.5.10.31.3.1.3
-- 1.3.6.1.4.1.37950.1.1.5.10.31.3.1.3
-- 1.3.6.1.4.1.37950.1.1.5.10.31.3.1.3
-- 1.3.6.1.4.1.37950.1.1.5.10.31.3.1.3
-- 1.3.6.1.4.1.37950.1.1.5.10.31.3.1.3
-- 1.3.6.1.4.1.37950.1.1.5.10.31.3.1.3
		-- 1.3.6.1.4.1.37950.1.1.5.10.31.3.1.3
		pppoeIaPortCircuitFormat OBJECT-TYPE
			SYNTAX INTEGER
				{
				common(0),
				extend(1),
				user-defined(2)
				}
			MAX-ACCESS read-write
			STATUS current
			DESCRIPTION
				"Description."
			::= { pppoeIaPortCfgEntry 3 }

		
--           1.3.6.1.4.1.37950.1.1.5.10.30.3.1.4
-- 1.3.6.1.4.1.37950.1.1.5.10.30.3.1.4
-- 1.3.6.1.4.1.37950.1.1.5.10.31.3.1.4
-- 1.3.6.1.4.1.37950.1.1.5.10.31.3.1.4
-- 1.3.6.1.4.1.37950.1.1.5.10.31.3.1.4
-- 1.3.6.1.4.1.37950.1.1.5.10.31.3.1.4
-- 1.3.6.1.4.1.37950.1.1.5.10.31.3.1.4
-- 1.3.6.1.4.1.37950.1.1.5.10.31.3.1.4
-- 1.3.6.1.4.1.37950.1.1.5.10.31.3.1.4
-- 1.3.6.1.4.1.37950.1.1.5.10.31.3.1.4
		-- 1.3.6.1.4.1.37950.1.1.5.10.31.3.1.4
		pppoeIaPortCircuit OBJECT-TYPE
			SYNTAX OCTET STRING
			MAX-ACCESS read-write
			STATUS current
			DESCRIPTION
				"Description."
			::= { pppoeIaPortCfgEntry 4 }

		
--           1.3.6.1.4.1.37950.1.1.5.10.30.3.1.5
-- 1.3.6.1.4.1.37950.1.1.5.10.30.3.1.5
-- 1.3.6.1.4.1.37950.1.1.5.10.31.3.1.5
-- 1.3.6.1.4.1.37950.1.1.5.10.31.3.1.5
-- 1.3.6.1.4.1.37950.1.1.5.10.31.3.1.5
-- 1.3.6.1.4.1.37950.1.1.5.10.31.3.1.5
-- 1.3.6.1.4.1.37950.1.1.5.10.31.3.1.5
-- 1.3.6.1.4.1.37950.1.1.5.10.31.3.1.5
-- 1.3.6.1.4.1.37950.1.1.5.10.31.3.1.5
-- 1.3.6.1.4.1.37950.1.1.5.10.31.3.1.5
		-- 1.3.6.1.4.1.37950.1.1.5.10.31.3.1.5
		pppoeIaPortRemoteFormat OBJECT-TYPE
			SYNTAX INTEGER
				{
				common(0),
				extend(1),
				user-defined(2)
				}
			MAX-ACCESS read-write
			STATUS current
			DESCRIPTION
				"Description."
			::= { pppoeIaPortCfgEntry 5 }

		
--           1.3.6.1.4.1.37950.1.1.5.10.30.3.1.6
-- 1.3.6.1.4.1.37950.1.1.5.10.30.3.1.6
-- 1.3.6.1.4.1.37950.1.1.5.10.31.3.1.6
-- 1.3.6.1.4.1.37950.1.1.5.10.31.3.1.6
-- 1.3.6.1.4.1.37950.1.1.5.10.31.3.1.6
-- 1.3.6.1.4.1.37950.1.1.5.10.31.3.1.6
-- 1.3.6.1.4.1.37950.1.1.5.10.31.3.1.6
-- 1.3.6.1.4.1.37950.1.1.5.10.31.3.1.6
-- 1.3.6.1.4.1.37950.1.1.5.10.31.3.1.6
-- 1.3.6.1.4.1.37950.1.1.5.10.31.3.1.6
		-- 1.3.6.1.4.1.37950.1.1.5.10.31.3.1.6
		pppoeIaPortRemote OBJECT-TYPE
			SYNTAX OCTET STRING
			MAX-ACCESS read-write
			STATUS current
			DESCRIPTION
				"Description."
			::= { pppoeIaPortCfgEntry 6 }

		
--         1.3.6.1.4.1.37950.1.1.5.10.32
-- 1.3.6.1.4.1.37950.1.1.5.10.32
-- 1.3.6.1.4.1.37950.1.1.5.10.32
-- 1.3.6.1.4.1.37950.1.1.5.10.32
-- 1.3.6.1.4.1.37950.1.1.5.10.32
-- 1.3.6.1.4.1.37950.1.1.5.10.32
-- 1.3.6.1.4.1.37950.1.1.5.10.32
-- 1.3.6.1.4.1.37950.1.1.5.10.32
		-- 1.3.6.1.4.1.37950.1.1.5.10.32
		v1600dBsClient OBJECT IDENTIFIER ::= { v1600dSwitch 32 }

		
--         1.3.6.1.4.1.37950.1.1.5.10.32.1
-- 1.3.6.1.4.1.37950.1.1.5.10.32.1
-- 1.3.6.1.4.1.37950.1.1.5.10.32.1
-- 1.3.6.1.4.1.37950.1.1.5.10.32.1
-- 1.3.6.1.4.1.37950.1.1.5.10.32.1
-- 1.3.6.1.4.1.37950.1.1.5.10.32.1
-- 1.3.6.1.4.1.37950.1.1.5.10.32.1
-- 1.3.6.1.4.1.37950.1.1.5.10.32.1
		-- 1.3.6.1.4.1.37950.1.1.5.10.32.1
		bsServer OBJECT-TYPE
			SYNTAX OCTET STRING
			MAX-ACCESS read-write
			STATUS current
			DESCRIPTION
				"Description."
			::= { v1600dBsClient 1 }

		
--         1.3.6.1.4.1.37950.1.1.5.10.32.2
-- 1.3.6.1.4.1.37950.1.1.5.10.32.2
-- 1.3.6.1.4.1.37950.1.1.5.10.32.2
-- 1.3.6.1.4.1.37950.1.1.5.10.32.2
-- 1.3.6.1.4.1.37950.1.1.5.10.32.2
-- 1.3.6.1.4.1.37950.1.1.5.10.32.2
-- 1.3.6.1.4.1.37950.1.1.5.10.32.2
-- 1.3.6.1.4.1.37950.1.1.5.10.32.2
		-- 1.3.6.1.4.1.37950.1.1.5.10.32.2
		bsUsername OBJECT-TYPE
			SYNTAX OCTET STRING
			MAX-ACCESS read-write
			STATUS current
			DESCRIPTION
				"Description."
			::= { v1600dBsClient 2 }

		
--         1.3.6.1.4.1.37950.1.1.5.10.32.3
-- 1.3.6.1.4.1.37950.1.1.5.10.32.3
-- 1.3.6.1.4.1.37950.1.1.5.10.32.3
-- 1.3.6.1.4.1.37950.1.1.5.10.32.3
-- 1.3.6.1.4.1.37950.1.1.5.10.32.3
-- 1.3.6.1.4.1.37950.1.1.5.10.32.3
-- 1.3.6.1.4.1.37950.1.1.5.10.32.3
-- 1.3.6.1.4.1.37950.1.1.5.10.32.3
		-- 1.3.6.1.4.1.37950.1.1.5.10.32.3
		bsPassword OBJECT-TYPE
			SYNTAX OCTET STRING
			MAX-ACCESS read-write
			STATUS current
			DESCRIPTION
				"Description."
			::= { v1600dBsClient 3 }

		
--         1.3.6.1.4.1.37950.1.1.5.10.32.4
-- 1.3.6.1.4.1.37950.1.1.5.10.32.4
-- 1.3.6.1.4.1.37950.1.1.5.10.32.4
-- 1.3.6.1.4.1.37950.1.1.5.10.32.4
-- 1.3.6.1.4.1.37950.1.1.5.10.32.4
-- 1.3.6.1.4.1.37950.1.1.5.10.32.4
-- 1.3.6.1.4.1.37950.1.1.5.10.32.4
-- 1.3.6.1.4.1.37950.1.1.5.10.32.4
		-- 1.3.6.1.4.1.37950.1.1.5.10.32.4
		bsSlaveServer OBJECT-TYPE
			SYNTAX OCTET STRING
			MAX-ACCESS read-write
			STATUS current
			DESCRIPTION
				"Description."
			::= { v1600dBsClient 4 }

		
--       1.3.6.1.4.1.37950.1.1.5.10.33
-- 1.3.6.1.4.1.37950.1.1.5.10.33
-- 1.3.6.1.4.1.37950.1.1.5.10.33
-- 1.3.6.1.4.1.37950.1.1.5.10.33
-- 1.3.6.1.4.1.37950.1.1.5.10.33
-- 1.3.6.1.4.1.37950.1.1.5.10.33
		-- 1.3.6.1.4.1.37950.1.1.5.10.33
		v1600dOspf6 OBJECT IDENTIFIER ::= { v1600dSwitch 33 }

		
--       1.3.6.1.4.1.37950.1.1.5.10.33.1
-- 1.3.6.1.4.1.37950.1.1.5.10.33.1
-- 1.3.6.1.4.1.37950.1.1.5.10.33.1
-- 1.3.6.1.4.1.37950.1.1.5.10.33.1
-- 1.3.6.1.4.1.37950.1.1.5.10.33.1
-- 1.3.6.1.4.1.37950.1.1.5.10.33.1
		-- 1.3.6.1.4.1.37950.1.1.5.10.33.1
		ospf6Information OBJECT IDENTIFIER ::= { v1600dOspf6 1 }

		
--       1.3.6.1.4.1.37950.1.1.5.10.33.1.1
-- 1.3.6.1.4.1.37950.1.1.5.10.33.1.1
-- 1.3.6.1.4.1.37950.1.1.5.10.33.1.1
-- 1.3.6.1.4.1.37950.1.1.5.10.33.1.1
-- 1.3.6.1.4.1.37950.1.1.5.10.33.1.1
-- 1.3.6.1.4.1.37950.1.1.5.10.33.1.1
		-- 1.3.6.1.4.1.37950.1.1.5.10.33.1.1
		ospf6NeighborTable OBJECT-TYPE
			SYNTAX SEQUENCE OF Ospf6NeighborEntry
			MAX-ACCESS not-accessible
			STATUS current
			DESCRIPTION
				"Description."
			::= { ospf6Information 1 }

		
--       1.3.6.1.4.1.37950.1.1.5.10.33.1.1.1
-- 1.3.6.1.4.1.37950.1.1.5.10.33.1.1.1
-- 1.3.6.1.4.1.37950.1.1.5.10.33.1.1.1
-- 1.3.6.1.4.1.37950.1.1.5.10.33.1.1.1
-- 1.3.6.1.4.1.37950.1.1.5.10.33.1.1.1
-- 1.3.6.1.4.1.37950.1.1.5.10.33.1.1.1
		-- 1.3.6.1.4.1.37950.1.1.5.10.33.1.1.1
		ospf6NeighborEntry OBJECT-TYPE
			SYNTAX Ospf6NeighborEntry
			MAX-ACCESS not-accessible
			STATUS current
			DESCRIPTION
				"Description."
			INDEX { ospf6NeighborIndex }
			::= { ospf6NeighborTable 1 }

		
		Ospf6NeighborEntry ::=
			SEQUENCE { 
				ospf6NeighborIndex
					Integer32,
				ospf6NeighborID
					OCTET STRING,
				ospf6NeighborPriority
					Integer32,
				ospf6NeighborDeadTime
					OCTET STRING,
				ospf6NeighborStateIfState
					OCTET STRING,
				ospf6NeighborDuration
					OCTET STRING,
				ospf6NeighborInterfaceState
					OCTET STRING
			 }

--       1.3.6.1.4.1.37950.1.1.5.10.33.1.1.1.1
-- 1.3.6.1.4.1.37950.1.1.5.10.33.1.1.1.1
-- 1.3.6.1.4.1.37950.1.1.5.10.33.1.1.1.1
-- 1.3.6.1.4.1.37950.1.1.5.10.33.1.1.1.1
-- 1.3.6.1.4.1.37950.1.1.5.10.33.1.1.1.1
-- 1.3.6.1.4.1.37950.1.1.5.10.33.1.1.1.1
		-- 1.3.6.1.4.1.37950.1.1.5.10.33.1.1.1.1
		ospf6NeighborIndex OBJECT-TYPE
			SYNTAX Integer32
			MAX-ACCESS read-only
			STATUS current
			DESCRIPTION
				"Description."
			::= { ospf6NeighborEntry 1 }

		
--       1.3.6.1.4.1.37950.1.1.5.10.33.1.1.1.2
-- 1.3.6.1.4.1.37950.1.1.5.10.33.1.1.1.2
-- 1.3.6.1.4.1.37950.1.1.5.10.33.1.1.1.2
-- 1.3.6.1.4.1.37950.1.1.5.10.33.1.1.1.2
-- 1.3.6.1.4.1.37950.1.1.5.10.33.1.1.1.2
-- 1.3.6.1.4.1.37950.1.1.5.10.33.1.1.1.2
		-- 1.3.6.1.4.1.37950.1.1.5.10.33.1.1.1.2
		ospf6NeighborID OBJECT-TYPE
			SYNTAX OCTET STRING
			MAX-ACCESS read-only
			STATUS current
			DESCRIPTION
				"Description."
			::= { ospf6NeighborEntry 2 }

		
--       1.3.6.1.4.1.37950.1.1.5.10.33.1.1.1.3
-- 1.3.6.1.4.1.37950.1.1.5.10.33.1.1.1.3
-- 1.3.6.1.4.1.37950.1.1.5.10.33.1.1.1.3
-- 1.3.6.1.4.1.37950.1.1.5.10.33.1.1.1.3
-- 1.3.6.1.4.1.37950.1.1.5.10.33.1.1.1.3
-- 1.3.6.1.4.1.37950.1.1.5.10.33.1.1.1.3
		-- 1.3.6.1.4.1.37950.1.1.5.10.33.1.1.1.3
		ospf6NeighborPriority OBJECT-TYPE
			SYNTAX Integer32
			MAX-ACCESS read-only
			STATUS current
			DESCRIPTION
				"Description."
			::= { ospf6NeighborEntry 3 }

		
--       1.3.6.1.4.1.37950.1.1.5.10.33.1.1.1.4
-- 1.3.6.1.4.1.37950.1.1.5.10.33.1.1.1.4
-- 1.3.6.1.4.1.37950.1.1.5.10.33.1.1.1.4
-- 1.3.6.1.4.1.37950.1.1.5.10.33.1.1.1.4
-- 1.3.6.1.4.1.37950.1.1.5.10.33.1.1.1.4
-- 1.3.6.1.4.1.37950.1.1.5.10.33.1.1.1.4
		-- 1.3.6.1.4.1.37950.1.1.5.10.33.1.1.1.4
		ospf6NeighborDeadTime OBJECT-TYPE
			SYNTAX OCTET STRING
			MAX-ACCESS read-only
			STATUS current
			DESCRIPTION
				"Description."
			::= { ospf6NeighborEntry 4 }

		
--       1.3.6.1.4.1.37950.1.1.5.10.33.1.1.1.5
-- 1.3.6.1.4.1.37950.1.1.5.10.33.1.1.1.5
-- 1.3.6.1.4.1.37950.1.1.5.10.33.1.1.1.5
-- 1.3.6.1.4.1.37950.1.1.5.10.33.1.1.1.5
-- 1.3.6.1.4.1.37950.1.1.5.10.33.1.1.1.5
-- 1.3.6.1.4.1.37950.1.1.5.10.33.1.1.1.5
		-- 1.3.6.1.4.1.37950.1.1.5.10.33.1.1.1.5
		ospf6NeighborStateIfState OBJECT-TYPE
			SYNTAX OCTET STRING
			MAX-ACCESS read-only
			STATUS current
			DESCRIPTION
				"Description."
			::= { ospf6NeighborEntry 5 }

		
--       1.3.6.1.4.1.37950.1.1.5.10.33.1.1.1.6
-- 1.3.6.1.4.1.37950.1.1.5.10.33.1.1.1.6
-- 1.3.6.1.4.1.37950.1.1.5.10.33.1.1.1.6
-- 1.3.6.1.4.1.37950.1.1.5.10.33.1.1.1.6
-- 1.3.6.1.4.1.37950.1.1.5.10.33.1.1.1.6
-- 1.3.6.1.4.1.37950.1.1.5.10.33.1.1.1.6
		-- 1.3.6.1.4.1.37950.1.1.5.10.33.1.1.1.6
		ospf6NeighborDuration OBJECT-TYPE
			SYNTAX OCTET STRING
			MAX-ACCESS read-only
			STATUS current
			DESCRIPTION
				"Description."
			::= { ospf6NeighborEntry 6 }

		
--       1.3.6.1.4.1.37950.1.1.5.10.33.1.1.1.7
-- 1.3.6.1.4.1.37950.1.1.5.10.33.1.1.1.7
-- 1.3.6.1.4.1.37950.1.1.5.10.33.1.1.1.7
-- 1.3.6.1.4.1.37950.1.1.5.10.33.1.1.1.7
-- 1.3.6.1.4.1.37950.1.1.5.10.33.1.1.1.7
-- 1.3.6.1.4.1.37950.1.1.5.10.33.1.1.1.7
		-- 1.3.6.1.4.1.37950.1.1.5.10.33.1.1.1.7
		ospf6NeighborInterfaceState OBJECT-TYPE
			SYNTAX OCTET STRING
			MAX-ACCESS read-only
			STATUS current
			DESCRIPTION
				"Description."
			::= { ospf6NeighborEntry 7 }

		
--       1.3.6.1.4.1.37950.1.1.5.10.33.1.2
-- 1.3.6.1.4.1.37950.1.1.5.10.33.1.2
-- 1.3.6.1.4.1.37950.1.1.5.10.33.1.2
-- 1.3.6.1.4.1.37950.1.1.5.10.33.1.2
-- 1.3.6.1.4.1.37950.1.1.5.10.33.1.2
-- 1.3.6.1.4.1.37950.1.1.5.10.33.1.2
		-- 1.3.6.1.4.1.37950.1.1.5.10.33.1.2
		ospf6RoutingTable OBJECT-TYPE
			SYNTAX SEQUENCE OF Ospf6RoutingEntry
			MAX-ACCESS not-accessible
			STATUS current
			DESCRIPTION
				"Description."
			::= { ospf6Information 2 }

		
--       1.3.6.1.4.1.37950.1.1.5.10.33.1.2.1
-- 1.3.6.1.4.1.37950.1.1.5.10.33.1.2.1
-- 1.3.6.1.4.1.37950.1.1.5.10.33.1.2.1
-- 1.3.6.1.4.1.37950.1.1.5.10.33.1.2.1
-- 1.3.6.1.4.1.37950.1.1.5.10.33.1.2.1
-- 1.3.6.1.4.1.37950.1.1.5.10.33.1.2.1
		-- 1.3.6.1.4.1.37950.1.1.5.10.33.1.2.1
		ospf6RoutingEntry OBJECT-TYPE
			SYNTAX Ospf6RoutingEntry
			MAX-ACCESS not-accessible
			STATUS current
			DESCRIPTION
				"Description."
			INDEX { ospf6RoutingIndex }
			::= { ospf6RoutingTable 1 }

		
		Ospf6RoutingEntry ::=
			SEQUENCE { 
				ospf6RoutingIndex
					Integer32,
				ospf6RoutingDestinationType
					OCTET STRING,
				ospf6RoutingPathType
					OCTET STRING,
				ospf6RoutingDestination
					OCTET STRING,
				ospf6RoutingNexthop
					OCTET STRING,
				ospf6RoutingInterface
					OCTET STRING,
				ospf6RoutingDuration
					OCTET STRING
			 }

--       1.3.6.1.4.1.37950.1.1.5.10.33.1.2.1.1
-- 1.3.6.1.4.1.37950.1.1.5.10.33.1.2.1.1
-- 1.3.6.1.4.1.37950.1.1.5.10.33.1.2.1.1
-- 1.3.6.1.4.1.37950.1.1.5.10.33.1.2.1.1
-- 1.3.6.1.4.1.37950.1.1.5.10.33.1.2.1.1
-- 1.3.6.1.4.1.37950.1.1.5.10.33.1.2.1.1
		-- 1.3.6.1.4.1.37950.1.1.5.10.33.1.2.1.1
		ospf6RoutingIndex OBJECT-TYPE
			SYNTAX Integer32
			MAX-ACCESS read-only
			STATUS current
			DESCRIPTION
				"Description."
			::= { ospf6RoutingEntry 1 }

		
--       1.3.6.1.4.1.37950.1.1.5.10.33.1.2.1.2
-- 1.3.6.1.4.1.37950.1.1.5.10.33.1.2.1.2
-- 1.3.6.1.4.1.37950.1.1.5.10.33.1.2.1.2
-- 1.3.6.1.4.1.37950.1.1.5.10.33.1.2.1.2
-- 1.3.6.1.4.1.37950.1.1.5.10.33.1.2.1.2
-- 1.3.6.1.4.1.37950.1.1.5.10.33.1.2.1.2
		-- 1.3.6.1.4.1.37950.1.1.5.10.33.1.2.1.2
		ospf6RoutingDestinationType OBJECT-TYPE
			SYNTAX OCTET STRING
			MAX-ACCESS read-only
			STATUS current
			DESCRIPTION
				"Description."
			::= { ospf6RoutingEntry 2 }

		
--       1.3.6.1.4.1.37950.1.1.5.10.33.1.2.1.3
-- 1.3.6.1.4.1.37950.1.1.5.10.33.1.2.1.3
-- 1.3.6.1.4.1.37950.1.1.5.10.33.1.2.1.3
-- 1.3.6.1.4.1.37950.1.1.5.10.33.1.2.1.3
-- 1.3.6.1.4.1.37950.1.1.5.10.33.1.2.1.3
-- 1.3.6.1.4.1.37950.1.1.5.10.33.1.2.1.3
		-- 1.3.6.1.4.1.37950.1.1.5.10.33.1.2.1.3
		ospf6RoutingPathType OBJECT-TYPE
			SYNTAX OCTET STRING
			MAX-ACCESS read-only
			STATUS current
			DESCRIPTION
				"Description."
			::= { ospf6RoutingEntry 3 }

		
--       1.3.6.1.4.1.37950.1.1.5.10.33.1.2.1.4
-- 1.3.6.1.4.1.37950.1.1.5.10.33.1.2.1.4
-- 1.3.6.1.4.1.37950.1.1.5.10.33.1.2.1.4
-- 1.3.6.1.4.1.37950.1.1.5.10.33.1.2.1.4
-- 1.3.6.1.4.1.37950.1.1.5.10.33.1.2.1.4
-- 1.3.6.1.4.1.37950.1.1.5.10.33.1.2.1.4
		-- 1.3.6.1.4.1.37950.1.1.5.10.33.1.2.1.4
		ospf6RoutingDestination OBJECT-TYPE
			SYNTAX OCTET STRING
			MAX-ACCESS read-only
			STATUS current
			DESCRIPTION
				"Description."
			::= { ospf6RoutingEntry 4 }

		
--       1.3.6.1.4.1.37950.1.1.5.10.33.1.2.1.5
-- 1.3.6.1.4.1.37950.1.1.5.10.33.1.2.1.5
-- 1.3.6.1.4.1.37950.1.1.5.10.33.1.2.1.5
-- 1.3.6.1.4.1.37950.1.1.5.10.33.1.2.1.5
-- 1.3.6.1.4.1.37950.1.1.5.10.33.1.2.1.5
-- 1.3.6.1.4.1.37950.1.1.5.10.33.1.2.1.5
		-- 1.3.6.1.4.1.37950.1.1.5.10.33.1.2.1.5
		ospf6RoutingNexthop OBJECT-TYPE
			SYNTAX OCTET STRING
			MAX-ACCESS read-only
			STATUS current
			DESCRIPTION
				"Description."
			::= { ospf6RoutingEntry 5 }

		
--       1.3.6.1.4.1.37950.1.1.5.10.33.1.2.1.6
-- 1.3.6.1.4.1.37950.1.1.5.10.33.1.2.1.6
-- 1.3.6.1.4.1.37950.1.1.5.10.33.1.2.1.6
-- 1.3.6.1.4.1.37950.1.1.5.10.33.1.2.1.6
-- 1.3.6.1.4.1.37950.1.1.5.10.33.1.2.1.6
-- 1.3.6.1.4.1.37950.1.1.5.10.33.1.2.1.6
		-- 1.3.6.1.4.1.37950.1.1.5.10.33.1.2.1.6
		ospf6RoutingInterface OBJECT-TYPE
			SYNTAX OCTET STRING
			MAX-ACCESS read-only
			STATUS current
			DESCRIPTION
				"Description."
			::= { ospf6RoutingEntry 6 }

		
--       1.3.6.1.4.1.37950.1.1.5.10.33.1.2.1.7
-- 1.3.6.1.4.1.37950.1.1.5.10.33.1.2.1.7
-- 1.3.6.1.4.1.37950.1.1.5.10.33.1.2.1.7
-- 1.3.6.1.4.1.37950.1.1.5.10.33.1.2.1.7
-- 1.3.6.1.4.1.37950.1.1.5.10.33.1.2.1.7
-- 1.3.6.1.4.1.37950.1.1.5.10.33.1.2.1.7
		-- 1.3.6.1.4.1.37950.1.1.5.10.33.1.2.1.7
		ospf6RoutingDuration OBJECT-TYPE
			SYNTAX OCTET STRING
			MAX-ACCESS read-only
			STATUS current
			DESCRIPTION
				"Description."
			::= { ospf6RoutingEntry 7 }

		
--       1.3.6.1.4.1.37950.1.1.5.10.33.2
-- 1.3.6.1.4.1.37950.1.1.5.10.33.2
-- 1.3.6.1.4.1.37950.1.1.5.10.33.2
-- 1.3.6.1.4.1.37950.1.1.5.10.33.2
-- 1.3.6.1.4.1.37950.1.1.5.10.33.2
-- 1.3.6.1.4.1.37950.1.1.5.10.33.2
		-- 1.3.6.1.4.1.37950.1.1.5.10.33.2
		ospf6Enable OBJECT IDENTIFIER ::= { v1600dOspf6 2 }

		
--       1.3.6.1.4.1.37950.1.1.5.10.33.2.1
-- 1.3.6.1.4.1.37950.1.1.5.10.33.2.1
-- 1.3.6.1.4.1.37950.1.1.5.10.33.2.1
-- 1.3.6.1.4.1.37950.1.1.5.10.33.2.1
-- 1.3.6.1.4.1.37950.1.1.5.10.33.2.1
-- 1.3.6.1.4.1.37950.1.1.5.10.33.2.1
		-- 1.3.6.1.4.1.37950.1.1.5.10.33.2.1
		ospf6RouteCfg OBJECT-TYPE
			SYNTAX INTEGER
				{
				disable(0),
				enable(1)
				}
			MAX-ACCESS read-write
			STATUS current
			DESCRIPTION
				"Description."
			::= { ospf6Enable 1 }

		
--       1.3.6.1.4.1.37950.1.1.5.10.33.2.2
-- 1.3.6.1.4.1.37950.1.1.5.10.33.2.2
-- 1.3.6.1.4.1.37950.1.1.5.10.33.2.2
-- 1.3.6.1.4.1.37950.1.1.5.10.33.2.2
-- 1.3.6.1.4.1.37950.1.1.5.10.33.2.2
-- 1.3.6.1.4.1.37950.1.1.5.10.33.2.2
		-- 1.3.6.1.4.1.37950.1.1.5.10.33.2.2
		ospf6RouteIdCfg OBJECT-TYPE
			SYNTAX IpAddress
			MAX-ACCESS read-write
			STATUS current
			DESCRIPTION
				"Description."
			::= { ospf6Enable 2 }

		
--       1.3.6.1.4.1.37950.1.1.5.10.33.3
-- 1.3.6.1.4.1.37950.1.1.5.10.33.3
-- 1.3.6.1.4.1.37950.1.1.5.10.33.3
-- 1.3.6.1.4.1.37950.1.1.5.10.33.3
-- 1.3.6.1.4.1.37950.1.1.5.10.33.3
-- 1.3.6.1.4.1.37950.1.1.5.10.33.3
		-- 1.3.6.1.4.1.37950.1.1.5.10.33.3
		ospf6RouteNetworking OBJECT IDENTIFIER ::= { v1600dOspf6 3 }

		
--       1.3.6.1.4.1.37950.1.1.5.10.33.3.1
-- 1.3.6.1.4.1.37950.1.1.5.10.33.3.1
-- 1.3.6.1.4.1.37950.1.1.5.10.33.3.1
-- 1.3.6.1.4.1.37950.1.1.5.10.33.3.1
-- 1.3.6.1.4.1.37950.1.1.5.10.33.3.1
-- 1.3.6.1.4.1.37950.1.1.5.10.33.3.1
		-- 1.3.6.1.4.1.37950.1.1.5.10.33.3.1
		ospf6RouteNetworkingCfg OBJECT IDENTIFIER ::= { ospf6RouteNetworking 1 }

		
--       1.3.6.1.4.1.37950.1.1.5.10.33.3.1.1
-- 1.3.6.1.4.1.37950.1.1.5.10.33.3.1.1
-- 1.3.6.1.4.1.37950.1.1.5.10.33.3.1.1
-- 1.3.6.1.4.1.37950.1.1.5.10.33.3.1.1
-- 1.3.6.1.4.1.37950.1.1.5.10.33.3.1.1
-- 1.3.6.1.4.1.37950.1.1.5.10.33.3.1.1
		-- 1.3.6.1.4.1.37950.1.1.5.10.33.3.1.1
		ospf6RouteNetworkingArea OBJECT-TYPE
			SYNTAX IpAddress
			MAX-ACCESS read-write
			STATUS current
			DESCRIPTION
				"Description."
			::= { ospf6RouteNetworkingCfg 1 }

		
--       1.3.6.1.4.1.37950.1.1.5.10.33.3.1.2
-- 1.3.6.1.4.1.37950.1.1.5.10.33.3.1.2
-- 1.3.6.1.4.1.37950.1.1.5.10.33.3.1.2
-- 1.3.6.1.4.1.37950.1.1.5.10.33.3.1.2
-- 1.3.6.1.4.1.37950.1.1.5.10.33.3.1.2
-- 1.3.6.1.4.1.37950.1.1.5.10.33.3.1.2
		-- 1.3.6.1.4.1.37950.1.1.5.10.33.3.1.2
		ospf6RouteNetworkingVlan OBJECT-TYPE
			SYNTAX Integer32 (1..4094)
			MAX-ACCESS read-write
			STATUS current
			DESCRIPTION
				"Description."
			::= { ospf6RouteNetworkingCfg 2 }

		
--       1.3.6.1.4.1.37950.1.1.5.10.33.3.1.3
-- 1.3.6.1.4.1.37950.1.1.5.10.33.3.1.3
-- 1.3.6.1.4.1.37950.1.1.5.10.33.3.1.3
-- 1.3.6.1.4.1.37950.1.1.5.10.33.3.1.3
-- 1.3.6.1.4.1.37950.1.1.5.10.33.3.1.3
-- 1.3.6.1.4.1.37950.1.1.5.10.33.3.1.3
		-- 1.3.6.1.4.1.37950.1.1.5.10.33.3.1.3
		ospf6RouteNetworkingAction OBJECT-TYPE
			SYNTAX INTEGER
				{
				add(1),
				delete(2)
				}
			MAX-ACCESS read-write
			STATUS current
			DESCRIPTION
				"Description."
			::= { ospf6RouteNetworkingCfg 3 }

		
--       1.3.6.1.4.1.37950.1.1.5.10.33.3.1.4
-- 1.3.6.1.4.1.37950.1.1.5.10.33.3.1.4
-- 1.3.6.1.4.1.37950.1.1.5.10.33.3.1.4
-- 1.3.6.1.4.1.37950.1.1.5.10.33.3.1.4
-- 1.3.6.1.4.1.37950.1.1.5.10.33.3.1.4
-- 1.3.6.1.4.1.37950.1.1.5.10.33.3.1.4
		-- 1.3.6.1.4.1.37950.1.1.5.10.33.3.1.4
		ospf6RouteNetworkingVlanTable OBJECT-TYPE
			SYNTAX SEQUENCE OF Ospf6RouteNetworkingVlanEntry
			MAX-ACCESS not-accessible
			STATUS current
			DESCRIPTION
				"Description."
			::= { ospf6RouteNetworkingCfg 4 }

		
--       1.3.6.1.4.1.37950.1.1.5.10.33.3.1.4.1
-- 1.3.6.1.4.1.37950.1.1.5.10.33.3.1.4.1
-- 1.3.6.1.4.1.37950.1.1.5.10.33.3.1.4.1
-- 1.3.6.1.4.1.37950.1.1.5.10.33.3.1.4.1
-- 1.3.6.1.4.1.37950.1.1.5.10.33.3.1.4.1
-- 1.3.6.1.4.1.37950.1.1.5.10.33.3.1.4.1
		-- 1.3.6.1.4.1.37950.1.1.5.10.33.3.1.4.1
		ospf6RouteNetworkingVlanEntry OBJECT-TYPE
			SYNTAX Ospf6RouteNetworkingVlanEntry
			MAX-ACCESS not-accessible
			STATUS current
			DESCRIPTION
				"Description."
			INDEX { ospf6RouteNetworkingVlanList }
			::= { ospf6RouteNetworkingVlanTable 1 }

		
		Ospf6RouteNetworkingVlanEntry ::=
			SEQUENCE { 
				ospf6RouteNetworkingVlanList
					Integer32
			 }

--       1.3.6.1.4.1.37950.1.1.5.10.33.3.1.4.1.1
-- 1.3.6.1.4.1.37950.1.1.5.10.33.3.1.4.1.1
-- 1.3.6.1.4.1.37950.1.1.5.10.33.3.1.4.1.1
-- 1.3.6.1.4.1.37950.1.1.5.10.33.3.1.4.1.1
-- 1.3.6.1.4.1.37950.1.1.5.10.33.3.1.4.1.1
-- 1.3.6.1.4.1.37950.1.1.5.10.33.3.1.4.1.1
		-- 1.3.6.1.4.1.37950.1.1.5.10.33.3.1.4.1.1
		ospf6RouteNetworkingVlanList OBJECT-TYPE
			SYNTAX Integer32
			MAX-ACCESS read-write
			STATUS current
			DESCRIPTION
				"Description."
			::= { ospf6RouteNetworkingVlanEntry 1 }

		
--       1.3.6.1.4.1.37950.1.1.5.10.33.3.2
-- 1.3.6.1.4.1.37950.1.1.5.10.33.3.2
-- 1.3.6.1.4.1.37950.1.1.5.10.33.3.2
-- 1.3.6.1.4.1.37950.1.1.5.10.33.3.2
-- 1.3.6.1.4.1.37950.1.1.5.10.33.3.2
-- 1.3.6.1.4.1.37950.1.1.5.10.33.3.2
		-- 1.3.6.1.4.1.37950.1.1.5.10.33.3.2
		ospf6RouteNetworkingTable OBJECT-TYPE
			SYNTAX SEQUENCE OF Ospf6RouteNetworkingEntry
			MAX-ACCESS not-accessible
			STATUS current
			DESCRIPTION
				"Description."
			::= { ospf6RouteNetworking 2 }

		
--       1.3.6.1.4.1.37950.1.1.5.10.33.3.2.1
-- 1.3.6.1.4.1.37950.1.1.5.10.33.3.2.1
-- 1.3.6.1.4.1.37950.1.1.5.10.33.3.2.1
-- 1.3.6.1.4.1.37950.1.1.5.10.33.3.2.1
-- 1.3.6.1.4.1.37950.1.1.5.10.33.3.2.1
-- 1.3.6.1.4.1.37950.1.1.5.10.33.3.2.1
		-- 1.3.6.1.4.1.37950.1.1.5.10.33.3.2.1
		ospf6RouteNetworkingEntry OBJECT-TYPE
			SYNTAX Ospf6RouteNetworkingEntry
			MAX-ACCESS not-accessible
			STATUS current
			DESCRIPTION
				"Description."
			INDEX { ospf6RouteNetworkingTableArea, ospf6RouteNetworkingTableVlan }
			::= { ospf6RouteNetworkingTable 1 }

		
		Ospf6RouteNetworkingEntry ::=
			SEQUENCE { 
				ospf6RouteNetworkingTableArea
					IpAddress,
				ospf6RouteNetworkingTableVlan
					Integer32
			 }

--       1.3.6.1.4.1.37950.1.1.5.10.33.3.2.1.1
-- 1.3.6.1.4.1.37950.1.1.5.10.33.3.2.1.1
-- 1.3.6.1.4.1.37950.1.1.5.10.33.3.2.1.1
-- 1.3.6.1.4.1.37950.1.1.5.10.33.3.2.1.1
-- 1.3.6.1.4.1.37950.1.1.5.10.33.3.2.1.1
-- 1.3.6.1.4.1.37950.1.1.5.10.33.3.2.1.1
		-- 1.3.6.1.4.1.37950.1.1.5.10.33.3.2.1.1
		ospf6RouteNetworkingTableArea OBJECT-TYPE
			SYNTAX IpAddress
			MAX-ACCESS read-only
			STATUS current
			DESCRIPTION
				"Description."
			::= { ospf6RouteNetworkingEntry 1 }

		
--       1.3.6.1.4.1.37950.1.1.5.10.33.3.2.1.2
-- 1.3.6.1.4.1.37950.1.1.5.10.33.3.2.1.2
-- 1.3.6.1.4.1.37950.1.1.5.10.33.3.2.1.2
-- 1.3.6.1.4.1.37950.1.1.5.10.33.3.2.1.2
-- 1.3.6.1.4.1.37950.1.1.5.10.33.3.2.1.2
-- 1.3.6.1.4.1.37950.1.1.5.10.33.3.2.1.2
		-- 1.3.6.1.4.1.37950.1.1.5.10.33.3.2.1.2
		ospf6RouteNetworkingTableVlan OBJECT-TYPE
			SYNTAX Integer32 (1..4094)
			MAX-ACCESS read-only
			STATUS current
			DESCRIPTION
				"Description."
			::= { ospf6RouteNetworkingEntry 2 }

		
--       1.3.6.1.4.1.37950.1.1.5.10.33.4
-- 1.3.6.1.4.1.37950.1.1.5.10.33.4
-- 1.3.6.1.4.1.37950.1.1.5.10.33.4
-- 1.3.6.1.4.1.37950.1.1.5.10.33.4
-- 1.3.6.1.4.1.37950.1.1.5.10.33.4
-- 1.3.6.1.4.1.37950.1.1.5.10.33.4
		-- 1.3.6.1.4.1.37950.1.1.5.10.33.4
		ospf6AreaSummary OBJECT IDENTIFIER ::= { v1600dOspf6 4 }

		
--       1.3.6.1.4.1.37950.1.1.5.10.33.4.1
-- 1.3.6.1.4.1.37950.1.1.5.10.33.4.1
-- 1.3.6.1.4.1.37950.1.1.5.10.33.4.1
-- 1.3.6.1.4.1.37950.1.1.5.10.33.4.1
-- 1.3.6.1.4.1.37950.1.1.5.10.33.4.1
-- 1.3.6.1.4.1.37950.1.1.5.10.33.4.1
		-- 1.3.6.1.4.1.37950.1.1.5.10.33.4.1
		ospf6AreaSummaryCfg OBJECT IDENTIFIER ::= { ospf6AreaSummary 1 }

		
--       1.3.6.1.4.1.37950.1.1.5.10.33.4.1.1
-- 1.3.6.1.4.1.37950.1.1.5.10.33.4.1.1
-- 1.3.6.1.4.1.37950.1.1.5.10.33.4.1.1
-- 1.3.6.1.4.1.37950.1.1.5.10.33.4.1.1
-- 1.3.6.1.4.1.37950.1.1.5.10.33.4.1.1
-- 1.3.6.1.4.1.37950.1.1.5.10.33.4.1.1
		-- 1.3.6.1.4.1.37950.1.1.5.10.33.4.1.1
		ospf6AreaSummaryArea OBJECT-TYPE
			SYNTAX IpAddress
			MAX-ACCESS read-write
			STATUS current
			DESCRIPTION
				"Description."
			::= { ospf6AreaSummaryCfg 1 }

		
--       1.3.6.1.4.1.37950.1.1.5.10.33.4.1.2
-- 1.3.6.1.4.1.37950.1.1.5.10.33.4.1.2
-- 1.3.6.1.4.1.37950.1.1.5.10.33.4.1.2
-- 1.3.6.1.4.1.37950.1.1.5.10.33.4.1.2
-- 1.3.6.1.4.1.37950.1.1.5.10.33.4.1.2
-- 1.3.6.1.4.1.37950.1.1.5.10.33.4.1.2
		-- 1.3.6.1.4.1.37950.1.1.5.10.33.4.1.2
		ospf6AreaSummaryAddress OBJECT-TYPE
			SYNTAX OCTET STRING
			MAX-ACCESS read-write
			STATUS current
			DESCRIPTION
				"Description."
			::= { ospf6AreaSummaryCfg 2 }

		
--       1.3.6.1.4.1.37950.1.1.5.10.33.4.1.3
-- 1.3.6.1.4.1.37950.1.1.5.10.33.4.1.3
-- 1.3.6.1.4.1.37950.1.1.5.10.33.4.1.3
-- 1.3.6.1.4.1.37950.1.1.5.10.33.4.1.3
-- 1.3.6.1.4.1.37950.1.1.5.10.33.4.1.3
-- 1.3.6.1.4.1.37950.1.1.5.10.33.4.1.3
		-- 1.3.6.1.4.1.37950.1.1.5.10.33.4.1.3
		ospf6AreaSummaryPrefixLen OBJECT-TYPE
			SYNTAX Integer32 (1..128)
			MAX-ACCESS read-write
			STATUS current
			DESCRIPTION
				"Description."
			::= { ospf6AreaSummaryCfg 3 }

		
--       1.3.6.1.4.1.37950.1.1.5.10.33.4.1.4
-- 1.3.6.1.4.1.37950.1.1.5.10.33.4.1.4
-- 1.3.6.1.4.1.37950.1.1.5.10.33.4.1.4
-- 1.3.6.1.4.1.37950.1.1.5.10.33.4.1.4
-- 1.3.6.1.4.1.37950.1.1.5.10.33.4.1.4
-- 1.3.6.1.4.1.37950.1.1.5.10.33.4.1.4
		-- 1.3.6.1.4.1.37950.1.1.5.10.33.4.1.4
		ospf6AreaSummaryAction OBJECT-TYPE
			SYNTAX INTEGER
				{
				add(1),
				delete(2)
				}
			MAX-ACCESS read-write
			STATUS current
			DESCRIPTION
				"Description."
			::= { ospf6AreaSummaryCfg 4 }

		
--       1.3.6.1.4.1.37950.1.1.5.10.33.4.1.5
-- 1.3.6.1.4.1.37950.1.1.5.10.33.4.1.5
-- 1.3.6.1.4.1.37950.1.1.5.10.33.4.1.5
-- 1.3.6.1.4.1.37950.1.1.5.10.33.4.1.5
-- 1.3.6.1.4.1.37950.1.1.5.10.33.4.1.5
-- 1.3.6.1.4.1.37950.1.1.5.10.33.4.1.5
		-- 1.3.6.1.4.1.37950.1.1.5.10.33.4.1.5
		ospf6AreaSummaryAreaTable OBJECT-TYPE
			SYNTAX SEQUENCE OF Ospf6AreaSummaryAreaEntry
			MAX-ACCESS not-accessible
			STATUS current
			DESCRIPTION
				"Description."
			::= { ospf6AreaSummaryCfg 5 }

		
--       1.3.6.1.4.1.37950.1.1.5.10.33.4.1.5.1
-- 1.3.6.1.4.1.37950.1.1.5.10.33.4.1.5.1
-- 1.3.6.1.4.1.37950.1.1.5.10.33.4.1.5.1
-- 1.3.6.1.4.1.37950.1.1.5.10.33.4.1.5.1
-- 1.3.6.1.4.1.37950.1.1.5.10.33.4.1.5.1
-- 1.3.6.1.4.1.37950.1.1.5.10.33.4.1.5.1
		-- 1.3.6.1.4.1.37950.1.1.5.10.33.4.1.5.1
		ospf6AreaSummaryAreaEntry OBJECT-TYPE
			SYNTAX Ospf6AreaSummaryAreaEntry
			MAX-ACCESS not-accessible
			STATUS current
			DESCRIPTION
				"Description."
			INDEX { ospf6AreaSummaryAreaList }
			::= { ospf6AreaSummaryAreaTable 1 }

		
		Ospf6AreaSummaryAreaEntry ::=
			SEQUENCE { 
				ospf6AreaSummaryAreaList
					IpAddress
			 }

--       1.3.6.1.4.1.37950.1.1.5.10.33.4.1.5.1.1
-- 1.3.6.1.4.1.37950.1.1.5.10.33.4.1.5.1.1
-- 1.3.6.1.4.1.37950.1.1.5.10.33.4.1.5.1.1
-- 1.3.6.1.4.1.37950.1.1.5.10.33.4.1.5.1.1
-- 1.3.6.1.4.1.37950.1.1.5.10.33.4.1.5.1.1
-- 1.3.6.1.4.1.37950.1.1.5.10.33.4.1.5.1.1
		-- 1.3.6.1.4.1.37950.1.1.5.10.33.4.1.5.1.1
		ospf6AreaSummaryAreaList OBJECT-TYPE
			SYNTAX IpAddress
			MAX-ACCESS read-write
			STATUS current
			DESCRIPTION
				"Description."
			::= { ospf6AreaSummaryAreaEntry 1 }

		
--       1.3.6.1.4.1.37950.1.1.5.10.33.4.2
-- 1.3.6.1.4.1.37950.1.1.5.10.33.4.2
-- 1.3.6.1.4.1.37950.1.1.5.10.33.4.2
-- 1.3.6.1.4.1.37950.1.1.5.10.33.4.2
-- 1.3.6.1.4.1.37950.1.1.5.10.33.4.2
-- 1.3.6.1.4.1.37950.1.1.5.10.33.4.2
		-- 1.3.6.1.4.1.37950.1.1.5.10.33.4.2
		ospf6AreaSummaryTable OBJECT-TYPE
			SYNTAX SEQUENCE OF Ospf6AreaSummaryEntry
			MAX-ACCESS not-accessible
			STATUS current
			DESCRIPTION
				"Description."
			::= { ospf6AreaSummary 2 }

		
--       1.3.6.1.4.1.37950.1.1.5.10.33.4.2.1
-- 1.3.6.1.4.1.37950.1.1.5.10.33.4.2.1
-- 1.3.6.1.4.1.37950.1.1.5.10.33.4.2.1
-- 1.3.6.1.4.1.37950.1.1.5.10.33.4.2.1
-- 1.3.6.1.4.1.37950.1.1.5.10.33.4.2.1
-- 1.3.6.1.4.1.37950.1.1.5.10.33.4.2.1
		-- 1.3.6.1.4.1.37950.1.1.5.10.33.4.2.1
		ospf6AreaSummaryEntry OBJECT-TYPE
			SYNTAX Ospf6AreaSummaryEntry
			MAX-ACCESS not-accessible
			STATUS current
			DESCRIPTION
				"Description."
			INDEX { ospf6AreaSummaryTableArea, ospf6AreaSummaryTableNetwork }
			::= { ospf6AreaSummaryTable 1 }

		
		Ospf6AreaSummaryEntry ::=
			SEQUENCE { 
				ospf6AreaSummaryTableArea
					IpAddress,
				ospf6AreaSummaryTableNetwork
					OCTET STRING
			 }

--       1.3.6.1.4.1.37950.1.1.5.10.33.4.2.1.1
-- 1.3.6.1.4.1.37950.1.1.5.10.33.4.2.1.1
-- 1.3.6.1.4.1.37950.1.1.5.10.33.4.2.1.1
-- 1.3.6.1.4.1.37950.1.1.5.10.33.4.2.1.1
-- 1.3.6.1.4.1.37950.1.1.5.10.33.4.2.1.1
-- 1.3.6.1.4.1.37950.1.1.5.10.33.4.2.1.1
		-- 1.3.6.1.4.1.37950.1.1.5.10.33.4.2.1.1
		ospf6AreaSummaryTableArea OBJECT-TYPE
			SYNTAX IpAddress
			MAX-ACCESS read-only
			STATUS current
			DESCRIPTION
				"Description."
			::= { ospf6AreaSummaryEntry 1 }

		
--       1.3.6.1.4.1.37950.1.1.5.10.33.4.2.1.2
-- 1.3.6.1.4.1.37950.1.1.5.10.33.4.2.1.2
-- 1.3.6.1.4.1.37950.1.1.5.10.33.4.2.1.2
-- 1.3.6.1.4.1.37950.1.1.5.10.33.4.2.1.2
-- 1.3.6.1.4.1.37950.1.1.5.10.33.4.2.1.2
-- 1.3.6.1.4.1.37950.1.1.5.10.33.4.2.1.2
		-- 1.3.6.1.4.1.37950.1.1.5.10.33.4.2.1.2
		ospf6AreaSummaryTableNetwork OBJECT-TYPE
			SYNTAX OCTET STRING
			MAX-ACCESS read-only
			STATUS current
			DESCRIPTION
				"Description."
			::= { ospf6AreaSummaryEntry 2 }

		
--       1.3.6.1.4.1.37950.1.1.5.10.33.5
-- 1.3.6.1.4.1.37950.1.1.5.10.33.5
-- 1.3.6.1.4.1.37950.1.1.5.10.33.5
-- 1.3.6.1.4.1.37950.1.1.5.10.33.5
-- 1.3.6.1.4.1.37950.1.1.5.10.33.5
-- 1.3.6.1.4.1.37950.1.1.5.10.33.5
		-- 1.3.6.1.4.1.37950.1.1.5.10.33.5
		ospf6Redistribute OBJECT IDENTIFIER ::= { v1600dOspf6 5 }

		
--       1.3.6.1.4.1.37950.1.1.5.10.33.5.1
-- 1.3.6.1.4.1.37950.1.1.5.10.33.5.1
-- 1.3.6.1.4.1.37950.1.1.5.10.33.5.1
-- 1.3.6.1.4.1.37950.1.1.5.10.33.5.1
-- 1.3.6.1.4.1.37950.1.1.5.10.33.5.1
-- 1.3.6.1.4.1.37950.1.1.5.10.33.5.1
		-- 1.3.6.1.4.1.37950.1.1.5.10.33.5.1
		ospf6RedistributeCfg OBJECT IDENTIFIER ::= { ospf6Redistribute 1 }

		
--       1.3.6.1.4.1.37950.1.1.5.10.33.5.1.1
-- 1.3.6.1.4.1.37950.1.1.5.10.33.5.1.1
-- 1.3.6.1.4.1.37950.1.1.5.10.33.5.1.1
-- 1.3.6.1.4.1.37950.1.1.5.10.33.5.1.1
-- 1.3.6.1.4.1.37950.1.1.5.10.33.5.1.1
-- 1.3.6.1.4.1.37950.1.1.5.10.33.5.1.1
		-- 1.3.6.1.4.1.37950.1.1.5.10.33.5.1.1
		ospf6RedistributeAttr OBJECT-TYPE
			SYNTAX OCTET STRING
			MAX-ACCESS read-write
			STATUS current
			DESCRIPTION
				"Description."
			::= { ospf6RedistributeCfg 1 }

		
--       1.3.6.1.4.1.37950.1.1.5.10.33.5.1.2
-- 1.3.6.1.4.1.37950.1.1.5.10.33.5.1.2
-- 1.3.6.1.4.1.37950.1.1.5.10.33.5.1.2
-- 1.3.6.1.4.1.37950.1.1.5.10.33.5.1.2
-- 1.3.6.1.4.1.37950.1.1.5.10.33.5.1.2
-- 1.3.6.1.4.1.37950.1.1.5.10.33.5.1.2
		-- 1.3.6.1.4.1.37950.1.1.5.10.33.5.1.2
		ospf6RedistributeAction OBJECT-TYPE
			SYNTAX INTEGER
				{
				add(1),
				delete(2)
				}
			MAX-ACCESS read-write
			STATUS current
			DESCRIPTION
				"Description."
			::= { ospf6RedistributeCfg 2 }

		
--       1.3.6.1.4.1.37950.1.1.5.10.33.5.2
-- 1.3.6.1.4.1.37950.1.1.5.10.33.5.2
-- 1.3.6.1.4.1.37950.1.1.5.10.33.5.2
-- 1.3.6.1.4.1.37950.1.1.5.10.33.5.2
-- 1.3.6.1.4.1.37950.1.1.5.10.33.5.2
-- 1.3.6.1.4.1.37950.1.1.5.10.33.5.2
		-- 1.3.6.1.4.1.37950.1.1.5.10.33.5.2
		ospf6RedistributeTable OBJECT-TYPE
			SYNTAX SEQUENCE OF Ospf6RedistributeEntry
			MAX-ACCESS not-accessible
			STATUS current
			DESCRIPTION
				"Description."
			::= { ospf6Redistribute 2 }

		
--       1.3.6.1.4.1.37950.1.1.5.10.33.5.2.1
-- 1.3.6.1.4.1.37950.1.1.5.10.33.5.2.1
-- 1.3.6.1.4.1.37950.1.1.5.10.33.5.2.1
-- 1.3.6.1.4.1.37950.1.1.5.10.33.5.2.1
-- 1.3.6.1.4.1.37950.1.1.5.10.33.5.2.1
-- 1.3.6.1.4.1.37950.1.1.5.10.33.5.2.1
		-- 1.3.6.1.4.1.37950.1.1.5.10.33.5.2.1
		ospf6RedistributeEntry OBJECT-TYPE
			SYNTAX Ospf6RedistributeEntry
			MAX-ACCESS not-accessible
			STATUS current
			DESCRIPTION
				"Description."
			INDEX { ospf6RedistributeAdded }
			::= { ospf6RedistributeTable 1 }

		
		Ospf6RedistributeEntry ::=
			SEQUENCE { 
				ospf6RedistributeAdded
					OCTET STRING
			 }

--       1.3.6.1.4.1.37950.1.1.5.10.33.5.2.1.1
-- 1.3.6.1.4.1.37950.1.1.5.10.33.5.2.1.1
-- 1.3.6.1.4.1.37950.1.1.5.10.33.5.2.1.1
-- 1.3.6.1.4.1.37950.1.1.5.10.33.5.2.1.1
-- 1.3.6.1.4.1.37950.1.1.5.10.33.5.2.1.1
-- 1.3.6.1.4.1.37950.1.1.5.10.33.5.2.1.1
		-- 1.3.6.1.4.1.37950.1.1.5.10.33.5.2.1.1
		ospf6RedistributeAdded OBJECT-TYPE
			SYNTAX OCTET STRING
			MAX-ACCESS read-write
			STATUS current
			DESCRIPTION
				"Description."
			::= { ospf6RedistributeEntry 1 }

		
--       1.3.6.1.4.1.37950.1.1.5.10.33.6
-- 1.3.6.1.4.1.37950.1.1.5.10.33.6
-- 1.3.6.1.4.1.37950.1.1.5.10.33.6
-- 1.3.6.1.4.1.37950.1.1.5.10.33.6
-- 1.3.6.1.4.1.37950.1.1.5.10.33.6
-- 1.3.6.1.4.1.37950.1.1.5.10.33.6
		-- 1.3.6.1.4.1.37950.1.1.5.10.33.6
		ospf6Interface OBJECT IDENTIFIER ::= { v1600dOspf6 6 }

		
--       1.3.6.1.4.1.37950.1.1.5.10.33.6.1
-- 1.3.6.1.4.1.37950.1.1.5.10.33.6.1
-- 1.3.6.1.4.1.37950.1.1.5.10.33.6.1
-- 1.3.6.1.4.1.37950.1.1.5.10.33.6.1
-- 1.3.6.1.4.1.37950.1.1.5.10.33.6.1
-- 1.3.6.1.4.1.37950.1.1.5.10.33.6.1
		-- 1.3.6.1.4.1.37950.1.1.5.10.33.6.1
		ospf6InterfaceCfg OBJECT IDENTIFIER ::= { ospf6Interface 1 }

		
--       1.3.6.1.4.1.37950.1.1.5.10.33.6.1.1
-- 1.3.6.1.4.1.37950.1.1.5.10.33.6.1.1
-- 1.3.6.1.4.1.37950.1.1.5.10.33.6.1.1
-- 1.3.6.1.4.1.37950.1.1.5.10.33.6.1.1
-- 1.3.6.1.4.1.37950.1.1.5.10.33.6.1.1
-- 1.3.6.1.4.1.37950.1.1.5.10.33.6.1.1
		-- 1.3.6.1.4.1.37950.1.1.5.10.33.6.1.1
		ospf6InterfaceCfgVlan OBJECT-TYPE
			SYNTAX Integer32 (1..4094)
			MAX-ACCESS read-write
			STATUS current
			DESCRIPTION
				"Description."
			::= { ospf6InterfaceCfg 1 }

		
--       1.3.6.1.4.1.37950.1.1.5.10.33.6.1.2
-- 1.3.6.1.4.1.37950.1.1.5.10.33.6.1.2
-- 1.3.6.1.4.1.37950.1.1.5.10.33.6.1.2
-- 1.3.6.1.4.1.37950.1.1.5.10.33.6.1.2
-- 1.3.6.1.4.1.37950.1.1.5.10.33.6.1.2
-- 1.3.6.1.4.1.37950.1.1.5.10.33.6.1.2
		-- 1.3.6.1.4.1.37950.1.1.5.10.33.6.1.2
		ospf6InterfaceCfgRetransmitInterval OBJECT-TYPE
			SYNTAX Integer32 (1..65535)
			MAX-ACCESS read-write
			STATUS current
			DESCRIPTION
				"Description."
			::= { ospf6InterfaceCfg 2 }

		
--       1.3.6.1.4.1.37950.1.1.5.10.33.6.1.3
-- 1.3.6.1.4.1.37950.1.1.5.10.33.6.1.3
-- 1.3.6.1.4.1.37950.1.1.5.10.33.6.1.3
-- 1.3.6.1.4.1.37950.1.1.5.10.33.6.1.3
-- 1.3.6.1.4.1.37950.1.1.5.10.33.6.1.3
-- 1.3.6.1.4.1.37950.1.1.5.10.33.6.1.3
		-- 1.3.6.1.4.1.37950.1.1.5.10.33.6.1.3
		ospf6InterfaceCfgTransmitDelay OBJECT-TYPE
			SYNTAX Integer32 (1..3600)
			MAX-ACCESS read-write
			STATUS current
			DESCRIPTION
				"Description."
			::= { ospf6InterfaceCfg 3 }

		
--       1.3.6.1.4.1.37950.1.1.5.10.33.6.1.4
-- 1.3.6.1.4.1.37950.1.1.5.10.33.6.1.4
-- 1.3.6.1.4.1.37950.1.1.5.10.33.6.1.4
-- 1.3.6.1.4.1.37950.1.1.5.10.33.6.1.4
-- 1.3.6.1.4.1.37950.1.1.5.10.33.6.1.4
-- 1.3.6.1.4.1.37950.1.1.5.10.33.6.1.4
		-- 1.3.6.1.4.1.37950.1.1.5.10.33.6.1.4
		ospf6InterfaceCfgHelloInterval OBJECT-TYPE
			SYNTAX Integer32 (1..65535)
			MAX-ACCESS read-write
			STATUS current
			DESCRIPTION
				"Description."
			::= { ospf6InterfaceCfg 4 }

		
--       1.3.6.1.4.1.37950.1.1.5.10.33.6.1.5
-- 1.3.6.1.4.1.37950.1.1.5.10.33.6.1.5
-- 1.3.6.1.4.1.37950.1.1.5.10.33.6.1.5
-- 1.3.6.1.4.1.37950.1.1.5.10.33.6.1.5
-- 1.3.6.1.4.1.37950.1.1.5.10.33.6.1.5
-- 1.3.6.1.4.1.37950.1.1.5.10.33.6.1.5
		-- 1.3.6.1.4.1.37950.1.1.5.10.33.6.1.5
		ospf6InterfaceCfgDeadInterval OBJECT-TYPE
			SYNTAX Integer32 (1..65535)
			MAX-ACCESS read-write
			STATUS current
			DESCRIPTION
				"Description."
			::= { ospf6InterfaceCfg 5 }

		
--       1.3.6.1.4.1.37950.1.1.5.10.33.6.1.6
-- 1.3.6.1.4.1.37950.1.1.5.10.33.6.1.6
-- 1.3.6.1.4.1.37950.1.1.5.10.33.6.1.6
-- 1.3.6.1.4.1.37950.1.1.5.10.33.6.1.6
-- 1.3.6.1.4.1.37950.1.1.5.10.33.6.1.6
-- 1.3.6.1.4.1.37950.1.1.5.10.33.6.1.6
		-- 1.3.6.1.4.1.37950.1.1.5.10.33.6.1.6
		ospf6InterfaceCfgPriority OBJECT-TYPE
			SYNTAX Integer32 (0..255)
			MAX-ACCESS read-write
			STATUS current
			DESCRIPTION
				"Description."
			::= { ospf6InterfaceCfg 6 }

		
--       1.3.6.1.4.1.37950.1.1.5.10.33.6.1.7
-- 1.3.6.1.4.1.37950.1.1.5.10.33.6.1.7
-- 1.3.6.1.4.1.37950.1.1.5.10.33.6.1.7
-- 1.3.6.1.4.1.37950.1.1.5.10.33.6.1.7
-- 1.3.6.1.4.1.37950.1.1.5.10.33.6.1.7
-- 1.3.6.1.4.1.37950.1.1.5.10.33.6.1.7
		-- 1.3.6.1.4.1.37950.1.1.5.10.33.6.1.7
		ospf6InterfaceCfgAction OBJECT-TYPE
			SYNTAX Integer32
			MAX-ACCESS read-write
			STATUS current
			DESCRIPTION
				"Description."
			::= { ospf6InterfaceCfg 7 }

		
--       1.3.6.1.4.1.37950.1.1.5.10.33.6.1.8
-- 1.3.6.1.4.1.37950.1.1.5.10.33.6.1.8
-- 1.3.6.1.4.1.37950.1.1.5.10.33.6.1.8
-- 1.3.6.1.4.1.37950.1.1.5.10.33.6.1.8
-- 1.3.6.1.4.1.37950.1.1.5.10.33.6.1.8
-- 1.3.6.1.4.1.37950.1.1.5.10.33.6.1.8
		-- 1.3.6.1.4.1.37950.1.1.5.10.33.6.1.8
		ospf6InterfaceCfgVlanTable OBJECT-TYPE
			SYNTAX SEQUENCE OF Ospf6InterfaceCfgVlanEntry
			MAX-ACCESS not-accessible
			STATUS current
			DESCRIPTION
				"Description."
			::= { ospf6InterfaceCfg 8 }

		
--       1.3.6.1.4.1.37950.1.1.5.10.33.6.1.8.1
-- 1.3.6.1.4.1.37950.1.1.5.10.33.6.1.8.1
-- 1.3.6.1.4.1.37950.1.1.5.10.33.6.1.8.1
-- 1.3.6.1.4.1.37950.1.1.5.10.33.6.1.8.1
-- 1.3.6.1.4.1.37950.1.1.5.10.33.6.1.8.1
-- 1.3.6.1.4.1.37950.1.1.5.10.33.6.1.8.1
		-- 1.3.6.1.4.1.37950.1.1.5.10.33.6.1.8.1
		ospf6InterfaceCfgVlanEntry OBJECT-TYPE
			SYNTAX Ospf6InterfaceCfgVlanEntry
			MAX-ACCESS not-accessible
			STATUS current
			DESCRIPTION
				"Description."
			INDEX { ospf6InterfaceCfgVlanList }
			::= { ospf6InterfaceCfgVlanTable 1 }

		
		Ospf6InterfaceCfgVlanEntry ::=
			SEQUENCE { 
				ospf6InterfaceCfgVlanList
					Integer32
			 }

--       1.3.6.1.4.1.37950.1.1.5.10.33.6.1.8.1.1
-- 1.3.6.1.4.1.37950.1.1.5.10.33.6.1.8.1.1
-- 1.3.6.1.4.1.37950.1.1.5.10.33.6.1.8.1.1
-- 1.3.6.1.4.1.37950.1.1.5.10.33.6.1.8.1.1
-- 1.3.6.1.4.1.37950.1.1.5.10.33.6.1.8.1.1
-- 1.3.6.1.4.1.37950.1.1.5.10.33.6.1.8.1.1
		-- 1.3.6.1.4.1.37950.1.1.5.10.33.6.1.8.1.1
		ospf6InterfaceCfgVlanList OBJECT-TYPE
			SYNTAX Integer32
			MAX-ACCESS read-write
			STATUS current
			DESCRIPTION
				"Description."
			::= { ospf6InterfaceCfgVlanEntry 1 }

		
--       1.3.6.1.4.1.37950.1.1.5.10.33.6.2
-- 1.3.6.1.4.1.37950.1.1.5.10.33.6.2
-- 1.3.6.1.4.1.37950.1.1.5.10.33.6.2
-- 1.3.6.1.4.1.37950.1.1.5.10.33.6.2
-- 1.3.6.1.4.1.37950.1.1.5.10.33.6.2
-- 1.3.6.1.4.1.37950.1.1.5.10.33.6.2
		-- 1.3.6.1.4.1.37950.1.1.5.10.33.6.2
		ospf6InterfaceTable OBJECT-TYPE
			SYNTAX SEQUENCE OF Ospf6InterfaceEntry
			MAX-ACCESS not-accessible
			STATUS current
			DESCRIPTION
				"Description."
			::= { ospf6Interface 2 }

		
--       1.3.6.1.4.1.37950.1.1.5.10.33.6.2.1
-- 1.3.6.1.4.1.37950.1.1.5.10.33.6.2.1
-- 1.3.6.1.4.1.37950.1.1.5.10.33.6.2.1
-- 1.3.6.1.4.1.37950.1.1.5.10.33.6.2.1
-- 1.3.6.1.4.1.37950.1.1.5.10.33.6.2.1
-- 1.3.6.1.4.1.37950.1.1.5.10.33.6.2.1
		-- 1.3.6.1.4.1.37950.1.1.5.10.33.6.2.1
		ospf6InterfaceEntry OBJECT-TYPE
			SYNTAX Ospf6InterfaceEntry
			MAX-ACCESS not-accessible
			STATUS current
			DESCRIPTION
				"Description."
			INDEX { ospf6InterfaceTableIndex }
			::= { ospf6InterfaceTable 1 }

		
		Ospf6InterfaceEntry ::=
			SEQUENCE { 
				ospf6InterfaceTableIndex
					Integer32,
				ospf6InterfaceTableVlan
					Integer32,
				ospf6InterfaceTableRetransmitInterval
					Integer32,
				ospf6InterfaceTableTransmitDelay
					Integer32,
				ospf6InterfaceTableHelloInterval
					Integer32,
				ospf6InterfaceTableDeadInterval
					Integer32,
				ospf6InterfaceTablePriority
					Integer32
			 }

--       1.3.6.1.4.1.37950.1.1.5.10.33.6.2.1.1
-- 1.3.6.1.4.1.37950.1.1.5.10.33.6.2.1.1
-- 1.3.6.1.4.1.37950.1.1.5.10.33.6.2.1.1
-- 1.3.6.1.4.1.37950.1.1.5.10.33.6.2.1.1
-- 1.3.6.1.4.1.37950.1.1.5.10.33.6.2.1.1
-- 1.3.6.1.4.1.37950.1.1.5.10.33.6.2.1.1
		-- 1.3.6.1.4.1.37950.1.1.5.10.33.6.2.1.1
		ospf6InterfaceTableIndex OBJECT-TYPE
			SYNTAX Integer32
			MAX-ACCESS read-write
			STATUS current
			DESCRIPTION
				"Description."
			::= { ospf6InterfaceEntry 1 }

		
--       1.3.6.1.4.1.37950.1.1.5.10.33.6.2.1.2
-- 1.3.6.1.4.1.37950.1.1.5.10.33.6.2.1.2
-- 1.3.6.1.4.1.37950.1.1.5.10.33.6.2.1.2
-- 1.3.6.1.4.1.37950.1.1.5.10.33.6.2.1.2
-- 1.3.6.1.4.1.37950.1.1.5.10.33.6.2.1.2
-- 1.3.6.1.4.1.37950.1.1.5.10.33.6.2.1.2
		-- 1.3.6.1.4.1.37950.1.1.5.10.33.6.2.1.2
		ospf6InterfaceTableVlan OBJECT-TYPE
			SYNTAX Integer32 (1..4094)
			MAX-ACCESS read-only
			STATUS current
			DESCRIPTION
				"Description."
			::= { ospf6InterfaceEntry 2 }

		
--       1.3.6.1.4.1.37950.1.1.5.10.33.6.2.1.3
-- 1.3.6.1.4.1.37950.1.1.5.10.33.6.2.1.3
-- 1.3.6.1.4.1.37950.1.1.5.10.33.6.2.1.3
-- 1.3.6.1.4.1.37950.1.1.5.10.33.6.2.1.3
-- 1.3.6.1.4.1.37950.1.1.5.10.33.6.2.1.3
-- 1.3.6.1.4.1.37950.1.1.5.10.33.6.2.1.3
		-- 1.3.6.1.4.1.37950.1.1.5.10.33.6.2.1.3
		ospf6InterfaceTableRetransmitInterval OBJECT-TYPE
			SYNTAX Integer32 (1..65535)
			MAX-ACCESS read-only
			STATUS current
			DESCRIPTION
				"Description."
			::= { ospf6InterfaceEntry 3 }

		
--       1.3.6.1.4.1.37950.1.1.5.10.33.6.2.1.4
-- 1.3.6.1.4.1.37950.1.1.5.10.33.6.2.1.4
-- 1.3.6.1.4.1.37950.1.1.5.10.33.6.2.1.4
-- 1.3.6.1.4.1.37950.1.1.5.10.33.6.2.1.4
-- 1.3.6.1.4.1.37950.1.1.5.10.33.6.2.1.4
-- 1.3.6.1.4.1.37950.1.1.5.10.33.6.2.1.4
		-- 1.3.6.1.4.1.37950.1.1.5.10.33.6.2.1.4
		ospf6InterfaceTableTransmitDelay OBJECT-TYPE
			SYNTAX Integer32 (1..3600)
			MAX-ACCESS read-only
			STATUS current
			DESCRIPTION
				"Description."
			::= { ospf6InterfaceEntry 4 }

		
--       1.3.6.1.4.1.37950.1.1.5.10.33.6.2.1.5
-- 1.3.6.1.4.1.37950.1.1.5.10.33.6.2.1.5
-- 1.3.6.1.4.1.37950.1.1.5.10.33.6.2.1.5
-- 1.3.6.1.4.1.37950.1.1.5.10.33.6.2.1.5
-- 1.3.6.1.4.1.37950.1.1.5.10.33.6.2.1.5
-- 1.3.6.1.4.1.37950.1.1.5.10.33.6.2.1.5
		-- 1.3.6.1.4.1.37950.1.1.5.10.33.6.2.1.5
		ospf6InterfaceTableHelloInterval OBJECT-TYPE
			SYNTAX Integer32 (1..65535)
			MAX-ACCESS read-only
			STATUS current
			DESCRIPTION
				"Description."
			::= { ospf6InterfaceEntry 5 }

		
--       1.3.6.1.4.1.37950.1.1.5.10.33.6.2.1.6
-- 1.3.6.1.4.1.37950.1.1.5.10.33.6.2.1.6
-- 1.3.6.1.4.1.37950.1.1.5.10.33.6.2.1.6
-- 1.3.6.1.4.1.37950.1.1.5.10.33.6.2.1.6
-- 1.3.6.1.4.1.37950.1.1.5.10.33.6.2.1.6
-- 1.3.6.1.4.1.37950.1.1.5.10.33.6.2.1.6
		-- 1.3.6.1.4.1.37950.1.1.5.10.33.6.2.1.6
		ospf6InterfaceTableDeadInterval OBJECT-TYPE
			SYNTAX Integer32 (1..65535)
			MAX-ACCESS read-only
			STATUS current
			DESCRIPTION
				"Description."
			::= { ospf6InterfaceEntry 6 }

		
--       1.3.6.1.4.1.37950.1.1.5.10.33.6.2.1.7
-- 1.3.6.1.4.1.37950.1.1.5.10.33.6.2.1.7
-- 1.3.6.1.4.1.37950.1.1.5.10.33.6.2.1.7
-- 1.3.6.1.4.1.37950.1.1.5.10.33.6.2.1.7
-- 1.3.6.1.4.1.37950.1.1.5.10.33.6.2.1.7
-- 1.3.6.1.4.1.37950.1.1.5.10.33.6.2.1.7
		-- 1.3.6.1.4.1.37950.1.1.5.10.33.6.2.1.7
		ospf6InterfaceTablePriority OBJECT-TYPE
			SYNTAX Integer32 (0..255)
			MAX-ACCESS read-only
			STATUS current
			DESCRIPTION
				"Description."
			::= { ospf6InterfaceEntry 7 }

		
--               1.3.6.1.4.1.37950.1.1.5.12
-- 1.3.6.1.4.1.37950.1.1.5.12
-- 1.3.6.1.4.1.37950.1.1.5.12
-- 1.3.6.1.4.1.37950.1.1.5.12
-- 1.3.6.1.4.1.37950.1.1.5.12
-- 1.3.6.1.4.1.37950.1.1.5.12
-- 1.3.6.1.4.1.37950.1.1.5.12
-- 1.3.6.1.4.1.37950.1.1.5.12
-- 1.3.6.1.4.1.37950.1.1.5.12
-- 1.3.6.1.4.1.37950.1.1.5.12
-- 1.3.6.1.4.1.37950.1.1.5.12
		-- 1.3.6.1.4.1.37950.1.1.5.12
		v1600dOnuMgmt OBJECT IDENTIFIER ::= { v1600d 12 }

		
--          1.3.6.1.4.1.37950.1.1.5.12.1
-- 1.3.6.1.4.1.37950.1.1.5.12.1
-- 1.3.6.1.4.1.37950.1.1.5.12.1
-- 1.3.6.1.4.1.37950.1.1.5.12.1
-- 1.3.6.1.4.1.37950.1.1.5.12.1
-- 1.3.6.1.4.1.37950.1.1.5.12.1
-- 1.3.6.1.4.1.37950.1.1.5.12.1
-- 1.3.6.1.4.1.37950.1.1.5.12.1
-- 1.3.6.1.4.1.37950.1.1.5.12.1
		-- 1.3.6.1.4.1.37950.1.1.5.12.1
		onuAuth OBJECT IDENTIFIER ::= { v1600dOnuMgmt 1 }

		
--          1.3.6.1.4.1.37950.1.1.5.12.1.1
-- 1.3.6.1.4.1.37950.1.1.5.12.1.1
-- 1.3.6.1.4.1.37950.1.1.5.12.1.1
-- 1.3.6.1.4.1.37950.1.1.5.12.1.1
-- 1.3.6.1.4.1.37950.1.1.5.12.1.1
-- 1.3.6.1.4.1.37950.1.1.5.12.1.1
-- 1.3.6.1.4.1.37950.1.1.5.12.1.1
-- 1.3.6.1.4.1.37950.1.1.5.12.1.1
-- 1.3.6.1.4.1.37950.1.1.5.12.1.1
		-- 1.3.6.1.4.1.37950.1.1.5.12.1.1
		authModeTable OBJECT-TYPE
			SYNTAX SEQUENCE OF AuthModeEntry
			MAX-ACCESS not-accessible
			STATUS current
			DESCRIPTION
				"Description."
			::= { onuAuth 1 }

		
--          1.3.6.1.4.1.37950.1.1.5.12.1.1.1
-- 1.3.6.1.4.1.37950.1.1.5.12.1.1.1
-- 1.3.6.1.4.1.37950.1.1.5.12.1.1.1
-- 1.3.6.1.4.1.37950.1.1.5.12.1.1.1
-- 1.3.6.1.4.1.37950.1.1.5.12.1.1.1
-- 1.3.6.1.4.1.37950.1.1.5.12.1.1.1
-- 1.3.6.1.4.1.37950.1.1.5.12.1.1.1
-- 1.3.6.1.4.1.37950.1.1.5.12.1.1.1
-- 1.3.6.1.4.1.37950.1.1.5.12.1.1.1
		-- 1.3.6.1.4.1.37950.1.1.5.12.1.1.1
		authModeEntry OBJECT-TYPE
			SYNTAX AuthModeEntry
			MAX-ACCESS not-accessible
			STATUS current
			DESCRIPTION
				"Description."
			INDEX { onuAuthPonNo }
			::= { authModeTable 1 }

		
		AuthModeEntry ::=
			SEQUENCE { 
				onuAuthPonNo
					INTEGER,
				onuAuthMode
					INTEGER
			 }

--          1.3.6.1.4.1.37950.1.1.5.12.1.1.1.1
-- 1.3.6.1.4.1.37950.1.1.5.12.1.1.1.1
-- 1.3.6.1.4.1.37950.1.1.5.12.1.1.1.1
-- 1.3.6.1.4.1.37950.1.1.5.12.1.1.1.1
-- 1.3.6.1.4.1.37950.1.1.5.12.1.1.1.1
-- 1.3.6.1.4.1.37950.1.1.5.12.1.1.1.1
-- 1.3.6.1.4.1.37950.1.1.5.12.1.1.1.1
-- 1.3.6.1.4.1.37950.1.1.5.12.1.1.1.1
-- 1.3.6.1.4.1.37950.1.1.5.12.1.1.1.1
		-- 1.3.6.1.4.1.37950.1.1.5.12.1.1.1.1
		onuAuthPonNo OBJECT-TYPE
			SYNTAX INTEGER (1..16)
			MAX-ACCESS read-write
			STATUS current
			DESCRIPTION
				"Description."
			::= { authModeEntry 1 }

		
--          1.3.6.1.4.1.37950.1.1.5.12.1.1.1.2
-- 1.3.6.1.4.1.37950.1.1.5.12.1.1.1.2
-- 1.3.6.1.4.1.37950.1.1.5.12.1.1.1.2
-- 1.3.6.1.4.1.37950.1.1.5.12.1.1.1.2
-- 1.3.6.1.4.1.37950.1.1.5.12.1.1.1.2
-- 1.3.6.1.4.1.37950.1.1.5.12.1.1.1.2
-- 1.3.6.1.4.1.37950.1.1.5.12.1.1.1.2
-- 1.3.6.1.4.1.37950.1.1.5.12.1.1.1.2
-- 1.3.6.1.4.1.37950.1.1.5.12.1.1.1.2
		-- 1.3.6.1.4.1.37950.1.1.5.12.1.1.1.2
		onuAuthMode OBJECT-TYPE
			SYNTAX INTEGER
				{
				disable(0),
				mac(1),
				loid(2),
				hybrid(3)
				}
			MAX-ACCESS read-write
			STATUS current
			DESCRIPTION
				"Description."
			::= { authModeEntry 2 }

		
--          1.3.6.1.4.1.37950.1.1.5.12.1.2
-- 1.3.6.1.4.1.37950.1.1.5.12.1.2
-- 1.3.6.1.4.1.37950.1.1.5.12.1.2
-- 1.3.6.1.4.1.37950.1.1.5.12.1.2
-- 1.3.6.1.4.1.37950.1.1.5.12.1.2
-- 1.3.6.1.4.1.37950.1.1.5.12.1.2
-- 1.3.6.1.4.1.37950.1.1.5.12.1.2
-- 1.3.6.1.4.1.37950.1.1.5.12.1.2
-- 1.3.6.1.4.1.37950.1.1.5.12.1.2
		-- 1.3.6.1.4.1.37950.1.1.5.12.1.2
		whiteMaclistCfg OBJECT IDENTIFIER ::= { onuAuth 2 }

		
--          1.3.6.1.4.1.37950.1.1.5.12.1.2.1
-- 1.3.6.1.4.1.37950.1.1.5.12.1.2.1
-- 1.3.6.1.4.1.37950.1.1.5.12.1.2.1
-- 1.3.6.1.4.1.37950.1.1.5.12.1.2.1
-- 1.3.6.1.4.1.37950.1.1.5.12.1.2.1
-- 1.3.6.1.4.1.37950.1.1.5.12.1.2.1
-- 1.3.6.1.4.1.37950.1.1.5.12.1.2.1
-- 1.3.6.1.4.1.37950.1.1.5.12.1.2.1
-- 1.3.6.1.4.1.37950.1.1.5.12.1.2.1
		-- 1.3.6.1.4.1.37950.1.1.5.12.1.2.1
		whiteMacPonNo OBJECT-TYPE
			SYNTAX INTEGER (1..16)
			MAX-ACCESS read-write
			STATUS current
			DESCRIPTION
				"Description."
			::= { whiteMaclistCfg 1 }

		
--          1.3.6.1.4.1.37950.1.1.5.12.1.2.2
-- 1.3.6.1.4.1.37950.1.1.5.12.1.2.2
-- 1.3.6.1.4.1.37950.1.1.5.12.1.2.2
-- 1.3.6.1.4.1.37950.1.1.5.12.1.2.2
-- 1.3.6.1.4.1.37950.1.1.5.12.1.2.2
-- 1.3.6.1.4.1.37950.1.1.5.12.1.2.2
-- 1.3.6.1.4.1.37950.1.1.5.12.1.2.2
-- 1.3.6.1.4.1.37950.1.1.5.12.1.2.2
-- 1.3.6.1.4.1.37950.1.1.5.12.1.2.2
		-- 1.3.6.1.4.1.37950.1.1.5.12.1.2.2
		whiteMacValue OBJECT-TYPE
			SYNTAX OCTET STRING
			MAX-ACCESS read-write
			STATUS current
			DESCRIPTION
				"Description."
			::= { whiteMaclistCfg 2 }

		
--          1.3.6.1.4.1.37950.1.1.5.12.1.2.3
-- 1.3.6.1.4.1.37950.1.1.5.12.1.2.3
-- 1.3.6.1.4.1.37950.1.1.5.12.1.2.3
-- 1.3.6.1.4.1.37950.1.1.5.12.1.2.3
-- 1.3.6.1.4.1.37950.1.1.5.12.1.2.3
-- 1.3.6.1.4.1.37950.1.1.5.12.1.2.3
-- 1.3.6.1.4.1.37950.1.1.5.12.1.2.3
-- 1.3.6.1.4.1.37950.1.1.5.12.1.2.3
-- 1.3.6.1.4.1.37950.1.1.5.12.1.2.3
		-- 1.3.6.1.4.1.37950.1.1.5.12.1.2.3
		whiteMacAction OBJECT-TYPE
			SYNTAX INTEGER
				{
				add(1),
				delete(2)
				}
			MAX-ACCESS read-write
			STATUS current
			DESCRIPTION
				"Description."
			::= { whiteMaclistCfg 3 }

		
--          1.3.6.1.4.1.37950.1.1.5.12.1.3
-- 1.3.6.1.4.1.37950.1.1.5.12.1.3
-- 1.3.6.1.4.1.37950.1.1.5.12.1.3
-- 1.3.6.1.4.1.37950.1.1.5.12.1.3
-- 1.3.6.1.4.1.37950.1.1.5.12.1.3
-- 1.3.6.1.4.1.37950.1.1.5.12.1.3
-- 1.3.6.1.4.1.37950.1.1.5.12.1.3
-- 1.3.6.1.4.1.37950.1.1.5.12.1.3
-- 1.3.6.1.4.1.37950.1.1.5.12.1.3
		-- 1.3.6.1.4.1.37950.1.1.5.12.1.3
		whiteMaclistTable OBJECT-TYPE
			SYNTAX SEQUENCE OF WhiteMaclistEntry
			MAX-ACCESS not-accessible
			STATUS current
			DESCRIPTION
				"Description."
			::= { onuAuth 3 }

		
--          1.3.6.1.4.1.37950.1.1.5.12.1.3.1
-- 1.3.6.1.4.1.37950.1.1.5.12.1.3.1
-- 1.3.6.1.4.1.37950.1.1.5.12.1.3.1
-- 1.3.6.1.4.1.37950.1.1.5.12.1.3.1
-- 1.3.6.1.4.1.37950.1.1.5.12.1.3.1
-- 1.3.6.1.4.1.37950.1.1.5.12.1.3.1
-- 1.3.6.1.4.1.37950.1.1.5.12.1.3.1
-- 1.3.6.1.4.1.37950.1.1.5.12.1.3.1
-- 1.3.6.1.4.1.37950.1.1.5.12.1.3.1
		-- 1.3.6.1.4.1.37950.1.1.5.12.1.3.1
		whiteMaclistEntry OBJECT-TYPE
			SYNTAX WhiteMaclistEntry
			MAX-ACCESS not-accessible
			STATUS current
			DESCRIPTION
				"Description."
			INDEX { whiteMacIndex }
			::= { whiteMaclistTable 1 }

		
		WhiteMaclistEntry ::=
			SEQUENCE { 
				whiteMacIndex
					Integer32,
				whiteMaclistPonNo
					Integer32,
				whiteMaclistValue
					OCTET STRING
			 }

--          1.3.6.1.4.1.37950.1.1.5.12.1.3.1.1
-- 1.3.6.1.4.1.37950.1.1.5.12.1.3.1.1
-- 1.3.6.1.4.1.37950.1.1.5.12.1.3.1.1
-- 1.3.6.1.4.1.37950.1.1.5.12.1.3.1.1
-- 1.3.6.1.4.1.37950.1.1.5.12.1.3.1.1
-- 1.3.6.1.4.1.37950.1.1.5.12.1.3.1.1
-- 1.3.6.1.4.1.37950.1.1.5.12.1.3.1.1
-- 1.3.6.1.4.1.37950.1.1.5.12.1.3.1.1
-- 1.3.6.1.4.1.37950.1.1.5.12.1.3.1.1
		-- 1.3.6.1.4.1.37950.1.1.5.12.1.3.1.1
		whiteMacIndex OBJECT-TYPE
			SYNTAX Integer32
			MAX-ACCESS read-only
			STATUS current
			DESCRIPTION
				"Description."
			::= { whiteMaclistEntry 1 }

		
--          1.3.6.1.4.1.37950.1.1.5.12.1.3.1.2
-- 1.3.6.1.4.1.37950.1.1.5.12.1.3.1.2
-- 1.3.6.1.4.1.37950.1.1.5.12.1.3.1.2
-- 1.3.6.1.4.1.37950.1.1.5.12.1.3.1.2
-- 1.3.6.1.4.1.37950.1.1.5.12.1.3.1.2
-- 1.3.6.1.4.1.37950.1.1.5.12.1.3.1.2
-- 1.3.6.1.4.1.37950.1.1.5.12.1.3.1.2
-- 1.3.6.1.4.1.37950.1.1.5.12.1.3.1.2
-- 1.3.6.1.4.1.37950.1.1.5.12.1.3.1.2
		-- 1.3.6.1.4.1.37950.1.1.5.12.1.3.1.2
		whiteMaclistPonNo OBJECT-TYPE
			SYNTAX Integer32 (1..16)
			MAX-ACCESS read-only
			STATUS current
			DESCRIPTION
				"Description."
			::= { whiteMaclistEntry 2 }

		
--          1.3.6.1.4.1.37950.1.1.5.12.1.3.1.3
-- 1.3.6.1.4.1.37950.1.1.5.12.1.3.1.3
-- 1.3.6.1.4.1.37950.1.1.5.12.1.3.1.3
-- 1.3.6.1.4.1.37950.1.1.5.12.1.3.1.3
-- 1.3.6.1.4.1.37950.1.1.5.12.1.3.1.3
-- 1.3.6.1.4.1.37950.1.1.5.12.1.3.1.3
-- 1.3.6.1.4.1.37950.1.1.5.12.1.3.1.3
-- 1.3.6.1.4.1.37950.1.1.5.12.1.3.1.3
-- 1.3.6.1.4.1.37950.1.1.5.12.1.3.1.3
		-- 1.3.6.1.4.1.37950.1.1.5.12.1.3.1.3
		whiteMaclistValue OBJECT-TYPE
			SYNTAX OCTET STRING
			MAX-ACCESS read-only
			STATUS current
			DESCRIPTION
				"Description."
			::= { whiteMaclistEntry 3 }

		
--          1.3.6.1.4.1.37950.1.1.5.12.1.4
-- 1.3.6.1.4.1.37950.1.1.5.12.1.4
-- 1.3.6.1.4.1.37950.1.1.5.12.1.4
-- 1.3.6.1.4.1.37950.1.1.5.12.1.4
-- 1.3.6.1.4.1.37950.1.1.5.12.1.4
-- 1.3.6.1.4.1.37950.1.1.5.12.1.4
-- 1.3.6.1.4.1.37950.1.1.5.12.1.4
-- 1.3.6.1.4.1.37950.1.1.5.12.1.4
-- 1.3.6.1.4.1.37950.1.1.5.12.1.4
		-- 1.3.6.1.4.1.37950.1.1.5.12.1.4
		blackMaclistCfg OBJECT IDENTIFIER ::= { onuAuth 4 }

		
--          1.3.6.1.4.1.37950.1.1.5.12.1.4.1
-- 1.3.6.1.4.1.37950.1.1.5.12.1.4.1
-- 1.3.6.1.4.1.37950.1.1.5.12.1.4.1
-- 1.3.6.1.4.1.37950.1.1.5.12.1.4.1
-- 1.3.6.1.4.1.37950.1.1.5.12.1.4.1
-- 1.3.6.1.4.1.37950.1.1.5.12.1.4.1
-- 1.3.6.1.4.1.37950.1.1.5.12.1.4.1
-- 1.3.6.1.4.1.37950.1.1.5.12.1.4.1
-- 1.3.6.1.4.1.37950.1.1.5.12.1.4.1
		-- 1.3.6.1.4.1.37950.1.1.5.12.1.4.1
		blackMacPonNo OBJECT-TYPE
			SYNTAX INTEGER (1..16)
			MAX-ACCESS read-write
			STATUS current
			DESCRIPTION
				"Description."
			::= { blackMaclistCfg 1 }

		
--          1.3.6.1.4.1.37950.1.1.5.12.1.4.2
-- 1.3.6.1.4.1.37950.1.1.5.12.1.4.2
-- 1.3.6.1.4.1.37950.1.1.5.12.1.4.2
-- 1.3.6.1.4.1.37950.1.1.5.12.1.4.2
-- 1.3.6.1.4.1.37950.1.1.5.12.1.4.2
-- 1.3.6.1.4.1.37950.1.1.5.12.1.4.2
-- 1.3.6.1.4.1.37950.1.1.5.12.1.4.2
-- 1.3.6.1.4.1.37950.1.1.5.12.1.4.2
-- 1.3.6.1.4.1.37950.1.1.5.12.1.4.2
		-- 1.3.6.1.4.1.37950.1.1.5.12.1.4.2
		blackMacValue OBJECT-TYPE
			SYNTAX OCTET STRING
			MAX-ACCESS read-write
			STATUS current
			DESCRIPTION
				"Description."
			::= { blackMaclistCfg 2 }

		
--          1.3.6.1.4.1.37950.1.1.5.12.1.4.3
-- 1.3.6.1.4.1.37950.1.1.5.12.1.4.3
-- 1.3.6.1.4.1.37950.1.1.5.12.1.4.3
-- 1.3.6.1.4.1.37950.1.1.5.12.1.4.3
-- 1.3.6.1.4.1.37950.1.1.5.12.1.4.3
-- 1.3.6.1.4.1.37950.1.1.5.12.1.4.3
-- 1.3.6.1.4.1.37950.1.1.5.12.1.4.3
-- 1.3.6.1.4.1.37950.1.1.5.12.1.4.3
-- 1.3.6.1.4.1.37950.1.1.5.12.1.4.3
		-- 1.3.6.1.4.1.37950.1.1.5.12.1.4.3
		blackMacAction OBJECT-TYPE
			SYNTAX INTEGER
				{
				add(1),
				delete(2)
				}
			MAX-ACCESS read-write
			STATUS current
			DESCRIPTION
				"Description."
			::= { blackMaclistCfg 3 }

		
--          1.3.6.1.4.1.37950.1.1.5.12.1.5
-- 1.3.6.1.4.1.37950.1.1.5.12.1.5
-- 1.3.6.1.4.1.37950.1.1.5.12.1.5
-- 1.3.6.1.4.1.37950.1.1.5.12.1.5
-- 1.3.6.1.4.1.37950.1.1.5.12.1.5
-- 1.3.6.1.4.1.37950.1.1.5.12.1.5
-- 1.3.6.1.4.1.37950.1.1.5.12.1.5
-- 1.3.6.1.4.1.37950.1.1.5.12.1.5
-- 1.3.6.1.4.1.37950.1.1.5.12.1.5
		-- 1.3.6.1.4.1.37950.1.1.5.12.1.5
		blackMaclistTable OBJECT-TYPE
			SYNTAX SEQUENCE OF BlackMaclistEntry
			MAX-ACCESS not-accessible
			STATUS current
			DESCRIPTION
				"Description."
			::= { onuAuth 5 }

		
--          1.3.6.1.4.1.37950.1.1.5.12.1.5.1
-- 1.3.6.1.4.1.37950.1.1.5.12.1.5.1
-- 1.3.6.1.4.1.37950.1.1.5.12.1.5.1
-- 1.3.6.1.4.1.37950.1.1.5.12.1.5.1
-- 1.3.6.1.4.1.37950.1.1.5.12.1.5.1
-- 1.3.6.1.4.1.37950.1.1.5.12.1.5.1
-- 1.3.6.1.4.1.37950.1.1.5.12.1.5.1
-- 1.3.6.1.4.1.37950.1.1.5.12.1.5.1
-- 1.3.6.1.4.1.37950.1.1.5.12.1.5.1
		-- 1.3.6.1.4.1.37950.1.1.5.12.1.5.1
		blackMaclistEntry OBJECT-TYPE
			SYNTAX BlackMaclistEntry
			MAX-ACCESS not-accessible
			STATUS current
			DESCRIPTION
				"Description."
			INDEX { blackMacIndex }
			::= { blackMaclistTable 1 }

		
		BlackMaclistEntry ::=
			SEQUENCE { 
				blackMacIndex
					Integer32,
				blackMaclistPonNo
					Integer32,
				blackMaclistValue
					OCTET STRING
			 }

--          1.3.6.1.4.1.37950.1.1.5.12.1.5.1.1
-- 1.3.6.1.4.1.37950.1.1.5.12.1.5.1.1
-- 1.3.6.1.4.1.37950.1.1.5.12.1.5.1.1
-- 1.3.6.1.4.1.37950.1.1.5.12.1.5.1.1
-- 1.3.6.1.4.1.37950.1.1.5.12.1.5.1.1
-- 1.3.6.1.4.1.37950.1.1.5.12.1.5.1.1
-- 1.3.6.1.4.1.37950.1.1.5.12.1.5.1.1
-- 1.3.6.1.4.1.37950.1.1.5.12.1.5.1.1
-- 1.3.6.1.4.1.37950.1.1.5.12.1.5.1.1
		-- 1.3.6.1.4.1.37950.1.1.5.12.1.5.1.1
		blackMacIndex OBJECT-TYPE
			SYNTAX Integer32
			MAX-ACCESS read-only
			STATUS current
			DESCRIPTION
				"Description."
			::= { blackMaclistEntry 1 }

		
--          1.3.6.1.4.1.37950.1.1.5.12.1.5.1.2
-- 1.3.6.1.4.1.37950.1.1.5.12.1.5.1.2
-- 1.3.6.1.4.1.37950.1.1.5.12.1.5.1.2
-- 1.3.6.1.4.1.37950.1.1.5.12.1.5.1.2
-- 1.3.6.1.4.1.37950.1.1.5.12.1.5.1.2
-- 1.3.6.1.4.1.37950.1.1.5.12.1.5.1.2
-- 1.3.6.1.4.1.37950.1.1.5.12.1.5.1.2
-- 1.3.6.1.4.1.37950.1.1.5.12.1.5.1.2
-- 1.3.6.1.4.1.37950.1.1.5.12.1.5.1.2
		-- 1.3.6.1.4.1.37950.1.1.5.12.1.5.1.2
		blackMaclistPonNo OBJECT-TYPE
			SYNTAX Integer32 (1..16)
			MAX-ACCESS read-only
			STATUS current
			DESCRIPTION
				"Description."
			::= { blackMaclistEntry 2 }

		
--          1.3.6.1.4.1.37950.1.1.5.12.1.5.1.3
-- 1.3.6.1.4.1.37950.1.1.5.12.1.5.1.3
-- 1.3.6.1.4.1.37950.1.1.5.12.1.5.1.3
-- 1.3.6.1.4.1.37950.1.1.5.12.1.5.1.3
-- 1.3.6.1.4.1.37950.1.1.5.12.1.5.1.3
-- 1.3.6.1.4.1.37950.1.1.5.12.1.5.1.3
-- 1.3.6.1.4.1.37950.1.1.5.12.1.5.1.3
-- 1.3.6.1.4.1.37950.1.1.5.12.1.5.1.3
-- 1.3.6.1.4.1.37950.1.1.5.12.1.5.1.3
		-- 1.3.6.1.4.1.37950.1.1.5.12.1.5.1.3
		blackMaclistValue OBJECT-TYPE
			SYNTAX OCTET STRING
			MAX-ACCESS read-only
			STATUS current
			DESCRIPTION
				"Description."
			::= { blackMaclistEntry 3 }

		
--          1.3.6.1.4.1.37950.1.1.5.12.1.6
-- 1.3.6.1.4.1.37950.1.1.5.12.1.6
-- 1.3.6.1.4.1.37950.1.1.5.12.1.6
-- 1.3.6.1.4.1.37950.1.1.5.12.1.6
-- 1.3.6.1.4.1.37950.1.1.5.12.1.6
-- 1.3.6.1.4.1.37950.1.1.5.12.1.6
-- 1.3.6.1.4.1.37950.1.1.5.12.1.6
-- 1.3.6.1.4.1.37950.1.1.5.12.1.6
-- 1.3.6.1.4.1.37950.1.1.5.12.1.6
		-- 1.3.6.1.4.1.37950.1.1.5.12.1.6
		loidListCfg OBJECT IDENTIFIER ::= { onuAuth 6 }

		
--          1.3.6.1.4.1.37950.1.1.5.12.1.6.1
-- 1.3.6.1.4.1.37950.1.1.5.12.1.6.1
-- 1.3.6.1.4.1.37950.1.1.5.12.1.6.1
-- 1.3.6.1.4.1.37950.1.1.5.12.1.6.1
-- 1.3.6.1.4.1.37950.1.1.5.12.1.6.1
-- 1.3.6.1.4.1.37950.1.1.5.12.1.6.1
-- 1.3.6.1.4.1.37950.1.1.5.12.1.6.1
-- 1.3.6.1.4.1.37950.1.1.5.12.1.6.1
-- 1.3.6.1.4.1.37950.1.1.5.12.1.6.1
		-- 1.3.6.1.4.1.37950.1.1.5.12.1.6.1
		loidPonNo OBJECT-TYPE
			SYNTAX INTEGER (1..16)
			MAX-ACCESS read-write
			STATUS current
			DESCRIPTION
				"Description."
			::= { loidListCfg 1 }

		
--          1.3.6.1.4.1.37950.1.1.5.12.1.6.2
-- 1.3.6.1.4.1.37950.1.1.5.12.1.6.2
-- 1.3.6.1.4.1.37950.1.1.5.12.1.6.2
-- 1.3.6.1.4.1.37950.1.1.5.12.1.6.2
-- 1.3.6.1.4.1.37950.1.1.5.12.1.6.2
-- 1.3.6.1.4.1.37950.1.1.5.12.1.6.2
-- 1.3.6.1.4.1.37950.1.1.5.12.1.6.2
-- 1.3.6.1.4.1.37950.1.1.5.12.1.6.2
-- 1.3.6.1.4.1.37950.1.1.5.12.1.6.2
		-- 1.3.6.1.4.1.37950.1.1.5.12.1.6.2
		loid OBJECT-TYPE
			SYNTAX OCTET STRING
			MAX-ACCESS read-write
			STATUS current
			DESCRIPTION
				"Description."
			::= { loidListCfg 2 }

		
--          1.3.6.1.4.1.37950.1.1.5.12.1.6.3
-- 1.3.6.1.4.1.37950.1.1.5.12.1.6.3
-- 1.3.6.1.4.1.37950.1.1.5.12.1.6.3
-- 1.3.6.1.4.1.37950.1.1.5.12.1.6.3
-- 1.3.6.1.4.1.37950.1.1.5.12.1.6.3
-- 1.3.6.1.4.1.37950.1.1.5.12.1.6.3
-- 1.3.6.1.4.1.37950.1.1.5.12.1.6.3
-- 1.3.6.1.4.1.37950.1.1.5.12.1.6.3
-- 1.3.6.1.4.1.37950.1.1.5.12.1.6.3
		-- 1.3.6.1.4.1.37950.1.1.5.12.1.6.3
		loidpw OBJECT-TYPE
			SYNTAX OCTET STRING
			MAX-ACCESS read-write
			STATUS current
			DESCRIPTION
				"Description."
			::= { loidListCfg 3 }

		
--          1.3.6.1.4.1.37950.1.1.5.12.1.6.4
-- 1.3.6.1.4.1.37950.1.1.5.12.1.6.4
-- 1.3.6.1.4.1.37950.1.1.5.12.1.6.4
-- 1.3.6.1.4.1.37950.1.1.5.12.1.6.4
-- 1.3.6.1.4.1.37950.1.1.5.12.1.6.4
-- 1.3.6.1.4.1.37950.1.1.5.12.1.6.4
-- 1.3.6.1.4.1.37950.1.1.5.12.1.6.4
-- 1.3.6.1.4.1.37950.1.1.5.12.1.6.4
-- 1.3.6.1.4.1.37950.1.1.5.12.1.6.4
		-- 1.3.6.1.4.1.37950.1.1.5.12.1.6.4
		loidAction OBJECT-TYPE
			SYNTAX INTEGER
				{
				add(1),
				delete(2)
				}
			MAX-ACCESS read-write
			STATUS current
			DESCRIPTION
				"Description."
			::= { loidListCfg 4 }

		
--          1.3.6.1.4.1.37950.1.1.5.12.1.7
-- 1.3.6.1.4.1.37950.1.1.5.12.1.7
-- 1.3.6.1.4.1.37950.1.1.5.12.1.7
-- 1.3.6.1.4.1.37950.1.1.5.12.1.7
-- 1.3.6.1.4.1.37950.1.1.5.12.1.7
-- 1.3.6.1.4.1.37950.1.1.5.12.1.7
-- 1.3.6.1.4.1.37950.1.1.5.12.1.7
-- 1.3.6.1.4.1.37950.1.1.5.12.1.7
-- 1.3.6.1.4.1.37950.1.1.5.12.1.7
		-- 1.3.6.1.4.1.37950.1.1.5.12.1.7
		loidListTable OBJECT-TYPE
			SYNTAX SEQUENCE OF LoidListEntry
			MAX-ACCESS not-accessible
			STATUS current
			DESCRIPTION
				"Description."
			::= { onuAuth 7 }

		
--          1.3.6.1.4.1.37950.1.1.5.12.1.7.1
-- 1.3.6.1.4.1.37950.1.1.5.12.1.7.1
-- 1.3.6.1.4.1.37950.1.1.5.12.1.7.1
-- 1.3.6.1.4.1.37950.1.1.5.12.1.7.1
-- 1.3.6.1.4.1.37950.1.1.5.12.1.7.1
-- 1.3.6.1.4.1.37950.1.1.5.12.1.7.1
-- 1.3.6.1.4.1.37950.1.1.5.12.1.7.1
-- 1.3.6.1.4.1.37950.1.1.5.12.1.7.1
-- 1.3.6.1.4.1.37950.1.1.5.12.1.7.1
		-- 1.3.6.1.4.1.37950.1.1.5.12.1.7.1
		loidListEntry OBJECT-TYPE
			SYNTAX LoidListEntry
			MAX-ACCESS not-accessible
			STATUS current
			DESCRIPTION
				"Description."
			INDEX { loidIndex }
			::= { loidListTable 1 }

		
		LoidListEntry ::=
			SEQUENCE { 
				loidIndex
					Integer32,
				loidListPonNo
					Integer32,
				loidValue
					OCTET STRING,
				loidpwValue
					OCTET STRING
			 }

--          1.3.6.1.4.1.37950.1.1.5.12.1.7.1.1
-- 1.3.6.1.4.1.37950.1.1.5.12.1.7.1.1
-- 1.3.6.1.4.1.37950.1.1.5.12.1.7.1.1
-- 1.3.6.1.4.1.37950.1.1.5.12.1.7.1.1
-- 1.3.6.1.4.1.37950.1.1.5.12.1.7.1.1
-- 1.3.6.1.4.1.37950.1.1.5.12.1.7.1.1
-- 1.3.6.1.4.1.37950.1.1.5.12.1.7.1.1
-- 1.3.6.1.4.1.37950.1.1.5.12.1.7.1.1
-- 1.3.6.1.4.1.37950.1.1.5.12.1.7.1.1
		-- 1.3.6.1.4.1.37950.1.1.5.12.1.7.1.1
		loidIndex OBJECT-TYPE
			SYNTAX Integer32
			MAX-ACCESS read-only
			STATUS current
			DESCRIPTION
				"Description."
			::= { loidListEntry 1 }

		
--          1.3.6.1.4.1.37950.1.1.5.12.1.7.1.2
-- 1.3.6.1.4.1.37950.1.1.5.12.1.7.1.2
-- 1.3.6.1.4.1.37950.1.1.5.12.1.7.1.2
-- 1.3.6.1.4.1.37950.1.1.5.12.1.7.1.2
-- 1.3.6.1.4.1.37950.1.1.5.12.1.7.1.2
-- 1.3.6.1.4.1.37950.1.1.5.12.1.7.1.2
-- 1.3.6.1.4.1.37950.1.1.5.12.1.7.1.2
-- 1.3.6.1.4.1.37950.1.1.5.12.1.7.1.2
-- 1.3.6.1.4.1.37950.1.1.5.12.1.7.1.2
		-- 1.3.6.1.4.1.37950.1.1.5.12.1.7.1.2
		loidListPonNo OBJECT-TYPE
			SYNTAX Integer32 (1..16)
			MAX-ACCESS read-only
			STATUS current
			DESCRIPTION
				"Description."
			::= { loidListEntry 2 }

		
--          1.3.6.1.4.1.37950.1.1.5.12.1.7.1.3
-- 1.3.6.1.4.1.37950.1.1.5.12.1.7.1.3
-- 1.3.6.1.4.1.37950.1.1.5.12.1.7.1.3
-- 1.3.6.1.4.1.37950.1.1.5.12.1.7.1.3
-- 1.3.6.1.4.1.37950.1.1.5.12.1.7.1.3
-- 1.3.6.1.4.1.37950.1.1.5.12.1.7.1.3
-- 1.3.6.1.4.1.37950.1.1.5.12.1.7.1.3
-- 1.3.6.1.4.1.37950.1.1.5.12.1.7.1.3
-- 1.3.6.1.4.1.37950.1.1.5.12.1.7.1.3
		-- 1.3.6.1.4.1.37950.1.1.5.12.1.7.1.3
		loidValue OBJECT-TYPE
			SYNTAX OCTET STRING
			MAX-ACCESS read-only
			STATUS current
			DESCRIPTION
				"Description."
			::= { loidListEntry 3 }

		
--          1.3.6.1.4.1.37950.1.1.5.12.1.7.1.4
-- 1.3.6.1.4.1.37950.1.1.5.12.1.7.1.4
-- 1.3.6.1.4.1.37950.1.1.5.12.1.7.1.4
-- 1.3.6.1.4.1.37950.1.1.5.12.1.7.1.4
-- 1.3.6.1.4.1.37950.1.1.5.12.1.7.1.4
-- 1.3.6.1.4.1.37950.1.1.5.12.1.7.1.4
-- 1.3.6.1.4.1.37950.1.1.5.12.1.7.1.4
-- 1.3.6.1.4.1.37950.1.1.5.12.1.7.1.4
-- 1.3.6.1.4.1.37950.1.1.5.12.1.7.1.4
		-- 1.3.6.1.4.1.37950.1.1.5.12.1.7.1.4
		loidpwValue OBJECT-TYPE
			SYNTAX OCTET STRING
			MAX-ACCESS read-only
			STATUS current
			DESCRIPTION
				"Description."
			::= { loidListEntry 4 }

		
--          1.3.6.1.4.1.37950.1.1.5.12.1.8
-- 1.3.6.1.4.1.37950.1.1.5.12.1.8
-- 1.3.6.1.4.1.37950.1.1.5.12.1.8
-- 1.3.6.1.4.1.37950.1.1.5.12.1.8
-- 1.3.6.1.4.1.37950.1.1.5.12.1.8
-- 1.3.6.1.4.1.37950.1.1.5.12.1.8
-- 1.3.6.1.4.1.37950.1.1.5.12.1.8
-- 1.3.6.1.4.1.37950.1.1.5.12.1.8
-- 1.3.6.1.4.1.37950.1.1.5.12.1.8
		-- 1.3.6.1.4.1.37950.1.1.5.12.1.8
		noAuthOnu OBJECT IDENTIFIER ::= { onuAuth 8 }

		
--          1.3.6.1.4.1.37950.1.1.5.12.1.8.1
-- 1.3.6.1.4.1.37950.1.1.5.12.1.8.1
-- 1.3.6.1.4.1.37950.1.1.5.12.1.8.1
-- 1.3.6.1.4.1.37950.1.1.5.12.1.8.1
-- 1.3.6.1.4.1.37950.1.1.5.12.1.8.1
-- 1.3.6.1.4.1.37950.1.1.5.12.1.8.1
-- 1.3.6.1.4.1.37950.1.1.5.12.1.8.1
-- 1.3.6.1.4.1.37950.1.1.5.12.1.8.1
-- 1.3.6.1.4.1.37950.1.1.5.12.1.8.1
		-- 1.3.6.1.4.1.37950.1.1.5.12.1.8.1
		ponNo OBJECT-TYPE
			SYNTAX INTEGER (1..16)
			MAX-ACCESS read-write
			STATUS current
			DESCRIPTION
				"Description."
			::= { noAuthOnu 1 }

		
--          1.3.6.1.4.1.37950.1.1.5.12.1.8.2
-- 1.3.6.1.4.1.37950.1.1.5.12.1.8.2
-- 1.3.6.1.4.1.37950.1.1.5.12.1.8.2
-- 1.3.6.1.4.1.37950.1.1.5.12.1.8.2
-- 1.3.6.1.4.1.37950.1.1.5.12.1.8.2
-- 1.3.6.1.4.1.37950.1.1.5.12.1.8.2
-- 1.3.6.1.4.1.37950.1.1.5.12.1.8.2
-- 1.3.6.1.4.1.37950.1.1.5.12.1.8.2
-- 1.3.6.1.4.1.37950.1.1.5.12.1.8.2
		-- 1.3.6.1.4.1.37950.1.1.5.12.1.8.2
		noAuthOnuId OBJECT-TYPE
			SYNTAX INTEGER (0..65535)
			MAX-ACCESS read-write
			STATUS current
			DESCRIPTION
				"Description."
			::= { noAuthOnu 2 }

		
--          1.3.6.1.4.1.37950.1.1.5.12.1.9
-- 1.3.6.1.4.1.37950.1.1.5.12.1.9
-- 1.3.6.1.4.1.37950.1.1.5.12.1.9
-- 1.3.6.1.4.1.37950.1.1.5.12.1.9
-- 1.3.6.1.4.1.37950.1.1.5.12.1.9
-- 1.3.6.1.4.1.37950.1.1.5.12.1.9
-- 1.3.6.1.4.1.37950.1.1.5.12.1.9
-- 1.3.6.1.4.1.37950.1.1.5.12.1.9
-- 1.3.6.1.4.1.37950.1.1.5.12.1.9
		-- 1.3.6.1.4.1.37950.1.1.5.12.1.9
		onuListTable OBJECT-TYPE
			SYNTAX SEQUENCE OF OnuListEntry
			MAX-ACCESS not-accessible
			STATUS current
			DESCRIPTION
				"Description."
			::= { onuAuth 9 }

		
--          1.3.6.1.4.1.37950.1.1.5.12.1.9.1
-- 1.3.6.1.4.1.37950.1.1.5.12.1.9.1
-- 1.3.6.1.4.1.37950.1.1.5.12.1.9.1
-- 1.3.6.1.4.1.37950.1.1.5.12.1.9.1
-- 1.3.6.1.4.1.37950.1.1.5.12.1.9.1
-- 1.3.6.1.4.1.37950.1.1.5.12.1.9.1
-- 1.3.6.1.4.1.37950.1.1.5.12.1.9.1
-- 1.3.6.1.4.1.37950.1.1.5.12.1.9.1
-- 1.3.6.1.4.1.37950.1.1.5.12.1.9.1
		-- 1.3.6.1.4.1.37950.1.1.5.12.1.9.1
		onuListEntry OBJECT-TYPE
			SYNTAX OnuListEntry
			MAX-ACCESS not-accessible
			STATUS current
			DESCRIPTION
				"Description."
			INDEX { onuIndex }
			::= { onuListTable 1 }

		
		OnuListEntry ::=
			SEQUENCE { 
				onuIndex
					Integer32,
				ponId
					Integer32,
				llid
					Integer32,
				status
					OCTET STRING,
				macAddress
					OCTET STRING
			 }

--          1.3.6.1.4.1.37950.1.1.5.12.1.9.1.1
-- 1.3.6.1.4.1.37950.1.1.5.12.1.9.1.1
-- 1.3.6.1.4.1.37950.1.1.5.12.1.9.1.1
-- 1.3.6.1.4.1.37950.1.1.5.12.1.9.1.1
-- 1.3.6.1.4.1.37950.1.1.5.12.1.9.1.1
-- 1.3.6.1.4.1.37950.1.1.5.12.1.9.1.1
-- 1.3.6.1.4.1.37950.1.1.5.12.1.9.1.1
-- 1.3.6.1.4.1.37950.1.1.5.12.1.9.1.1
-- 1.3.6.1.4.1.37950.1.1.5.12.1.9.1.1
		-- 1.3.6.1.4.1.37950.1.1.5.12.1.9.1.1
		onuIndex OBJECT-TYPE
			SYNTAX Integer32
			MAX-ACCESS read-only
			STATUS current
			DESCRIPTION
				"Description."
			::= { onuListEntry 1 }

		
--          1.3.6.1.4.1.37950.1.1.5.12.1.9.1.2
-- 1.3.6.1.4.1.37950.1.1.5.12.1.9.1.2
-- 1.3.6.1.4.1.37950.1.1.5.12.1.9.1.2
-- 1.3.6.1.4.1.37950.1.1.5.12.1.9.1.2
-- 1.3.6.1.4.1.37950.1.1.5.12.1.9.1.2
-- 1.3.6.1.4.1.37950.1.1.5.12.1.9.1.2
-- 1.3.6.1.4.1.37950.1.1.5.12.1.9.1.2
-- 1.3.6.1.4.1.37950.1.1.5.12.1.9.1.2
-- 1.3.6.1.4.1.37950.1.1.5.12.1.9.1.2
		-- 1.3.6.1.4.1.37950.1.1.5.12.1.9.1.2
		ponId OBJECT-TYPE
			SYNTAX Integer32
			MAX-ACCESS read-only
			STATUS current
			DESCRIPTION
				"Description."
			::= { onuListEntry 2 }

		
--          1.3.6.1.4.1.37950.1.1.5.12.1.9.1.3
-- 1.3.6.1.4.1.37950.1.1.5.12.1.9.1.3
-- 1.3.6.1.4.1.37950.1.1.5.12.1.9.1.3
-- 1.3.6.1.4.1.37950.1.1.5.12.1.9.1.3
-- 1.3.6.1.4.1.37950.1.1.5.12.1.9.1.3
-- 1.3.6.1.4.1.37950.1.1.5.12.1.9.1.3
-- 1.3.6.1.4.1.37950.1.1.5.12.1.9.1.3
-- 1.3.6.1.4.1.37950.1.1.5.12.1.9.1.3
-- 1.3.6.1.4.1.37950.1.1.5.12.1.9.1.3
		-- 1.3.6.1.4.1.37950.1.1.5.12.1.9.1.3
		llid OBJECT-TYPE
			SYNTAX Integer32
			MAX-ACCESS read-only
			STATUS current
			DESCRIPTION
				"Description."
			::= { onuListEntry 3 }

		
--          1.3.6.1.4.1.37950.1.1.5.12.1.9.1.4
-- 1.3.6.1.4.1.37950.1.1.5.12.1.9.1.4
-- 1.3.6.1.4.1.37950.1.1.5.12.1.9.1.4
-- 1.3.6.1.4.1.37950.1.1.5.12.1.9.1.4
-- 1.3.6.1.4.1.37950.1.1.5.12.1.9.1.4
-- 1.3.6.1.4.1.37950.1.1.5.12.1.9.1.4
-- 1.3.6.1.4.1.37950.1.1.5.12.1.9.1.4
-- 1.3.6.1.4.1.37950.1.1.5.12.1.9.1.4
-- 1.3.6.1.4.1.37950.1.1.5.12.1.9.1.4
		-- 1.3.6.1.4.1.37950.1.1.5.12.1.9.1.4
		status OBJECT-TYPE
			SYNTAX OCTET STRING
			MAX-ACCESS read-only
			STATUS current
			DESCRIPTION
				"Description."
			::= { onuListEntry 4 }

		
--          1.3.6.1.4.1.37950.1.1.5.12.1.9.1.5
-- 1.3.6.1.4.1.37950.1.1.5.12.1.9.1.5
-- 1.3.6.1.4.1.37950.1.1.5.12.1.9.1.5
-- 1.3.6.1.4.1.37950.1.1.5.12.1.9.1.5
-- 1.3.6.1.4.1.37950.1.1.5.12.1.9.1.5
-- 1.3.6.1.4.1.37950.1.1.5.12.1.9.1.5
-- 1.3.6.1.4.1.37950.1.1.5.12.1.9.1.5
-- 1.3.6.1.4.1.37950.1.1.5.12.1.9.1.5
-- 1.3.6.1.4.1.37950.1.1.5.12.1.9.1.5
		-- 1.3.6.1.4.1.37950.1.1.5.12.1.9.1.5
		macAddress OBJECT-TYPE
			SYNTAX OCTET STRING
			MAX-ACCESS read-only
			STATUS current
			DESCRIPTION
				"Description."
			::= { onuListEntry 5 }

		
--          1.3.6.1.4.1.37950.1.1.5.12.1.10
-- 1.3.6.1.4.1.37950.1.1.5.12.1.10
-- 1.3.6.1.4.1.37950.1.1.5.12.1.10
-- 1.3.6.1.4.1.37950.1.1.5.12.1.10
-- 1.3.6.1.4.1.37950.1.1.5.12.1.10
-- 1.3.6.1.4.1.37950.1.1.5.12.1.10
-- 1.3.6.1.4.1.37950.1.1.5.12.1.10
-- 1.3.6.1.4.1.37950.1.1.5.12.1.10
-- 1.3.6.1.4.1.37950.1.1.5.12.1.10
		-- 1.3.6.1.4.1.37950.1.1.5.12.1.10
		onuTypeCfg OBJECT IDENTIFIER ::= { onuAuth 10 }

		
--          1.3.6.1.4.1.37950.1.1.5.12.1.10.1
-- 1.3.6.1.4.1.37950.1.1.5.12.1.10.1
-- 1.3.6.1.4.1.37950.1.1.5.12.1.10.1
-- 1.3.6.1.4.1.37950.1.1.5.12.1.10.1
-- 1.3.6.1.4.1.37950.1.1.5.12.1.10.1
-- 1.3.6.1.4.1.37950.1.1.5.12.1.10.1
-- 1.3.6.1.4.1.37950.1.1.5.12.1.10.1
-- 1.3.6.1.4.1.37950.1.1.5.12.1.10.1
-- 1.3.6.1.4.1.37950.1.1.5.12.1.10.1
		-- 1.3.6.1.4.1.37950.1.1.5.12.1.10.1
		onuVerdorId OBJECT-TYPE
			SYNTAX OCTET STRING (SIZE (4))
			MAX-ACCESS read-write
			STATUS current
			DESCRIPTION
				"Description."
			::= { onuTypeCfg 1 }

		
--          1.3.6.1.4.1.37950.1.1.5.12.1.10.2
-- 1.3.6.1.4.1.37950.1.1.5.12.1.10.2
-- 1.3.6.1.4.1.37950.1.1.5.12.1.10.2
-- 1.3.6.1.4.1.37950.1.1.5.12.1.10.2
-- 1.3.6.1.4.1.37950.1.1.5.12.1.10.2
-- 1.3.6.1.4.1.37950.1.1.5.12.1.10.2
-- 1.3.6.1.4.1.37950.1.1.5.12.1.10.2
-- 1.3.6.1.4.1.37950.1.1.5.12.1.10.2
-- 1.3.6.1.4.1.37950.1.1.5.12.1.10.2
		-- 1.3.6.1.4.1.37950.1.1.5.12.1.10.2
		onuModelId OBJECT-TYPE
			SYNTAX OCTET STRING (SIZE (4))
			MAX-ACCESS read-write
			STATUS current
			DESCRIPTION
				"Description."
			::= { onuTypeCfg 2 }

		
--          1.3.6.1.4.1.37950.1.1.5.12.1.10.3
-- 1.3.6.1.4.1.37950.1.1.5.12.1.10.3
-- 1.3.6.1.4.1.37950.1.1.5.12.1.10.3
-- 1.3.6.1.4.1.37950.1.1.5.12.1.10.3
-- 1.3.6.1.4.1.37950.1.1.5.12.1.10.3
-- 1.3.6.1.4.1.37950.1.1.5.12.1.10.3
-- 1.3.6.1.4.1.37950.1.1.5.12.1.10.3
-- 1.3.6.1.4.1.37950.1.1.5.12.1.10.3
-- 1.3.6.1.4.1.37950.1.1.5.12.1.10.3
		-- 1.3.6.1.4.1.37950.1.1.5.12.1.10.3
		onuTpyeLanPortNo OBJECT-TYPE
			SYNTAX INTEGER (1..255)
			MAX-ACCESS read-write
			STATUS current
			DESCRIPTION
				"Description."
			::= { onuTypeCfg 3 }

		
--          1.3.6.1.4.1.37950.1.1.5.12.1.10.4
-- 1.3.6.1.4.1.37950.1.1.5.12.1.10.4
-- 1.3.6.1.4.1.37950.1.1.5.12.1.10.4
-- 1.3.6.1.4.1.37950.1.1.5.12.1.10.4
-- 1.3.6.1.4.1.37950.1.1.5.12.1.10.4
-- 1.3.6.1.4.1.37950.1.1.5.12.1.10.4
-- 1.3.6.1.4.1.37950.1.1.5.12.1.10.4
-- 1.3.6.1.4.1.37950.1.1.5.12.1.10.4
-- 1.3.6.1.4.1.37950.1.1.5.12.1.10.4
		-- 1.3.6.1.4.1.37950.1.1.5.12.1.10.4
		onuTypeValue OBJECT-TYPE
			SYNTAX OCTET STRING (SIZE (1..16))
			MAX-ACCESS read-write
			STATUS current
			DESCRIPTION
				"Description."
			::= { onuTypeCfg 4 }

		
--          1.3.6.1.4.1.37950.1.1.5.12.1.10.5
-- 1.3.6.1.4.1.37950.1.1.5.12.1.10.5
-- 1.3.6.1.4.1.37950.1.1.5.12.1.10.5
-- 1.3.6.1.4.1.37950.1.1.5.12.1.10.5
-- 1.3.6.1.4.1.37950.1.1.5.12.1.10.5
-- 1.3.6.1.4.1.37950.1.1.5.12.1.10.5
-- 1.3.6.1.4.1.37950.1.1.5.12.1.10.5
-- 1.3.6.1.4.1.37950.1.1.5.12.1.10.5
-- 1.3.6.1.4.1.37950.1.1.5.12.1.10.5
		-- 1.3.6.1.4.1.37950.1.1.5.12.1.10.5
		onuTypeAction OBJECT-TYPE
			SYNTAX INTEGER
				{
				add(1),
				delete(2)
				}
			MAX-ACCESS read-write
			STATUS current
			DESCRIPTION
				"Description."
			::= { onuTypeCfg 5 }

		
--          1.3.6.1.4.1.37950.1.1.5.12.1.11
-- 1.3.6.1.4.1.37950.1.1.5.12.1.11
-- 1.3.6.1.4.1.37950.1.1.5.12.1.11
-- 1.3.6.1.4.1.37950.1.1.5.12.1.11
-- 1.3.6.1.4.1.37950.1.1.5.12.1.11
-- 1.3.6.1.4.1.37950.1.1.5.12.1.11
-- 1.3.6.1.4.1.37950.1.1.5.12.1.11
-- 1.3.6.1.4.1.37950.1.1.5.12.1.11
-- 1.3.6.1.4.1.37950.1.1.5.12.1.11
		-- 1.3.6.1.4.1.37950.1.1.5.12.1.11
		onuTypeTable OBJECT-TYPE
			SYNTAX SEQUENCE OF OnuTypeEntry
			MAX-ACCESS not-accessible
			STATUS current
			DESCRIPTION
				"Description."
			::= { onuAuth 11 }

		
--          1.3.6.1.4.1.37950.1.1.5.12.1.11.1
-- 1.3.6.1.4.1.37950.1.1.5.12.1.11.1
-- 1.3.6.1.4.1.37950.1.1.5.12.1.11.1
-- 1.3.6.1.4.1.37950.1.1.5.12.1.11.1
-- 1.3.6.1.4.1.37950.1.1.5.12.1.11.1
-- 1.3.6.1.4.1.37950.1.1.5.12.1.11.1
-- 1.3.6.1.4.1.37950.1.1.5.12.1.11.1
-- 1.3.6.1.4.1.37950.1.1.5.12.1.11.1
-- 1.3.6.1.4.1.37950.1.1.5.12.1.11.1
		-- 1.3.6.1.4.1.37950.1.1.5.12.1.11.1
		onuTypeEntry OBJECT-TYPE
			SYNTAX OnuTypeEntry
			MAX-ACCESS not-accessible
			STATUS current
			DESCRIPTION
				"Description."
			INDEX { onuTypeIndex }
			::= { onuTypeTable 1 }

		
		OnuTypeEntry ::=
			SEQUENCE { 
				onuTypeIndex
					Integer32,
				onuVerdorID
					OCTET STRING,
				onuModelID
					OCTET STRING,
				onuTypeLanPortVal
					Integer32,
				onuTypeVal
					OCTET STRING
			 }

--          1.3.6.1.4.1.37950.1.1.5.12.1.11.1.1
-- 1.3.6.1.4.1.37950.1.1.5.12.1.11.1.1
-- 1.3.6.1.4.1.37950.1.1.5.12.1.11.1.1
-- 1.3.6.1.4.1.37950.1.1.5.12.1.11.1.1
-- 1.3.6.1.4.1.37950.1.1.5.12.1.11.1.1
-- 1.3.6.1.4.1.37950.1.1.5.12.1.11.1.1
-- 1.3.6.1.4.1.37950.1.1.5.12.1.11.1.1
-- 1.3.6.1.4.1.37950.1.1.5.12.1.11.1.1
-- 1.3.6.1.4.1.37950.1.1.5.12.1.11.1.1
		-- 1.3.6.1.4.1.37950.1.1.5.12.1.11.1.1
		onuTypeIndex OBJECT-TYPE
			SYNTAX Integer32
			MAX-ACCESS read-only
			STATUS current
			DESCRIPTION
				"Description."
			::= { onuTypeEntry 1 }

		
--          1.3.6.1.4.1.37950.1.1.5.12.1.11.1.2
-- 1.3.6.1.4.1.37950.1.1.5.12.1.11.1.2
-- 1.3.6.1.4.1.37950.1.1.5.12.1.11.1.2
-- 1.3.6.1.4.1.37950.1.1.5.12.1.11.1.2
-- 1.3.6.1.4.1.37950.1.1.5.12.1.11.1.2
-- 1.3.6.1.4.1.37950.1.1.5.12.1.11.1.2
-- 1.3.6.1.4.1.37950.1.1.5.12.1.11.1.2
-- 1.3.6.1.4.1.37950.1.1.5.12.1.11.1.2
-- 1.3.6.1.4.1.37950.1.1.5.12.1.11.1.2
		-- 1.3.6.1.4.1.37950.1.1.5.12.1.11.1.2
		onuVerdorID OBJECT-TYPE
			SYNTAX OCTET STRING
			MAX-ACCESS read-only
			STATUS current
			DESCRIPTION
				"Description."
			::= { onuTypeEntry 2 }

		
--          1.3.6.1.4.1.37950.1.1.5.12.1.11.1.3
-- 1.3.6.1.4.1.37950.1.1.5.12.1.11.1.3
-- 1.3.6.1.4.1.37950.1.1.5.12.1.11.1.3
-- 1.3.6.1.4.1.37950.1.1.5.12.1.11.1.3
-- 1.3.6.1.4.1.37950.1.1.5.12.1.11.1.3
-- 1.3.6.1.4.1.37950.1.1.5.12.1.11.1.3
-- 1.3.6.1.4.1.37950.1.1.5.12.1.11.1.3
-- 1.3.6.1.4.1.37950.1.1.5.12.1.11.1.3
-- 1.3.6.1.4.1.37950.1.1.5.12.1.11.1.3
		-- 1.3.6.1.4.1.37950.1.1.5.12.1.11.1.3
		onuModelID OBJECT-TYPE
			SYNTAX OCTET STRING
			MAX-ACCESS read-only
			STATUS current
			DESCRIPTION
				"Description."
			::= { onuTypeEntry 3 }

		
--          1.3.6.1.4.1.37950.1.1.5.12.1.11.1.4
-- 1.3.6.1.4.1.37950.1.1.5.12.1.11.1.4
-- 1.3.6.1.4.1.37950.1.1.5.12.1.11.1.4
-- 1.3.6.1.4.1.37950.1.1.5.12.1.11.1.4
-- 1.3.6.1.4.1.37950.1.1.5.12.1.11.1.4
-- 1.3.6.1.4.1.37950.1.1.5.12.1.11.1.4
-- 1.3.6.1.4.1.37950.1.1.5.12.1.11.1.4
-- 1.3.6.1.4.1.37950.1.1.5.12.1.11.1.4
-- 1.3.6.1.4.1.37950.1.1.5.12.1.11.1.4
		-- 1.3.6.1.4.1.37950.1.1.5.12.1.11.1.4
		onuTypeLanPortVal OBJECT-TYPE
			SYNTAX Integer32
			MAX-ACCESS read-write
			STATUS current
			DESCRIPTION
				"Description."
			::= { onuTypeEntry 4 }

		
--          1.3.6.1.4.1.37950.1.1.5.12.1.11.1.5
-- 1.3.6.1.4.1.37950.1.1.5.12.1.11.1.5
-- 1.3.6.1.4.1.37950.1.1.5.12.1.11.1.5
-- 1.3.6.1.4.1.37950.1.1.5.12.1.11.1.5
-- 1.3.6.1.4.1.37950.1.1.5.12.1.11.1.5
-- 1.3.6.1.4.1.37950.1.1.5.12.1.11.1.5
-- 1.3.6.1.4.1.37950.1.1.5.12.1.11.1.5
-- 1.3.6.1.4.1.37950.1.1.5.12.1.11.1.5
-- 1.3.6.1.4.1.37950.1.1.5.12.1.11.1.5
		-- 1.3.6.1.4.1.37950.1.1.5.12.1.11.1.5
		onuTypeVal OBJECT-TYPE
			SYNTAX OCTET STRING
			MAX-ACCESS read-only
			STATUS current
			DESCRIPTION
				"Description."
			::= { onuTypeEntry 5 }

		
--          1.3.6.1.4.1.37950.1.1.5.12.1.12
-- 1.3.6.1.4.1.37950.1.1.5.12.1.12
-- 1.3.6.1.4.1.37950.1.1.5.12.1.12
-- 1.3.6.1.4.1.37950.1.1.5.12.1.12
-- 1.3.6.1.4.1.37950.1.1.5.12.1.12
-- 1.3.6.1.4.1.37950.1.1.5.12.1.12
-- 1.3.6.1.4.1.37950.1.1.5.12.1.12
-- 1.3.6.1.4.1.37950.1.1.5.12.1.12
-- 1.3.6.1.4.1.37950.1.1.5.12.1.12
		-- 1.3.6.1.4.1.37950.1.1.5.12.1.12
		onuAuthInfoTable OBJECT-TYPE
			SYNTAX SEQUENCE OF OnuAuthInfoEntry
			MAX-ACCESS not-accessible
			STATUS current
			DESCRIPTION
				"Description."
			::= { onuAuth 12 }

		
--          1.3.6.1.4.1.37950.1.1.5.12.1.12.1
-- 1.3.6.1.4.1.37950.1.1.5.12.1.12.1
-- 1.3.6.1.4.1.37950.1.1.5.12.1.12.1
-- 1.3.6.1.4.1.37950.1.1.5.12.1.12.1
-- 1.3.6.1.4.1.37950.1.1.5.12.1.12.1
-- 1.3.6.1.4.1.37950.1.1.5.12.1.12.1
-- 1.3.6.1.4.1.37950.1.1.5.12.1.12.1
-- 1.3.6.1.4.1.37950.1.1.5.12.1.12.1
-- 1.3.6.1.4.1.37950.1.1.5.12.1.12.1
		-- 1.3.6.1.4.1.37950.1.1.5.12.1.12.1
		onuAuthInfoEntry OBJECT-TYPE
			SYNTAX OnuAuthInfoEntry
			MAX-ACCESS not-accessible
			STATUS current
			DESCRIPTION
				"Description."
			INDEX { authInfoIndex }
			::= { onuAuthInfoTable 1 }

		
		OnuAuthInfoEntry ::=
			SEQUENCE { 
				authInfoIndex
					Integer32,
				authInfoPonNo
					Integer32,
				authInfoOnuNo
					Integer32,
				authInfoLlid
					Integer32,
				lineStatus
					INTEGER,
				onuMacAddr
					OCTET STRING,
				onutype
					OCTET STRING,
				exchange
					INTEGER,
				authMode
					INTEGER,
				onuAuthInfoDescription
					OCTET STRING,
				onuAuthInfoLoid
					OCTET STRING,
				onuAuthInfoLoidPwd
					OCTET STRING,
				onuAuthInfoRtt
					INTEGER,
				onuType2
					OCTET STRING
			 }

--          1.3.6.1.4.1.37950.1.1.5.12.1.12.1.1
-- 1.3.6.1.4.1.37950.1.1.5.12.1.12.1.1
-- 1.3.6.1.4.1.37950.1.1.5.12.1.12.1.1
-- 1.3.6.1.4.1.37950.1.1.5.12.1.12.1.1
-- 1.3.6.1.4.1.37950.1.1.5.12.1.12.1.1
-- 1.3.6.1.4.1.37950.1.1.5.12.1.12.1.1
-- 1.3.6.1.4.1.37950.1.1.5.12.1.12.1.1
-- 1.3.6.1.4.1.37950.1.1.5.12.1.12.1.1
-- 1.3.6.1.4.1.37950.1.1.5.12.1.12.1.1
		-- 1.3.6.1.4.1.37950.1.1.5.12.1.12.1.1
		authInfoIndex OBJECT-TYPE
			SYNTAX Integer32
			MAX-ACCESS read-only
			STATUS current
			DESCRIPTION
				"Description."
			::= { onuAuthInfoEntry 1 }

		
--          1.3.6.1.4.1.37950.1.1.5.12.1.12.1.2
-- 1.3.6.1.4.1.37950.1.1.5.12.1.12.1.2
-- 1.3.6.1.4.1.37950.1.1.5.12.1.12.1.2
-- 1.3.6.1.4.1.37950.1.1.5.12.1.12.1.2
-- 1.3.6.1.4.1.37950.1.1.5.12.1.12.1.2
-- 1.3.6.1.4.1.37950.1.1.5.12.1.12.1.2
-- 1.3.6.1.4.1.37950.1.1.5.12.1.12.1.2
-- 1.3.6.1.4.1.37950.1.1.5.12.1.12.1.2
-- 1.3.6.1.4.1.37950.1.1.5.12.1.12.1.2
		-- 1.3.6.1.4.1.37950.1.1.5.12.1.12.1.2
		authInfoPonNo OBJECT-TYPE
			SYNTAX Integer32
			MAX-ACCESS read-only
			STATUS current
			DESCRIPTION
				"Description."
			::= { onuAuthInfoEntry 2 }

		
--          1.3.6.1.4.1.37950.1.1.5.12.1.12.1.3
-- 1.3.6.1.4.1.37950.1.1.5.12.1.12.1.3
-- 1.3.6.1.4.1.37950.1.1.5.12.1.12.1.3
-- 1.3.6.1.4.1.37950.1.1.5.12.1.12.1.3
-- 1.3.6.1.4.1.37950.1.1.5.12.1.12.1.3
-- 1.3.6.1.4.1.37950.1.1.5.12.1.12.1.3
-- 1.3.6.1.4.1.37950.1.1.5.12.1.12.1.3
-- 1.3.6.1.4.1.37950.1.1.5.12.1.12.1.3
-- 1.3.6.1.4.1.37950.1.1.5.12.1.12.1.3
		-- 1.3.6.1.4.1.37950.1.1.5.12.1.12.1.3
		authInfoOnuNo OBJECT-TYPE
			SYNTAX Integer32
			MAX-ACCESS read-only
			STATUS current
			DESCRIPTION
				"Description."
			::= { onuAuthInfoEntry 3 }

		
--          1.3.6.1.4.1.37950.1.1.5.12.1.12.1.4
-- 1.3.6.1.4.1.37950.1.1.5.12.1.12.1.4
-- 1.3.6.1.4.1.37950.1.1.5.12.1.12.1.4
-- 1.3.6.1.4.1.37950.1.1.5.12.1.12.1.4
-- 1.3.6.1.4.1.37950.1.1.5.12.1.12.1.4
-- 1.3.6.1.4.1.37950.1.1.5.12.1.12.1.4
-- 1.3.6.1.4.1.37950.1.1.5.12.1.12.1.4
-- 1.3.6.1.4.1.37950.1.1.5.12.1.12.1.4
-- 1.3.6.1.4.1.37950.1.1.5.12.1.12.1.4
		-- 1.3.6.1.4.1.37950.1.1.5.12.1.12.1.4
		authInfoLlid OBJECT-TYPE
			SYNTAX Integer32
			MAX-ACCESS read-only
			STATUS current
			DESCRIPTION
				"Description."
			::= { onuAuthInfoEntry 4 }

		
--          1.3.6.1.4.1.37950.1.1.5.12.1.12.1.5
-- 1.3.6.1.4.1.37950.1.1.5.12.1.12.1.5
-- 1.3.6.1.4.1.37950.1.1.5.12.1.12.1.5
-- 1.3.6.1.4.1.37950.1.1.5.12.1.12.1.5
-- 1.3.6.1.4.1.37950.1.1.5.12.1.12.1.5
-- 1.3.6.1.4.1.37950.1.1.5.12.1.12.1.5
-- 1.3.6.1.4.1.37950.1.1.5.12.1.12.1.5
-- 1.3.6.1.4.1.37950.1.1.5.12.1.12.1.5
-- 1.3.6.1.4.1.37950.1.1.5.12.1.12.1.5
		-- 1.3.6.1.4.1.37950.1.1.5.12.1.12.1.5
		lineStatus OBJECT-TYPE
			SYNTAX INTEGER
				{
				offline(0),
				online(1)
				}
			MAX-ACCESS read-only
			STATUS current
			DESCRIPTION
				"Description."
			::= { onuAuthInfoEntry 5 }

		
--          1.3.6.1.4.1.37950.1.1.5.12.1.12.1.6
-- 1.3.6.1.4.1.37950.1.1.5.12.1.12.1.6
-- 1.3.6.1.4.1.37950.1.1.5.12.1.12.1.6
-- 1.3.6.1.4.1.37950.1.1.5.12.1.12.1.6
-- 1.3.6.1.4.1.37950.1.1.5.12.1.12.1.6
-- 1.3.6.1.4.1.37950.1.1.5.12.1.12.1.6
-- 1.3.6.1.4.1.37950.1.1.5.12.1.12.1.6
-- 1.3.6.1.4.1.37950.1.1.5.12.1.12.1.6
-- 1.3.6.1.4.1.37950.1.1.5.12.1.12.1.6
		-- 1.3.6.1.4.1.37950.1.1.5.12.1.12.1.6
		onuMacAddr OBJECT-TYPE
			SYNTAX OCTET STRING
			MAX-ACCESS read-only
			STATUS current
			DESCRIPTION
				"Description."
			::= { onuAuthInfoEntry 6 }

		
--          1.3.6.1.4.1.37950.1.1.5.12.1.12.1.7
-- 1.3.6.1.4.1.37950.1.1.5.12.1.12.1.7
-- 1.3.6.1.4.1.37950.1.1.5.12.1.12.1.7
-- 1.3.6.1.4.1.37950.1.1.5.12.1.12.1.7
-- 1.3.6.1.4.1.37950.1.1.5.12.1.12.1.7
-- 1.3.6.1.4.1.37950.1.1.5.12.1.12.1.7
-- 1.3.6.1.4.1.37950.1.1.5.12.1.12.1.7
-- 1.3.6.1.4.1.37950.1.1.5.12.1.12.1.7
-- 1.3.6.1.4.1.37950.1.1.5.12.1.12.1.7
		-- 1.3.6.1.4.1.37950.1.1.5.12.1.12.1.7
		onutype OBJECT-TYPE
			SYNTAX OCTET STRING
			MAX-ACCESS read-only
			STATUS current
			DESCRIPTION
				"Description."
			::= { onuAuthInfoEntry 7 }

		
--          1.3.6.1.4.1.37950.1.1.5.12.1.12.1.8
-- 1.3.6.1.4.1.37950.1.1.5.12.1.12.1.8
-- 1.3.6.1.4.1.37950.1.1.5.12.1.12.1.8
-- 1.3.6.1.4.1.37950.1.1.5.12.1.12.1.8
-- 1.3.6.1.4.1.37950.1.1.5.12.1.12.1.8
-- 1.3.6.1.4.1.37950.1.1.5.12.1.12.1.8
-- 1.3.6.1.4.1.37950.1.1.5.12.1.12.1.8
-- 1.3.6.1.4.1.37950.1.1.5.12.1.12.1.8
-- 1.3.6.1.4.1.37950.1.1.5.12.1.12.1.8
		-- 1.3.6.1.4.1.37950.1.1.5.12.1.12.1.8
		exchange OBJECT-TYPE
			SYNTAX INTEGER
				{
				idle(1),
				busy(2)
				}
			MAX-ACCESS read-only
			STATUS current
			DESCRIPTION
				"Description."
			::= { onuAuthInfoEntry 8 }

		
--          1.3.6.1.4.1.37950.1.1.5.12.1.12.1.9
-- 1.3.6.1.4.1.37950.1.1.5.12.1.12.1.9
-- 1.3.6.1.4.1.37950.1.1.5.12.1.12.1.9
-- 1.3.6.1.4.1.37950.1.1.5.12.1.12.1.9
-- 1.3.6.1.4.1.37950.1.1.5.12.1.12.1.9
-- 1.3.6.1.4.1.37950.1.1.5.12.1.12.1.9
-- 1.3.6.1.4.1.37950.1.1.5.12.1.12.1.9
-- 1.3.6.1.4.1.37950.1.1.5.12.1.12.1.9
-- 1.3.6.1.4.1.37950.1.1.5.12.1.12.1.9
		-- 1.3.6.1.4.1.37950.1.1.5.12.1.12.1.9
		authMode OBJECT-TYPE
			SYNTAX INTEGER
				{
				none(0),
				macAuth(1),
				loidAuth(2)
				}
			MAX-ACCESS read-only
			STATUS current
			DESCRIPTION
				"Description."
			::= { onuAuthInfoEntry 9 }

		
--          1.3.6.1.4.1.37950.1.1.5.12.1.12.1.10
-- 1.3.6.1.4.1.37950.1.1.5.12.1.12.1.10
-- 1.3.6.1.4.1.37950.1.1.5.12.1.12.1.10
-- 1.3.6.1.4.1.37950.1.1.5.12.1.12.1.10
-- 1.3.6.1.4.1.37950.1.1.5.12.1.12.1.10
-- 1.3.6.1.4.1.37950.1.1.5.12.1.12.1.10
-- 1.3.6.1.4.1.37950.1.1.5.12.1.12.1.10
-- 1.3.6.1.4.1.37950.1.1.5.12.1.12.1.10
-- 1.3.6.1.4.1.37950.1.1.5.12.1.12.1.10
		-- 1.3.6.1.4.1.37950.1.1.5.12.1.12.1.10
		onuAuthInfoDescription OBJECT-TYPE
			SYNTAX OCTET STRING
			MAX-ACCESS read-only
			STATUS current
			DESCRIPTION
				"Description."
			::= { onuAuthInfoEntry 10 }

		
--          1.3.6.1.4.1.37950.1.1.5.12.1.12.1.11
-- 1.3.6.1.4.1.37950.1.1.5.12.1.12.1.11
-- 1.3.6.1.4.1.37950.1.1.5.12.1.12.1.11
-- 1.3.6.1.4.1.37950.1.1.5.12.1.12.1.11
-- 1.3.6.1.4.1.37950.1.1.5.12.1.12.1.11
-- 1.3.6.1.4.1.37950.1.1.5.12.1.12.1.11
-- 1.3.6.1.4.1.37950.1.1.5.12.1.12.1.11
-- 1.3.6.1.4.1.37950.1.1.5.12.1.12.1.11
-- 1.3.6.1.4.1.37950.1.1.5.12.1.12.1.11
		-- 1.3.6.1.4.1.37950.1.1.5.12.1.12.1.11
		onuAuthInfoLoid OBJECT-TYPE
			SYNTAX OCTET STRING
			MAX-ACCESS read-only
			STATUS current
			DESCRIPTION
				"Description."
			::= { onuAuthInfoEntry 11 }

		
--          1.3.6.1.4.1.37950.1.1.5.12.1.12.1.12
-- 1.3.6.1.4.1.37950.1.1.5.12.1.12.1.12
-- 1.3.6.1.4.1.37950.1.1.5.12.1.12.1.12
-- 1.3.6.1.4.1.37950.1.1.5.12.1.12.1.12
-- 1.3.6.1.4.1.37950.1.1.5.12.1.12.1.12
-- 1.3.6.1.4.1.37950.1.1.5.12.1.12.1.12
-- 1.3.6.1.4.1.37950.1.1.5.12.1.12.1.12
-- 1.3.6.1.4.1.37950.1.1.5.12.1.12.1.12
-- 1.3.6.1.4.1.37950.1.1.5.12.1.12.1.12
		-- 1.3.6.1.4.1.37950.1.1.5.12.1.12.1.12
		onuAuthInfoLoidPwd OBJECT-TYPE
			SYNTAX OCTET STRING
			MAX-ACCESS read-only
			STATUS current
			DESCRIPTION
				"Description."
			::= { onuAuthInfoEntry 12 }

		
--          1.3.6.1.4.1.37950.1.1.5.12.1.12.1.13
-- 1.3.6.1.4.1.37950.1.1.5.12.1.12.1.13
-- 1.3.6.1.4.1.37950.1.1.5.12.1.12.1.13
-- 1.3.6.1.4.1.37950.1.1.5.12.1.12.1.13
-- 1.3.6.1.4.1.37950.1.1.5.12.1.12.1.13
-- 1.3.6.1.4.1.37950.1.1.5.12.1.12.1.13
-- 1.3.6.1.4.1.37950.1.1.5.12.1.12.1.13
-- 1.3.6.1.4.1.37950.1.1.5.12.1.12.1.13
-- 1.3.6.1.4.1.37950.1.1.5.12.1.12.1.13
		-- 1.3.6.1.4.1.37950.1.1.5.12.1.12.1.13
		onuAuthInfoRtt OBJECT-TYPE
			SYNTAX INTEGER
			MAX-ACCESS read-write
			STATUS current
			DESCRIPTION
				"Description."
			::= { onuAuthInfoEntry 13 }

		
--          1.3.6.1.4.1.37950.1.1.5.12.1.12.1.14
-- 1.3.6.1.4.1.37950.1.1.5.12.1.12.1.14
-- 1.3.6.1.4.1.37950.1.1.5.12.1.12.1.14
-- 1.3.6.1.4.1.37950.1.1.5.12.1.12.1.14
-- 1.3.6.1.4.1.37950.1.1.5.12.1.12.1.14
-- 1.3.6.1.4.1.37950.1.1.5.12.1.12.1.14
-- 1.3.6.1.4.1.37950.1.1.5.12.1.12.1.14
-- 1.3.6.1.4.1.37950.1.1.5.12.1.12.1.14
-- 1.3.6.1.4.1.37950.1.1.5.12.1.12.1.14
		-- 1.3.6.1.4.1.37950.1.1.5.12.1.12.1.14
		onuType2 OBJECT-TYPE
			SYNTAX OCTET STRING
			MAX-ACCESS read-write
			STATUS current
			DESCRIPTION
				"Description."
			::= { onuAuthInfoEntry 14 }

		
--          1.3.6.1.4.1.37950.1.1.5.12.1.13
-- 1.3.6.1.4.1.37950.1.1.5.12.1.13
-- 1.3.6.1.4.1.37950.1.1.5.12.1.13
-- 1.3.6.1.4.1.37950.1.1.5.12.1.13
-- 1.3.6.1.4.1.37950.1.1.5.12.1.13
-- 1.3.6.1.4.1.37950.1.1.5.12.1.13
-- 1.3.6.1.4.1.37950.1.1.5.12.1.13
-- 1.3.6.1.4.1.37950.1.1.5.12.1.13
-- 1.3.6.1.4.1.37950.1.1.5.12.1.13
		-- 1.3.6.1.4.1.37950.1.1.5.12.1.13
		onuAutoFindTable OBJECT-TYPE
			SYNTAX SEQUENCE OF OnuAutoFindEntry
			MAX-ACCESS not-accessible
			STATUS current
			DESCRIPTION
				"Description."
			::= { onuAuth 13 }

		
--          1.3.6.1.4.1.37950.1.1.5.12.1.13.1
-- 1.3.6.1.4.1.37950.1.1.5.12.1.13.1
-- 1.3.6.1.4.1.37950.1.1.5.12.1.13.1
-- 1.3.6.1.4.1.37950.1.1.5.12.1.13.1
-- 1.3.6.1.4.1.37950.1.1.5.12.1.13.1
-- 1.3.6.1.4.1.37950.1.1.5.12.1.13.1
-- 1.3.6.1.4.1.37950.1.1.5.12.1.13.1
-- 1.3.6.1.4.1.37950.1.1.5.12.1.13.1
-- 1.3.6.1.4.1.37950.1.1.5.12.1.13.1
		-- 1.3.6.1.4.1.37950.1.1.5.12.1.13.1
		onuAutoFindEntry OBJECT-TYPE
			SYNTAX OnuAutoFindEntry
			MAX-ACCESS not-accessible
			STATUS current
			DESCRIPTION
				"Description."
			INDEX { onuAutoFindIndex }
			::= { onuAutoFindTable 1 }

		
		OnuAutoFindEntry ::=
			SEQUENCE { 
				onuAutoFindIndex
					Integer32,
				onuAutoFindPon
					INTEGER,
				onuAutoFindMac
					OCTET STRING,
				onuAutoFindTimeout
					Integer32,
				onuAutoFindLoid
					OCTET STRING,
				onuAutoFindLoidPwd
					OCTET STRING
			 }

--          1.3.6.1.4.1.37950.1.1.5.12.1.13.1.1
-- 1.3.6.1.4.1.37950.1.1.5.12.1.13.1.1
-- 1.3.6.1.4.1.37950.1.1.5.12.1.13.1.1
-- 1.3.6.1.4.1.37950.1.1.5.12.1.13.1.1
-- 1.3.6.1.4.1.37950.1.1.5.12.1.13.1.1
-- 1.3.6.1.4.1.37950.1.1.5.12.1.13.1.1
-- 1.3.6.1.4.1.37950.1.1.5.12.1.13.1.1
-- 1.3.6.1.4.1.37950.1.1.5.12.1.13.1.1
-- 1.3.6.1.4.1.37950.1.1.5.12.1.13.1.1
		-- 1.3.6.1.4.1.37950.1.1.5.12.1.13.1.1
		onuAutoFindIndex OBJECT-TYPE
			SYNTAX Integer32
			MAX-ACCESS read-only
			STATUS current
			DESCRIPTION
				"Description."
			::= { onuAutoFindEntry 1 }

		
--          1.3.6.1.4.1.37950.1.1.5.12.1.13.1.2
-- 1.3.6.1.4.1.37950.1.1.5.12.1.13.1.2
-- 1.3.6.1.4.1.37950.1.1.5.12.1.13.1.2
-- 1.3.6.1.4.1.37950.1.1.5.12.1.13.1.2
-- 1.3.6.1.4.1.37950.1.1.5.12.1.13.1.2
-- 1.3.6.1.4.1.37950.1.1.5.12.1.13.1.2
-- 1.3.6.1.4.1.37950.1.1.5.12.1.13.1.2
-- 1.3.6.1.4.1.37950.1.1.5.12.1.13.1.2
-- 1.3.6.1.4.1.37950.1.1.5.12.1.13.1.2
		-- 1.3.6.1.4.1.37950.1.1.5.12.1.13.1.2
		onuAutoFindPon OBJECT-TYPE
			SYNTAX INTEGER (1..16)
			MAX-ACCESS read-only
			STATUS current
			DESCRIPTION
				"Description."
			::= { onuAutoFindEntry 2 }

		
--          1.3.6.1.4.1.37950.1.1.5.12.1.13.1.3
-- 1.3.6.1.4.1.37950.1.1.5.12.1.13.1.3
-- 1.3.6.1.4.1.37950.1.1.5.12.1.13.1.3
-- 1.3.6.1.4.1.37950.1.1.5.12.1.13.1.3
-- 1.3.6.1.4.1.37950.1.1.5.12.1.13.1.3
-- 1.3.6.1.4.1.37950.1.1.5.12.1.13.1.3
-- 1.3.6.1.4.1.37950.1.1.5.12.1.13.1.3
-- 1.3.6.1.4.1.37950.1.1.5.12.1.13.1.3
-- 1.3.6.1.4.1.37950.1.1.5.12.1.13.1.3
		-- 1.3.6.1.4.1.37950.1.1.5.12.1.13.1.3
		onuAutoFindMac OBJECT-TYPE
			SYNTAX OCTET STRING
			MAX-ACCESS read-only
			STATUS current
			DESCRIPTION
				"Description."
			::= { onuAutoFindEntry 3 }

		
--          1.3.6.1.4.1.37950.1.1.5.12.1.13.1.4
-- 1.3.6.1.4.1.37950.1.1.5.12.1.13.1.4
-- 1.3.6.1.4.1.37950.1.1.5.12.1.13.1.4
-- 1.3.6.1.4.1.37950.1.1.5.12.1.13.1.4
-- 1.3.6.1.4.1.37950.1.1.5.12.1.13.1.4
-- 1.3.6.1.4.1.37950.1.1.5.12.1.13.1.4
-- 1.3.6.1.4.1.37950.1.1.5.12.1.13.1.4
-- 1.3.6.1.4.1.37950.1.1.5.12.1.13.1.4
-- 1.3.6.1.4.1.37950.1.1.5.12.1.13.1.4
		-- 1.3.6.1.4.1.37950.1.1.5.12.1.13.1.4
		onuAutoFindTimeout OBJECT-TYPE
			SYNTAX Integer32
			MAX-ACCESS read-only
			STATUS current
			DESCRIPTION
				"Description."
			::= { onuAutoFindEntry 4 }

		
--          1.3.6.1.4.1.37950.1.1.5.12.1.13.1.5
-- 1.3.6.1.4.1.37950.1.1.5.12.1.13.1.5
-- 1.3.6.1.4.1.37950.1.1.5.12.1.13.1.5
-- 1.3.6.1.4.1.37950.1.1.5.12.1.13.1.5
-- 1.3.6.1.4.1.37950.1.1.5.12.1.13.1.5
-- 1.3.6.1.4.1.37950.1.1.5.12.1.13.1.5
-- 1.3.6.1.4.1.37950.1.1.5.12.1.13.1.5
-- 1.3.6.1.4.1.37950.1.1.5.12.1.13.1.5
-- 1.3.6.1.4.1.37950.1.1.5.12.1.13.1.5
		-- 1.3.6.1.4.1.37950.1.1.5.12.1.13.1.5
		onuAutoFindLoid OBJECT-TYPE
			SYNTAX OCTET STRING
			MAX-ACCESS read-only
			STATUS current
			DESCRIPTION
				"Description."
			::= { onuAutoFindEntry 5 }

		
--          1.3.6.1.4.1.37950.1.1.5.12.1.13.1.6
-- 1.3.6.1.4.1.37950.1.1.5.12.1.13.1.6
-- 1.3.6.1.4.1.37950.1.1.5.12.1.13.1.6
-- 1.3.6.1.4.1.37950.1.1.5.12.1.13.1.6
-- 1.3.6.1.4.1.37950.1.1.5.12.1.13.1.6
-- 1.3.6.1.4.1.37950.1.1.5.12.1.13.1.6
-- 1.3.6.1.4.1.37950.1.1.5.12.1.13.1.6
-- 1.3.6.1.4.1.37950.1.1.5.12.1.13.1.6
-- 1.3.6.1.4.1.37950.1.1.5.12.1.13.1.6
		-- 1.3.6.1.4.1.37950.1.1.5.12.1.13.1.6
		onuAutoFindLoidPwd OBJECT-TYPE
			SYNTAX OCTET STRING
			MAX-ACCESS read-only
			STATUS current
			DESCRIPTION
				"Description."
			::= { onuAutoFindEntry 6 }

		
--          1.3.6.1.4.1.37950.1.1.5.12.1.14
-- 1.3.6.1.4.1.37950.1.1.5.12.1.14
-- 1.3.6.1.4.1.37950.1.1.5.12.1.14
-- 1.3.6.1.4.1.37950.1.1.5.12.1.14
-- 1.3.6.1.4.1.37950.1.1.5.12.1.14
-- 1.3.6.1.4.1.37950.1.1.5.12.1.14
-- 1.3.6.1.4.1.37950.1.1.5.12.1.14
-- 1.3.6.1.4.1.37950.1.1.5.12.1.14
-- 1.3.6.1.4.1.37950.1.1.5.12.1.14
		-- 1.3.6.1.4.1.37950.1.1.5.12.1.14
		deregisterOnu OBJECT IDENTIFIER ::= { onuAuth 14 }

		
--          1.3.6.1.4.1.37950.1.1.5.12.1.14.1
-- 1.3.6.1.4.1.37950.1.1.5.12.1.14.1
-- 1.3.6.1.4.1.37950.1.1.5.12.1.14.1
-- 1.3.6.1.4.1.37950.1.1.5.12.1.14.1
-- 1.3.6.1.4.1.37950.1.1.5.12.1.14.1
-- 1.3.6.1.4.1.37950.1.1.5.12.1.14.1
-- 1.3.6.1.4.1.37950.1.1.5.12.1.14.1
-- 1.3.6.1.4.1.37950.1.1.5.12.1.14.1
-- 1.3.6.1.4.1.37950.1.1.5.12.1.14.1
		-- 1.3.6.1.4.1.37950.1.1.5.12.1.14.1
		deregisterOnuPonIndex OBJECT-TYPE
			SYNTAX Integer32 (1..16)
			MAX-ACCESS read-write
			STATUS current
			DESCRIPTION
				"Description."
			::= { deregisterOnu 1 }

		
--          1.3.6.1.4.1.37950.1.1.5.12.1.14.2
-- 1.3.6.1.4.1.37950.1.1.5.12.1.14.2
-- 1.3.6.1.4.1.37950.1.1.5.12.1.14.2
-- 1.3.6.1.4.1.37950.1.1.5.12.1.14.2
-- 1.3.6.1.4.1.37950.1.1.5.12.1.14.2
-- 1.3.6.1.4.1.37950.1.1.5.12.1.14.2
-- 1.3.6.1.4.1.37950.1.1.5.12.1.14.2
-- 1.3.6.1.4.1.37950.1.1.5.12.1.14.2
-- 1.3.6.1.4.1.37950.1.1.5.12.1.14.2
		-- 1.3.6.1.4.1.37950.1.1.5.12.1.14.2
		deregisterOnuIndex OBJECT-TYPE
			SYNTAX Integer32 (0..65535)
			MAX-ACCESS read-write
			STATUS current
			DESCRIPTION
				"Description."
			::= { deregisterOnu 2 }

		
--          1.3.6.1.4.1.37950.1.1.5.12.1.15
-- 1.3.6.1.4.1.37950.1.1.5.12.1.15
-- 1.3.6.1.4.1.37950.1.1.5.12.1.15
-- 1.3.6.1.4.1.37950.1.1.5.12.1.15
-- 1.3.6.1.4.1.37950.1.1.5.12.1.15
-- 1.3.6.1.4.1.37950.1.1.5.12.1.15
-- 1.3.6.1.4.1.37950.1.1.5.12.1.15
-- 1.3.6.1.4.1.37950.1.1.5.12.1.15
-- 1.3.6.1.4.1.37950.1.1.5.12.1.15
		-- 1.3.6.1.4.1.37950.1.1.5.12.1.15
		resetOnu OBJECT IDENTIFIER ::= { onuAuth 15 }

		
--          1.3.6.1.4.1.37950.1.1.5.12.1.15.1
-- 1.3.6.1.4.1.37950.1.1.5.12.1.15.1
-- 1.3.6.1.4.1.37950.1.1.5.12.1.15.1
-- 1.3.6.1.4.1.37950.1.1.5.12.1.15.1
-- 1.3.6.1.4.1.37950.1.1.5.12.1.15.1
-- 1.3.6.1.4.1.37950.1.1.5.12.1.15.1
-- 1.3.6.1.4.1.37950.1.1.5.12.1.15.1
-- 1.3.6.1.4.1.37950.1.1.5.12.1.15.1
-- 1.3.6.1.4.1.37950.1.1.5.12.1.15.1
		-- 1.3.6.1.4.1.37950.1.1.5.12.1.15.1
		resetOnuPonIndex OBJECT-TYPE
			SYNTAX INTEGER (1..16)
			MAX-ACCESS read-write
			STATUS current
			DESCRIPTION
				"Description."
			::= { resetOnu 1 }

		
--          1.3.6.1.4.1.37950.1.1.5.12.1.15.2
-- 1.3.6.1.4.1.37950.1.1.5.12.1.15.2
-- 1.3.6.1.4.1.37950.1.1.5.12.1.15.2
-- 1.3.6.1.4.1.37950.1.1.5.12.1.15.2
-- 1.3.6.1.4.1.37950.1.1.5.12.1.15.2
-- 1.3.6.1.4.1.37950.1.1.5.12.1.15.2
-- 1.3.6.1.4.1.37950.1.1.5.12.1.15.2
-- 1.3.6.1.4.1.37950.1.1.5.12.1.15.2
-- 1.3.6.1.4.1.37950.1.1.5.12.1.15.2
		-- 1.3.6.1.4.1.37950.1.1.5.12.1.15.2
		resetOnuIndex OBJECT-TYPE
			SYNTAX INTEGER (0..65535)
			MAX-ACCESS read-write
			STATUS current
			DESCRIPTION
				"Description."
			::= { resetOnu 2 }

		
--          1.3.6.1.4.1.37950.1.1.5.12.1.16
-- 1.3.6.1.4.1.37950.1.1.5.12.1.16
-- 1.3.6.1.4.1.37950.1.1.5.12.1.16
-- 1.3.6.1.4.1.37950.1.1.5.12.1.16
-- 1.3.6.1.4.1.37950.1.1.5.12.1.16
-- 1.3.6.1.4.1.37950.1.1.5.12.1.16
-- 1.3.6.1.4.1.37950.1.1.5.12.1.16
-- 1.3.6.1.4.1.37950.1.1.5.12.1.16
-- 1.3.6.1.4.1.37950.1.1.5.12.1.16
		-- 1.3.6.1.4.1.37950.1.1.5.12.1.16
		onuDescription OBJECT IDENTIFIER ::= { onuAuth 16 }

		
--          1.3.6.1.4.1.37950.1.1.5.12.1.16.1
-- 1.3.6.1.4.1.37950.1.1.5.12.1.16.1
-- 1.3.6.1.4.1.37950.1.1.5.12.1.16.1
-- 1.3.6.1.4.1.37950.1.1.5.12.1.16.1
-- 1.3.6.1.4.1.37950.1.1.5.12.1.16.1
-- 1.3.6.1.4.1.37950.1.1.5.12.1.16.1
-- 1.3.6.1.4.1.37950.1.1.5.12.1.16.1
-- 1.3.6.1.4.1.37950.1.1.5.12.1.16.1
-- 1.3.6.1.4.1.37950.1.1.5.12.1.16.1
		-- 1.3.6.1.4.1.37950.1.1.5.12.1.16.1
		onuDescriptionPon OBJECT-TYPE
			SYNTAX INTEGER (1..16)
			MAX-ACCESS read-write
			STATUS current
			DESCRIPTION
				"Description."
			::= { onuDescription 1 }

		
--          1.3.6.1.4.1.37950.1.1.5.12.1.16.2
-- 1.3.6.1.4.1.37950.1.1.5.12.1.16.2
-- 1.3.6.1.4.1.37950.1.1.5.12.1.16.2
-- 1.3.6.1.4.1.37950.1.1.5.12.1.16.2
-- 1.3.6.1.4.1.37950.1.1.5.12.1.16.2
-- 1.3.6.1.4.1.37950.1.1.5.12.1.16.2
-- 1.3.6.1.4.1.37950.1.1.5.12.1.16.2
-- 1.3.6.1.4.1.37950.1.1.5.12.1.16.2
-- 1.3.6.1.4.1.37950.1.1.5.12.1.16.2
		-- 1.3.6.1.4.1.37950.1.1.5.12.1.16.2
		onuDescriptionOnu OBJECT-TYPE
			SYNTAX INTEGER (1..65535)
			MAX-ACCESS read-write
			STATUS current
			DESCRIPTION
				"Description."
			::= { onuDescription 2 }

		
--          1.3.6.1.4.1.37950.1.1.5.12.1.16.3
-- 1.3.6.1.4.1.37950.1.1.5.12.1.16.3
-- 1.3.6.1.4.1.37950.1.1.5.12.1.16.3
-- 1.3.6.1.4.1.37950.1.1.5.12.1.16.3
-- 1.3.6.1.4.1.37950.1.1.5.12.1.16.3
-- 1.3.6.1.4.1.37950.1.1.5.12.1.16.3
-- 1.3.6.1.4.1.37950.1.1.5.12.1.16.3
-- 1.3.6.1.4.1.37950.1.1.5.12.1.16.3
-- 1.3.6.1.4.1.37950.1.1.5.12.1.16.3
		-- 1.3.6.1.4.1.37950.1.1.5.12.1.16.3
		onuDescriptionStr OBJECT-TYPE
			SYNTAX OCTET STRING
			MAX-ACCESS read-write
			STATUS current
			DESCRIPTION
				"Description."
			::= { onuDescription 3 }

		
--          1.3.6.1.4.1.37950.1.1.5.12.1.16.4
-- 1.3.6.1.4.1.37950.1.1.5.12.1.16.4
-- 1.3.6.1.4.1.37950.1.1.5.12.1.16.4
-- 1.3.6.1.4.1.37950.1.1.5.12.1.16.4
-- 1.3.6.1.4.1.37950.1.1.5.12.1.16.4
-- 1.3.6.1.4.1.37950.1.1.5.12.1.16.4
-- 1.3.6.1.4.1.37950.1.1.5.12.1.16.4
-- 1.3.6.1.4.1.37950.1.1.5.12.1.16.4
-- 1.3.6.1.4.1.37950.1.1.5.12.1.16.4
		-- 1.3.6.1.4.1.37950.1.1.5.12.1.16.4
		onuDescriptionAction OBJECT-TYPE
			SYNTAX INTEGER
				{
				commit(1),
				delete(2)
				}
			MAX-ACCESS read-write
			STATUS current
			DESCRIPTION
				"Description."
			::= { onuDescription 4 }

		
--          1.3.6.1.4.1.37950.1.1.5.12.1.17
-- 1.3.6.1.4.1.37950.1.1.5.12.1.17
-- 1.3.6.1.4.1.37950.1.1.5.12.1.17
-- 1.3.6.1.4.1.37950.1.1.5.12.1.17
-- 1.3.6.1.4.1.37950.1.1.5.12.1.17
-- 1.3.6.1.4.1.37950.1.1.5.12.1.17
-- 1.3.6.1.4.1.37950.1.1.5.12.1.17
-- 1.3.6.1.4.1.37950.1.1.5.12.1.17
-- 1.3.6.1.4.1.37950.1.1.5.12.1.17
		-- 1.3.6.1.4.1.37950.1.1.5.12.1.17
		onuRttTable OBJECT-TYPE
			SYNTAX SEQUENCE OF OnuRttEntry
			MAX-ACCESS not-accessible
			STATUS current
			DESCRIPTION
				"Description."
			::= { onuAuth 17 }

		
--          1.3.6.1.4.1.37950.1.1.5.12.1.17.1
-- 1.3.6.1.4.1.37950.1.1.5.12.1.17.1
-- 1.3.6.1.4.1.37950.1.1.5.12.1.17.1
-- 1.3.6.1.4.1.37950.1.1.5.12.1.17.1
-- 1.3.6.1.4.1.37950.1.1.5.12.1.17.1
-- 1.3.6.1.4.1.37950.1.1.5.12.1.17.1
-- 1.3.6.1.4.1.37950.1.1.5.12.1.17.1
-- 1.3.6.1.4.1.37950.1.1.5.12.1.17.1
-- 1.3.6.1.4.1.37950.1.1.5.12.1.17.1
		-- 1.3.6.1.4.1.37950.1.1.5.12.1.17.1
		onuRttEntry OBJECT-TYPE
			SYNTAX OnuRttEntry
			MAX-ACCESS not-accessible
			STATUS current
			DESCRIPTION
				"Description."
			INDEX { onuRttPon, onuRttOnu }
			::= { onuRttTable 1 }

		
		OnuRttEntry ::=
			SEQUENCE { 
				onuRttPon
					INTEGER,
				onuRttOnu
					INTEGER,
				onuRttValue
					INTEGER
			 }

--          1.3.6.1.4.1.37950.1.1.5.12.1.17.1.1
-- 1.3.6.1.4.1.37950.1.1.5.12.1.17.1.1
-- 1.3.6.1.4.1.37950.1.1.5.12.1.17.1.1
-- 1.3.6.1.4.1.37950.1.1.5.12.1.17.1.1
-- 1.3.6.1.4.1.37950.1.1.5.12.1.17.1.1
-- 1.3.6.1.4.1.37950.1.1.5.12.1.17.1.1
-- 1.3.6.1.4.1.37950.1.1.5.12.1.17.1.1
-- 1.3.6.1.4.1.37950.1.1.5.12.1.17.1.1
-- 1.3.6.1.4.1.37950.1.1.5.12.1.17.1.1
		-- 1.3.6.1.4.1.37950.1.1.5.12.1.17.1.1
		onuRttPon OBJECT-TYPE
			SYNTAX INTEGER (1..16)
			MAX-ACCESS read-only
			STATUS current
			DESCRIPTION
				"Description."
			::= { onuRttEntry 1 }

		
--          1.3.6.1.4.1.37950.1.1.5.12.1.17.1.2
-- 1.3.6.1.4.1.37950.1.1.5.12.1.17.1.2
-- 1.3.6.1.4.1.37950.1.1.5.12.1.17.1.2
-- 1.3.6.1.4.1.37950.1.1.5.12.1.17.1.2
-- 1.3.6.1.4.1.37950.1.1.5.12.1.17.1.2
-- 1.3.6.1.4.1.37950.1.1.5.12.1.17.1.2
-- 1.3.6.1.4.1.37950.1.1.5.12.1.17.1.2
-- 1.3.6.1.4.1.37950.1.1.5.12.1.17.1.2
-- 1.3.6.1.4.1.37950.1.1.5.12.1.17.1.2
		-- 1.3.6.1.4.1.37950.1.1.5.12.1.17.1.2
		onuRttOnu OBJECT-TYPE
			SYNTAX INTEGER (1..65535)
			MAX-ACCESS read-only
			STATUS current
			DESCRIPTION
				"Description."
			::= { onuRttEntry 2 }

		
--          1.3.6.1.4.1.37950.1.1.5.12.1.17.1.3
-- 1.3.6.1.4.1.37950.1.1.5.12.1.17.1.3
-- 1.3.6.1.4.1.37950.1.1.5.12.1.17.1.3
-- 1.3.6.1.4.1.37950.1.1.5.12.1.17.1.3
-- 1.3.6.1.4.1.37950.1.1.5.12.1.17.1.3
-- 1.3.6.1.4.1.37950.1.1.5.12.1.17.1.3
-- 1.3.6.1.4.1.37950.1.1.5.12.1.17.1.3
-- 1.3.6.1.4.1.37950.1.1.5.12.1.17.1.3
-- 1.3.6.1.4.1.37950.1.1.5.12.1.17.1.3
		-- 1.3.6.1.4.1.37950.1.1.5.12.1.17.1.3
		onuRttValue OBJECT-TYPE
			SYNTAX INTEGER
			MAX-ACCESS read-only
			STATUS current
			DESCRIPTION
				"Description."
			::= { onuRttEntry 3 }

		
--          1.3.6.1.4.1.37950.1.1.5.12.1.18
-- 1.3.6.1.4.1.37950.1.1.5.12.1.18
-- 1.3.6.1.4.1.37950.1.1.5.12.1.18
-- 1.3.6.1.4.1.37950.1.1.5.12.1.18
-- 1.3.6.1.4.1.37950.1.1.5.12.1.18
-- 1.3.6.1.4.1.37950.1.1.5.12.1.18
-- 1.3.6.1.4.1.37950.1.1.5.12.1.18
-- 1.3.6.1.4.1.37950.1.1.5.12.1.18
-- 1.3.6.1.4.1.37950.1.1.5.12.1.18
		-- 1.3.6.1.4.1.37950.1.1.5.12.1.18
		onuEncryption OBJECT IDENTIFIER ::= { onuAuth 18 }

		
--          1.3.6.1.4.1.37950.1.1.5.12.1.18.1
-- 1.3.6.1.4.1.37950.1.1.5.12.1.18.1
-- 1.3.6.1.4.1.37950.1.1.5.12.1.18.1
-- 1.3.6.1.4.1.37950.1.1.5.12.1.18.1
-- 1.3.6.1.4.1.37950.1.1.5.12.1.18.1
-- 1.3.6.1.4.1.37950.1.1.5.12.1.18.1
-- 1.3.6.1.4.1.37950.1.1.5.12.1.18.1
-- 1.3.6.1.4.1.37950.1.1.5.12.1.18.1
-- 1.3.6.1.4.1.37950.1.1.5.12.1.18.1
		-- 1.3.6.1.4.1.37950.1.1.5.12.1.18.1
		onuEncryptionPon OBJECT-TYPE
			SYNTAX INTEGER (1..16)
			MAX-ACCESS read-write
			STATUS current
			DESCRIPTION
				"Description."
			::= { onuEncryption 1 }

		
--          1.3.6.1.4.1.37950.1.1.5.12.1.18.2
-- 1.3.6.1.4.1.37950.1.1.5.12.1.18.2
-- 1.3.6.1.4.1.37950.1.1.5.12.1.18.2
-- 1.3.6.1.4.1.37950.1.1.5.12.1.18.2
-- 1.3.6.1.4.1.37950.1.1.5.12.1.18.2
-- 1.3.6.1.4.1.37950.1.1.5.12.1.18.2
-- 1.3.6.1.4.1.37950.1.1.5.12.1.18.2
-- 1.3.6.1.4.1.37950.1.1.5.12.1.18.2
-- 1.3.6.1.4.1.37950.1.1.5.12.1.18.2
		-- 1.3.6.1.4.1.37950.1.1.5.12.1.18.2
		onuEncryptionOnu OBJECT-TYPE
			SYNTAX INTEGER (1..65535)
			MAX-ACCESS read-write
			STATUS current
			DESCRIPTION
				"Description."
			::= { onuEncryption 2 }

		
--          1.3.6.1.4.1.37950.1.1.5.12.1.18.3
-- 1.3.6.1.4.1.37950.1.1.5.12.1.18.3
-- 1.3.6.1.4.1.37950.1.1.5.12.1.18.3
-- 1.3.6.1.4.1.37950.1.1.5.12.1.18.3
-- 1.3.6.1.4.1.37950.1.1.5.12.1.18.3
-- 1.3.6.1.4.1.37950.1.1.5.12.1.18.3
-- 1.3.6.1.4.1.37950.1.1.5.12.1.18.3
-- 1.3.6.1.4.1.37950.1.1.5.12.1.18.3
-- 1.3.6.1.4.1.37950.1.1.5.12.1.18.3
		-- 1.3.6.1.4.1.37950.1.1.5.12.1.18.3
		onuEncryptionEnable OBJECT-TYPE
			SYNTAX INTEGER
				{
				disable(0),
				enable(1)
				}
			MAX-ACCESS read-write
			STATUS current
			DESCRIPTION
				"Description."
			::= { onuEncryption 3 }

		
--          1.3.6.1.4.1.37950.1.1.5.12.1.18.4
-- 1.3.6.1.4.1.37950.1.1.5.12.1.18.4
-- 1.3.6.1.4.1.37950.1.1.5.12.1.18.4
-- 1.3.6.1.4.1.37950.1.1.5.12.1.18.4
-- 1.3.6.1.4.1.37950.1.1.5.12.1.18.4
-- 1.3.6.1.4.1.37950.1.1.5.12.1.18.4
-- 1.3.6.1.4.1.37950.1.1.5.12.1.18.4
-- 1.3.6.1.4.1.37950.1.1.5.12.1.18.4
-- 1.3.6.1.4.1.37950.1.1.5.12.1.18.4
		-- 1.3.6.1.4.1.37950.1.1.5.12.1.18.4
		onuEncryptionAction OBJECT-TYPE
			SYNTAX INTEGER
				{
				commit(1),
				delete(2)
				}
			MAX-ACCESS read-write
			STATUS current
			DESCRIPTION
				"Description."
			::= { onuEncryption 4 }

		
--          1.3.6.1.4.1.37950.1.1.5.12.1.19
-- 1.3.6.1.4.1.37950.1.1.5.12.1.19
-- 1.3.6.1.4.1.37950.1.1.5.12.1.19
-- 1.3.6.1.4.1.37950.1.1.5.12.1.19
-- 1.3.6.1.4.1.37950.1.1.5.12.1.19
-- 1.3.6.1.4.1.37950.1.1.5.12.1.19
-- 1.3.6.1.4.1.37950.1.1.5.12.1.19
-- 1.3.6.1.4.1.37950.1.1.5.12.1.19
-- 1.3.6.1.4.1.37950.1.1.5.12.1.19
		-- 1.3.6.1.4.1.37950.1.1.5.12.1.19
		onuEncryptionTable OBJECT-TYPE
			SYNTAX SEQUENCE OF OnuEncryptionEntry
			MAX-ACCESS not-accessible
			STATUS current
			DESCRIPTION
				"Description."
			::= { onuAuth 19 }

		
--          1.3.6.1.4.1.37950.1.1.5.12.1.19.1
-- 1.3.6.1.4.1.37950.1.1.5.12.1.19.1
-- 1.3.6.1.4.1.37950.1.1.5.12.1.19.1
-- 1.3.6.1.4.1.37950.1.1.5.12.1.19.1
-- 1.3.6.1.4.1.37950.1.1.5.12.1.19.1
-- 1.3.6.1.4.1.37950.1.1.5.12.1.19.1
-- 1.3.6.1.4.1.37950.1.1.5.12.1.19.1
-- 1.3.6.1.4.1.37950.1.1.5.12.1.19.1
-- 1.3.6.1.4.1.37950.1.1.5.12.1.19.1
		-- 1.3.6.1.4.1.37950.1.1.5.12.1.19.1
		onuEncryptionEntry OBJECT-TYPE
			SYNTAX OnuEncryptionEntry
			MAX-ACCESS not-accessible
			STATUS current
			DESCRIPTION
				"Description."
			INDEX { onuEncryptionPonS, onuEncryptionOnuS }
			::= { onuEncryptionTable 1 }

		
		OnuEncryptionEntry ::=
			SEQUENCE { 
				onuEncryptionPonS
					INTEGER,
				onuEncryptionOnuS
					INTEGER,
				onuEncryptionEnableS
					INTEGER
			 }

--          1.3.6.1.4.1.37950.1.1.5.12.1.19.1.1
-- 1.3.6.1.4.1.37950.1.1.5.12.1.19.1.1
-- 1.3.6.1.4.1.37950.1.1.5.12.1.19.1.1
-- 1.3.6.1.4.1.37950.1.1.5.12.1.19.1.1
-- 1.3.6.1.4.1.37950.1.1.5.12.1.19.1.1
-- 1.3.6.1.4.1.37950.1.1.5.12.1.19.1.1
-- 1.3.6.1.4.1.37950.1.1.5.12.1.19.1.1
-- 1.3.6.1.4.1.37950.1.1.5.12.1.19.1.1
-- 1.3.6.1.4.1.37950.1.1.5.12.1.19.1.1
		-- 1.3.6.1.4.1.37950.1.1.5.12.1.19.1.1
		onuEncryptionPonS OBJECT-TYPE
			SYNTAX INTEGER (1..16)
			MAX-ACCESS read-only
			STATUS current
			DESCRIPTION
				"Description."
			::= { onuEncryptionEntry 1 }

		
--          1.3.6.1.4.1.37950.1.1.5.12.1.19.1.2
-- 1.3.6.1.4.1.37950.1.1.5.12.1.19.1.2
-- 1.3.6.1.4.1.37950.1.1.5.12.1.19.1.2
-- 1.3.6.1.4.1.37950.1.1.5.12.1.19.1.2
-- 1.3.6.1.4.1.37950.1.1.5.12.1.19.1.2
-- 1.3.6.1.4.1.37950.1.1.5.12.1.19.1.2
-- 1.3.6.1.4.1.37950.1.1.5.12.1.19.1.2
-- 1.3.6.1.4.1.37950.1.1.5.12.1.19.1.2
-- 1.3.6.1.4.1.37950.1.1.5.12.1.19.1.2
		-- 1.3.6.1.4.1.37950.1.1.5.12.1.19.1.2
		onuEncryptionOnuS OBJECT-TYPE
			SYNTAX INTEGER (1..65535)
			MAX-ACCESS read-write
			STATUS current
			DESCRIPTION
				"Description."
			::= { onuEncryptionEntry 2 }

		
--          1.3.6.1.4.1.37950.1.1.5.12.1.19.1.3
-- 1.3.6.1.4.1.37950.1.1.5.12.1.19.1.3
-- 1.3.6.1.4.1.37950.1.1.5.12.1.19.1.3
-- 1.3.6.1.4.1.37950.1.1.5.12.1.19.1.3
-- 1.3.6.1.4.1.37950.1.1.5.12.1.19.1.3
-- 1.3.6.1.4.1.37950.1.1.5.12.1.19.1.3
-- 1.3.6.1.4.1.37950.1.1.5.12.1.19.1.3
-- 1.3.6.1.4.1.37950.1.1.5.12.1.19.1.3
-- 1.3.6.1.4.1.37950.1.1.5.12.1.19.1.3
		-- 1.3.6.1.4.1.37950.1.1.5.12.1.19.1.3
		onuEncryptionEnableS OBJECT-TYPE
			SYNTAX INTEGER
				{
				disable(0),
				enable(1)
				}
			MAX-ACCESS read-only
			STATUS current
			DESCRIPTION
				"Description."
			::= { onuEncryptionEntry 3 }

		
--          1.3.6.1.4.1.37950.1.1.5.12.1.20
-- 1.3.6.1.4.1.37950.1.1.5.12.1.20
-- 1.3.6.1.4.1.37950.1.1.5.12.1.20
-- 1.3.6.1.4.1.37950.1.1.5.12.1.20
-- 1.3.6.1.4.1.37950.1.1.5.12.1.20
-- 1.3.6.1.4.1.37950.1.1.5.12.1.20
-- 1.3.6.1.4.1.37950.1.1.5.12.1.20
-- 1.3.6.1.4.1.37950.1.1.5.12.1.20
-- 1.3.6.1.4.1.37950.1.1.5.12.1.20
		-- 1.3.6.1.4.1.37950.1.1.5.12.1.20
		onuStatisticsTable OBJECT-TYPE
			SYNTAX SEQUENCE OF OnuStatisticsEntry
			MAX-ACCESS not-accessible
			STATUS current
			DESCRIPTION
				"Description."
			::= { onuAuth 20 }

		
--          1.3.6.1.4.1.37950.1.1.5.12.1.20.1
-- 1.3.6.1.4.1.37950.1.1.5.12.1.20.1
-- 1.3.6.1.4.1.37950.1.1.5.12.1.20.1
-- 1.3.6.1.4.1.37950.1.1.5.12.1.20.1
-- 1.3.6.1.4.1.37950.1.1.5.12.1.20.1
-- 1.3.6.1.4.1.37950.1.1.5.12.1.20.1
-- 1.3.6.1.4.1.37950.1.1.5.12.1.20.1
-- 1.3.6.1.4.1.37950.1.1.5.12.1.20.1
-- 1.3.6.1.4.1.37950.1.1.5.12.1.20.1
		-- 1.3.6.1.4.1.37950.1.1.5.12.1.20.1
		onuStatisticsEntry OBJECT-TYPE
			SYNTAX OnuStatisticsEntry
			MAX-ACCESS not-accessible
			STATUS current
			DESCRIPTION
				"Description."
			INDEX { onuStatisticsPon, onuStatisticsOnu }
			::= { onuStatisticsTable 1 }

		
		OnuStatisticsEntry ::=
			SEQUENCE { 
				onuStatisticsPon
					INTEGER,
				onuStatisticsOnu
					INTEGER,
				statRxGoodOctets
					Counter64,
				statRxUcastFrames
					Unsigned32,
				statRxMcastFrames
					Unsigned32,
				statRxBcastFrames
					Unsigned32,
				statRxRegreqFrames
					Unsigned32,
				statRxRegackFrames
					Unsigned32,
				statRxReportFrames
					Unsigned32,
				statTxGoodOctets
					Counter64,
				statTxUcastFrames
					Unsigned32,
				statTxMcastFrames
					Unsigned32,
				statTxBcastFrames
					Unsigned32,
				statTxGateFrames
					Unsigned32,
				statTxRegFrames
					Unsigned32,
				statTxOamFrames
					Unsigned32,
				statRxGoodOpi
					Unsigned32,
				statRxBadCrc32
					Unsigned32,
				statRxOamFrames
					Unsigned32
			 }

--          1.3.6.1.4.1.37950.1.1.5.12.1.20.1.1
-- 1.3.6.1.4.1.37950.1.1.5.12.1.20.1.1
-- 1.3.6.1.4.1.37950.1.1.5.12.1.20.1.1
-- 1.3.6.1.4.1.37950.1.1.5.12.1.20.1.1
-- 1.3.6.1.4.1.37950.1.1.5.12.1.20.1.1
-- 1.3.6.1.4.1.37950.1.1.5.12.1.20.1.1
-- 1.3.6.1.4.1.37950.1.1.5.12.1.20.1.1
-- 1.3.6.1.4.1.37950.1.1.5.12.1.20.1.1
-- 1.3.6.1.4.1.37950.1.1.5.12.1.20.1.1
		-- 1.3.6.1.4.1.37950.1.1.5.12.1.20.1.1
		onuStatisticsPon OBJECT-TYPE
			SYNTAX INTEGER (1..16)
			MAX-ACCESS read-only
			STATUS current
			DESCRIPTION
				"Description."
			::= { onuStatisticsEntry 1 }

		
--          1.3.6.1.4.1.37950.1.1.5.12.1.20.1.2
-- 1.3.6.1.4.1.37950.1.1.5.12.1.20.1.2
-- 1.3.6.1.4.1.37950.1.1.5.12.1.20.1.2
-- 1.3.6.1.4.1.37950.1.1.5.12.1.20.1.2
-- 1.3.6.1.4.1.37950.1.1.5.12.1.20.1.2
-- 1.3.6.1.4.1.37950.1.1.5.12.1.20.1.2
-- 1.3.6.1.4.1.37950.1.1.5.12.1.20.1.2
-- 1.3.6.1.4.1.37950.1.1.5.12.1.20.1.2
-- 1.3.6.1.4.1.37950.1.1.5.12.1.20.1.2
		-- 1.3.6.1.4.1.37950.1.1.5.12.1.20.1.2
		onuStatisticsOnu OBJECT-TYPE
			SYNTAX INTEGER (1..65535)
			MAX-ACCESS read-only
			STATUS current
			DESCRIPTION
				"Description."
			::= { onuStatisticsEntry 2 }

		
--          1.3.6.1.4.1.37950.1.1.5.12.1.20.1.3
-- 1.3.6.1.4.1.37950.1.1.5.12.1.20.1.3
-- 1.3.6.1.4.1.37950.1.1.5.12.1.20.1.3
-- 1.3.6.1.4.1.37950.1.1.5.12.1.20.1.3
-- 1.3.6.1.4.1.37950.1.1.5.12.1.20.1.3
-- 1.3.6.1.4.1.37950.1.1.5.12.1.20.1.3
-- 1.3.6.1.4.1.37950.1.1.5.12.1.20.1.3
-- 1.3.6.1.4.1.37950.1.1.5.12.1.20.1.3
-- 1.3.6.1.4.1.37950.1.1.5.12.1.20.1.3
		-- 1.3.6.1.4.1.37950.1.1.5.12.1.20.1.3
		statRxGoodOctets OBJECT-TYPE
			SYNTAX Counter64
			MAX-ACCESS read-only
			STATUS current
			DESCRIPTION
				"Description."
			::= { onuStatisticsEntry 3 }

		
--          1.3.6.1.4.1.37950.1.1.5.12.1.20.1.4
-- 1.3.6.1.4.1.37950.1.1.5.12.1.20.1.4
-- 1.3.6.1.4.1.37950.1.1.5.12.1.20.1.4
-- 1.3.6.1.4.1.37950.1.1.5.12.1.20.1.4
-- 1.3.6.1.4.1.37950.1.1.5.12.1.20.1.4
-- 1.3.6.1.4.1.37950.1.1.5.12.1.20.1.4
-- 1.3.6.1.4.1.37950.1.1.5.12.1.20.1.4
-- 1.3.6.1.4.1.37950.1.1.5.12.1.20.1.4
-- 1.3.6.1.4.1.37950.1.1.5.12.1.20.1.4
		-- 1.3.6.1.4.1.37950.1.1.5.12.1.20.1.4
		statRxUcastFrames OBJECT-TYPE
			SYNTAX Unsigned32
			MAX-ACCESS read-only
			STATUS current
			DESCRIPTION
				"Description."
			::= { onuStatisticsEntry 4 }

		
--          1.3.6.1.4.1.37950.1.1.5.12.1.20.1.5
-- 1.3.6.1.4.1.37950.1.1.5.12.1.20.1.5
-- 1.3.6.1.4.1.37950.1.1.5.12.1.20.1.5
-- 1.3.6.1.4.1.37950.1.1.5.12.1.20.1.5
-- 1.3.6.1.4.1.37950.1.1.5.12.1.20.1.5
-- 1.3.6.1.4.1.37950.1.1.5.12.1.20.1.5
-- 1.3.6.1.4.1.37950.1.1.5.12.1.20.1.5
-- 1.3.6.1.4.1.37950.1.1.5.12.1.20.1.5
-- 1.3.6.1.4.1.37950.1.1.5.12.1.20.1.5
		-- 1.3.6.1.4.1.37950.1.1.5.12.1.20.1.5
		statRxMcastFrames OBJECT-TYPE
			SYNTAX Unsigned32
			MAX-ACCESS read-only
			STATUS current
			DESCRIPTION
				"Description."
			::= { onuStatisticsEntry 5 }

		
--          1.3.6.1.4.1.37950.1.1.5.12.1.20.1.6
-- 1.3.6.1.4.1.37950.1.1.5.12.1.20.1.6
-- 1.3.6.1.4.1.37950.1.1.5.12.1.20.1.6
-- 1.3.6.1.4.1.37950.1.1.5.12.1.20.1.6
-- 1.3.6.1.4.1.37950.1.1.5.12.1.20.1.6
-- 1.3.6.1.4.1.37950.1.1.5.12.1.20.1.6
-- 1.3.6.1.4.1.37950.1.1.5.12.1.20.1.6
-- 1.3.6.1.4.1.37950.1.1.5.12.1.20.1.6
-- 1.3.6.1.4.1.37950.1.1.5.12.1.20.1.6
		-- 1.3.6.1.4.1.37950.1.1.5.12.1.20.1.6
		statRxBcastFrames OBJECT-TYPE
			SYNTAX Unsigned32
			MAX-ACCESS read-only
			STATUS current
			DESCRIPTION
				"Description."
			::= { onuStatisticsEntry 6 }

		
--          1.3.6.1.4.1.37950.1.1.5.12.1.20.1.7
-- 1.3.6.1.4.1.37950.1.1.5.12.1.20.1.7
-- 1.3.6.1.4.1.37950.1.1.5.12.1.20.1.7
-- 1.3.6.1.4.1.37950.1.1.5.12.1.20.1.7
-- 1.3.6.1.4.1.37950.1.1.5.12.1.20.1.7
-- 1.3.6.1.4.1.37950.1.1.5.12.1.20.1.7
-- 1.3.6.1.4.1.37950.1.1.5.12.1.20.1.7
-- 1.3.6.1.4.1.37950.1.1.5.12.1.20.1.7
-- 1.3.6.1.4.1.37950.1.1.5.12.1.20.1.7
		-- 1.3.6.1.4.1.37950.1.1.5.12.1.20.1.7
		statRxRegreqFrames OBJECT-TYPE
			SYNTAX Unsigned32
			MAX-ACCESS read-only
			STATUS current
			DESCRIPTION
				"Description."
			::= { onuStatisticsEntry 7 }

		
--          1.3.6.1.4.1.37950.1.1.5.12.1.20.1.8
-- 1.3.6.1.4.1.37950.1.1.5.12.1.20.1.8
-- 1.3.6.1.4.1.37950.1.1.5.12.1.20.1.8
-- 1.3.6.1.4.1.37950.1.1.5.12.1.20.1.8
-- 1.3.6.1.4.1.37950.1.1.5.12.1.20.1.8
-- 1.3.6.1.4.1.37950.1.1.5.12.1.20.1.8
-- 1.3.6.1.4.1.37950.1.1.5.12.1.20.1.8
-- 1.3.6.1.4.1.37950.1.1.5.12.1.20.1.8
-- 1.3.6.1.4.1.37950.1.1.5.12.1.20.1.8
		-- 1.3.6.1.4.1.37950.1.1.5.12.1.20.1.8
		statRxRegackFrames OBJECT-TYPE
			SYNTAX Unsigned32
			MAX-ACCESS read-only
			STATUS current
			DESCRIPTION
				"Description."
			::= { onuStatisticsEntry 8 }

		
--          1.3.6.1.4.1.37950.1.1.5.12.1.20.1.9
-- 1.3.6.1.4.1.37950.1.1.5.12.1.20.1.9
-- 1.3.6.1.4.1.37950.1.1.5.12.1.20.1.9
-- 1.3.6.1.4.1.37950.1.1.5.12.1.20.1.9
-- 1.3.6.1.4.1.37950.1.1.5.12.1.20.1.9
-- 1.3.6.1.4.1.37950.1.1.5.12.1.20.1.9
-- 1.3.6.1.4.1.37950.1.1.5.12.1.20.1.9
-- 1.3.6.1.4.1.37950.1.1.5.12.1.20.1.9
-- 1.3.6.1.4.1.37950.1.1.5.12.1.20.1.9
		-- 1.3.6.1.4.1.37950.1.1.5.12.1.20.1.9
		statRxReportFrames OBJECT-TYPE
			SYNTAX Unsigned32
			MAX-ACCESS read-only
			STATUS current
			DESCRIPTION
				"Description."
			::= { onuStatisticsEntry 9 }

		
--          1.3.6.1.4.1.37950.1.1.5.12.1.20.1.10
-- 1.3.6.1.4.1.37950.1.1.5.12.1.20.1.10
-- 1.3.6.1.4.1.37950.1.1.5.12.1.20.1.10
-- 1.3.6.1.4.1.37950.1.1.5.12.1.20.1.10
-- 1.3.6.1.4.1.37950.1.1.5.12.1.20.1.10
-- 1.3.6.1.4.1.37950.1.1.5.12.1.20.1.10
-- 1.3.6.1.4.1.37950.1.1.5.12.1.20.1.10
-- 1.3.6.1.4.1.37950.1.1.5.12.1.20.1.10
-- 1.3.6.1.4.1.37950.1.1.5.12.1.20.1.10
		-- 1.3.6.1.4.1.37950.1.1.5.12.1.20.1.10
		statTxGoodOctets OBJECT-TYPE
			SYNTAX Counter64
			MAX-ACCESS read-only
			STATUS current
			DESCRIPTION
				"Description."
			::= { onuStatisticsEntry 10 }

		
--          1.3.6.1.4.1.37950.1.1.5.12.1.20.1.11
-- 1.3.6.1.4.1.37950.1.1.5.12.1.20.1.11
-- 1.3.6.1.4.1.37950.1.1.5.12.1.20.1.11
-- 1.3.6.1.4.1.37950.1.1.5.12.1.20.1.11
-- 1.3.6.1.4.1.37950.1.1.5.12.1.20.1.11
-- 1.3.6.1.4.1.37950.1.1.5.12.1.20.1.11
-- 1.3.6.1.4.1.37950.1.1.5.12.1.20.1.11
-- 1.3.6.1.4.1.37950.1.1.5.12.1.20.1.11
-- 1.3.6.1.4.1.37950.1.1.5.12.1.20.1.11
		-- 1.3.6.1.4.1.37950.1.1.5.12.1.20.1.11
		statTxUcastFrames OBJECT-TYPE
			SYNTAX Unsigned32
			MAX-ACCESS read-only
			STATUS current
			DESCRIPTION
				"Description."
			::= { onuStatisticsEntry 11 }

		
--          1.3.6.1.4.1.37950.1.1.5.12.1.20.1.12
-- 1.3.6.1.4.1.37950.1.1.5.12.1.20.1.12
-- 1.3.6.1.4.1.37950.1.1.5.12.1.20.1.12
-- 1.3.6.1.4.1.37950.1.1.5.12.1.20.1.12
-- 1.3.6.1.4.1.37950.1.1.5.12.1.20.1.12
-- 1.3.6.1.4.1.37950.1.1.5.12.1.20.1.12
-- 1.3.6.1.4.1.37950.1.1.5.12.1.20.1.12
-- 1.3.6.1.4.1.37950.1.1.5.12.1.20.1.12
-- 1.3.6.1.4.1.37950.1.1.5.12.1.20.1.12
		-- 1.3.6.1.4.1.37950.1.1.5.12.1.20.1.12
		statTxMcastFrames OBJECT-TYPE
			SYNTAX Unsigned32
			MAX-ACCESS read-only
			STATUS current
			DESCRIPTION
				"Description."
			::= { onuStatisticsEntry 12 }

		
--          1.3.6.1.4.1.37950.1.1.5.12.1.20.1.13
-- 1.3.6.1.4.1.37950.1.1.5.12.1.20.1.13
-- 1.3.6.1.4.1.37950.1.1.5.12.1.20.1.13
-- 1.3.6.1.4.1.37950.1.1.5.12.1.20.1.13
-- 1.3.6.1.4.1.37950.1.1.5.12.1.20.1.13
-- 1.3.6.1.4.1.37950.1.1.5.12.1.20.1.13
-- 1.3.6.1.4.1.37950.1.1.5.12.1.20.1.13
-- 1.3.6.1.4.1.37950.1.1.5.12.1.20.1.13
-- 1.3.6.1.4.1.37950.1.1.5.12.1.20.1.13
		-- 1.3.6.1.4.1.37950.1.1.5.12.1.20.1.13
		statTxBcastFrames OBJECT-TYPE
			SYNTAX Unsigned32
			MAX-ACCESS read-only
			STATUS current
			DESCRIPTION
				"Description."
			::= { onuStatisticsEntry 13 }

		
--          1.3.6.1.4.1.37950.1.1.5.12.1.20.1.14
-- 1.3.6.1.4.1.37950.1.1.5.12.1.20.1.14
-- 1.3.6.1.4.1.37950.1.1.5.12.1.20.1.14
-- 1.3.6.1.4.1.37950.1.1.5.12.1.20.1.14
-- 1.3.6.1.4.1.37950.1.1.5.12.1.20.1.14
-- 1.3.6.1.4.1.37950.1.1.5.12.1.20.1.14
-- 1.3.6.1.4.1.37950.1.1.5.12.1.20.1.14
-- 1.3.6.1.4.1.37950.1.1.5.12.1.20.1.14
-- 1.3.6.1.4.1.37950.1.1.5.12.1.20.1.14
		-- 1.3.6.1.4.1.37950.1.1.5.12.1.20.1.14
		statTxGateFrames OBJECT-TYPE
			SYNTAX Unsigned32
			MAX-ACCESS read-only
			STATUS current
			DESCRIPTION
				"Description."
			::= { onuStatisticsEntry 14 }

		
--          1.3.6.1.4.1.37950.1.1.5.12.1.20.1.15
-- 1.3.6.1.4.1.37950.1.1.5.12.1.20.1.15
-- 1.3.6.1.4.1.37950.1.1.5.12.1.20.1.15
-- 1.3.6.1.4.1.37950.1.1.5.12.1.20.1.15
-- 1.3.6.1.4.1.37950.1.1.5.12.1.20.1.15
-- 1.3.6.1.4.1.37950.1.1.5.12.1.20.1.15
-- 1.3.6.1.4.1.37950.1.1.5.12.1.20.1.15
-- 1.3.6.1.4.1.37950.1.1.5.12.1.20.1.15
-- 1.3.6.1.4.1.37950.1.1.5.12.1.20.1.15
		-- 1.3.6.1.4.1.37950.1.1.5.12.1.20.1.15
		statTxRegFrames OBJECT-TYPE
			SYNTAX Unsigned32
			MAX-ACCESS read-only
			STATUS current
			DESCRIPTION
				"Description."
			::= { onuStatisticsEntry 15 }

		
--          1.3.6.1.4.1.37950.1.1.5.12.1.20.1.16
-- 1.3.6.1.4.1.37950.1.1.5.12.1.20.1.16
-- 1.3.6.1.4.1.37950.1.1.5.12.1.20.1.16
-- 1.3.6.1.4.1.37950.1.1.5.12.1.20.1.16
-- 1.3.6.1.4.1.37950.1.1.5.12.1.20.1.16
-- 1.3.6.1.4.1.37950.1.1.5.12.1.20.1.16
-- 1.3.6.1.4.1.37950.1.1.5.12.1.20.1.16
-- 1.3.6.1.4.1.37950.1.1.5.12.1.20.1.16
-- 1.3.6.1.4.1.37950.1.1.5.12.1.20.1.16
		-- 1.3.6.1.4.1.37950.1.1.5.12.1.20.1.16
		statTxOamFrames OBJECT-TYPE
			SYNTAX Unsigned32
			MAX-ACCESS read-only
			STATUS current
			DESCRIPTION
				"Description."
			::= { onuStatisticsEntry 16 }

		
--          1.3.6.1.4.1.37950.1.1.5.12.1.20.1.17
-- 1.3.6.1.4.1.37950.1.1.5.12.1.20.1.17
-- 1.3.6.1.4.1.37950.1.1.5.12.1.20.1.17
-- 1.3.6.1.4.1.37950.1.1.5.12.1.20.1.17
-- 1.3.6.1.4.1.37950.1.1.5.12.1.20.1.17
-- 1.3.6.1.4.1.37950.1.1.5.12.1.20.1.17
-- 1.3.6.1.4.1.37950.1.1.5.12.1.20.1.17
-- 1.3.6.1.4.1.37950.1.1.5.12.1.20.1.17
-- 1.3.6.1.4.1.37950.1.1.5.12.1.20.1.17
		-- 1.3.6.1.4.1.37950.1.1.5.12.1.20.1.17
		statRxGoodOpi OBJECT-TYPE
			SYNTAX Unsigned32
			MAX-ACCESS read-only
			STATUS current
			DESCRIPTION
				"Description."
			::= { onuStatisticsEntry 17 }

		
--          1.3.6.1.4.1.37950.1.1.5.12.1.20.1.18
-- 1.3.6.1.4.1.37950.1.1.5.12.1.20.1.18
-- 1.3.6.1.4.1.37950.1.1.5.12.1.20.1.18
-- 1.3.6.1.4.1.37950.1.1.5.12.1.20.1.18
-- 1.3.6.1.4.1.37950.1.1.5.12.1.20.1.18
-- 1.3.6.1.4.1.37950.1.1.5.12.1.20.1.18
-- 1.3.6.1.4.1.37950.1.1.5.12.1.20.1.18
-- 1.3.6.1.4.1.37950.1.1.5.12.1.20.1.18
-- 1.3.6.1.4.1.37950.1.1.5.12.1.20.1.18
		-- 1.3.6.1.4.1.37950.1.1.5.12.1.20.1.18
		statRxBadCrc32 OBJECT-TYPE
			SYNTAX Unsigned32
			MAX-ACCESS read-only
			STATUS current
			DESCRIPTION
				"Description."
			::= { onuStatisticsEntry 18 }

		
--          1.3.6.1.4.1.37950.1.1.5.12.1.20.1.19
-- 1.3.6.1.4.1.37950.1.1.5.12.1.20.1.19
-- 1.3.6.1.4.1.37950.1.1.5.12.1.20.1.19
-- 1.3.6.1.4.1.37950.1.1.5.12.1.20.1.19
-- 1.3.6.1.4.1.37950.1.1.5.12.1.20.1.19
-- 1.3.6.1.4.1.37950.1.1.5.12.1.20.1.19
-- 1.3.6.1.4.1.37950.1.1.5.12.1.20.1.19
-- 1.3.6.1.4.1.37950.1.1.5.12.1.20.1.19
-- 1.3.6.1.4.1.37950.1.1.5.12.1.20.1.19
		-- 1.3.6.1.4.1.37950.1.1.5.12.1.20.1.19
		statRxOamFrames OBJECT-TYPE
			SYNTAX Unsigned32
			MAX-ACCESS read-write
			STATUS current
			DESCRIPTION
				"Description."
			::= { onuStatisticsEntry 19 }

		
--          1.3.6.1.4.1.37950.1.1.5.12.1.21
-- 1.3.6.1.4.1.37950.1.1.5.12.1.21
-- 1.3.6.1.4.1.37950.1.1.5.12.1.21
-- 1.3.6.1.4.1.37950.1.1.5.12.1.21
-- 1.3.6.1.4.1.37950.1.1.5.12.1.21
-- 1.3.6.1.4.1.37950.1.1.5.12.1.21
-- 1.3.6.1.4.1.37950.1.1.5.12.1.21
-- 1.3.6.1.4.1.37950.1.1.5.12.1.21
-- 1.3.6.1.4.1.37950.1.1.5.12.1.21
		-- 1.3.6.1.4.1.37950.1.1.5.12.1.21
		onuUpstream OBJECT IDENTIFIER ::= { onuAuth 21 }

		
--          1.3.6.1.4.1.37950.1.1.5.12.1.21.1
-- 1.3.6.1.4.1.37950.1.1.5.12.1.21.1
-- 1.3.6.1.4.1.37950.1.1.5.12.1.21.1
-- 1.3.6.1.4.1.37950.1.1.5.12.1.21.1
-- 1.3.6.1.4.1.37950.1.1.5.12.1.21.1
-- 1.3.6.1.4.1.37950.1.1.5.12.1.21.1
-- 1.3.6.1.4.1.37950.1.1.5.12.1.21.1
-- 1.3.6.1.4.1.37950.1.1.5.12.1.21.1
-- 1.3.6.1.4.1.37950.1.1.5.12.1.21.1
		-- 1.3.6.1.4.1.37950.1.1.5.12.1.21.1
		onuUpstreamPon OBJECT-TYPE
			SYNTAX INTEGER (1..16)
			MAX-ACCESS read-write
			STATUS current
			DESCRIPTION
				"Description."
			::= { onuUpstream 1 }

		
--          1.3.6.1.4.1.37950.1.1.5.12.1.21.2
-- 1.3.6.1.4.1.37950.1.1.5.12.1.21.2
-- 1.3.6.1.4.1.37950.1.1.5.12.1.21.2
-- 1.3.6.1.4.1.37950.1.1.5.12.1.21.2
-- 1.3.6.1.4.1.37950.1.1.5.12.1.21.2
-- 1.3.6.1.4.1.37950.1.1.5.12.1.21.2
-- 1.3.6.1.4.1.37950.1.1.5.12.1.21.2
-- 1.3.6.1.4.1.37950.1.1.5.12.1.21.2
-- 1.3.6.1.4.1.37950.1.1.5.12.1.21.2
		-- 1.3.6.1.4.1.37950.1.1.5.12.1.21.2
		onuUpstreamOnu OBJECT-TYPE
			SYNTAX INTEGER (1..65535)
			MAX-ACCESS read-write
			STATUS current
			DESCRIPTION
				"Description."
			::= { onuUpstream 2 }

		
--          1.3.6.1.4.1.37950.1.1.5.12.1.21.3
-- 1.3.6.1.4.1.37950.1.1.5.12.1.21.3
-- 1.3.6.1.4.1.37950.1.1.5.12.1.21.3
-- 1.3.6.1.4.1.37950.1.1.5.12.1.21.3
-- 1.3.6.1.4.1.37950.1.1.5.12.1.21.3
-- 1.3.6.1.4.1.37950.1.1.5.12.1.21.3
-- 1.3.6.1.4.1.37950.1.1.5.12.1.21.3
-- 1.3.6.1.4.1.37950.1.1.5.12.1.21.3
-- 1.3.6.1.4.1.37950.1.1.5.12.1.21.3
		-- 1.3.6.1.4.1.37950.1.1.5.12.1.21.3
		onuUpstreamFir OBJECT-TYPE
			SYNTAX INTEGER (0..950000)
			MAX-ACCESS read-write
			STATUS current
			DESCRIPTION
				"Description."
			::= { onuUpstream 3 }

		
--          1.3.6.1.4.1.37950.1.1.5.12.1.21.4
-- 1.3.6.1.4.1.37950.1.1.5.12.1.21.4
-- 1.3.6.1.4.1.37950.1.1.5.12.1.21.4
-- 1.3.6.1.4.1.37950.1.1.5.12.1.21.4
-- 1.3.6.1.4.1.37950.1.1.5.12.1.21.4
-- 1.3.6.1.4.1.37950.1.1.5.12.1.21.4
-- 1.3.6.1.4.1.37950.1.1.5.12.1.21.4
-- 1.3.6.1.4.1.37950.1.1.5.12.1.21.4
-- 1.3.6.1.4.1.37950.1.1.5.12.1.21.4
		-- 1.3.6.1.4.1.37950.1.1.5.12.1.21.4
		onuUpstreamCir OBJECT-TYPE
			SYNTAX INTEGER (1..950000)
			MAX-ACCESS read-write
			STATUS current
			DESCRIPTION
				"Description."
			::= { onuUpstream 4 }

		
--          1.3.6.1.4.1.37950.1.1.5.12.1.21.5
-- 1.3.6.1.4.1.37950.1.1.5.12.1.21.5
-- 1.3.6.1.4.1.37950.1.1.5.12.1.21.5
-- 1.3.6.1.4.1.37950.1.1.5.12.1.21.5
-- 1.3.6.1.4.1.37950.1.1.5.12.1.21.5
-- 1.3.6.1.4.1.37950.1.1.5.12.1.21.5
-- 1.3.6.1.4.1.37950.1.1.5.12.1.21.5
-- 1.3.6.1.4.1.37950.1.1.5.12.1.21.5
-- 1.3.6.1.4.1.37950.1.1.5.12.1.21.5
		-- 1.3.6.1.4.1.37950.1.1.5.12.1.21.5
		onuUpstreamPir OBJECT-TYPE
			SYNTAX INTEGER (512..1000000)
			MAX-ACCESS read-write
			STATUS current
			DESCRIPTION
				"Description."
			::= { onuUpstream 5 }

		
--          1.3.6.1.4.1.37950.1.1.5.12.1.21.6
-- 1.3.6.1.4.1.37950.1.1.5.12.1.21.6
-- 1.3.6.1.4.1.37950.1.1.5.12.1.21.6
-- 1.3.6.1.4.1.37950.1.1.5.12.1.21.6
-- 1.3.6.1.4.1.37950.1.1.5.12.1.21.6
-- 1.3.6.1.4.1.37950.1.1.5.12.1.21.6
-- 1.3.6.1.4.1.37950.1.1.5.12.1.21.6
-- 1.3.6.1.4.1.37950.1.1.5.12.1.21.6
-- 1.3.6.1.4.1.37950.1.1.5.12.1.21.6
		-- 1.3.6.1.4.1.37950.1.1.5.12.1.21.6
		onuUpstreamWeight OBJECT-TYPE
			SYNTAX INTEGER (1..20)
			MAX-ACCESS read-write
			STATUS current
			DESCRIPTION
				"Description."
			::= { onuUpstream 6 }

		
--          1.3.6.1.4.1.37950.1.1.5.12.1.21.7
-- 1.3.6.1.4.1.37950.1.1.5.12.1.21.7
-- 1.3.6.1.4.1.37950.1.1.5.12.1.21.7
-- 1.3.6.1.4.1.37950.1.1.5.12.1.21.7
-- 1.3.6.1.4.1.37950.1.1.5.12.1.21.7
-- 1.3.6.1.4.1.37950.1.1.5.12.1.21.7
-- 1.3.6.1.4.1.37950.1.1.5.12.1.21.7
-- 1.3.6.1.4.1.37950.1.1.5.12.1.21.7
-- 1.3.6.1.4.1.37950.1.1.5.12.1.21.7
		-- 1.3.6.1.4.1.37950.1.1.5.12.1.21.7
		onuUpstreamAction OBJECT-TYPE
			SYNTAX INTEGER
				{
				commit(1),
				delete(2)
				}
			MAX-ACCESS read-write
			STATUS current
			DESCRIPTION
				"Description."
			::= { onuUpstream 7 }

		
--          1.3.6.1.4.1.37950.1.1.5.12.1.22
-- 1.3.6.1.4.1.37950.1.1.5.12.1.22
-- 1.3.6.1.4.1.37950.1.1.5.12.1.22
-- 1.3.6.1.4.1.37950.1.1.5.12.1.22
-- 1.3.6.1.4.1.37950.1.1.5.12.1.22
-- 1.3.6.1.4.1.37950.1.1.5.12.1.22
-- 1.3.6.1.4.1.37950.1.1.5.12.1.22
-- 1.3.6.1.4.1.37950.1.1.5.12.1.22
-- 1.3.6.1.4.1.37950.1.1.5.12.1.22
		-- 1.3.6.1.4.1.37950.1.1.5.12.1.22
		onuUpstreamTable OBJECT-TYPE
			SYNTAX SEQUENCE OF OnuUpstreamEntry
			MAX-ACCESS not-accessible
			STATUS current
			DESCRIPTION
				"Description."
			::= { onuAuth 22 }

		
--          1.3.6.1.4.1.37950.1.1.5.12.1.22.1
-- 1.3.6.1.4.1.37950.1.1.5.12.1.22.1
-- 1.3.6.1.4.1.37950.1.1.5.12.1.22.1
-- 1.3.6.1.4.1.37950.1.1.5.12.1.22.1
-- 1.3.6.1.4.1.37950.1.1.5.12.1.22.1
-- 1.3.6.1.4.1.37950.1.1.5.12.1.22.1
-- 1.3.6.1.4.1.37950.1.1.5.12.1.22.1
-- 1.3.6.1.4.1.37950.1.1.5.12.1.22.1
-- 1.3.6.1.4.1.37950.1.1.5.12.1.22.1
		-- 1.3.6.1.4.1.37950.1.1.5.12.1.22.1
		onuUpstreamEntry OBJECT-TYPE
			SYNTAX OnuUpstreamEntry
			MAX-ACCESS not-accessible
			STATUS current
			DESCRIPTION
				"Description."
			INDEX { onuUpstreamPonS, onuUpstreamOnuS }
			::= { onuUpstreamTable 1 }

		
		OnuUpstreamEntry ::=
			SEQUENCE { 
				onuUpstreamPonS
					INTEGER,
				onuUpstreamOnuS
					INTEGER,
				onuUpstreamFirS
					INTEGER,
				onuUpstreamCirS
					INTEGER,
				onuUpstreamPirS
					INTEGER,
				onuUpstreamWeightS
					INTEGER
			 }

--          1.3.6.1.4.1.37950.1.1.5.12.1.22.1.1
-- 1.3.6.1.4.1.37950.1.1.5.12.1.22.1.1
-- 1.3.6.1.4.1.37950.1.1.5.12.1.22.1.1
-- 1.3.6.1.4.1.37950.1.1.5.12.1.22.1.1
-- 1.3.6.1.4.1.37950.1.1.5.12.1.22.1.1
-- 1.3.6.1.4.1.37950.1.1.5.12.1.22.1.1
-- 1.3.6.1.4.1.37950.1.1.5.12.1.22.1.1
-- 1.3.6.1.4.1.37950.1.1.5.12.1.22.1.1
-- 1.3.6.1.4.1.37950.1.1.5.12.1.22.1.1
		-- 1.3.6.1.4.1.37950.1.1.5.12.1.22.1.1
		onuUpstreamPonS OBJECT-TYPE
			SYNTAX INTEGER (1..16)
			MAX-ACCESS read-only
			STATUS current
			DESCRIPTION
				"Description."
			::= { onuUpstreamEntry 1 }

		
--          1.3.6.1.4.1.37950.1.1.5.12.1.22.1.2
-- 1.3.6.1.4.1.37950.1.1.5.12.1.22.1.2
-- 1.3.6.1.4.1.37950.1.1.5.12.1.22.1.2
-- 1.3.6.1.4.1.37950.1.1.5.12.1.22.1.2
-- 1.3.6.1.4.1.37950.1.1.5.12.1.22.1.2
-- 1.3.6.1.4.1.37950.1.1.5.12.1.22.1.2
-- 1.3.6.1.4.1.37950.1.1.5.12.1.22.1.2
-- 1.3.6.1.4.1.37950.1.1.5.12.1.22.1.2
-- 1.3.6.1.4.1.37950.1.1.5.12.1.22.1.2
		-- 1.3.6.1.4.1.37950.1.1.5.12.1.22.1.2
		onuUpstreamOnuS OBJECT-TYPE
			SYNTAX INTEGER (1..65535)
			MAX-ACCESS read-only
			STATUS current
			DESCRIPTION
				"Description."
			::= { onuUpstreamEntry 2 }

		
--          1.3.6.1.4.1.37950.1.1.5.12.1.22.1.3
-- 1.3.6.1.4.1.37950.1.1.5.12.1.22.1.3
-- 1.3.6.1.4.1.37950.1.1.5.12.1.22.1.3
-- 1.3.6.1.4.1.37950.1.1.5.12.1.22.1.3
-- 1.3.6.1.4.1.37950.1.1.5.12.1.22.1.3
-- 1.3.6.1.4.1.37950.1.1.5.12.1.22.1.3
-- 1.3.6.1.4.1.37950.1.1.5.12.1.22.1.3
-- 1.3.6.1.4.1.37950.1.1.5.12.1.22.1.3
-- 1.3.6.1.4.1.37950.1.1.5.12.1.22.1.3
		-- 1.3.6.1.4.1.37950.1.1.5.12.1.22.1.3
		onuUpstreamFirS OBJECT-TYPE
			SYNTAX INTEGER (0..950000)
			MAX-ACCESS read-only
			STATUS current
			DESCRIPTION
				"Description."
			::= { onuUpstreamEntry 3 }

		
--          1.3.6.1.4.1.37950.1.1.5.12.1.22.1.4
-- 1.3.6.1.4.1.37950.1.1.5.12.1.22.1.4
-- 1.3.6.1.4.1.37950.1.1.5.12.1.22.1.4
-- 1.3.6.1.4.1.37950.1.1.5.12.1.22.1.4
-- 1.3.6.1.4.1.37950.1.1.5.12.1.22.1.4
-- 1.3.6.1.4.1.37950.1.1.5.12.1.22.1.4
-- 1.3.6.1.4.1.37950.1.1.5.12.1.22.1.4
-- 1.3.6.1.4.1.37950.1.1.5.12.1.22.1.4
-- 1.3.6.1.4.1.37950.1.1.5.12.1.22.1.4
		-- 1.3.6.1.4.1.37950.1.1.5.12.1.22.1.4
		onuUpstreamCirS OBJECT-TYPE
			SYNTAX INTEGER (1..950000)
			MAX-ACCESS read-only
			STATUS current
			DESCRIPTION
				"Description."
			::= { onuUpstreamEntry 4 }

		
--          1.3.6.1.4.1.37950.1.1.5.12.1.22.1.5
-- 1.3.6.1.4.1.37950.1.1.5.12.1.22.1.5
-- 1.3.6.1.4.1.37950.1.1.5.12.1.22.1.5
-- 1.3.6.1.4.1.37950.1.1.5.12.1.22.1.5
-- 1.3.6.1.4.1.37950.1.1.5.12.1.22.1.5
-- 1.3.6.1.4.1.37950.1.1.5.12.1.22.1.5
-- 1.3.6.1.4.1.37950.1.1.5.12.1.22.1.5
-- 1.3.6.1.4.1.37950.1.1.5.12.1.22.1.5
-- 1.3.6.1.4.1.37950.1.1.5.12.1.22.1.5
		-- 1.3.6.1.4.1.37950.1.1.5.12.1.22.1.5
		onuUpstreamPirS OBJECT-TYPE
			SYNTAX INTEGER (512..1000000)
			MAX-ACCESS read-only
			STATUS current
			DESCRIPTION
				"Description."
			::= { onuUpstreamEntry 5 }

		
--          1.3.6.1.4.1.37950.1.1.5.12.1.22.1.6
-- 1.3.6.1.4.1.37950.1.1.5.12.1.22.1.6
-- 1.3.6.1.4.1.37950.1.1.5.12.1.22.1.6
-- 1.3.6.1.4.1.37950.1.1.5.12.1.22.1.6
-- 1.3.6.1.4.1.37950.1.1.5.12.1.22.1.6
-- 1.3.6.1.4.1.37950.1.1.5.12.1.22.1.6
-- 1.3.6.1.4.1.37950.1.1.5.12.1.22.1.6
-- 1.3.6.1.4.1.37950.1.1.5.12.1.22.1.6
-- 1.3.6.1.4.1.37950.1.1.5.12.1.22.1.6
		-- 1.3.6.1.4.1.37950.1.1.5.12.1.22.1.6
		onuUpstreamWeightS OBJECT-TYPE
			SYNTAX INTEGER (1..20)
			MAX-ACCESS read-only
			STATUS current
			DESCRIPTION
				"Description."
			::= { onuUpstreamEntry 6 }

		
--          1.3.6.1.4.1.37950.1.1.5.12.1.23
-- 1.3.6.1.4.1.37950.1.1.5.12.1.23
-- 1.3.6.1.4.1.37950.1.1.5.12.1.23
-- 1.3.6.1.4.1.37950.1.1.5.12.1.23
-- 1.3.6.1.4.1.37950.1.1.5.12.1.23
-- 1.3.6.1.4.1.37950.1.1.5.12.1.23
-- 1.3.6.1.4.1.37950.1.1.5.12.1.23
-- 1.3.6.1.4.1.37950.1.1.5.12.1.23
-- 1.3.6.1.4.1.37950.1.1.5.12.1.23
		-- 1.3.6.1.4.1.37950.1.1.5.12.1.23
		onuDownsteam OBJECT IDENTIFIER ::= { onuAuth 23 }

		
--          1.3.6.1.4.1.37950.1.1.5.12.1.23.1
-- 1.3.6.1.4.1.37950.1.1.5.12.1.23.1
-- 1.3.6.1.4.1.37950.1.1.5.12.1.23.1
-- 1.3.6.1.4.1.37950.1.1.5.12.1.23.1
-- 1.3.6.1.4.1.37950.1.1.5.12.1.23.1
-- 1.3.6.1.4.1.37950.1.1.5.12.1.23.1
-- 1.3.6.1.4.1.37950.1.1.5.12.1.23.1
-- 1.3.6.1.4.1.37950.1.1.5.12.1.23.1
-- 1.3.6.1.4.1.37950.1.1.5.12.1.23.1
		-- 1.3.6.1.4.1.37950.1.1.5.12.1.23.1
		onuDownsteamPon OBJECT-TYPE
			SYNTAX INTEGER (1..16)
			MAX-ACCESS read-write
			STATUS current
			DESCRIPTION
				"Description."
			::= { onuDownsteam 1 }

		
--          1.3.6.1.4.1.37950.1.1.5.12.1.23.2
-- 1.3.6.1.4.1.37950.1.1.5.12.1.23.2
-- 1.3.6.1.4.1.37950.1.1.5.12.1.23.2
-- 1.3.6.1.4.1.37950.1.1.5.12.1.23.2
-- 1.3.6.1.4.1.37950.1.1.5.12.1.23.2
-- 1.3.6.1.4.1.37950.1.1.5.12.1.23.2
-- 1.3.6.1.4.1.37950.1.1.5.12.1.23.2
-- 1.3.6.1.4.1.37950.1.1.5.12.1.23.2
-- 1.3.6.1.4.1.37950.1.1.5.12.1.23.2
		-- 1.3.6.1.4.1.37950.1.1.5.12.1.23.2
		onuDownsteamOnu OBJECT-TYPE
			SYNTAX INTEGER (1..65535)
			MAX-ACCESS read-write
			STATUS current
			DESCRIPTION
				"Description."
			::= { onuDownsteam 2 }

		
--          1.3.6.1.4.1.37950.1.1.5.12.1.23.3
-- 1.3.6.1.4.1.37950.1.1.5.12.1.23.3
-- 1.3.6.1.4.1.37950.1.1.5.12.1.23.3
-- 1.3.6.1.4.1.37950.1.1.5.12.1.23.3
-- 1.3.6.1.4.1.37950.1.1.5.12.1.23.3
-- 1.3.6.1.4.1.37950.1.1.5.12.1.23.3
-- 1.3.6.1.4.1.37950.1.1.5.12.1.23.3
-- 1.3.6.1.4.1.37950.1.1.5.12.1.23.3
-- 1.3.6.1.4.1.37950.1.1.5.12.1.23.3
		-- 1.3.6.1.4.1.37950.1.1.5.12.1.23.3
		onuDownsteamPir OBJECT-TYPE
			SYNTAX INTEGER (0..1000000)
			MAX-ACCESS read-write
			STATUS current
			DESCRIPTION
				"Description."
			::= { onuDownsteam 3 }

		
--          1.3.6.1.4.1.37950.1.1.5.12.1.23.4
-- 1.3.6.1.4.1.37950.1.1.5.12.1.23.4
-- 1.3.6.1.4.1.37950.1.1.5.12.1.23.4
-- 1.3.6.1.4.1.37950.1.1.5.12.1.23.4
-- 1.3.6.1.4.1.37950.1.1.5.12.1.23.4
-- 1.3.6.1.4.1.37950.1.1.5.12.1.23.4
-- 1.3.6.1.4.1.37950.1.1.5.12.1.23.4
-- 1.3.6.1.4.1.37950.1.1.5.12.1.23.4
-- 1.3.6.1.4.1.37950.1.1.5.12.1.23.4
		-- 1.3.6.1.4.1.37950.1.1.5.12.1.23.4
		onuDownsteamWeight OBJECT-TYPE
			SYNTAX INTEGER (1..16)
			MAX-ACCESS read-write
			STATUS current
			DESCRIPTION
				"Description."
			::= { onuDownsteam 4 }

		
--          1.3.6.1.4.1.37950.1.1.5.12.1.23.5
-- 1.3.6.1.4.1.37950.1.1.5.12.1.23.5
-- 1.3.6.1.4.1.37950.1.1.5.12.1.23.5
-- 1.3.6.1.4.1.37950.1.1.5.12.1.23.5
-- 1.3.6.1.4.1.37950.1.1.5.12.1.23.5
-- 1.3.6.1.4.1.37950.1.1.5.12.1.23.5
-- 1.3.6.1.4.1.37950.1.1.5.12.1.23.5
-- 1.3.6.1.4.1.37950.1.1.5.12.1.23.5
-- 1.3.6.1.4.1.37950.1.1.5.12.1.23.5
		-- 1.3.6.1.4.1.37950.1.1.5.12.1.23.5
		onuDownsteamAction OBJECT-TYPE
			SYNTAX INTEGER
				{
				commit(1),
				delete(2)
				}
			MAX-ACCESS read-write
			STATUS current
			DESCRIPTION
				"Description."
			::= { onuDownsteam 5 }

		
--          1.3.6.1.4.1.37950.1.1.5.12.1.24
-- 1.3.6.1.4.1.37950.1.1.5.12.1.24
-- 1.3.6.1.4.1.37950.1.1.5.12.1.24
-- 1.3.6.1.4.1.37950.1.1.5.12.1.24
-- 1.3.6.1.4.1.37950.1.1.5.12.1.24
-- 1.3.6.1.4.1.37950.1.1.5.12.1.24
-- 1.3.6.1.4.1.37950.1.1.5.12.1.24
-- 1.3.6.1.4.1.37950.1.1.5.12.1.24
-- 1.3.6.1.4.1.37950.1.1.5.12.1.24
		-- 1.3.6.1.4.1.37950.1.1.5.12.1.24
		onuDownsteamTable OBJECT-TYPE
			SYNTAX SEQUENCE OF OnuDownsteamEntry
			MAX-ACCESS not-accessible
			STATUS current
			DESCRIPTION
				"Description."
			::= { onuAuth 24 }

		
--          1.3.6.1.4.1.37950.1.1.5.12.1.24.1
-- 1.3.6.1.4.1.37950.1.1.5.12.1.24.1
-- 1.3.6.1.4.1.37950.1.1.5.12.1.24.1
-- 1.3.6.1.4.1.37950.1.1.5.12.1.24.1
-- 1.3.6.1.4.1.37950.1.1.5.12.1.24.1
-- 1.3.6.1.4.1.37950.1.1.5.12.1.24.1
-- 1.3.6.1.4.1.37950.1.1.5.12.1.24.1
-- 1.3.6.1.4.1.37950.1.1.5.12.1.24.1
-- 1.3.6.1.4.1.37950.1.1.5.12.1.24.1
		-- 1.3.6.1.4.1.37950.1.1.5.12.1.24.1
		onuDownsteamEntry OBJECT-TYPE
			SYNTAX OnuDownsteamEntry
			MAX-ACCESS not-accessible
			STATUS current
			DESCRIPTION
				"Description."
			INDEX { onuDownsteamPonS, onuDownsteamOnuS }
			::= { onuDownsteamTable 1 }

		
		OnuDownsteamEntry ::=
			SEQUENCE { 
				onuDownsteamPonS
					INTEGER,
				onuDownsteamOnuS
					INTEGER,
				onuDownsteamPirS
					INTEGER,
				onuDownsteamWeightS
					INTEGER
			 }

--          1.3.6.1.4.1.37950.1.1.5.12.1.24.1.1
-- 1.3.6.1.4.1.37950.1.1.5.12.1.24.1.1
-- 1.3.6.1.4.1.37950.1.1.5.12.1.24.1.1
-- 1.3.6.1.4.1.37950.1.1.5.12.1.24.1.1
-- 1.3.6.1.4.1.37950.1.1.5.12.1.24.1.1
-- 1.3.6.1.4.1.37950.1.1.5.12.1.24.1.1
-- 1.3.6.1.4.1.37950.1.1.5.12.1.24.1.1
-- 1.3.6.1.4.1.37950.1.1.5.12.1.24.1.1
-- 1.3.6.1.4.1.37950.1.1.5.12.1.24.1.1
		-- 1.3.6.1.4.1.37950.1.1.5.12.1.24.1.1
		onuDownsteamPonS OBJECT-TYPE
			SYNTAX INTEGER (1..16)
			MAX-ACCESS read-only
			STATUS current
			DESCRIPTION
				"Description."
			::= { onuDownsteamEntry 1 }

		
--          1.3.6.1.4.1.37950.1.1.5.12.1.24.1.2
-- 1.3.6.1.4.1.37950.1.1.5.12.1.24.1.2
-- 1.3.6.1.4.1.37950.1.1.5.12.1.24.1.2
-- 1.3.6.1.4.1.37950.1.1.5.12.1.24.1.2
-- 1.3.6.1.4.1.37950.1.1.5.12.1.24.1.2
-- 1.3.6.1.4.1.37950.1.1.5.12.1.24.1.2
-- 1.3.6.1.4.1.37950.1.1.5.12.1.24.1.2
-- 1.3.6.1.4.1.37950.1.1.5.12.1.24.1.2
-- 1.3.6.1.4.1.37950.1.1.5.12.1.24.1.2
		-- 1.3.6.1.4.1.37950.1.1.5.12.1.24.1.2
		onuDownsteamOnuS OBJECT-TYPE
			SYNTAX INTEGER (1..65535)
			MAX-ACCESS read-only
			STATUS current
			DESCRIPTION
				"Description."
			::= { onuDownsteamEntry 2 }

		
--          1.3.6.1.4.1.37950.1.1.5.12.1.24.1.3
-- 1.3.6.1.4.1.37950.1.1.5.12.1.24.1.3
-- 1.3.6.1.4.1.37950.1.1.5.12.1.24.1.3
-- 1.3.6.1.4.1.37950.1.1.5.12.1.24.1.3
-- 1.3.6.1.4.1.37950.1.1.5.12.1.24.1.3
-- 1.3.6.1.4.1.37950.1.1.5.12.1.24.1.3
-- 1.3.6.1.4.1.37950.1.1.5.12.1.24.1.3
-- 1.3.6.1.4.1.37950.1.1.5.12.1.24.1.3
-- 1.3.6.1.4.1.37950.1.1.5.12.1.24.1.3
		-- 1.3.6.1.4.1.37950.1.1.5.12.1.24.1.3
		onuDownsteamPirS OBJECT-TYPE
			SYNTAX INTEGER (0..1000000)
			MAX-ACCESS read-only
			STATUS current
			DESCRIPTION
				"Description."
			::= { onuDownsteamEntry 3 }

		
--          1.3.6.1.4.1.37950.1.1.5.12.1.24.1.4
-- 1.3.6.1.4.1.37950.1.1.5.12.1.24.1.4
-- 1.3.6.1.4.1.37950.1.1.5.12.1.24.1.4
-- 1.3.6.1.4.1.37950.1.1.5.12.1.24.1.4
-- 1.3.6.1.4.1.37950.1.1.5.12.1.24.1.4
-- 1.3.6.1.4.1.37950.1.1.5.12.1.24.1.4
-- 1.3.6.1.4.1.37950.1.1.5.12.1.24.1.4
-- 1.3.6.1.4.1.37950.1.1.5.12.1.24.1.4
-- 1.3.6.1.4.1.37950.1.1.5.12.1.24.1.4
		-- 1.3.6.1.4.1.37950.1.1.5.12.1.24.1.4
		onuDownsteamWeightS OBJECT-TYPE
			SYNTAX INTEGER (1..16)
			MAX-ACCESS read-only
			STATUS current
			DESCRIPTION
				"Description."
			::= { onuDownsteamEntry 4 }

		
--          1.3.6.1.4.1.37950.1.1.5.12.1.25
-- 1.3.6.1.4.1.37950.1.1.5.12.1.25
-- 1.3.6.1.4.1.37950.1.1.5.12.1.25
-- 1.3.6.1.4.1.37950.1.1.5.12.1.25
-- 1.3.6.1.4.1.37950.1.1.5.12.1.25
-- 1.3.6.1.4.1.37950.1.1.5.12.1.25
-- 1.3.6.1.4.1.37950.1.1.5.12.1.25
-- 1.3.6.1.4.1.37950.1.1.5.12.1.25
-- 1.3.6.1.4.1.37950.1.1.5.12.1.25
		-- 1.3.6.1.4.1.37950.1.1.5.12.1.25
		onuAuthInfo2Table OBJECT-TYPE
			SYNTAX SEQUENCE OF OnuAuthInfo2Entry
			MAX-ACCESS not-accessible
			STATUS current
			DESCRIPTION
				"Description."
			::= { onuAuth 25 }

		
--          1.3.6.1.4.1.37950.1.1.5.12.1.25.1
-- 1.3.6.1.4.1.37950.1.1.5.12.1.25.1
-- 1.3.6.1.4.1.37950.1.1.5.12.1.25.1
-- 1.3.6.1.4.1.37950.1.1.5.12.1.25.1
-- 1.3.6.1.4.1.37950.1.1.5.12.1.25.1
-- 1.3.6.1.4.1.37950.1.1.5.12.1.25.1
-- 1.3.6.1.4.1.37950.1.1.5.12.1.25.1
-- 1.3.6.1.4.1.37950.1.1.5.12.1.25.1
-- 1.3.6.1.4.1.37950.1.1.5.12.1.25.1
		-- 1.3.6.1.4.1.37950.1.1.5.12.1.25.1
		onuAuthInfo2Entry OBJECT-TYPE
			SYNTAX OnuAuthInfo2Entry
			MAX-ACCESS not-accessible
			STATUS current
			DESCRIPTION
				"Description."
			INDEX { authInfoPonNo2, authInfoOnuNo2 }
			::= { onuAuthInfo2Table 1 }

		
		OnuAuthInfo2Entry ::=
			SEQUENCE { 
				authInfoPonNo2
					Integer32,
				authInfoOnuNo2
					Integer32,
				authInfoLlid2
					Integer32,
				lineStatus2
					INTEGER,
				onuMacAddr2
					OCTET STRING,
				onutype2
					OCTET STRING,
				exchange2
					INTEGER,
				authMode2
					INTEGER,
				onuAuthInfoDescription2
					OCTET STRING,
				onuAuthInfoLoid2
					OCTET STRING,
				onuAuthInfoLoidPwd2
					OCTET STRING,
				onuAuthInfoRtt2
					INTEGER,
				onutype22
					OCTET STRING,
				onuAuthInfoStatus2
					INTEGER,
				onuAuthInfo2DeregReason
					INTEGER,
				onuAuthInfo2PriSupport
					Unsigned32,
				onuAuthInfoDistance2
					Unsigned32,
				onuAuthInfoLastRegTime
					OCTET STRING,
				onuAuthInfoLastDeregTime
					OCTET STRING,
				onuAuthInfoAliveTime
					OCTET STRING,
				onuAuthInfoPriSupportNew
					Unsigned32
			 }

--          1.3.6.1.4.1.37950.1.1.5.12.1.25.1.1
-- 1.3.6.1.4.1.37950.1.1.5.12.1.25.1.1
-- 1.3.6.1.4.1.37950.1.1.5.12.1.25.1.1
-- 1.3.6.1.4.1.37950.1.1.5.12.1.25.1.1
-- 1.3.6.1.4.1.37950.1.1.5.12.1.25.1.1
-- 1.3.6.1.4.1.37950.1.1.5.12.1.25.1.1
-- 1.3.6.1.4.1.37950.1.1.5.12.1.25.1.1
-- 1.3.6.1.4.1.37950.1.1.5.12.1.25.1.1
-- 1.3.6.1.4.1.37950.1.1.5.12.1.25.1.1
		-- 1.3.6.1.4.1.37950.1.1.5.12.1.25.1.1
		authInfoPonNo2 OBJECT-TYPE
			SYNTAX Integer32
			MAX-ACCESS read-only
			STATUS current
			DESCRIPTION
				"Description."
			::= { onuAuthInfo2Entry 1 }

		
--          1.3.6.1.4.1.37950.1.1.5.12.1.25.1.2
-- 1.3.6.1.4.1.37950.1.1.5.12.1.25.1.2
-- 1.3.6.1.4.1.37950.1.1.5.12.1.25.1.2
-- 1.3.6.1.4.1.37950.1.1.5.12.1.25.1.2
-- 1.3.6.1.4.1.37950.1.1.5.12.1.25.1.2
-- 1.3.6.1.4.1.37950.1.1.5.12.1.25.1.2
-- 1.3.6.1.4.1.37950.1.1.5.12.1.25.1.2
-- 1.3.6.1.4.1.37950.1.1.5.12.1.25.1.2
-- 1.3.6.1.4.1.37950.1.1.5.12.1.25.1.2
		-- 1.3.6.1.4.1.37950.1.1.5.12.1.25.1.2
		authInfoOnuNo2 OBJECT-TYPE
			SYNTAX Integer32
			MAX-ACCESS read-only
			STATUS current
			DESCRIPTION
				"Description."
			::= { onuAuthInfo2Entry 2 }

		
--          1.3.6.1.4.1.37950.1.1.5.12.1.25.1.3
-- 1.3.6.1.4.1.37950.1.1.5.12.1.25.1.3
-- 1.3.6.1.4.1.37950.1.1.5.12.1.25.1.3
-- 1.3.6.1.4.1.37950.1.1.5.12.1.25.1.3
-- 1.3.6.1.4.1.37950.1.1.5.12.1.25.1.3
-- 1.3.6.1.4.1.37950.1.1.5.12.1.25.1.3
-- 1.3.6.1.4.1.37950.1.1.5.12.1.25.1.3
-- 1.3.6.1.4.1.37950.1.1.5.12.1.25.1.3
-- 1.3.6.1.4.1.37950.1.1.5.12.1.25.1.3
		-- 1.3.6.1.4.1.37950.1.1.5.12.1.25.1.3
		authInfoLlid2 OBJECT-TYPE
			SYNTAX Integer32
			MAX-ACCESS read-only
			STATUS current
			DESCRIPTION
				"Description."
			::= { onuAuthInfo2Entry 3 }

		
--          1.3.6.1.4.1.37950.1.1.5.12.1.25.1.4
-- 1.3.6.1.4.1.37950.1.1.5.12.1.25.1.4
-- 1.3.6.1.4.1.37950.1.1.5.12.1.25.1.4
-- 1.3.6.1.4.1.37950.1.1.5.12.1.25.1.4
-- 1.3.6.1.4.1.37950.1.1.5.12.1.25.1.4
-- 1.3.6.1.4.1.37950.1.1.5.12.1.25.1.4
-- 1.3.6.1.4.1.37950.1.1.5.12.1.25.1.4
-- 1.3.6.1.4.1.37950.1.1.5.12.1.25.1.4
-- 1.3.6.1.4.1.37950.1.1.5.12.1.25.1.4
		-- 1.3.6.1.4.1.37950.1.1.5.12.1.25.1.4
		lineStatus2 OBJECT-TYPE
			SYNTAX INTEGER
				{
				offline(0),
				online(1)
				}
			MAX-ACCESS read-only
			STATUS current
			DESCRIPTION
				"Description."
			::= { onuAuthInfo2Entry 4 }

		
--          1.3.6.1.4.1.37950.1.1.5.12.1.25.1.5
-- 1.3.6.1.4.1.37950.1.1.5.12.1.25.1.5
-- 1.3.6.1.4.1.37950.1.1.5.12.1.25.1.5
-- 1.3.6.1.4.1.37950.1.1.5.12.1.25.1.5
-- 1.3.6.1.4.1.37950.1.1.5.12.1.25.1.5
-- 1.3.6.1.4.1.37950.1.1.5.12.1.25.1.5
-- 1.3.6.1.4.1.37950.1.1.5.12.1.25.1.5
-- 1.3.6.1.4.1.37950.1.1.5.12.1.25.1.5
-- 1.3.6.1.4.1.37950.1.1.5.12.1.25.1.5
		-- 1.3.6.1.4.1.37950.1.1.5.12.1.25.1.5
		onuMacAddr2 OBJECT-TYPE
			SYNTAX OCTET STRING
			MAX-ACCESS read-only
			STATUS current
			DESCRIPTION
				"Description."
			::= { onuAuthInfo2Entry 5 }

		
--          1.3.6.1.4.1.37950.1.1.5.12.1.25.1.6
-- 1.3.6.1.4.1.37950.1.1.5.12.1.25.1.6
-- 1.3.6.1.4.1.37950.1.1.5.12.1.25.1.6
-- 1.3.6.1.4.1.37950.1.1.5.12.1.25.1.6
-- 1.3.6.1.4.1.37950.1.1.5.12.1.25.1.6
-- 1.3.6.1.4.1.37950.1.1.5.12.1.25.1.6
-- 1.3.6.1.4.1.37950.1.1.5.12.1.25.1.6
-- 1.3.6.1.4.1.37950.1.1.5.12.1.25.1.6
-- 1.3.6.1.4.1.37950.1.1.5.12.1.25.1.6
		-- 1.3.6.1.4.1.37950.1.1.5.12.1.25.1.6
		onutype2 OBJECT-TYPE
			SYNTAX OCTET STRING
			MAX-ACCESS read-only
			STATUS current
			DESCRIPTION
				"Description."
			::= { onuAuthInfo2Entry 6 }

		
--          1.3.6.1.4.1.37950.1.1.5.12.1.25.1.7
-- 1.3.6.1.4.1.37950.1.1.5.12.1.25.1.7
-- 1.3.6.1.4.1.37950.1.1.5.12.1.25.1.7
-- 1.3.6.1.4.1.37950.1.1.5.12.1.25.1.7
-- 1.3.6.1.4.1.37950.1.1.5.12.1.25.1.7
-- 1.3.6.1.4.1.37950.1.1.5.12.1.25.1.7
-- 1.3.6.1.4.1.37950.1.1.5.12.1.25.1.7
-- 1.3.6.1.4.1.37950.1.1.5.12.1.25.1.7
-- 1.3.6.1.4.1.37950.1.1.5.12.1.25.1.7
		-- 1.3.6.1.4.1.37950.1.1.5.12.1.25.1.7
		exchange2 OBJECT-TYPE
			SYNTAX INTEGER
				{
				idle(1),
				busy(2)
				}
			MAX-ACCESS read-only
			STATUS current
			DESCRIPTION
				"Description."
			::= { onuAuthInfo2Entry 7 }

		
--          1.3.6.1.4.1.37950.1.1.5.12.1.25.1.8
-- 1.3.6.1.4.1.37950.1.1.5.12.1.25.1.8
-- 1.3.6.1.4.1.37950.1.1.5.12.1.25.1.8
-- 1.3.6.1.4.1.37950.1.1.5.12.1.25.1.8
-- 1.3.6.1.4.1.37950.1.1.5.12.1.25.1.8
-- 1.3.6.1.4.1.37950.1.1.5.12.1.25.1.8
-- 1.3.6.1.4.1.37950.1.1.5.12.1.25.1.8
-- 1.3.6.1.4.1.37950.1.1.5.12.1.25.1.8
-- 1.3.6.1.4.1.37950.1.1.5.12.1.25.1.8
		-- 1.3.6.1.4.1.37950.1.1.5.12.1.25.1.8
		authMode2 OBJECT-TYPE
			SYNTAX INTEGER
				{
				none(0),
				macAuth(1),
				loidAuth(2)
				}
			MAX-ACCESS read-only
			STATUS current
			DESCRIPTION
				"Description."
			::= { onuAuthInfo2Entry 8 }

		
--          1.3.6.1.4.1.37950.1.1.5.12.1.25.1.9
-- 1.3.6.1.4.1.37950.1.1.5.12.1.25.1.9
-- 1.3.6.1.4.1.37950.1.1.5.12.1.25.1.9
-- 1.3.6.1.4.1.37950.1.1.5.12.1.25.1.9
-- 1.3.6.1.4.1.37950.1.1.5.12.1.25.1.9
-- 1.3.6.1.4.1.37950.1.1.5.12.1.25.1.9
-- 1.3.6.1.4.1.37950.1.1.5.12.1.25.1.9
-- 1.3.6.1.4.1.37950.1.1.5.12.1.25.1.9
-- 1.3.6.1.4.1.37950.1.1.5.12.1.25.1.9
		-- 1.3.6.1.4.1.37950.1.1.5.12.1.25.1.9
		onuAuthInfoDescription2 OBJECT-TYPE
			SYNTAX OCTET STRING
			MAX-ACCESS read-only
			STATUS current
			DESCRIPTION
				"Description."
			::= { onuAuthInfo2Entry 9 }

		
--          1.3.6.1.4.1.37950.1.1.5.12.1.25.1.10
-- 1.3.6.1.4.1.37950.1.1.5.12.1.25.1.10
-- 1.3.6.1.4.1.37950.1.1.5.12.1.25.1.10
-- 1.3.6.1.4.1.37950.1.1.5.12.1.25.1.10
-- 1.3.6.1.4.1.37950.1.1.5.12.1.25.1.10
-- 1.3.6.1.4.1.37950.1.1.5.12.1.25.1.10
-- 1.3.6.1.4.1.37950.1.1.5.12.1.25.1.10
-- 1.3.6.1.4.1.37950.1.1.5.12.1.25.1.10
-- 1.3.6.1.4.1.37950.1.1.5.12.1.25.1.10
		-- 1.3.6.1.4.1.37950.1.1.5.12.1.25.1.10
		onuAuthInfoLoid2 OBJECT-TYPE
			SYNTAX OCTET STRING
			MAX-ACCESS read-only
			STATUS current
			DESCRIPTION
				"Description."
			::= { onuAuthInfo2Entry 10 }

		
--          1.3.6.1.4.1.37950.1.1.5.12.1.25.1.11
-- 1.3.6.1.4.1.37950.1.1.5.12.1.25.1.11
-- 1.3.6.1.4.1.37950.1.1.5.12.1.25.1.11
-- 1.3.6.1.4.1.37950.1.1.5.12.1.25.1.11
-- 1.3.6.1.4.1.37950.1.1.5.12.1.25.1.11
-- 1.3.6.1.4.1.37950.1.1.5.12.1.25.1.11
-- 1.3.6.1.4.1.37950.1.1.5.12.1.25.1.11
-- 1.3.6.1.4.1.37950.1.1.5.12.1.25.1.11
-- 1.3.6.1.4.1.37950.1.1.5.12.1.25.1.11
		-- 1.3.6.1.4.1.37950.1.1.5.12.1.25.1.11
		onuAuthInfoLoidPwd2 OBJECT-TYPE
			SYNTAX OCTET STRING
			MAX-ACCESS read-only
			STATUS current
			DESCRIPTION
				"Description."
			::= { onuAuthInfo2Entry 11 }

		
--          1.3.6.1.4.1.37950.1.1.5.12.1.25.1.12
-- 1.3.6.1.4.1.37950.1.1.5.12.1.25.1.12
-- 1.3.6.1.4.1.37950.1.1.5.12.1.25.1.12
-- 1.3.6.1.4.1.37950.1.1.5.12.1.25.1.12
-- 1.3.6.1.4.1.37950.1.1.5.12.1.25.1.12
-- 1.3.6.1.4.1.37950.1.1.5.12.1.25.1.12
-- 1.3.6.1.4.1.37950.1.1.5.12.1.25.1.12
-- 1.3.6.1.4.1.37950.1.1.5.12.1.25.1.12
-- 1.3.6.1.4.1.37950.1.1.5.12.1.25.1.12
		-- 1.3.6.1.4.1.37950.1.1.5.12.1.25.1.12
		onuAuthInfoRtt2 OBJECT-TYPE
			SYNTAX INTEGER
			MAX-ACCESS read-write
			STATUS current
			DESCRIPTION
				"Description."
			::= { onuAuthInfo2Entry 12 }

		
--          1.3.6.1.4.1.37950.1.1.5.12.1.25.1.13
-- 1.3.6.1.4.1.37950.1.1.5.12.1.25.1.13
-- 1.3.6.1.4.1.37950.1.1.5.12.1.25.1.13
-- 1.3.6.1.4.1.37950.1.1.5.12.1.25.1.13
-- 1.3.6.1.4.1.37950.1.1.5.12.1.25.1.13
-- 1.3.6.1.4.1.37950.1.1.5.12.1.25.1.13
-- 1.3.6.1.4.1.37950.1.1.5.12.1.25.1.13
-- 1.3.6.1.4.1.37950.1.1.5.12.1.25.1.13
-- 1.3.6.1.4.1.37950.1.1.5.12.1.25.1.13
		-- 1.3.6.1.4.1.37950.1.1.5.12.1.25.1.13
		onutype22 OBJECT-TYPE
			SYNTAX OCTET STRING
			MAX-ACCESS read-write
			STATUS current
			DESCRIPTION
				"Description."
			::= { onuAuthInfo2Entry 13 }

		
--          1.3.6.1.4.1.37950.1.1.5.12.1.25.1.14
-- 1.3.6.1.4.1.37950.1.1.5.12.1.25.1.14
-- 1.3.6.1.4.1.37950.1.1.5.12.1.25.1.14
-- 1.3.6.1.4.1.37950.1.1.5.12.1.25.1.14
-- 1.3.6.1.4.1.37950.1.1.5.12.1.25.1.14
-- 1.3.6.1.4.1.37950.1.1.5.12.1.25.1.14
-- 1.3.6.1.4.1.37950.1.1.5.12.1.25.1.14
-- 1.3.6.1.4.1.37950.1.1.5.12.1.25.1.14
-- 1.3.6.1.4.1.37950.1.1.5.12.1.25.1.14
		-- 1.3.6.1.4.1.37950.1.1.5.12.1.25.1.14
		onuAuthInfoStatus2 OBJECT-TYPE
			SYNTAX INTEGER
				{
				unfinish(0),
				finish(1)
				}
			MAX-ACCESS read-write
			STATUS current
			DESCRIPTION
				"Description."
			::= { onuAuthInfo2Entry 14 }

		
--          1.3.6.1.4.1.37950.1.1.5.12.1.25.1.15
-- 1.3.6.1.4.1.37950.1.1.5.12.1.25.1.15
-- 1.3.6.1.4.1.37950.1.1.5.12.1.25.1.15
-- 1.3.6.1.4.1.37950.1.1.5.12.1.25.1.15
-- 1.3.6.1.4.1.37950.1.1.5.12.1.25.1.15
-- 1.3.6.1.4.1.37950.1.1.5.12.1.25.1.15
-- 1.3.6.1.4.1.37950.1.1.5.12.1.25.1.15
-- 1.3.6.1.4.1.37950.1.1.5.12.1.25.1.15
-- 1.3.6.1.4.1.37950.1.1.5.12.1.25.1.15
		-- 1.3.6.1.4.1.37950.1.1.5.12.1.25.1.15
		onuAuthInfo2DeregReason OBJECT-TYPE
			SYNTAX INTEGER
				{
				wire-down(0),
				power-off(1)
				}
			MAX-ACCESS read-write
			STATUS current
			DESCRIPTION
				"Description."
			::= { onuAuthInfo2Entry 15 }

		
--          1.3.6.1.4.1.37950.1.1.5.12.1.25.1.16
-- 1.3.6.1.4.1.37950.1.1.5.12.1.25.1.16
-- 1.3.6.1.4.1.37950.1.1.5.12.1.25.1.16
-- 1.3.6.1.4.1.37950.1.1.5.12.1.25.1.16
-- 1.3.6.1.4.1.37950.1.1.5.12.1.25.1.16
-- 1.3.6.1.4.1.37950.1.1.5.12.1.25.1.16
-- 1.3.6.1.4.1.37950.1.1.5.12.1.25.1.16
-- 1.3.6.1.4.1.37950.1.1.5.12.1.25.1.16
-- 1.3.6.1.4.1.37950.1.1.5.12.1.25.1.16
		-- 1.3.6.1.4.1.37950.1.1.5.12.1.25.1.16
		onuAuthInfo2PriSupport OBJECT-TYPE
			SYNTAX Unsigned32
			MAX-ACCESS read-write
			STATUS current
			DESCRIPTION
				"Description."
			::= { onuAuthInfo2Entry 16 }

		
--         1.3.6.1.4.1.37950.1.1.5.12.1.25.1.17
-- 1.3.6.1.4.1.37950.1.1.5.12.1.25.1.17
-- 1.3.6.1.4.1.37950.1.1.5.12.1.25.1.17
-- 1.3.6.1.4.1.37950.1.1.5.12.1.25.1.17
-- 1.3.6.1.4.1.37950.1.1.5.12.1.25.1.17
-- 1.3.6.1.4.1.37950.1.1.5.12.1.25.1.17
-- 1.3.6.1.4.1.37950.1.1.5.12.1.25.1.17
-- 1.3.6.1.4.1.37950.1.1.5.12.1.25.1.17
		-- 1.3.6.1.4.1.37950.1.1.5.12.1.25.1.17
		onuAuthInfoDistance2 OBJECT-TYPE
			SYNTAX Unsigned32
			MAX-ACCESS read-write
			STATUS current
			DESCRIPTION
				"Description."
			::= { onuAuthInfo2Entry 17 }

		
--         1.3.6.1.4.1.37950.1.1.5.12.1.25.1.18
-- 1.3.6.1.4.1.37950.1.1.5.12.1.25.1.18
-- 1.3.6.1.4.1.37950.1.1.5.12.1.25.1.18
-- 1.3.6.1.4.1.37950.1.1.5.12.1.25.1.18
-- 1.3.6.1.4.1.37950.1.1.5.12.1.25.1.18
-- 1.3.6.1.4.1.37950.1.1.5.12.1.25.1.18
-- 1.3.6.1.4.1.37950.1.1.5.12.1.25.1.18
-- 1.3.6.1.4.1.37950.1.1.5.12.1.25.1.18
		-- 1.3.6.1.4.1.37950.1.1.5.12.1.25.1.18
		onuAuthInfoLastRegTime OBJECT-TYPE
			SYNTAX OCTET STRING
			MAX-ACCESS read-write
			STATUS current
			DESCRIPTION
				"Description."
			::= { onuAuthInfo2Entry 18 }

		
--         1.3.6.1.4.1.37950.1.1.5.12.1.25.1.19
-- 1.3.6.1.4.1.37950.1.1.5.12.1.25.1.19
-- 1.3.6.1.4.1.37950.1.1.5.12.1.25.1.19
-- 1.3.6.1.4.1.37950.1.1.5.12.1.25.1.19
-- 1.3.6.1.4.1.37950.1.1.5.12.1.25.1.19
-- 1.3.6.1.4.1.37950.1.1.5.12.1.25.1.19
-- 1.3.6.1.4.1.37950.1.1.5.12.1.25.1.19
-- 1.3.6.1.4.1.37950.1.1.5.12.1.25.1.19
		-- 1.3.6.1.4.1.37950.1.1.5.12.1.25.1.19
		onuAuthInfoLastDeregTime OBJECT-TYPE
			SYNTAX OCTET STRING
			MAX-ACCESS read-write
			STATUS current
			DESCRIPTION
				"Description."
			::= { onuAuthInfo2Entry 19 }

		
--         1.3.6.1.4.1.37950.1.1.5.12.1.25.1.20
-- 1.3.6.1.4.1.37950.1.1.5.12.1.25.1.20
-- 1.3.6.1.4.1.37950.1.1.5.12.1.25.1.20
-- 1.3.6.1.4.1.37950.1.1.5.12.1.25.1.20
-- 1.3.6.1.4.1.37950.1.1.5.12.1.25.1.20
-- 1.3.6.1.4.1.37950.1.1.5.12.1.25.1.20
-- 1.3.6.1.4.1.37950.1.1.5.12.1.25.1.20
-- 1.3.6.1.4.1.37950.1.1.5.12.1.25.1.20
		-- 1.3.6.1.4.1.37950.1.1.5.12.1.25.1.20
		onuAuthInfoAliveTime OBJECT-TYPE
			SYNTAX OCTET STRING
			MAX-ACCESS read-write
			STATUS current
			DESCRIPTION
				"Description."
			::= { onuAuthInfo2Entry 20 }

		
--         1.3.6.1.4.1.37950.1.1.5.12.1.25.1.21
-- 1.3.6.1.4.1.37950.1.1.5.12.1.25.1.21
-- 1.3.6.1.4.1.37950.1.1.5.12.1.25.1.21
-- 1.3.6.1.4.1.37950.1.1.5.12.1.25.1.21
-- 1.3.6.1.4.1.37950.1.1.5.12.1.25.1.21
-- 1.3.6.1.4.1.37950.1.1.5.12.1.25.1.21
-- 1.3.6.1.4.1.37950.1.1.5.12.1.25.1.21
-- 1.3.6.1.4.1.37950.1.1.5.12.1.25.1.21
		-- 1.3.6.1.4.1.37950.1.1.5.12.1.25.1.21
		onuAuthInfoPriSupportNew OBJECT-TYPE
			SYNTAX Unsigned32
			MAX-ACCESS read-write
			STATUS current
			DESCRIPTION
				"Description."
			::= { onuAuthInfo2Entry 21 }

		
--         1.3.6.1.4.1.37950.1.1.5.12.1.26
-- 1.3.6.1.4.1.37950.1.1.5.12.1.26
-- 1.3.6.1.4.1.37950.1.1.5.12.1.26
-- 1.3.6.1.4.1.37950.1.1.5.12.1.26
-- 1.3.6.1.4.1.37950.1.1.5.12.1.26
-- 1.3.6.1.4.1.37950.1.1.5.12.1.26
-- 1.3.6.1.4.1.37950.1.1.5.12.1.26
-- 1.3.6.1.4.1.37950.1.1.5.12.1.26
		-- 1.3.6.1.4.1.37950.1.1.5.12.1.26
		onuMacTable OBJECT-TYPE
			SYNTAX SEQUENCE OF OnuMacEntry
			MAX-ACCESS not-accessible
			STATUS current
			DESCRIPTION
				"Description."
			::= { onuAuth 26 }

		
--         1.3.6.1.4.1.37950.1.1.5.12.1.26.1
-- 1.3.6.1.4.1.37950.1.1.5.12.1.26.1
-- 1.3.6.1.4.1.37950.1.1.5.12.1.26.1
-- 1.3.6.1.4.1.37950.1.1.5.12.1.26.1
-- 1.3.6.1.4.1.37950.1.1.5.12.1.26.1
-- 1.3.6.1.4.1.37950.1.1.5.12.1.26.1
-- 1.3.6.1.4.1.37950.1.1.5.12.1.26.1
-- 1.3.6.1.4.1.37950.1.1.5.12.1.26.1
		-- 1.3.6.1.4.1.37950.1.1.5.12.1.26.1
		onuMacEntry OBJECT-TYPE
			SYNTAX OnuMacEntry
			MAX-ACCESS not-accessible
			STATUS current
			DESCRIPTION
				"Description."
			INDEX { onuMacPon, onuMacOnuId, onuMacNum }
			::= { onuMacTable 1 }

		
		OnuMacEntry ::=
			SEQUENCE { 
				onuMacPon
					Integer32,
				onuMacOnuId
					Integer32,
				onuMacNum
					Integer32,
				onuMacVlan
					Integer32,
				onuMacAddress
					OCTET STRING,
				onuMacAge
					Integer32
			 }

--         1.3.6.1.4.1.37950.1.1.5.12.1.26.1.1
-- 1.3.6.1.4.1.37950.1.1.5.12.1.26.1.1
-- 1.3.6.1.4.1.37950.1.1.5.12.1.26.1.1
-- 1.3.6.1.4.1.37950.1.1.5.12.1.26.1.1
-- 1.3.6.1.4.1.37950.1.1.5.12.1.26.1.1
-- 1.3.6.1.4.1.37950.1.1.5.12.1.26.1.1
-- 1.3.6.1.4.1.37950.1.1.5.12.1.26.1.1
-- 1.3.6.1.4.1.37950.1.1.5.12.1.26.1.1
		-- 1.3.6.1.4.1.37950.1.1.5.12.1.26.1.1
		onuMacPon OBJECT-TYPE
			SYNTAX Integer32
			MAX-ACCESS read-write
			STATUS current
			DESCRIPTION
				"Description."
			::= { onuMacEntry 1 }

		
--         1.3.6.1.4.1.37950.1.1.5.12.1.26.1.2
-- 1.3.6.1.4.1.37950.1.1.5.12.1.26.1.2
-- 1.3.6.1.4.1.37950.1.1.5.12.1.26.1.2
-- 1.3.6.1.4.1.37950.1.1.5.12.1.26.1.2
-- 1.3.6.1.4.1.37950.1.1.5.12.1.26.1.2
-- 1.3.6.1.4.1.37950.1.1.5.12.1.26.1.2
-- 1.3.6.1.4.1.37950.1.1.5.12.1.26.1.2
-- 1.3.6.1.4.1.37950.1.1.5.12.1.26.1.2
		-- 1.3.6.1.4.1.37950.1.1.5.12.1.26.1.2
		onuMacOnuId OBJECT-TYPE
			SYNTAX Integer32
			MAX-ACCESS read-write
			STATUS current
			DESCRIPTION
				"Description."
			::= { onuMacEntry 2 }

		
--         1.3.6.1.4.1.37950.1.1.5.12.1.26.1.3
-- 1.3.6.1.4.1.37950.1.1.5.12.1.26.1.3
-- 1.3.6.1.4.1.37950.1.1.5.12.1.26.1.3
-- 1.3.6.1.4.1.37950.1.1.5.12.1.26.1.3
-- 1.3.6.1.4.1.37950.1.1.5.12.1.26.1.3
-- 1.3.6.1.4.1.37950.1.1.5.12.1.26.1.3
-- 1.3.6.1.4.1.37950.1.1.5.12.1.26.1.3
-- 1.3.6.1.4.1.37950.1.1.5.12.1.26.1.3
		-- 1.3.6.1.4.1.37950.1.1.5.12.1.26.1.3
		onuMacNum OBJECT-TYPE
			SYNTAX Integer32
			MAX-ACCESS read-write
			STATUS current
			DESCRIPTION
				"Description."
			::= { onuMacEntry 3 }

		
--         1.3.6.1.4.1.37950.1.1.5.12.1.26.1.4
-- 1.3.6.1.4.1.37950.1.1.5.12.1.26.1.4
-- 1.3.6.1.4.1.37950.1.1.5.12.1.26.1.4
-- 1.3.6.1.4.1.37950.1.1.5.12.1.26.1.4
-- 1.3.6.1.4.1.37950.1.1.5.12.1.26.1.4
-- 1.3.6.1.4.1.37950.1.1.5.12.1.26.1.4
-- 1.3.6.1.4.1.37950.1.1.5.12.1.26.1.4
-- 1.3.6.1.4.1.37950.1.1.5.12.1.26.1.4
		-- 1.3.6.1.4.1.37950.1.1.5.12.1.26.1.4
		onuMacVlan OBJECT-TYPE
			SYNTAX Integer32
			MAX-ACCESS read-write
			STATUS current
			DESCRIPTION
				"Description."
			::= { onuMacEntry 4 }

		
--         1.3.6.1.4.1.37950.1.1.5.12.1.26.1.5
-- 1.3.6.1.4.1.37950.1.1.5.12.1.26.1.5
-- 1.3.6.1.4.1.37950.1.1.5.12.1.26.1.5
-- 1.3.6.1.4.1.37950.1.1.5.12.1.26.1.5
-- 1.3.6.1.4.1.37950.1.1.5.12.1.26.1.5
-- 1.3.6.1.4.1.37950.1.1.5.12.1.26.1.5
-- 1.3.6.1.4.1.37950.1.1.5.12.1.26.1.5
-- 1.3.6.1.4.1.37950.1.1.5.12.1.26.1.5
		-- 1.3.6.1.4.1.37950.1.1.5.12.1.26.1.5
		onuMacAddress OBJECT-TYPE
			SYNTAX OCTET STRING
			MAX-ACCESS read-write
			STATUS current
			DESCRIPTION
				"Description."
			::= { onuMacEntry 5 }

		
--         1.3.6.1.4.1.37950.1.1.5.12.1.26.1.6
-- 1.3.6.1.4.1.37950.1.1.5.12.1.26.1.6
-- 1.3.6.1.4.1.37950.1.1.5.12.1.26.1.6
-- 1.3.6.1.4.1.37950.1.1.5.12.1.26.1.6
-- 1.3.6.1.4.1.37950.1.1.5.12.1.26.1.6
-- 1.3.6.1.4.1.37950.1.1.5.12.1.26.1.6
-- 1.3.6.1.4.1.37950.1.1.5.12.1.26.1.6
-- 1.3.6.1.4.1.37950.1.1.5.12.1.26.1.6
		-- 1.3.6.1.4.1.37950.1.1.5.12.1.26.1.6
		onuMacAge OBJECT-TYPE
			SYNTAX Integer32
			MAX-ACCESS read-write
			STATUS current
			DESCRIPTION
				"Description."
			::= { onuMacEntry 6 }

		
--         1.3.6.1.4.1.37950.1.1.5.12.1.27
-- 1.3.6.1.4.1.37950.1.1.5.12.1.27
-- 1.3.6.1.4.1.37950.1.1.5.12.1.27
-- 1.3.6.1.4.1.37950.1.1.5.12.1.27
-- 1.3.6.1.4.1.37950.1.1.5.12.1.27
-- 1.3.6.1.4.1.37950.1.1.5.12.1.27
-- 1.3.6.1.4.1.37950.1.1.5.12.1.27
-- 1.3.6.1.4.1.37950.1.1.5.12.1.27
		-- 1.3.6.1.4.1.37950.1.1.5.12.1.27
		onuNumberTable OBJECT-TYPE
			SYNTAX SEQUENCE OF OnuNumberEntry
			MAX-ACCESS not-accessible
			STATUS current
			DESCRIPTION
				"Description."
			::= { onuAuth 27 }

		
--         1.3.6.1.4.1.37950.1.1.5.12.1.27.1
-- 1.3.6.1.4.1.37950.1.1.5.12.1.27.1
-- 1.3.6.1.4.1.37950.1.1.5.12.1.27.1
-- 1.3.6.1.4.1.37950.1.1.5.12.1.27.1
-- 1.3.6.1.4.1.37950.1.1.5.12.1.27.1
-- 1.3.6.1.4.1.37950.1.1.5.12.1.27.1
-- 1.3.6.1.4.1.37950.1.1.5.12.1.27.1
-- 1.3.6.1.4.1.37950.1.1.5.12.1.27.1
		-- 1.3.6.1.4.1.37950.1.1.5.12.1.27.1
		onuNumberEntry OBJECT-TYPE
			SYNTAX OnuNumberEntry
			MAX-ACCESS not-accessible
			STATUS current
			DESCRIPTION
				"Description."
			INDEX { onuNumberPon }
			::= { onuNumberTable 1 }

		
		OnuNumberEntry ::=
			SEQUENCE { 
				onuNumberPon
					Integer32,
				onuNumberAll
					Integer32,
				onuNumberOnline
					Integer32
			 }

--         1.3.6.1.4.1.37950.1.1.5.12.1.27.1.1
-- 1.3.6.1.4.1.37950.1.1.5.12.1.27.1.1
-- 1.3.6.1.4.1.37950.1.1.5.12.1.27.1.1
-- 1.3.6.1.4.1.37950.1.1.5.12.1.27.1.1
-- 1.3.6.1.4.1.37950.1.1.5.12.1.27.1.1
-- 1.3.6.1.4.1.37950.1.1.5.12.1.27.1.1
-- 1.3.6.1.4.1.37950.1.1.5.12.1.27.1.1
-- 1.3.6.1.4.1.37950.1.1.5.12.1.27.1.1
		-- 1.3.6.1.4.1.37950.1.1.5.12.1.27.1.1
		onuNumberPon OBJECT-TYPE
			SYNTAX Integer32
			MAX-ACCESS read-write
			STATUS current
			DESCRIPTION
				"Description."
			::= { onuNumberEntry 1 }

		
--         1.3.6.1.4.1.37950.1.1.5.12.1.27.1.2
-- 1.3.6.1.4.1.37950.1.1.5.12.1.27.1.2
-- 1.3.6.1.4.1.37950.1.1.5.12.1.27.1.2
-- 1.3.6.1.4.1.37950.1.1.5.12.1.27.1.2
-- 1.3.6.1.4.1.37950.1.1.5.12.1.27.1.2
-- 1.3.6.1.4.1.37950.1.1.5.12.1.27.1.2
-- 1.3.6.1.4.1.37950.1.1.5.12.1.27.1.2
-- 1.3.6.1.4.1.37950.1.1.5.12.1.27.1.2
		-- 1.3.6.1.4.1.37950.1.1.5.12.1.27.1.2
		onuNumberAll OBJECT-TYPE
			SYNTAX Integer32
			MAX-ACCESS read-write
			STATUS current
			DESCRIPTION
				"Description."
			::= { onuNumberEntry 2 }

		
--         1.3.6.1.4.1.37950.1.1.5.12.1.27.1.3
-- 1.3.6.1.4.1.37950.1.1.5.12.1.27.1.3
-- 1.3.6.1.4.1.37950.1.1.5.12.1.27.1.3
-- 1.3.6.1.4.1.37950.1.1.5.12.1.27.1.3
-- 1.3.6.1.4.1.37950.1.1.5.12.1.27.1.3
-- 1.3.6.1.4.1.37950.1.1.5.12.1.27.1.3
-- 1.3.6.1.4.1.37950.1.1.5.12.1.27.1.3
-- 1.3.6.1.4.1.37950.1.1.5.12.1.27.1.3
		-- 1.3.6.1.4.1.37950.1.1.5.12.1.27.1.3
		onuNumberOnline OBJECT-TYPE
			SYNTAX Integer32
			MAX-ACCESS read-write
			STATUS current
			DESCRIPTION
				"Description."
			::= { onuNumberEntry 3 }

		
--         1.3.6.1.4.1.37950.1.1.5.12.1.28
-- 1.3.6.1.4.1.37950.1.1.5.12.1.28
-- 1.3.6.1.4.1.37950.1.1.5.12.1.28
-- 1.3.6.1.4.1.37950.1.1.5.12.1.28
-- 1.3.6.1.4.1.37950.1.1.5.12.1.28
-- 1.3.6.1.4.1.37950.1.1.5.12.1.28
-- 1.3.6.1.4.1.37950.1.1.5.12.1.28
-- 1.3.6.1.4.1.37950.1.1.5.12.1.28
		-- 1.3.6.1.4.1.37950.1.1.5.12.1.28
		onuRecievePowerTable OBJECT-TYPE
			SYNTAX SEQUENCE OF OnuRecievePowerEntry
			MAX-ACCESS not-accessible
			STATUS current
			DESCRIPTION
				"Description."
			::= { onuAuth 28 }

		
--         1.3.6.1.4.1.37950.1.1.5.12.1.28.1
-- 1.3.6.1.4.1.37950.1.1.5.12.1.28.1
-- 1.3.6.1.4.1.37950.1.1.5.12.1.28.1
-- 1.3.6.1.4.1.37950.1.1.5.12.1.28.1
-- 1.3.6.1.4.1.37950.1.1.5.12.1.28.1
-- 1.3.6.1.4.1.37950.1.1.5.12.1.28.1
-- 1.3.6.1.4.1.37950.1.1.5.12.1.28.1
-- 1.3.6.1.4.1.37950.1.1.5.12.1.28.1
		-- 1.3.6.1.4.1.37950.1.1.5.12.1.28.1
		onuRecievePowerEntry OBJECT-TYPE
			SYNTAX OnuRecievePowerEntry
			MAX-ACCESS not-accessible
			STATUS current
			DESCRIPTION
				"Description."
			INDEX { onuid }
			::= { onuRecievePowerTable 1 }

		
		OnuRecievePowerEntry ::=
			SEQUENCE { 
				onuid
					Integer32,
				onuMACAddr
					OCTET STRING,
				onuRecievepower
					OCTET STRING
			 }

--         1.3.6.1.4.1.37950.1.1.5.12.1.28.1.1
-- 1.3.6.1.4.1.37950.1.1.5.12.1.28.1.1
-- 1.3.6.1.4.1.37950.1.1.5.12.1.28.1.1
-- 1.3.6.1.4.1.37950.1.1.5.12.1.28.1.1
-- 1.3.6.1.4.1.37950.1.1.5.12.1.28.1.1
-- 1.3.6.1.4.1.37950.1.1.5.12.1.28.1.1
-- 1.3.6.1.4.1.37950.1.1.5.12.1.28.1.1
-- 1.3.6.1.4.1.37950.1.1.5.12.1.28.1.1
		-- 1.3.6.1.4.1.37950.1.1.5.12.1.28.1.1
		onuid OBJECT-TYPE
			SYNTAX Integer32
			MAX-ACCESS read-write
			STATUS current
			DESCRIPTION
				"Description."
			::= { onuRecievePowerEntry 1 }

		
--         1.3.6.1.4.1.37950.1.1.5.12.1.28.1.2
-- 1.3.6.1.4.1.37950.1.1.5.12.1.28.1.2
-- 1.3.6.1.4.1.37950.1.1.5.12.1.28.1.2
-- 1.3.6.1.4.1.37950.1.1.5.12.1.28.1.2
-- 1.3.6.1.4.1.37950.1.1.5.12.1.28.1.2
-- 1.3.6.1.4.1.37950.1.1.5.12.1.28.1.2
-- 1.3.6.1.4.1.37950.1.1.5.12.1.28.1.2
-- 1.3.6.1.4.1.37950.1.1.5.12.1.28.1.2
		-- 1.3.6.1.4.1.37950.1.1.5.12.1.28.1.2
		onuMACAddr OBJECT-TYPE
			SYNTAX OCTET STRING
			MAX-ACCESS read-write
			STATUS current
			DESCRIPTION
				"Description."
			::= { onuRecievePowerEntry 2 }

		
--         1.3.6.1.4.1.37950.1.1.5.12.1.28.1.3
-- 1.3.6.1.4.1.37950.1.1.5.12.1.28.1.3
-- 1.3.6.1.4.1.37950.1.1.5.12.1.28.1.3
-- 1.3.6.1.4.1.37950.1.1.5.12.1.28.1.3
-- 1.3.6.1.4.1.37950.1.1.5.12.1.28.1.3
-- 1.3.6.1.4.1.37950.1.1.5.12.1.28.1.3
-- 1.3.6.1.4.1.37950.1.1.5.12.1.28.1.3
-- 1.3.6.1.4.1.37950.1.1.5.12.1.28.1.3
		-- 1.3.6.1.4.1.37950.1.1.5.12.1.28.1.3
		onuRecievepower OBJECT-TYPE
			SYNTAX OCTET STRING
			MAX-ACCESS read-write
			STATUS current
			DESCRIPTION
				"Description."
			::= { onuRecievePowerEntry 3 }

		
--           1.3.6.1.4.1.37950.1.1.5.12.1.25
-- 1.3.6.1.4.1.37950.1.1.5.12.1.25
-- 1.3.6.1.4.1.37950.1.1.5.12.1.29
-- 1.3.6.1.4.1.37950.1.1.5.12.1.29
-- 1.3.6.1.4.1.37950.1.1.5.12.1.29
-- 1.3.6.1.4.1.37950.1.1.5.12.1.29
-- 1.3.6.1.4.1.37950.1.1.5.12.1.29
-- 1.3.6.1.4.1.37950.1.1.5.12.1.29
-- 1.3.6.1.4.1.37950.1.1.5.12.1.29
-- 1.3.6.1.4.1.37950.1.1.5.12.1.29
		-- 1.3.6.1.4.1.37950.1.1.5.12.1.29
		onlineOnuAuthInfoTable OBJECT-TYPE
			SYNTAX SEQUENCE OF OnlineOnuAuthInfoEntry
			MAX-ACCESS not-accessible
			STATUS current
			DESCRIPTION
				"Description."
			::= { onuAuth 29 }

		
--           1.3.6.1.4.1.37950.1.1.5.12.1.25.1
-- 1.3.6.1.4.1.37950.1.1.5.12.1.25.1
-- 1.3.6.1.4.1.37950.1.1.5.12.1.29.1
-- 1.3.6.1.4.1.37950.1.1.5.12.1.29.1
-- 1.3.6.1.4.1.37950.1.1.5.12.1.29.1
-- 1.3.6.1.4.1.37950.1.1.5.12.1.29.1
-- 1.3.6.1.4.1.37950.1.1.5.12.1.29.1
-- 1.3.6.1.4.1.37950.1.1.5.12.1.29.1
-- 1.3.6.1.4.1.37950.1.1.5.12.1.29.1
-- 1.3.6.1.4.1.37950.1.1.5.12.1.29.1
		-- 1.3.6.1.4.1.37950.1.1.5.12.1.29.1
		onlineOnuAuthInfoEntry OBJECT-TYPE
			SYNTAX OnlineOnuAuthInfoEntry
			MAX-ACCESS not-accessible
			STATUS current
			DESCRIPTION
				"Description."
			INDEX { onlineOnuAuthInfoPonNo, onlineOnuAuthInfoOnuNo }
			::= { onlineOnuAuthInfoTable 1 }

		
		OnlineOnuAuthInfoEntry ::=
			SEQUENCE { 
				onlineOnuAuthInfoPonNo
					Integer32,
				onlineOnuAuthInfoOnuNo
					Integer32,
				onlineOnuAuthInfoLlid
					Integer32,
				onlineOnulineStatus
					INTEGER,
				onlineOnuMacAddr
					OCTET STRING,
				onlineOnutype
					OCTET STRING,
				onlineOnuExchange
					INTEGER,
				onlineOnuAuthMode
					INTEGER,
				onlineOnuAuthInfoDescription
					OCTET STRING,
				onlineOnuAuthInfoLoid
					OCTET STRING,
				onlineOnuAuthInfoLoidPwd
					OCTET STRING,
				onlineOnuAuthInfoRtt
					INTEGER,
				onlineOnutype1
					OCTET STRING,
				onlineOnuAuthInfoStatus
					INTEGER,
				onlineOnuAuthInfoDeregReason
					INTEGER,
				onlineOnuAuthInfoPriSupport
					Unsigned32,
				onlineOnuAuthInfoDistance
					Unsigned32,
				onlineOnuAuthInfoLastRegTime
					OCTET STRING,
				onlineOnuAuthInfoLastDeregTime
					OCTET STRING,
				onlineOnuAuthInfoAliveTime
					OCTET STRING,
				onlineOnuAuthInfoPriSupportNew
					Unsigned32
			 }

--           1.3.6.1.4.1.37950.1.1.5.12.1.25.1.1
-- 1.3.6.1.4.1.37950.1.1.5.12.1.25.1.1
-- 1.3.6.1.4.1.37950.1.1.5.12.1.29.1.1
-- 1.3.6.1.4.1.37950.1.1.5.12.1.29.1.1
-- 1.3.6.1.4.1.37950.1.1.5.12.1.29.1.1
-- 1.3.6.1.4.1.37950.1.1.5.12.1.29.1.1
-- 1.3.6.1.4.1.37950.1.1.5.12.1.29.1.1
-- 1.3.6.1.4.1.37950.1.1.5.12.1.29.1.1
-- 1.3.6.1.4.1.37950.1.1.5.12.1.29.1.1
-- 1.3.6.1.4.1.37950.1.1.5.12.1.29.1.1
		-- 1.3.6.1.4.1.37950.1.1.5.12.1.29.1.1
		onlineOnuAuthInfoPonNo OBJECT-TYPE
			SYNTAX Integer32
			MAX-ACCESS read-only
			STATUS current
			DESCRIPTION
				"Description."
			::= { onlineOnuAuthInfoEntry 1 }

		
--           1.3.6.1.4.1.37950.1.1.5.12.1.25.1.2
-- 1.3.6.1.4.1.37950.1.1.5.12.1.25.1.2
-- 1.3.6.1.4.1.37950.1.1.5.12.1.29.1.2
-- 1.3.6.1.4.1.37950.1.1.5.12.1.29.1.2
-- 1.3.6.1.4.1.37950.1.1.5.12.1.29.1.2
-- 1.3.6.1.4.1.37950.1.1.5.12.1.29.1.2
-- 1.3.6.1.4.1.37950.1.1.5.12.1.29.1.2
-- 1.3.6.1.4.1.37950.1.1.5.12.1.29.1.2
-- 1.3.6.1.4.1.37950.1.1.5.12.1.29.1.2
-- 1.3.6.1.4.1.37950.1.1.5.12.1.29.1.2
		-- 1.3.6.1.4.1.37950.1.1.5.12.1.29.1.2
		onlineOnuAuthInfoOnuNo OBJECT-TYPE
			SYNTAX Integer32
			MAX-ACCESS read-only
			STATUS current
			DESCRIPTION
				"Description."
			::= { onlineOnuAuthInfoEntry 2 }

		
--           1.3.6.1.4.1.37950.1.1.5.12.1.25.1.3
-- 1.3.6.1.4.1.37950.1.1.5.12.1.25.1.3
-- 1.3.6.1.4.1.37950.1.1.5.12.1.29.1.3
-- 1.3.6.1.4.1.37950.1.1.5.12.1.29.1.3
-- 1.3.6.1.4.1.37950.1.1.5.12.1.29.1.3
-- 1.3.6.1.4.1.37950.1.1.5.12.1.29.1.3
-- 1.3.6.1.4.1.37950.1.1.5.12.1.29.1.3
-- 1.3.6.1.4.1.37950.1.1.5.12.1.29.1.3
-- 1.3.6.1.4.1.37950.1.1.5.12.1.29.1.3
-- 1.3.6.1.4.1.37950.1.1.5.12.1.29.1.3
		-- 1.3.6.1.4.1.37950.1.1.5.12.1.29.1.3
		onlineOnuAuthInfoLlid OBJECT-TYPE
			SYNTAX Integer32
			MAX-ACCESS read-only
			STATUS current
			DESCRIPTION
				"Description."
			::= { onlineOnuAuthInfoEntry 3 }

		
--           1.3.6.1.4.1.37950.1.1.5.12.1.25.1.4
-- 1.3.6.1.4.1.37950.1.1.5.12.1.25.1.4
-- 1.3.6.1.4.1.37950.1.1.5.12.1.29.1.4
-- 1.3.6.1.4.1.37950.1.1.5.12.1.29.1.4
-- 1.3.6.1.4.1.37950.1.1.5.12.1.29.1.4
-- 1.3.6.1.4.1.37950.1.1.5.12.1.29.1.4
-- 1.3.6.1.4.1.37950.1.1.5.12.1.29.1.4
-- 1.3.6.1.4.1.37950.1.1.5.12.1.29.1.4
-- 1.3.6.1.4.1.37950.1.1.5.12.1.29.1.4
-- 1.3.6.1.4.1.37950.1.1.5.12.1.29.1.4
		-- 1.3.6.1.4.1.37950.1.1.5.12.1.29.1.4
		onlineOnulineStatus OBJECT-TYPE
			SYNTAX INTEGER
				{
				offline(0),
				online(1)
				}
			MAX-ACCESS read-only
			STATUS current
			DESCRIPTION
				"Description."
			::= { onlineOnuAuthInfoEntry 4 }

		
--           1.3.6.1.4.1.37950.1.1.5.12.1.25.1.5
-- 1.3.6.1.4.1.37950.1.1.5.12.1.25.1.5
-- 1.3.6.1.4.1.37950.1.1.5.12.1.29.1.5
-- 1.3.6.1.4.1.37950.1.1.5.12.1.29.1.5
-- 1.3.6.1.4.1.37950.1.1.5.12.1.29.1.5
-- 1.3.6.1.4.1.37950.1.1.5.12.1.29.1.5
-- 1.3.6.1.4.1.37950.1.1.5.12.1.29.1.5
-- 1.3.6.1.4.1.37950.1.1.5.12.1.29.1.5
-- 1.3.6.1.4.1.37950.1.1.5.12.1.29.1.5
-- 1.3.6.1.4.1.37950.1.1.5.12.1.29.1.5
		-- 1.3.6.1.4.1.37950.1.1.5.12.1.29.1.5
		onlineOnuMacAddr OBJECT-TYPE
			SYNTAX OCTET STRING
			MAX-ACCESS read-only
			STATUS current
			DESCRIPTION
				"Description."
			::= { onlineOnuAuthInfoEntry 5 }

		
--           1.3.6.1.4.1.37950.1.1.5.12.1.25.1.6
-- 1.3.6.1.4.1.37950.1.1.5.12.1.25.1.6
-- 1.3.6.1.4.1.37950.1.1.5.12.1.29.1.6
-- 1.3.6.1.4.1.37950.1.1.5.12.1.29.1.6
-- 1.3.6.1.4.1.37950.1.1.5.12.1.29.1.6
-- 1.3.6.1.4.1.37950.1.1.5.12.1.29.1.6
-- 1.3.6.1.4.1.37950.1.1.5.12.1.29.1.6
-- 1.3.6.1.4.1.37950.1.1.5.12.1.29.1.6
-- 1.3.6.1.4.1.37950.1.1.5.12.1.29.1.6
-- 1.3.6.1.4.1.37950.1.1.5.12.1.29.1.6
		-- 1.3.6.1.4.1.37950.1.1.5.12.1.29.1.6
		onlineOnutype OBJECT-TYPE
			SYNTAX OCTET STRING
			MAX-ACCESS read-only
			STATUS current
			DESCRIPTION
				"Description."
			::= { onlineOnuAuthInfoEntry 6 }

		
--           1.3.6.1.4.1.37950.1.1.5.12.1.25.1.7
-- 1.3.6.1.4.1.37950.1.1.5.12.1.25.1.7
-- 1.3.6.1.4.1.37950.1.1.5.12.1.29.1.7
-- 1.3.6.1.4.1.37950.1.1.5.12.1.29.1.7
-- 1.3.6.1.4.1.37950.1.1.5.12.1.29.1.7
-- 1.3.6.1.4.1.37950.1.1.5.12.1.29.1.7
-- 1.3.6.1.4.1.37950.1.1.5.12.1.29.1.7
-- 1.3.6.1.4.1.37950.1.1.5.12.1.29.1.7
-- 1.3.6.1.4.1.37950.1.1.5.12.1.29.1.7
-- 1.3.6.1.4.1.37950.1.1.5.12.1.29.1.7
		-- 1.3.6.1.4.1.37950.1.1.5.12.1.29.1.7
		onlineOnuExchange OBJECT-TYPE
			SYNTAX INTEGER
				{
				idle(1),
				busy(2)
				}
			MAX-ACCESS read-only
			STATUS current
			DESCRIPTION
				"Description."
			::= { onlineOnuAuthInfoEntry 7 }

		
--           1.3.6.1.4.1.37950.1.1.5.12.1.25.1.8
-- 1.3.6.1.4.1.37950.1.1.5.12.1.25.1.8
-- 1.3.6.1.4.1.37950.1.1.5.12.1.29.1.8
-- 1.3.6.1.4.1.37950.1.1.5.12.1.29.1.8
-- 1.3.6.1.4.1.37950.1.1.5.12.1.29.1.8
-- 1.3.6.1.4.1.37950.1.1.5.12.1.29.1.8
-- 1.3.6.1.4.1.37950.1.1.5.12.1.29.1.8
-- 1.3.6.1.4.1.37950.1.1.5.12.1.29.1.8
-- 1.3.6.1.4.1.37950.1.1.5.12.1.29.1.8
-- 1.3.6.1.4.1.37950.1.1.5.12.1.29.1.8
		-- 1.3.6.1.4.1.37950.1.1.5.12.1.29.1.8
		onlineOnuAuthMode OBJECT-TYPE
			SYNTAX INTEGER
				{
				none(0),
				macAuth(1),
				loidAuth(2)
				}
			MAX-ACCESS read-only
			STATUS current
			DESCRIPTION
				"Description."
			::= { onlineOnuAuthInfoEntry 8 }

		
--           1.3.6.1.4.1.37950.1.1.5.12.1.25.1.9
-- 1.3.6.1.4.1.37950.1.1.5.12.1.25.1.9
-- 1.3.6.1.4.1.37950.1.1.5.12.1.29.1.9
-- 1.3.6.1.4.1.37950.1.1.5.12.1.29.1.9
-- 1.3.6.1.4.1.37950.1.1.5.12.1.29.1.9
-- 1.3.6.1.4.1.37950.1.1.5.12.1.29.1.9
-- 1.3.6.1.4.1.37950.1.1.5.12.1.29.1.9
-- 1.3.6.1.4.1.37950.1.1.5.12.1.29.1.9
-- 1.3.6.1.4.1.37950.1.1.5.12.1.29.1.9
-- 1.3.6.1.4.1.37950.1.1.5.12.1.29.1.9
		-- 1.3.6.1.4.1.37950.1.1.5.12.1.29.1.9
		onlineOnuAuthInfoDescription OBJECT-TYPE
			SYNTAX OCTET STRING
			MAX-ACCESS read-only
			STATUS current
			DESCRIPTION
				"Description."
			::= { onlineOnuAuthInfoEntry 9 }

		
--           1.3.6.1.4.1.37950.1.1.5.12.1.25.1.10
-- 1.3.6.1.4.1.37950.1.1.5.12.1.25.1.10
-- 1.3.6.1.4.1.37950.1.1.5.12.1.29.1.10
-- 1.3.6.1.4.1.37950.1.1.5.12.1.29.1.10
-- 1.3.6.1.4.1.37950.1.1.5.12.1.29.1.10
-- 1.3.6.1.4.1.37950.1.1.5.12.1.29.1.10
-- 1.3.6.1.4.1.37950.1.1.5.12.1.29.1.10
-- 1.3.6.1.4.1.37950.1.1.5.12.1.29.1.10
-- 1.3.6.1.4.1.37950.1.1.5.12.1.29.1.10
-- 1.3.6.1.4.1.37950.1.1.5.12.1.29.1.10
		-- 1.3.6.1.4.1.37950.1.1.5.12.1.29.1.10
		onlineOnuAuthInfoLoid OBJECT-TYPE
			SYNTAX OCTET STRING
			MAX-ACCESS read-only
			STATUS current
			DESCRIPTION
				"Description."
			::= { onlineOnuAuthInfoEntry 10 }

		
--           1.3.6.1.4.1.37950.1.1.5.12.1.25.1.11
-- 1.3.6.1.4.1.37950.1.1.5.12.1.25.1.11
-- 1.3.6.1.4.1.37950.1.1.5.12.1.29.1.11
-- 1.3.6.1.4.1.37950.1.1.5.12.1.29.1.11
-- 1.3.6.1.4.1.37950.1.1.5.12.1.29.1.11
-- 1.3.6.1.4.1.37950.1.1.5.12.1.29.1.11
-- 1.3.6.1.4.1.37950.1.1.5.12.1.29.1.11
-- 1.3.6.1.4.1.37950.1.1.5.12.1.29.1.11
-- 1.3.6.1.4.1.37950.1.1.5.12.1.29.1.11
-- 1.3.6.1.4.1.37950.1.1.5.12.1.29.1.11
		-- 1.3.6.1.4.1.37950.1.1.5.12.1.29.1.11
		onlineOnuAuthInfoLoidPwd OBJECT-TYPE
			SYNTAX OCTET STRING
			MAX-ACCESS read-only
			STATUS current
			DESCRIPTION
				"Description."
			::= { onlineOnuAuthInfoEntry 11 }

		
--           1.3.6.1.4.1.37950.1.1.5.12.1.25.1.12
-- 1.3.6.1.4.1.37950.1.1.5.12.1.25.1.12
-- 1.3.6.1.4.1.37950.1.1.5.12.1.29.1.12
-- 1.3.6.1.4.1.37950.1.1.5.12.1.29.1.12
-- 1.3.6.1.4.1.37950.1.1.5.12.1.29.1.12
-- 1.3.6.1.4.1.37950.1.1.5.12.1.29.1.12
-- 1.3.6.1.4.1.37950.1.1.5.12.1.29.1.12
-- 1.3.6.1.4.1.37950.1.1.5.12.1.29.1.12
-- 1.3.6.1.4.1.37950.1.1.5.12.1.29.1.12
-- 1.3.6.1.4.1.37950.1.1.5.12.1.29.1.12
		-- 1.3.6.1.4.1.37950.1.1.5.12.1.29.1.12
		onlineOnuAuthInfoRtt OBJECT-TYPE
			SYNTAX INTEGER
			MAX-ACCESS read-write
			STATUS current
			DESCRIPTION
				"Description."
			::= { onlineOnuAuthInfoEntry 12 }

		
--           1.3.6.1.4.1.37950.1.1.5.12.1.25.1.13
-- 1.3.6.1.4.1.37950.1.1.5.12.1.25.1.13
-- 1.3.6.1.4.1.37950.1.1.5.12.1.29.1.13
-- 1.3.6.1.4.1.37950.1.1.5.12.1.29.1.13
-- 1.3.6.1.4.1.37950.1.1.5.12.1.29.1.13
-- 1.3.6.1.4.1.37950.1.1.5.12.1.29.1.13
-- 1.3.6.1.4.1.37950.1.1.5.12.1.29.1.13
-- 1.3.6.1.4.1.37950.1.1.5.12.1.29.1.13
-- 1.3.6.1.4.1.37950.1.1.5.12.1.29.1.13
-- 1.3.6.1.4.1.37950.1.1.5.12.1.29.1.13
		-- 1.3.6.1.4.1.37950.1.1.5.12.1.29.1.13
		onlineOnutype1 OBJECT-TYPE
			SYNTAX OCTET STRING
			MAX-ACCESS read-write
			STATUS current
			DESCRIPTION
				"Description."
			::= { onlineOnuAuthInfoEntry 13 }

		
--           1.3.6.1.4.1.37950.1.1.5.12.1.25.1.14
-- 1.3.6.1.4.1.37950.1.1.5.12.1.25.1.14
-- 1.3.6.1.4.1.37950.1.1.5.12.1.29.1.14
-- 1.3.6.1.4.1.37950.1.1.5.12.1.29.1.14
-- 1.3.6.1.4.1.37950.1.1.5.12.1.29.1.14
-- 1.3.6.1.4.1.37950.1.1.5.12.1.29.1.14
-- 1.3.6.1.4.1.37950.1.1.5.12.1.29.1.14
-- 1.3.6.1.4.1.37950.1.1.5.12.1.29.1.14
-- 1.3.6.1.4.1.37950.1.1.5.12.1.29.1.14
-- 1.3.6.1.4.1.37950.1.1.5.12.1.29.1.14
		-- 1.3.6.1.4.1.37950.1.1.5.12.1.29.1.14
		onlineOnuAuthInfoStatus OBJECT-TYPE
			SYNTAX INTEGER
				{
				unfinish(0),
				finish(1)
				}
			MAX-ACCESS read-write
			STATUS current
			DESCRIPTION
				"Description."
			::= { onlineOnuAuthInfoEntry 14 }

		
--           1.3.6.1.4.1.37950.1.1.5.12.1.25.1.15
-- 1.3.6.1.4.1.37950.1.1.5.12.1.25.1.15
-- 1.3.6.1.4.1.37950.1.1.5.12.1.29.1.15
-- 1.3.6.1.4.1.37950.1.1.5.12.1.29.1.15
-- 1.3.6.1.4.1.37950.1.1.5.12.1.29.1.15
-- 1.3.6.1.4.1.37950.1.1.5.12.1.29.1.15
-- 1.3.6.1.4.1.37950.1.1.5.12.1.29.1.15
-- 1.3.6.1.4.1.37950.1.1.5.12.1.29.1.15
-- 1.3.6.1.4.1.37950.1.1.5.12.1.29.1.15
-- 1.3.6.1.4.1.37950.1.1.5.12.1.29.1.15
		-- 1.3.6.1.4.1.37950.1.1.5.12.1.29.1.15
		onlineOnuAuthInfoDeregReason OBJECT-TYPE
			SYNTAX INTEGER
				{
				wire-down(0),
				power-off(1)
				}
			MAX-ACCESS read-write
			STATUS current
			DESCRIPTION
				"Description."
			::= { onlineOnuAuthInfoEntry 15 }

		
--           1.3.6.1.4.1.37950.1.1.5.12.1.25.1.16
-- 1.3.6.1.4.1.37950.1.1.5.12.1.25.1.16
-- 1.3.6.1.4.1.37950.1.1.5.12.1.29.1.16
-- 1.3.6.1.4.1.37950.1.1.5.12.1.29.1.16
-- 1.3.6.1.4.1.37950.1.1.5.12.1.29.1.16
-- 1.3.6.1.4.1.37950.1.1.5.12.1.29.1.16
-- 1.3.6.1.4.1.37950.1.1.5.12.1.29.1.16
-- 1.3.6.1.4.1.37950.1.1.5.12.1.29.1.16
-- 1.3.6.1.4.1.37950.1.1.5.12.1.29.1.16
-- 1.3.6.1.4.1.37950.1.1.5.12.1.29.1.16
		-- 1.3.6.1.4.1.37950.1.1.5.12.1.29.1.16
		onlineOnuAuthInfoPriSupport OBJECT-TYPE
			SYNTAX Unsigned32
			MAX-ACCESS read-write
			STATUS current
			DESCRIPTION
				"Description."
			::= { onlineOnuAuthInfoEntry 16 }

		
--          1.3.6.1.4.1.37950.1.1.5.12.1.25.1.17
-- 1.3.6.1.4.1.37950.1.1.5.12.1.29.1.17
-- 1.3.6.1.4.1.37950.1.1.5.12.1.29.1.17
-- 1.3.6.1.4.1.37950.1.1.5.12.1.29.1.17
-- 1.3.6.1.4.1.37950.1.1.5.12.1.29.1.17
-- 1.3.6.1.4.1.37950.1.1.5.12.1.29.1.17
-- 1.3.6.1.4.1.37950.1.1.5.12.1.29.1.17
-- 1.3.6.1.4.1.37950.1.1.5.12.1.29.1.17
-- 1.3.6.1.4.1.37950.1.1.5.12.1.29.1.17
		-- 1.3.6.1.4.1.37950.1.1.5.12.1.29.1.17
		onlineOnuAuthInfoDistance OBJECT-TYPE
			SYNTAX Unsigned32
			MAX-ACCESS read-write
			STATUS current
			DESCRIPTION
				"Description."
			::= { onlineOnuAuthInfoEntry 17 }

		
--          1.3.6.1.4.1.37950.1.1.5.12.1.25.1.18
-- 1.3.6.1.4.1.37950.1.1.5.12.1.29.1.18
-- 1.3.6.1.4.1.37950.1.1.5.12.1.29.1.18
-- 1.3.6.1.4.1.37950.1.1.5.12.1.29.1.18
-- 1.3.6.1.4.1.37950.1.1.5.12.1.29.1.18
-- 1.3.6.1.4.1.37950.1.1.5.12.1.29.1.18
-- 1.3.6.1.4.1.37950.1.1.5.12.1.29.1.18
-- 1.3.6.1.4.1.37950.1.1.5.12.1.29.1.18
-- 1.3.6.1.4.1.37950.1.1.5.12.1.29.1.18
		-- 1.3.6.1.4.1.37950.1.1.5.12.1.29.1.18
		onlineOnuAuthInfoLastRegTime OBJECT-TYPE
			SYNTAX OCTET STRING
			MAX-ACCESS read-write
			STATUS current
			DESCRIPTION
				"Description."
			::= { onlineOnuAuthInfoEntry 18 }

		
--          1.3.6.1.4.1.37950.1.1.5.12.1.25.1.19
-- 1.3.6.1.4.1.37950.1.1.5.12.1.29.1.19
-- 1.3.6.1.4.1.37950.1.1.5.12.1.29.1.19
-- 1.3.6.1.4.1.37950.1.1.5.12.1.29.1.19
-- 1.3.6.1.4.1.37950.1.1.5.12.1.29.1.19
-- 1.3.6.1.4.1.37950.1.1.5.12.1.29.1.19
-- 1.3.6.1.4.1.37950.1.1.5.12.1.29.1.19
-- 1.3.6.1.4.1.37950.1.1.5.12.1.29.1.19
-- 1.3.6.1.4.1.37950.1.1.5.12.1.29.1.19
		-- 1.3.6.1.4.1.37950.1.1.5.12.1.29.1.19
		onlineOnuAuthInfoLastDeregTime OBJECT-TYPE
			SYNTAX OCTET STRING
			MAX-ACCESS read-write
			STATUS current
			DESCRIPTION
				"Description."
			::= { onlineOnuAuthInfoEntry 19 }

		
--          1.3.6.1.4.1.37950.1.1.5.12.1.25.1.20
-- 1.3.6.1.4.1.37950.1.1.5.12.1.29.1.20
-- 1.3.6.1.4.1.37950.1.1.5.12.1.29.1.20
-- 1.3.6.1.4.1.37950.1.1.5.12.1.29.1.20
-- 1.3.6.1.4.1.37950.1.1.5.12.1.29.1.20
-- 1.3.6.1.4.1.37950.1.1.5.12.1.29.1.20
-- 1.3.6.1.4.1.37950.1.1.5.12.1.29.1.20
-- 1.3.6.1.4.1.37950.1.1.5.12.1.29.1.20
-- 1.3.6.1.4.1.37950.1.1.5.12.1.29.1.20
		-- 1.3.6.1.4.1.37950.1.1.5.12.1.29.1.20
		onlineOnuAuthInfoAliveTime OBJECT-TYPE
			SYNTAX OCTET STRING
			MAX-ACCESS read-write
			STATUS current
			DESCRIPTION
				"Description."
			::= { onlineOnuAuthInfoEntry 20 }

		
--         1.3.6.1.4.1.37950.1.1.5.12.1.29.1.21
-- 1.3.6.1.4.1.37950.1.1.5.12.1.29.1.21
-- 1.3.6.1.4.1.37950.1.1.5.12.1.29.1.21
-- 1.3.6.1.4.1.37950.1.1.5.12.1.29.1.21
-- 1.3.6.1.4.1.37950.1.1.5.12.1.29.1.21
-- 1.3.6.1.4.1.37950.1.1.5.12.1.29.1.21
-- 1.3.6.1.4.1.37950.1.1.5.12.1.29.1.21
-- 1.3.6.1.4.1.37950.1.1.5.12.1.29.1.21
		-- 1.3.6.1.4.1.37950.1.1.5.12.1.29.1.21
		onlineOnuAuthInfoPriSupportNew OBJECT-TYPE
			SYNTAX Unsigned32
			MAX-ACCESS read-write
			STATUS current
			DESCRIPTION
				"Description."
			::= { onlineOnuAuthInfoEntry 21 }

		
--         1.3.6.1.4.1.37950.1.1.5.12.1.30
-- 1.3.6.1.4.1.37950.1.1.5.12.1.30
-- 1.3.6.1.4.1.37950.1.1.5.12.1.30
-- 1.3.6.1.4.1.37950.1.1.5.12.1.30
-- 1.3.6.1.4.1.37950.1.1.5.12.1.30
-- 1.3.6.1.4.1.37950.1.1.5.12.1.30
-- 1.3.6.1.4.1.37950.1.1.5.12.1.30
-- 1.3.6.1.4.1.37950.1.1.5.12.1.30
		-- 1.3.6.1.4.1.37950.1.1.5.12.1.30
		onuMacAddrLimit OBJECT IDENTIFIER ::= { onuAuth 30 }

		
--         1.3.6.1.4.1.37950.1.1.5.12.1.30.1
-- 1.3.6.1.4.1.37950.1.1.5.12.1.30.1
-- 1.3.6.1.4.1.37950.1.1.5.12.1.30.1
-- 1.3.6.1.4.1.37950.1.1.5.12.1.30.1
-- 1.3.6.1.4.1.37950.1.1.5.12.1.30.1
-- 1.3.6.1.4.1.37950.1.1.5.12.1.30.1
-- 1.3.6.1.4.1.37950.1.1.5.12.1.30.1
-- 1.3.6.1.4.1.37950.1.1.5.12.1.30.1
		-- 1.3.6.1.4.1.37950.1.1.5.12.1.30.1
		onuMacLimitPon OBJECT-TYPE
			SYNTAX INTEGER (1..16)
			MAX-ACCESS read-write
			STATUS current
			DESCRIPTION
				"Description."
			::= { onuMacAddrLimit 1 }

		
--         1.3.6.1.4.1.37950.1.1.5.12.1.30.2
-- 1.3.6.1.4.1.37950.1.1.5.12.1.30.2
-- 1.3.6.1.4.1.37950.1.1.5.12.1.30.2
-- 1.3.6.1.4.1.37950.1.1.5.12.1.30.2
-- 1.3.6.1.4.1.37950.1.1.5.12.1.30.2
-- 1.3.6.1.4.1.37950.1.1.5.12.1.30.2
-- 1.3.6.1.4.1.37950.1.1.5.12.1.30.2
-- 1.3.6.1.4.1.37950.1.1.5.12.1.30.2
		-- 1.3.6.1.4.1.37950.1.1.5.12.1.30.2
		onuMacLimitOnu OBJECT-TYPE
			SYNTAX INTEGER (1..65535)
			MAX-ACCESS read-write
			STATUS current
			DESCRIPTION
				"Description."
			::= { onuMacAddrLimit 2 }

		
--         1.3.6.1.4.1.37950.1.1.5.12.1.30.3
-- 1.3.6.1.4.1.37950.1.1.5.12.1.30.3
-- 1.3.6.1.4.1.37950.1.1.5.12.1.30.3
-- 1.3.6.1.4.1.37950.1.1.5.12.1.30.3
-- 1.3.6.1.4.1.37950.1.1.5.12.1.30.3
-- 1.3.6.1.4.1.37950.1.1.5.12.1.30.3
-- 1.3.6.1.4.1.37950.1.1.5.12.1.30.3
-- 1.3.6.1.4.1.37950.1.1.5.12.1.30.3
		-- 1.3.6.1.4.1.37950.1.1.5.12.1.30.3
		onuMacLimitNum OBJECT-TYPE
			SYNTAX Integer32 (-1..16383)
			MAX-ACCESS read-write
			STATUS current
			DESCRIPTION
				"Description."
			::= { onuMacAddrLimit 3 }

		
--         1.3.6.1.4.1.37950.1.1.5.12.1.31
-- 1.3.6.1.4.1.37950.1.1.5.12.1.31
-- 1.3.6.1.4.1.37950.1.1.5.12.1.31
-- 1.3.6.1.4.1.37950.1.1.5.12.1.31
-- 1.3.6.1.4.1.37950.1.1.5.12.1.31
-- 1.3.6.1.4.1.37950.1.1.5.12.1.31
-- 1.3.6.1.4.1.37950.1.1.5.12.1.31
-- 1.3.6.1.4.1.37950.1.1.5.12.1.31
		-- 1.3.6.1.4.1.37950.1.1.5.12.1.31
		onuAuthInfo3Table OBJECT-TYPE
			SYNTAX SEQUENCE OF OnuAuthInfo3Entry
			MAX-ACCESS not-accessible
			STATUS current
			DESCRIPTION
				"Description."
			::= { onuAuth 31 }

		
--         1.3.6.1.4.1.37950.1.1.5.12.1.31.1
-- 1.3.6.1.4.1.37950.1.1.5.12.1.31.1
-- 1.3.6.1.4.1.37950.1.1.5.12.1.31.1
-- 1.3.6.1.4.1.37950.1.1.5.12.1.31.1
-- 1.3.6.1.4.1.37950.1.1.5.12.1.31.1
-- 1.3.6.1.4.1.37950.1.1.5.12.1.31.1
-- 1.3.6.1.4.1.37950.1.1.5.12.1.31.1
-- 1.3.6.1.4.1.37950.1.1.5.12.1.31.1
		-- 1.3.6.1.4.1.37950.1.1.5.12.1.31.1
		onuAuthInfo3Entry OBJECT-TYPE
			SYNTAX OnuAuthInfo3Entry
			MAX-ACCESS not-accessible
			STATUS current
			DESCRIPTION
				"Description."
			INDEX { authInfoPonNo3, authInfoOnuNo3 }
			::= { onuAuthInfo3Table 1 }

		
		OnuAuthInfo3Entry ::=
			SEQUENCE { 
				authInfoPonNo3
					Integer32,
				authInfoOnuNo3
					Integer32,
				onuAuthInfo3Details
					OCTET STRING
			 }

--         1.3.6.1.4.1.37950.1.1.5.12.1.31.1.1
-- 1.3.6.1.4.1.37950.1.1.5.12.1.31.1.1
-- 1.3.6.1.4.1.37950.1.1.5.12.1.31.1.1
-- 1.3.6.1.4.1.37950.1.1.5.12.1.31.1.1
-- 1.3.6.1.4.1.37950.1.1.5.12.1.31.1.1
-- 1.3.6.1.4.1.37950.1.1.5.12.1.31.1.1
-- 1.3.6.1.4.1.37950.1.1.5.12.1.31.1.1
-- 1.3.6.1.4.1.37950.1.1.5.12.1.31.1.1
		-- 1.3.6.1.4.1.37950.1.1.5.12.1.31.1.1
		authInfoPonNo3 OBJECT-TYPE
			SYNTAX Integer32
			MAX-ACCESS read-only
			STATUS current
			DESCRIPTION
				"Description."
			::= { onuAuthInfo3Entry 1 }

		
--         1.3.6.1.4.1.37950.1.1.5.12.1.31.1.2
-- 1.3.6.1.4.1.37950.1.1.5.12.1.31.1.2
-- 1.3.6.1.4.1.37950.1.1.5.12.1.31.1.2
-- 1.3.6.1.4.1.37950.1.1.5.12.1.31.1.2
-- 1.3.6.1.4.1.37950.1.1.5.12.1.31.1.2
-- 1.3.6.1.4.1.37950.1.1.5.12.1.31.1.2
-- 1.3.6.1.4.1.37950.1.1.5.12.1.31.1.2
-- 1.3.6.1.4.1.37950.1.1.5.12.1.31.1.2
		-- 1.3.6.1.4.1.37950.1.1.5.12.1.31.1.2
		authInfoOnuNo3 OBJECT-TYPE
			SYNTAX Integer32
			MAX-ACCESS read-only
			STATUS current
			DESCRIPTION
				"Description."
			::= { onuAuthInfo3Entry 2 }

		
--         1.3.6.1.4.1.37950.1.1.5.12.1.31.1.3
-- 1.3.6.1.4.1.37950.1.1.5.12.1.31.1.3
-- 1.3.6.1.4.1.37950.1.1.5.12.1.31.1.3
-- 1.3.6.1.4.1.37950.1.1.5.12.1.31.1.3
-- 1.3.6.1.4.1.37950.1.1.5.12.1.31.1.3
-- 1.3.6.1.4.1.37950.1.1.5.12.1.31.1.3
-- 1.3.6.1.4.1.37950.1.1.5.12.1.31.1.3
-- 1.3.6.1.4.1.37950.1.1.5.12.1.31.1.3
		-- 1.3.6.1.4.1.37950.1.1.5.12.1.31.1.3
		onuAuthInfo3Details OBJECT-TYPE
			SYNTAX OCTET STRING
			MAX-ACCESS read-only
			STATUS current
			DESCRIPTION
				"Description."
			::= { onuAuthInfo3Entry 3 }

		
--         1.3.6.1.4.1.37950.1.1.5.12.1.32
-- 1.3.6.1.4.1.37950.1.1.5.12.1.32
-- 1.3.6.1.4.1.37950.1.1.5.12.1.32
-- 1.3.6.1.4.1.37950.1.1.5.12.1.32
-- 1.3.6.1.4.1.37950.1.1.5.12.1.32
-- 1.3.6.1.4.1.37950.1.1.5.12.1.32
-- 1.3.6.1.4.1.37950.1.1.5.12.1.32
-- 1.3.6.1.4.1.37950.1.1.5.12.1.32
		-- 1.3.6.1.4.1.37950.1.1.5.12.1.32
		onlineOnuAuthInfo3Table OBJECT-TYPE
			SYNTAX SEQUENCE OF OnlineOnuAuthInfo3Entry
			MAX-ACCESS not-accessible
			STATUS current
			DESCRIPTION
				"Description."
			::= { onuAuth 32 }

		
--         1.3.6.1.4.1.37950.1.1.5.12.1.32.1
-- 1.3.6.1.4.1.37950.1.1.5.12.1.32.1
-- 1.3.6.1.4.1.37950.1.1.5.12.1.32.1
-- 1.3.6.1.4.1.37950.1.1.5.12.1.32.1
-- 1.3.6.1.4.1.37950.1.1.5.12.1.32.1
-- 1.3.6.1.4.1.37950.1.1.5.12.1.32.1
-- 1.3.6.1.4.1.37950.1.1.5.12.1.32.1
-- 1.3.6.1.4.1.37950.1.1.5.12.1.32.1
		-- 1.3.6.1.4.1.37950.1.1.5.12.1.32.1
		onlineOnuAuthInfo3Entry OBJECT-TYPE
			SYNTAX OnlineOnuAuthInfo3Entry
			MAX-ACCESS not-accessible
			STATUS current
			DESCRIPTION
				"Description."
			INDEX { onlineOnuAuthInfoPonNo3, onlineOnuAuthInfoOnuNo3 }
			::= { onlineOnuAuthInfo3Table 1 }

		
		OnlineOnuAuthInfo3Entry ::=
			SEQUENCE { 
				onlineOnuAuthInfoPonNo3
					Integer32,
				onlineOnuAuthInfoOnuNo3
					Integer32,
				onlineOnuAuthInfo3Details
					OCTET STRING
			 }

--         1.3.6.1.4.1.37950.1.1.5.12.1.32.1.1
-- 1.3.6.1.4.1.37950.1.1.5.12.1.32.1.1
-- 1.3.6.1.4.1.37950.1.1.5.12.1.32.1.1
-- 1.3.6.1.4.1.37950.1.1.5.12.1.32.1.1
-- 1.3.6.1.4.1.37950.1.1.5.12.1.32.1.1
-- 1.3.6.1.4.1.37950.1.1.5.12.1.32.1.1
-- 1.3.6.1.4.1.37950.1.1.5.12.1.32.1.1
-- 1.3.6.1.4.1.37950.1.1.5.12.1.32.1.1
		-- 1.3.6.1.4.1.37950.1.1.5.12.1.32.1.1
		onlineOnuAuthInfoPonNo3 OBJECT-TYPE
			SYNTAX Integer32
			MAX-ACCESS read-only
			STATUS current
			DESCRIPTION
				"Description."
			::= { onlineOnuAuthInfo3Entry 1 }

		
--         1.3.6.1.4.1.37950.1.1.5.12.1.32.1.2
-- 1.3.6.1.4.1.37950.1.1.5.12.1.32.1.2
-- 1.3.6.1.4.1.37950.1.1.5.12.1.32.1.2
-- 1.3.6.1.4.1.37950.1.1.5.12.1.32.1.2
-- 1.3.6.1.4.1.37950.1.1.5.12.1.32.1.2
-- 1.3.6.1.4.1.37950.1.1.5.12.1.32.1.2
-- 1.3.6.1.4.1.37950.1.1.5.12.1.32.1.2
-- 1.3.6.1.4.1.37950.1.1.5.12.1.32.1.2
		-- 1.3.6.1.4.1.37950.1.1.5.12.1.32.1.2
		onlineOnuAuthInfoOnuNo3 OBJECT-TYPE
			SYNTAX Integer32
			MAX-ACCESS read-only
			STATUS current
			DESCRIPTION
				"Description."
			::= { onlineOnuAuthInfo3Entry 2 }

		
--         1.3.6.1.4.1.37950.1.1.5.12.1.32.1.3
-- 1.3.6.1.4.1.37950.1.1.5.12.1.32.1.3
-- 1.3.6.1.4.1.37950.1.1.5.12.1.32.1.3
-- 1.3.6.1.4.1.37950.1.1.5.12.1.32.1.3
-- 1.3.6.1.4.1.37950.1.1.5.12.1.32.1.3
-- 1.3.6.1.4.1.37950.1.1.5.12.1.32.1.3
-- 1.3.6.1.4.1.37950.1.1.5.12.1.32.1.3
-- 1.3.6.1.4.1.37950.1.1.5.12.1.32.1.3
		-- 1.3.6.1.4.1.37950.1.1.5.12.1.32.1.3
		onlineOnuAuthInfo3Details OBJECT-TYPE
			SYNTAX OCTET STRING
			MAX-ACCESS read-only
			STATUS current
			DESCRIPTION
				"Description."
			::= { onlineOnuAuthInfo3Entry 3 }

		
--   1.3.6.1.4.1.37950.1.1.5.12.1.33
-- 1.3.6.1.4.1.37950.1.1.5.12.1.33
		-- 1.3.6.1.4.1.37950.1.1.5.12.1.33
		manualConfirmOnu OBJECT IDENTIFIER ::= { onuAuth 33 }

		
--   1.3.6.1.4.1.37950.1.1.5.12.1.33.1
-- 1.3.6.1.4.1.37950.1.1.5.12.1.33.1
		-- 1.3.6.1.4.1.37950.1.1.5.12.1.33.1
		onuConfirmMac OBJECT IDENTIFIER ::= { manualConfirmOnu 1 }

		
--   1.3.6.1.4.1.37950.1.1.5.12.1.33.1.1
-- 1.3.6.1.4.1.37950.1.1.5.12.1.33.1.1
		-- 1.3.6.1.4.1.37950.1.1.5.12.1.33.1.1
		confirmMac OBJECT-TYPE
			SYNTAX OCTET STRING
			MAX-ACCESS read-write
			STATUS current
			DESCRIPTION
				"Description."
			::= { onuConfirmMac 1 }

		
--   1.3.6.1.4.1.37950.1.1.5.12.1.33.1.2
-- 1.3.6.1.4.1.37950.1.1.5.12.1.33.1.2
		-- 1.3.6.1.4.1.37950.1.1.5.12.1.33.1.2
		confirmOnuid OBJECT-TYPE
			SYNTAX Integer32 (1..65535)
			MAX-ACCESS read-write
			STATUS current
			DESCRIPTION
				"Description."
			::= { onuConfirmMac 2 }

		
--   1.3.6.1.4.1.37950.1.1.5.12.1.33.1.3
-- 1.3.6.1.4.1.37950.1.1.5.12.1.33.1.3
		-- 1.3.6.1.4.1.37950.1.1.5.12.1.33.1.3
		authModeMac OBJECT-TYPE
			SYNTAX INTEGER { add(1) }
			MAX-ACCESS read-write
			STATUS current
			DESCRIPTION
				"Description."
			::= { onuConfirmMac 3 }

		
--   1.3.6.1.4.1.37950.1.1.5.12.1.33.1.4
-- 1.3.6.1.4.1.37950.1.1.5.12.1.33.1.4
		-- 1.3.6.1.4.1.37950.1.1.5.12.1.33.1.4
		confirmMacPonNo OBJECT-TYPE
			SYNTAX Integer32 (1..16)
			MAX-ACCESS read-write
			STATUS current
			DESCRIPTION
				"Description."
			::= { onuConfirmMac 4 }

		
--   1.3.6.1.4.1.37950.1.1.5.12.1.33.1.5
-- 1.3.6.1.4.1.37950.1.1.5.12.1.33.1.5
		-- 1.3.6.1.4.1.37950.1.1.5.12.1.33.1.5
		confirmMacAction OBJECT-TYPE
			SYNTAX INTEGER { add(1) }
			MAX-ACCESS read-write
			STATUS current
			DESCRIPTION
				"Description."
			::= { onuConfirmMac 5 }

		
--   1.3.6.1.4.1.37950.1.1.5.12.1.33.3
-- 1.3.6.1.4.1.37950.1.1.5.12.1.33.3
		-- 1.3.6.1.4.1.37950.1.1.5.12.1.33.3
		onuConfirmLoid OBJECT IDENTIFIER ::= { manualConfirmOnu 3 }

		
--   1.3.6.1.4.1.37950.1.1.5.12.1.33.3.1
-- 1.3.6.1.4.1.37950.1.1.5.12.1.33.3.1
		-- 1.3.6.1.4.1.37950.1.1.5.12.1.33.3.1
		confirmLoid OBJECT-TYPE
			SYNTAX OCTET STRING
			MAX-ACCESS read-write
			STATUS current
			DESCRIPTION
				"Description."
			::= { onuConfirmLoid 1 }

		
--   1.3.6.1.4.1.37950.1.1.5.12.1.33.3.2
-- 1.3.6.1.4.1.37950.1.1.5.12.1.33.3.2
		-- 1.3.6.1.4.1.37950.1.1.5.12.1.33.3.2
		confirmLoidPassword OBJECT-TYPE
			SYNTAX OCTET STRING
			MAX-ACCESS read-write
			STATUS current
			DESCRIPTION
				"Description."
			::= { onuConfirmLoid 2 }

		
--   1.3.6.1.4.1.37950.1.1.5.12.1.33.3.3
-- 1.3.6.1.4.1.37950.1.1.5.12.1.33.3.3
		-- 1.3.6.1.4.1.37950.1.1.5.12.1.33.3.3
		confirmLoidMac OBJECT-TYPE
			SYNTAX OCTET STRING
			MAX-ACCESS read-write
			STATUS current
			DESCRIPTION
				"Description."
			::= { onuConfirmLoid 3 }

		
--   1.3.6.1.4.1.37950.1.1.5.12.1.33.3.4
-- 1.3.6.1.4.1.37950.1.1.5.12.1.33.3.4
		-- 1.3.6.1.4.1.37950.1.1.5.12.1.33.3.4
		confirmLoidOnuid OBJECT-TYPE
			SYNTAX Integer32 (1..65535)
			MAX-ACCESS read-write
			STATUS current
			DESCRIPTION
				"Description."
			::= { onuConfirmLoid 4 }

		
--   1.3.6.1.4.1.37950.1.1.5.12.1.33.3.5
-- 1.3.6.1.4.1.37950.1.1.5.12.1.33.3.5
		-- 1.3.6.1.4.1.37950.1.1.5.12.1.33.3.5
		confirmLoidPonNo OBJECT-TYPE
			SYNTAX Integer32 (1..16)
			MAX-ACCESS read-write
			STATUS current
			DESCRIPTION
				"Description."
			::= { onuConfirmLoid 5 }

		
--   1.3.6.1.4.1.37950.1.1.5.12.1.33.3.6
-- 1.3.6.1.4.1.37950.1.1.5.12.1.33.3.6
		-- 1.3.6.1.4.1.37950.1.1.5.12.1.33.3.6
		confirmLoidAction OBJECT-TYPE
			SYNTAX INTEGER { add(1) }
			MAX-ACCESS read-write
			STATUS current
			DESCRIPTION
				"Description."
			::= { onuConfirmLoid 6 }

		
--          1.3.6.1.4.1.37950.1.1.5.12.2
-- 1.3.6.1.4.1.37950.1.1.5.12.2
-- 1.3.6.1.4.1.37950.1.1.5.12.2
-- 1.3.6.1.4.1.37950.1.1.5.12.2
-- 1.3.6.1.4.1.37950.1.1.5.12.2
-- 1.3.6.1.4.1.37950.1.1.5.12.2
-- 1.3.6.1.4.1.37950.1.1.5.12.2
-- 1.3.6.1.4.1.37950.1.1.5.12.2
-- 1.3.6.1.4.1.37950.1.1.5.12.2
		-- 1.3.6.1.4.1.37950.1.1.5.12.2
		onuGlobalCfg OBJECT IDENTIFIER ::= { v1600dOnuMgmt 2 }

		
--          1.3.6.1.4.1.37950.1.1.5.12.2.1
-- 1.3.6.1.4.1.37950.1.1.5.12.2.1
-- 1.3.6.1.4.1.37950.1.1.5.12.2.1
-- 1.3.6.1.4.1.37950.1.1.5.12.2.1
-- 1.3.6.1.4.1.37950.1.1.5.12.2.1
-- 1.3.6.1.4.1.37950.1.1.5.12.2.1
-- 1.3.6.1.4.1.37950.1.1.5.12.2.1
-- 1.3.6.1.4.1.37950.1.1.5.12.2.1
-- 1.3.6.1.4.1.37950.1.1.5.12.2.1
		-- 1.3.6.1.4.1.37950.1.1.5.12.2.1
		onuInfo OBJECT IDENTIFIER ::= { onuGlobalCfg 1 }

		
--          1.3.6.1.4.1.37950.1.1.5.12.2.1.1
-- 1.3.6.1.4.1.37950.1.1.5.12.2.1.1
-- 1.3.6.1.4.1.37950.1.1.5.12.2.1.1
-- 1.3.6.1.4.1.37950.1.1.5.12.2.1.1
-- 1.3.6.1.4.1.37950.1.1.5.12.2.1.1
-- 1.3.6.1.4.1.37950.1.1.5.12.2.1.1
-- 1.3.6.1.4.1.37950.1.1.5.12.2.1.1
-- 1.3.6.1.4.1.37950.1.1.5.12.2.1.1
-- 1.3.6.1.4.1.37950.1.1.5.12.2.1.1
		-- 1.3.6.1.4.1.37950.1.1.5.12.2.1.1
		onuCtcInfoTable OBJECT-TYPE
			SYNTAX SEQUENCE OF OnuCtcInfoEntry
			MAX-ACCESS not-accessible
			STATUS current
			DESCRIPTION
				"Description."
			::= { onuInfo 1 }

		
--          1.3.6.1.4.1.37950.1.1.5.12.2.1.1.1
-- 1.3.6.1.4.1.37950.1.1.5.12.2.1.1.1
-- 1.3.6.1.4.1.37950.1.1.5.12.2.1.1.1
-- 1.3.6.1.4.1.37950.1.1.5.12.2.1.1.1
-- 1.3.6.1.4.1.37950.1.1.5.12.2.1.1.1
-- 1.3.6.1.4.1.37950.1.1.5.12.2.1.1.1
-- 1.3.6.1.4.1.37950.1.1.5.12.2.1.1.1
-- 1.3.6.1.4.1.37950.1.1.5.12.2.1.1.1
-- 1.3.6.1.4.1.37950.1.1.5.12.2.1.1.1
		-- 1.3.6.1.4.1.37950.1.1.5.12.2.1.1.1
		onuCtcInfoEntry OBJECT-TYPE
			SYNTAX OnuCtcInfoEntry
			MAX-ACCESS not-accessible
			STATUS current
			DESCRIPTION
				"Description."
			INDEX { onuCtcInfoPonIndex, onuCtcInfoOnuIndex }
			::= { onuCtcInfoTable 1 }

		
		OnuCtcInfoEntry ::=
			SEQUENCE { 
				onuCtcInfoPonIndex
					Integer32,
				onuCtcInfoOnuIndex
					Integer32,
				onuOamVersion
					OCTET STRING,
				onuOamOUI
					OCTET STRING
			 }

--          1.3.6.1.4.1.37950.1.1.5.12.2.1.1.1.1
-- 1.3.6.1.4.1.37950.1.1.5.12.2.1.1.1.1
-- 1.3.6.1.4.1.37950.1.1.5.12.2.1.1.1.1
-- 1.3.6.1.4.1.37950.1.1.5.12.2.1.1.1.1
-- 1.3.6.1.4.1.37950.1.1.5.12.2.1.1.1.1
-- 1.3.6.1.4.1.37950.1.1.5.12.2.1.1.1.1
-- 1.3.6.1.4.1.37950.1.1.5.12.2.1.1.1.1
-- 1.3.6.1.4.1.37950.1.1.5.12.2.1.1.1.1
-- 1.3.6.1.4.1.37950.1.1.5.12.2.1.1.1.1
		-- 1.3.6.1.4.1.37950.1.1.5.12.2.1.1.1.1
		onuCtcInfoPonIndex OBJECT-TYPE
			SYNTAX Integer32
			MAX-ACCESS read-only
			STATUS current
			DESCRIPTION
				"Description."
			::= { onuCtcInfoEntry 1 }

		
--          1.3.6.1.4.1.37950.1.1.5.12.2.1.1.1.2
-- 1.3.6.1.4.1.37950.1.1.5.12.2.1.1.1.2
-- 1.3.6.1.4.1.37950.1.1.5.12.2.1.1.1.2
-- 1.3.6.1.4.1.37950.1.1.5.12.2.1.1.1.2
-- 1.3.6.1.4.1.37950.1.1.5.12.2.1.1.1.2
-- 1.3.6.1.4.1.37950.1.1.5.12.2.1.1.1.2
-- 1.3.6.1.4.1.37950.1.1.5.12.2.1.1.1.2
-- 1.3.6.1.4.1.37950.1.1.5.12.2.1.1.1.2
-- 1.3.6.1.4.1.37950.1.1.5.12.2.1.1.1.2
		-- 1.3.6.1.4.1.37950.1.1.5.12.2.1.1.1.2
		onuCtcInfoOnuIndex OBJECT-TYPE
			SYNTAX Integer32
			MAX-ACCESS read-only
			STATUS current
			DESCRIPTION
				"Description."
			::= { onuCtcInfoEntry 2 }

		
--          1.3.6.1.4.1.37950.1.1.5.12.2.1.1.1.3
-- 1.3.6.1.4.1.37950.1.1.5.12.2.1.1.1.3
-- 1.3.6.1.4.1.37950.1.1.5.12.2.1.1.1.3
-- 1.3.6.1.4.1.37950.1.1.5.12.2.1.1.1.3
-- 1.3.6.1.4.1.37950.1.1.5.12.2.1.1.1.3
-- 1.3.6.1.4.1.37950.1.1.5.12.2.1.1.1.3
-- 1.3.6.1.4.1.37950.1.1.5.12.2.1.1.1.3
-- 1.3.6.1.4.1.37950.1.1.5.12.2.1.1.1.3
-- 1.3.6.1.4.1.37950.1.1.5.12.2.1.1.1.3
		-- 1.3.6.1.4.1.37950.1.1.5.12.2.1.1.1.3
		onuOamVersion OBJECT-TYPE
			SYNTAX OCTET STRING
			MAX-ACCESS read-only
			STATUS current
			DESCRIPTION
				"Description."
			::= { onuCtcInfoEntry 3 }

		
--          1.3.6.1.4.1.37950.1.1.5.12.2.1.1.1.4
-- 1.3.6.1.4.1.37950.1.1.5.12.2.1.1.1.4
-- 1.3.6.1.4.1.37950.1.1.5.12.2.1.1.1.4
-- 1.3.6.1.4.1.37950.1.1.5.12.2.1.1.1.4
-- 1.3.6.1.4.1.37950.1.1.5.12.2.1.1.1.4
-- 1.3.6.1.4.1.37950.1.1.5.12.2.1.1.1.4
-- 1.3.6.1.4.1.37950.1.1.5.12.2.1.1.1.4
-- 1.3.6.1.4.1.37950.1.1.5.12.2.1.1.1.4
-- 1.3.6.1.4.1.37950.1.1.5.12.2.1.1.1.4
		-- 1.3.6.1.4.1.37950.1.1.5.12.2.1.1.1.4
		onuOamOUI OBJECT-TYPE
			SYNTAX OCTET STRING
			MAX-ACCESS read-only
			STATUS current
			DESCRIPTION
				"Description."
			::= { onuCtcInfoEntry 4 }

		
--          1.3.6.1.4.1.37950.1.1.5.12.2.1.2
-- 1.3.6.1.4.1.37950.1.1.5.12.2.1.2
-- 1.3.6.1.4.1.37950.1.1.5.12.2.1.2
-- 1.3.6.1.4.1.37950.1.1.5.12.2.1.2
-- 1.3.6.1.4.1.37950.1.1.5.12.2.1.2
-- 1.3.6.1.4.1.37950.1.1.5.12.2.1.2
-- 1.3.6.1.4.1.37950.1.1.5.12.2.1.2
-- 1.3.6.1.4.1.37950.1.1.5.12.2.1.2
-- 1.3.6.1.4.1.37950.1.1.5.12.2.1.2
		-- 1.3.6.1.4.1.37950.1.1.5.12.2.1.2
		onuSnInfoTable OBJECT-TYPE
			SYNTAX SEQUENCE OF OnuSnInfoEntry
			MAX-ACCESS not-accessible
			STATUS current
			DESCRIPTION
				"Description."
			::= { onuInfo 2 }

		
--          1.3.6.1.4.1.37950.1.1.5.12.2.1.2.1
-- 1.3.6.1.4.1.37950.1.1.5.12.2.1.2.1
-- 1.3.6.1.4.1.37950.1.1.5.12.2.1.2.1
-- 1.3.6.1.4.1.37950.1.1.5.12.2.1.2.1
-- 1.3.6.1.4.1.37950.1.1.5.12.2.1.2.1
-- 1.3.6.1.4.1.37950.1.1.5.12.2.1.2.1
-- 1.3.6.1.4.1.37950.1.1.5.12.2.1.2.1
-- 1.3.6.1.4.1.37950.1.1.5.12.2.1.2.1
-- 1.3.6.1.4.1.37950.1.1.5.12.2.1.2.1
		-- 1.3.6.1.4.1.37950.1.1.5.12.2.1.2.1
		onuSnInfoEntry OBJECT-TYPE
			SYNTAX OnuSnInfoEntry
			MAX-ACCESS not-accessible
			STATUS current
			DESCRIPTION
				"Description."
			INDEX { onuSnInfoPonIndex, onuSnInfoOnuIndex }
			::= { onuSnInfoTable 1 }

		
		OnuSnInfoEntry ::=
			SEQUENCE { 
				onuSnInfoPonIndex
					Integer32,
				onuSnInfoOnuIndex
					Integer32,
				onuVendorId
					OCTET STRING,
				onuModel
					OCTET STRING,
				onuID
					OCTET STRING,
				onuHardwareVersion
					OCTET STRING,
				onuSoftwareVersion
					OCTET STRING
			 }

--          1.3.6.1.4.1.37950.1.1.5.12.2.1.2.1.1
-- 1.3.6.1.4.1.37950.1.1.5.12.2.1.2.1.1
-- 1.3.6.1.4.1.37950.1.1.5.12.2.1.2.1.1
-- 1.3.6.1.4.1.37950.1.1.5.12.2.1.2.1.1
-- 1.3.6.1.4.1.37950.1.1.5.12.2.1.2.1.1
-- 1.3.6.1.4.1.37950.1.1.5.12.2.1.2.1.1
-- 1.3.6.1.4.1.37950.1.1.5.12.2.1.2.1.1
-- 1.3.6.1.4.1.37950.1.1.5.12.2.1.2.1.1
-- 1.3.6.1.4.1.37950.1.1.5.12.2.1.2.1.1
		-- 1.3.6.1.4.1.37950.1.1.5.12.2.1.2.1.1
		onuSnInfoPonIndex OBJECT-TYPE
			SYNTAX Integer32
			MAX-ACCESS read-only
			STATUS current
			DESCRIPTION
				"Description."
			::= { onuSnInfoEntry 1 }

		
--          1.3.6.1.4.1.37950.1.1.5.12.2.1.2.1.2
-- 1.3.6.1.4.1.37950.1.1.5.12.2.1.2.1.2
-- 1.3.6.1.4.1.37950.1.1.5.12.2.1.2.1.2
-- 1.3.6.1.4.1.37950.1.1.5.12.2.1.2.1.2
-- 1.3.6.1.4.1.37950.1.1.5.12.2.1.2.1.2
-- 1.3.6.1.4.1.37950.1.1.5.12.2.1.2.1.2
-- 1.3.6.1.4.1.37950.1.1.5.12.2.1.2.1.2
-- 1.3.6.1.4.1.37950.1.1.5.12.2.1.2.1.2
-- 1.3.6.1.4.1.37950.1.1.5.12.2.1.2.1.2
		-- 1.3.6.1.4.1.37950.1.1.5.12.2.1.2.1.2
		onuSnInfoOnuIndex OBJECT-TYPE
			SYNTAX Integer32
			MAX-ACCESS read-only
			STATUS current
			DESCRIPTION
				"Description."
			::= { onuSnInfoEntry 2 }

		
--          1.3.6.1.4.1.37950.1.1.5.12.2.1.2.1.3
-- 1.3.6.1.4.1.37950.1.1.5.12.2.1.2.1.3
-- 1.3.6.1.4.1.37950.1.1.5.12.2.1.2.1.3
-- 1.3.6.1.4.1.37950.1.1.5.12.2.1.2.1.3
-- 1.3.6.1.4.1.37950.1.1.5.12.2.1.2.1.3
-- 1.3.6.1.4.1.37950.1.1.5.12.2.1.2.1.3
-- 1.3.6.1.4.1.37950.1.1.5.12.2.1.2.1.3
-- 1.3.6.1.4.1.37950.1.1.5.12.2.1.2.1.3
-- 1.3.6.1.4.1.37950.1.1.5.12.2.1.2.1.3
		-- 1.3.6.1.4.1.37950.1.1.5.12.2.1.2.1.3
		onuVendorId OBJECT-TYPE
			SYNTAX OCTET STRING
			MAX-ACCESS read-only
			STATUS current
			DESCRIPTION
				"Description."
			::= { onuSnInfoEntry 3 }

		
--          1.3.6.1.4.1.37950.1.1.5.12.2.1.2.1.4
-- 1.3.6.1.4.1.37950.1.1.5.12.2.1.2.1.4
-- 1.3.6.1.4.1.37950.1.1.5.12.2.1.2.1.4
-- 1.3.6.1.4.1.37950.1.1.5.12.2.1.2.1.4
-- 1.3.6.1.4.1.37950.1.1.5.12.2.1.2.1.4
-- 1.3.6.1.4.1.37950.1.1.5.12.2.1.2.1.4
-- 1.3.6.1.4.1.37950.1.1.5.12.2.1.2.1.4
-- 1.3.6.1.4.1.37950.1.1.5.12.2.1.2.1.4
-- 1.3.6.1.4.1.37950.1.1.5.12.2.1.2.1.4
		-- 1.3.6.1.4.1.37950.1.1.5.12.2.1.2.1.4
		onuModel OBJECT-TYPE
			SYNTAX OCTET STRING
			MAX-ACCESS read-only
			STATUS current
			DESCRIPTION
				"Description."
			::= { onuSnInfoEntry 4 }

		
--          1.3.6.1.4.1.37950.1.1.5.12.2.1.2.1.5
-- 1.3.6.1.4.1.37950.1.1.5.12.2.1.2.1.5
-- 1.3.6.1.4.1.37950.1.1.5.12.2.1.2.1.5
-- 1.3.6.1.4.1.37950.1.1.5.12.2.1.2.1.5
-- 1.3.6.1.4.1.37950.1.1.5.12.2.1.2.1.5
-- 1.3.6.1.4.1.37950.1.1.5.12.2.1.2.1.5
-- 1.3.6.1.4.1.37950.1.1.5.12.2.1.2.1.5
-- 1.3.6.1.4.1.37950.1.1.5.12.2.1.2.1.5
-- 1.3.6.1.4.1.37950.1.1.5.12.2.1.2.1.5
		-- 1.3.6.1.4.1.37950.1.1.5.12.2.1.2.1.5
		onuID OBJECT-TYPE
			SYNTAX OCTET STRING
			MAX-ACCESS read-only
			STATUS current
			DESCRIPTION
				"Description."
			::= { onuSnInfoEntry 5 }

		
--          1.3.6.1.4.1.37950.1.1.5.12.2.1.2.1.6
-- 1.3.6.1.4.1.37950.1.1.5.12.2.1.2.1.6
-- 1.3.6.1.4.1.37950.1.1.5.12.2.1.2.1.6
-- 1.3.6.1.4.1.37950.1.1.5.12.2.1.2.1.6
-- 1.3.6.1.4.1.37950.1.1.5.12.2.1.2.1.6
-- 1.3.6.1.4.1.37950.1.1.5.12.2.1.2.1.6
-- 1.3.6.1.4.1.37950.1.1.5.12.2.1.2.1.6
-- 1.3.6.1.4.1.37950.1.1.5.12.2.1.2.1.6
-- 1.3.6.1.4.1.37950.1.1.5.12.2.1.2.1.6
		-- 1.3.6.1.4.1.37950.1.1.5.12.2.1.2.1.6
		onuHardwareVersion OBJECT-TYPE
			SYNTAX OCTET STRING
			MAX-ACCESS read-only
			STATUS current
			DESCRIPTION
				"Description."
			::= { onuSnInfoEntry 6 }

		
--          1.3.6.1.4.1.37950.1.1.5.12.2.1.2.1.7
-- 1.3.6.1.4.1.37950.1.1.5.12.2.1.2.1.7
-- 1.3.6.1.4.1.37950.1.1.5.12.2.1.2.1.7
-- 1.3.6.1.4.1.37950.1.1.5.12.2.1.2.1.7
-- 1.3.6.1.4.1.37950.1.1.5.12.2.1.2.1.7
-- 1.3.6.1.4.1.37950.1.1.5.12.2.1.2.1.7
-- 1.3.6.1.4.1.37950.1.1.5.12.2.1.2.1.7
-- 1.3.6.1.4.1.37950.1.1.5.12.2.1.2.1.7
-- 1.3.6.1.4.1.37950.1.1.5.12.2.1.2.1.7
		-- 1.3.6.1.4.1.37950.1.1.5.12.2.1.2.1.7
		onuSoftwareVersion OBJECT-TYPE
			SYNTAX OCTET STRING
			MAX-ACCESS read-only
			STATUS current
			DESCRIPTION
				"Description."
			::= { onuSnInfoEntry 7 }

		
--          1.3.6.1.4.1.37950.1.1.5.12.2.1.3
-- 1.3.6.1.4.1.37950.1.1.5.12.2.1.3
-- 1.3.6.1.4.1.37950.1.1.5.12.2.1.3
-- 1.3.6.1.4.1.37950.1.1.5.12.2.1.3
-- 1.3.6.1.4.1.37950.1.1.5.12.2.1.3
-- 1.3.6.1.4.1.37950.1.1.5.12.2.1.3
-- 1.3.6.1.4.1.37950.1.1.5.12.2.1.3
-- 1.3.6.1.4.1.37950.1.1.5.12.2.1.3
-- 1.3.6.1.4.1.37950.1.1.5.12.2.1.3
		-- 1.3.6.1.4.1.37950.1.1.5.12.2.1.3
		fwVersionInfoTable OBJECT-TYPE
			SYNTAX SEQUENCE OF FwVersionInfoEntry
			MAX-ACCESS not-accessible
			STATUS current
			DESCRIPTION
				"Description."
			::= { onuInfo 3 }

		
--          1.3.6.1.4.1.37950.1.1.5.12.2.1.3.1
-- 1.3.6.1.4.1.37950.1.1.5.12.2.1.3.1
-- 1.3.6.1.4.1.37950.1.1.5.12.2.1.3.1
-- 1.3.6.1.4.1.37950.1.1.5.12.2.1.3.1
-- 1.3.6.1.4.1.37950.1.1.5.12.2.1.3.1
-- 1.3.6.1.4.1.37950.1.1.5.12.2.1.3.1
-- 1.3.6.1.4.1.37950.1.1.5.12.2.1.3.1
-- 1.3.6.1.4.1.37950.1.1.5.12.2.1.3.1
-- 1.3.6.1.4.1.37950.1.1.5.12.2.1.3.1
		-- 1.3.6.1.4.1.37950.1.1.5.12.2.1.3.1
		fwVersionInfoEntry OBJECT-TYPE
			SYNTAX FwVersionInfoEntry
			MAX-ACCESS not-accessible
			STATUS current
			DESCRIPTION
				"Description."
			INDEX { fwVersionInfoPonIndex, fwVersionInfoOnuIndex }
			::= { fwVersionInfoTable 1 }

		
		FwVersionInfoEntry ::=
			SEQUENCE { 
				fwVersionInfoPonIndex
					Integer32,
				fwVersionInfoOnuIndex
					Integer32,
				fwVersion
					OCTET STRING
			 }

--          1.3.6.1.4.1.37950.1.1.5.12.2.1.3.1.1
-- 1.3.6.1.4.1.37950.1.1.5.12.2.1.3.1.1
-- 1.3.6.1.4.1.37950.1.1.5.12.2.1.3.1.1
-- 1.3.6.1.4.1.37950.1.1.5.12.2.1.3.1.1
-- 1.3.6.1.4.1.37950.1.1.5.12.2.1.3.1.1
-- 1.3.6.1.4.1.37950.1.1.5.12.2.1.3.1.1
-- 1.3.6.1.4.1.37950.1.1.5.12.2.1.3.1.1
-- 1.3.6.1.4.1.37950.1.1.5.12.2.1.3.1.1
-- 1.3.6.1.4.1.37950.1.1.5.12.2.1.3.1.1
		-- 1.3.6.1.4.1.37950.1.1.5.12.2.1.3.1.1
		fwVersionInfoPonIndex OBJECT-TYPE
			SYNTAX Integer32
			MAX-ACCESS read-only
			STATUS current
			DESCRIPTION
				"Description."
			::= { fwVersionInfoEntry 1 }

		
--          1.3.6.1.4.1.37950.1.1.5.12.2.1.3.1.2
-- 1.3.6.1.4.1.37950.1.1.5.12.2.1.3.1.2
-- 1.3.6.1.4.1.37950.1.1.5.12.2.1.3.1.2
-- 1.3.6.1.4.1.37950.1.1.5.12.2.1.3.1.2
-- 1.3.6.1.4.1.37950.1.1.5.12.2.1.3.1.2
-- 1.3.6.1.4.1.37950.1.1.5.12.2.1.3.1.2
-- 1.3.6.1.4.1.37950.1.1.5.12.2.1.3.1.2
-- 1.3.6.1.4.1.37950.1.1.5.12.2.1.3.1.2
-- 1.3.6.1.4.1.37950.1.1.5.12.2.1.3.1.2
		-- 1.3.6.1.4.1.37950.1.1.5.12.2.1.3.1.2
		fwVersionInfoOnuIndex OBJECT-TYPE
			SYNTAX Integer32
			MAX-ACCESS read-only
			STATUS current
			DESCRIPTION
				"Description."
			::= { fwVersionInfoEntry 2 }

		
--          1.3.6.1.4.1.37950.1.1.5.12.2.1.3.1.3
-- 1.3.6.1.4.1.37950.1.1.5.12.2.1.3.1.3
-- 1.3.6.1.4.1.37950.1.1.5.12.2.1.3.1.3
-- 1.3.6.1.4.1.37950.1.1.5.12.2.1.3.1.3
-- 1.3.6.1.4.1.37950.1.1.5.12.2.1.3.1.3
-- 1.3.6.1.4.1.37950.1.1.5.12.2.1.3.1.3
-- 1.3.6.1.4.1.37950.1.1.5.12.2.1.3.1.3
-- 1.3.6.1.4.1.37950.1.1.5.12.2.1.3.1.3
-- 1.3.6.1.4.1.37950.1.1.5.12.2.1.3.1.3
		-- 1.3.6.1.4.1.37950.1.1.5.12.2.1.3.1.3
		fwVersion OBJECT-TYPE
			SYNTAX OCTET STRING
			MAX-ACCESS read-only
			STATUS current
			DESCRIPTION
				"Description."
			::= { fwVersionInfoEntry 3 }

		
--          1.3.6.1.4.1.37950.1.1.5.12.2.1.4
-- 1.3.6.1.4.1.37950.1.1.5.12.2.1.4
-- 1.3.6.1.4.1.37950.1.1.5.12.2.1.4
-- 1.3.6.1.4.1.37950.1.1.5.12.2.1.4
-- 1.3.6.1.4.1.37950.1.1.5.12.2.1.4
-- 1.3.6.1.4.1.37950.1.1.5.12.2.1.4
-- 1.3.6.1.4.1.37950.1.1.5.12.2.1.4
-- 1.3.6.1.4.1.37950.1.1.5.12.2.1.4
-- 1.3.6.1.4.1.37950.1.1.5.12.2.1.4
		-- 1.3.6.1.4.1.37950.1.1.5.12.2.1.4
		chipIdInfoTable OBJECT-TYPE
			SYNTAX SEQUENCE OF ChipIdInfoEntry
			MAX-ACCESS not-accessible
			STATUS current
			DESCRIPTION
				"Description."
			::= { onuInfo 4 }

		
--          1.3.6.1.4.1.37950.1.1.5.12.2.1.4.1
-- 1.3.6.1.4.1.37950.1.1.5.12.2.1.4.1
-- 1.3.6.1.4.1.37950.1.1.5.12.2.1.4.1
-- 1.3.6.1.4.1.37950.1.1.5.12.2.1.4.1
-- 1.3.6.1.4.1.37950.1.1.5.12.2.1.4.1
-- 1.3.6.1.4.1.37950.1.1.5.12.2.1.4.1
-- 1.3.6.1.4.1.37950.1.1.5.12.2.1.4.1
-- 1.3.6.1.4.1.37950.1.1.5.12.2.1.4.1
-- 1.3.6.1.4.1.37950.1.1.5.12.2.1.4.1
		-- 1.3.6.1.4.1.37950.1.1.5.12.2.1.4.1
		chipIdInfoEntry OBJECT-TYPE
			SYNTAX ChipIdInfoEntry
			MAX-ACCESS not-accessible
			STATUS current
			DESCRIPTION
				"Description."
			INDEX { chipIdInfoPonIndex, chipIdInfoOnuIndex }
			::= { chipIdInfoTable 1 }

		
		ChipIdInfoEntry ::=
			SEQUENCE { 
				chipIdInfoPonIndex
					Integer32,
				chipIdInfoOnuIndex
					Integer32,
				verderId
					OCTET STRING,
				chipModel
					OCTET STRING,
				date
					OCTET STRING
			 }

--          1.3.6.1.4.1.37950.1.1.5.12.2.1.4.1.1
-- 1.3.6.1.4.1.37950.1.1.5.12.2.1.4.1.1
-- 1.3.6.1.4.1.37950.1.1.5.12.2.1.4.1.1
-- 1.3.6.1.4.1.37950.1.1.5.12.2.1.4.1.1
-- 1.3.6.1.4.1.37950.1.1.5.12.2.1.4.1.1
-- 1.3.6.1.4.1.37950.1.1.5.12.2.1.4.1.1
-- 1.3.6.1.4.1.37950.1.1.5.12.2.1.4.1.1
-- 1.3.6.1.4.1.37950.1.1.5.12.2.1.4.1.1
-- 1.3.6.1.4.1.37950.1.1.5.12.2.1.4.1.1
		-- 1.3.6.1.4.1.37950.1.1.5.12.2.1.4.1.1
		chipIdInfoPonIndex OBJECT-TYPE
			SYNTAX Integer32
			MAX-ACCESS read-only
			STATUS current
			DESCRIPTION
				"Description."
			::= { chipIdInfoEntry 1 }

		
--          1.3.6.1.4.1.37950.1.1.5.12.2.1.4.1.2
-- 1.3.6.1.4.1.37950.1.1.5.12.2.1.4.1.2
-- 1.3.6.1.4.1.37950.1.1.5.12.2.1.4.1.2
-- 1.3.6.1.4.1.37950.1.1.5.12.2.1.4.1.2
-- 1.3.6.1.4.1.37950.1.1.5.12.2.1.4.1.2
-- 1.3.6.1.4.1.37950.1.1.5.12.2.1.4.1.2
-- 1.3.6.1.4.1.37950.1.1.5.12.2.1.4.1.2
-- 1.3.6.1.4.1.37950.1.1.5.12.2.1.4.1.2
-- 1.3.6.1.4.1.37950.1.1.5.12.2.1.4.1.2
		-- 1.3.6.1.4.1.37950.1.1.5.12.2.1.4.1.2
		chipIdInfoOnuIndex OBJECT-TYPE
			SYNTAX Integer32
			MAX-ACCESS read-only
			STATUS current
			DESCRIPTION
				"Description."
			::= { chipIdInfoEntry 2 }

		
--          1.3.6.1.4.1.37950.1.1.5.12.2.1.4.1.3
-- 1.3.6.1.4.1.37950.1.1.5.12.2.1.4.1.3
-- 1.3.6.1.4.1.37950.1.1.5.12.2.1.4.1.3
-- 1.3.6.1.4.1.37950.1.1.5.12.2.1.4.1.3
-- 1.3.6.1.4.1.37950.1.1.5.12.2.1.4.1.3
-- 1.3.6.1.4.1.37950.1.1.5.12.2.1.4.1.3
-- 1.3.6.1.4.1.37950.1.1.5.12.2.1.4.1.3
-- 1.3.6.1.4.1.37950.1.1.5.12.2.1.4.1.3
-- 1.3.6.1.4.1.37950.1.1.5.12.2.1.4.1.3
		-- 1.3.6.1.4.1.37950.1.1.5.12.2.1.4.1.3
		verderId OBJECT-TYPE
			SYNTAX OCTET STRING
			MAX-ACCESS read-only
			STATUS current
			DESCRIPTION
				"Description."
			::= { chipIdInfoEntry 3 }

		
--          1.3.6.1.4.1.37950.1.1.5.12.2.1.4.1.4
-- 1.3.6.1.4.1.37950.1.1.5.12.2.1.4.1.4
-- 1.3.6.1.4.1.37950.1.1.5.12.2.1.4.1.4
-- 1.3.6.1.4.1.37950.1.1.5.12.2.1.4.1.4
-- 1.3.6.1.4.1.37950.1.1.5.12.2.1.4.1.4
-- 1.3.6.1.4.1.37950.1.1.5.12.2.1.4.1.4
-- 1.3.6.1.4.1.37950.1.1.5.12.2.1.4.1.4
-- 1.3.6.1.4.1.37950.1.1.5.12.2.1.4.1.4
-- 1.3.6.1.4.1.37950.1.1.5.12.2.1.4.1.4
		-- 1.3.6.1.4.1.37950.1.1.5.12.2.1.4.1.4
		chipModel OBJECT-TYPE
			SYNTAX OCTET STRING
			MAX-ACCESS read-only
			STATUS current
			DESCRIPTION
				"Description."
			::= { chipIdInfoEntry 4 }

		
--          1.3.6.1.4.1.37950.1.1.5.12.2.1.4.1.5
-- 1.3.6.1.4.1.37950.1.1.5.12.2.1.4.1.5
-- 1.3.6.1.4.1.37950.1.1.5.12.2.1.4.1.5
-- 1.3.6.1.4.1.37950.1.1.5.12.2.1.4.1.5
-- 1.3.6.1.4.1.37950.1.1.5.12.2.1.4.1.5
-- 1.3.6.1.4.1.37950.1.1.5.12.2.1.4.1.5
-- 1.3.6.1.4.1.37950.1.1.5.12.2.1.4.1.5
-- 1.3.6.1.4.1.37950.1.1.5.12.2.1.4.1.5
-- 1.3.6.1.4.1.37950.1.1.5.12.2.1.4.1.5
		-- 1.3.6.1.4.1.37950.1.1.5.12.2.1.4.1.5
		date OBJECT-TYPE
			SYNTAX OCTET STRING
			MAX-ACCESS read-only
			STATUS current
			DESCRIPTION
				"Description."
			::= { chipIdInfoEntry 5 }

		
--          1.3.6.1.4.1.37950.1.1.5.12.2.1.5
-- 1.3.6.1.4.1.37950.1.1.5.12.2.1.5
-- 1.3.6.1.4.1.37950.1.1.5.12.2.1.5
-- 1.3.6.1.4.1.37950.1.1.5.12.2.1.5
-- 1.3.6.1.4.1.37950.1.1.5.12.2.1.5
-- 1.3.6.1.4.1.37950.1.1.5.12.2.1.5
-- 1.3.6.1.4.1.37950.1.1.5.12.2.1.5
-- 1.3.6.1.4.1.37950.1.1.5.12.2.1.5
-- 1.3.6.1.4.1.37950.1.1.5.12.2.1.5
		-- 1.3.6.1.4.1.37950.1.1.5.12.2.1.5
		cap1InfoTable OBJECT-TYPE
			SYNTAX SEQUENCE OF Cap1InfoEntry
			MAX-ACCESS not-accessible
			STATUS current
			DESCRIPTION
				"Description."
			::= { onuInfo 5 }

		
--          1.3.6.1.4.1.37950.1.1.5.12.2.1.5.1
-- 1.3.6.1.4.1.37950.1.1.5.12.2.1.5.1
-- 1.3.6.1.4.1.37950.1.1.5.12.2.1.5.1
-- 1.3.6.1.4.1.37950.1.1.5.12.2.1.5.1
-- 1.3.6.1.4.1.37950.1.1.5.12.2.1.5.1
-- 1.3.6.1.4.1.37950.1.1.5.12.2.1.5.1
-- 1.3.6.1.4.1.37950.1.1.5.12.2.1.5.1
-- 1.3.6.1.4.1.37950.1.1.5.12.2.1.5.1
-- 1.3.6.1.4.1.37950.1.1.5.12.2.1.5.1
		-- 1.3.6.1.4.1.37950.1.1.5.12.2.1.5.1
		cap1InfoEntry OBJECT-TYPE
			SYNTAX Cap1InfoEntry
			MAX-ACCESS not-accessible
			STATUS current
			DESCRIPTION
				"Description."
			INDEX { cap1InfoPonIndex, cap1InfoOnuIndex }
			::= { cap1InfoTable 1 }

		
		Cap1InfoEntry ::=
			SEQUENCE { 
				cap1InfoPonIndex
					Integer32,
				cap1InfoOnuIndex
					Integer32,
				serviceSupported
					OCTET STRING,
				numGEPorts
					INTEGER,
				geBitMap
					OCTET STRING,
				numFEPorts
					INTEGER,
				feBitMap
					OCTET STRING,
				numPOTSPorts
					INTEGER,
				numE1Ports
					INTEGER,
				numUSQueues
					INTEGER,
				maxQueueUSPort
					INTEGER,
				numDSQueues
					INTEGER,
				maxQueueDSPort
					INTEGER,
				batteryBackup
					INTEGER
			 }

--          1.3.6.1.4.1.37950.1.1.5.12.2.1.5.1.1
-- 1.3.6.1.4.1.37950.1.1.5.12.2.1.5.1.1
-- 1.3.6.1.4.1.37950.1.1.5.12.2.1.5.1.1
-- 1.3.6.1.4.1.37950.1.1.5.12.2.1.5.1.1
-- 1.3.6.1.4.1.37950.1.1.5.12.2.1.5.1.1
-- 1.3.6.1.4.1.37950.1.1.5.12.2.1.5.1.1
-- 1.3.6.1.4.1.37950.1.1.5.12.2.1.5.1.1
-- 1.3.6.1.4.1.37950.1.1.5.12.2.1.5.1.1
-- 1.3.6.1.4.1.37950.1.1.5.12.2.1.5.1.1
		-- 1.3.6.1.4.1.37950.1.1.5.12.2.1.5.1.1
		cap1InfoPonIndex OBJECT-TYPE
			SYNTAX Integer32
			MAX-ACCESS read-only
			STATUS current
			DESCRIPTION
				"Description."
			::= { cap1InfoEntry 1 }

		
--          1.3.6.1.4.1.37950.1.1.5.12.2.1.5.1.2
-- 1.3.6.1.4.1.37950.1.1.5.12.2.1.5.1.2
-- 1.3.6.1.4.1.37950.1.1.5.12.2.1.5.1.2
-- 1.3.6.1.4.1.37950.1.1.5.12.2.1.5.1.2
-- 1.3.6.1.4.1.37950.1.1.5.12.2.1.5.1.2
-- 1.3.6.1.4.1.37950.1.1.5.12.2.1.5.1.2
-- 1.3.6.1.4.1.37950.1.1.5.12.2.1.5.1.2
-- 1.3.6.1.4.1.37950.1.1.5.12.2.1.5.1.2
-- 1.3.6.1.4.1.37950.1.1.5.12.2.1.5.1.2
		-- 1.3.6.1.4.1.37950.1.1.5.12.2.1.5.1.2
		cap1InfoOnuIndex OBJECT-TYPE
			SYNTAX Integer32
			MAX-ACCESS read-only
			STATUS current
			DESCRIPTION
				"Description."
			::= { cap1InfoEntry 2 }

		
--          1.3.6.1.4.1.37950.1.1.5.12.2.1.5.1.3
-- 1.3.6.1.4.1.37950.1.1.5.12.2.1.5.1.3
-- 1.3.6.1.4.1.37950.1.1.5.12.2.1.5.1.3
-- 1.3.6.1.4.1.37950.1.1.5.12.2.1.5.1.3
-- 1.3.6.1.4.1.37950.1.1.5.12.2.1.5.1.3
-- 1.3.6.1.4.1.37950.1.1.5.12.2.1.5.1.3
-- 1.3.6.1.4.1.37950.1.1.5.12.2.1.5.1.3
-- 1.3.6.1.4.1.37950.1.1.5.12.2.1.5.1.3
-- 1.3.6.1.4.1.37950.1.1.5.12.2.1.5.1.3
		-- 1.3.6.1.4.1.37950.1.1.5.12.2.1.5.1.3
		serviceSupported OBJECT-TYPE
			SYNTAX OCTET STRING
			MAX-ACCESS read-only
			STATUS current
			DESCRIPTION
				"Description."
			::= { cap1InfoEntry 3 }

		
--          1.3.6.1.4.1.37950.1.1.5.12.2.1.5.1.4
-- 1.3.6.1.4.1.37950.1.1.5.12.2.1.5.1.4
-- 1.3.6.1.4.1.37950.1.1.5.12.2.1.5.1.4
-- 1.3.6.1.4.1.37950.1.1.5.12.2.1.5.1.4
-- 1.3.6.1.4.1.37950.1.1.5.12.2.1.5.1.4
-- 1.3.6.1.4.1.37950.1.1.5.12.2.1.5.1.4
-- 1.3.6.1.4.1.37950.1.1.5.12.2.1.5.1.4
-- 1.3.6.1.4.1.37950.1.1.5.12.2.1.5.1.4
-- 1.3.6.1.4.1.37950.1.1.5.12.2.1.5.1.4
		-- 1.3.6.1.4.1.37950.1.1.5.12.2.1.5.1.4
		numGEPorts OBJECT-TYPE
			SYNTAX INTEGER
			MAX-ACCESS read-only
			STATUS current
			DESCRIPTION
				"Description."
			::= { cap1InfoEntry 4 }

		
--          1.3.6.1.4.1.37950.1.1.5.12.2.1.5.1.5
-- 1.3.6.1.4.1.37950.1.1.5.12.2.1.5.1.5
-- 1.3.6.1.4.1.37950.1.1.5.12.2.1.5.1.5
-- 1.3.6.1.4.1.37950.1.1.5.12.2.1.5.1.5
-- 1.3.6.1.4.1.37950.1.1.5.12.2.1.5.1.5
-- 1.3.6.1.4.1.37950.1.1.5.12.2.1.5.1.5
-- 1.3.6.1.4.1.37950.1.1.5.12.2.1.5.1.5
-- 1.3.6.1.4.1.37950.1.1.5.12.2.1.5.1.5
-- 1.3.6.1.4.1.37950.1.1.5.12.2.1.5.1.5
		-- 1.3.6.1.4.1.37950.1.1.5.12.2.1.5.1.5
		geBitMap OBJECT-TYPE
			SYNTAX OCTET STRING
			MAX-ACCESS read-only
			STATUS current
			DESCRIPTION
				"Description."
			::= { cap1InfoEntry 5 }

		
--          1.3.6.1.4.1.37950.1.1.5.12.2.1.5.1.6
-- 1.3.6.1.4.1.37950.1.1.5.12.2.1.5.1.6
-- 1.3.6.1.4.1.37950.1.1.5.12.2.1.5.1.6
-- 1.3.6.1.4.1.37950.1.1.5.12.2.1.5.1.6
-- 1.3.6.1.4.1.37950.1.1.5.12.2.1.5.1.6
-- 1.3.6.1.4.1.37950.1.1.5.12.2.1.5.1.6
-- 1.3.6.1.4.1.37950.1.1.5.12.2.1.5.1.6
-- 1.3.6.1.4.1.37950.1.1.5.12.2.1.5.1.6
-- 1.3.6.1.4.1.37950.1.1.5.12.2.1.5.1.6
		-- 1.3.6.1.4.1.37950.1.1.5.12.2.1.5.1.6
		numFEPorts OBJECT-TYPE
			SYNTAX INTEGER
			MAX-ACCESS read-only
			STATUS current
			DESCRIPTION
				"Description."
			::= { cap1InfoEntry 6 }

		
--          1.3.6.1.4.1.37950.1.1.5.12.2.1.5.1.7
-- 1.3.6.1.4.1.37950.1.1.5.12.2.1.5.1.7
-- 1.3.6.1.4.1.37950.1.1.5.12.2.1.5.1.7
-- 1.3.6.1.4.1.37950.1.1.5.12.2.1.5.1.7
-- 1.3.6.1.4.1.37950.1.1.5.12.2.1.5.1.7
-- 1.3.6.1.4.1.37950.1.1.5.12.2.1.5.1.7
-- 1.3.6.1.4.1.37950.1.1.5.12.2.1.5.1.7
-- 1.3.6.1.4.1.37950.1.1.5.12.2.1.5.1.7
-- 1.3.6.1.4.1.37950.1.1.5.12.2.1.5.1.7
		-- 1.3.6.1.4.1.37950.1.1.5.12.2.1.5.1.7
		feBitMap OBJECT-TYPE
			SYNTAX OCTET STRING
			MAX-ACCESS read-only
			STATUS current
			DESCRIPTION
				"Description."
			::= { cap1InfoEntry 7 }

		
--          1.3.6.1.4.1.37950.1.1.5.12.2.1.5.1.8
-- 1.3.6.1.4.1.37950.1.1.5.12.2.1.5.1.8
-- 1.3.6.1.4.1.37950.1.1.5.12.2.1.5.1.8
-- 1.3.6.1.4.1.37950.1.1.5.12.2.1.5.1.8
-- 1.3.6.1.4.1.37950.1.1.5.12.2.1.5.1.8
-- 1.3.6.1.4.1.37950.1.1.5.12.2.1.5.1.8
-- 1.3.6.1.4.1.37950.1.1.5.12.2.1.5.1.8
-- 1.3.6.1.4.1.37950.1.1.5.12.2.1.5.1.8
-- 1.3.6.1.4.1.37950.1.1.5.12.2.1.5.1.8
		-- 1.3.6.1.4.1.37950.1.1.5.12.2.1.5.1.8
		numPOTSPorts OBJECT-TYPE
			SYNTAX INTEGER
			MAX-ACCESS read-only
			STATUS current
			DESCRIPTION
				"Description."
			::= { cap1InfoEntry 8 }

		
--          1.3.6.1.4.1.37950.1.1.5.12.2.1.5.1.9
-- 1.3.6.1.4.1.37950.1.1.5.12.2.1.5.1.9
-- 1.3.6.1.4.1.37950.1.1.5.12.2.1.5.1.9
-- 1.3.6.1.4.1.37950.1.1.5.12.2.1.5.1.9
-- 1.3.6.1.4.1.37950.1.1.5.12.2.1.5.1.9
-- 1.3.6.1.4.1.37950.1.1.5.12.2.1.5.1.9
-- 1.3.6.1.4.1.37950.1.1.5.12.2.1.5.1.9
-- 1.3.6.1.4.1.37950.1.1.5.12.2.1.5.1.9
-- 1.3.6.1.4.1.37950.1.1.5.12.2.1.5.1.9
		-- 1.3.6.1.4.1.37950.1.1.5.12.2.1.5.1.9
		numE1Ports OBJECT-TYPE
			SYNTAX INTEGER
			MAX-ACCESS read-only
			STATUS current
			DESCRIPTION
				"Description."
			::= { cap1InfoEntry 9 }

		
--          1.3.6.1.4.1.37950.1.1.5.12.2.1.5.1.10
-- 1.3.6.1.4.1.37950.1.1.5.12.2.1.5.1.10
-- 1.3.6.1.4.1.37950.1.1.5.12.2.1.5.1.10
-- 1.3.6.1.4.1.37950.1.1.5.12.2.1.5.1.10
-- 1.3.6.1.4.1.37950.1.1.5.12.2.1.5.1.10
-- 1.3.6.1.4.1.37950.1.1.5.12.2.1.5.1.10
-- 1.3.6.1.4.1.37950.1.1.5.12.2.1.5.1.10
-- 1.3.6.1.4.1.37950.1.1.5.12.2.1.5.1.10
-- 1.3.6.1.4.1.37950.1.1.5.12.2.1.5.1.10
		-- 1.3.6.1.4.1.37950.1.1.5.12.2.1.5.1.10
		numUSQueues OBJECT-TYPE
			SYNTAX INTEGER
			MAX-ACCESS read-only
			STATUS current
			DESCRIPTION
				"Description."
			::= { cap1InfoEntry 10 }

		
--          1.3.6.1.4.1.37950.1.1.5.12.2.1.5.1.11
-- 1.3.6.1.4.1.37950.1.1.5.12.2.1.5.1.11
-- 1.3.6.1.4.1.37950.1.1.5.12.2.1.5.1.11
-- 1.3.6.1.4.1.37950.1.1.5.12.2.1.5.1.11
-- 1.3.6.1.4.1.37950.1.1.5.12.2.1.5.1.11
-- 1.3.6.1.4.1.37950.1.1.5.12.2.1.5.1.11
-- 1.3.6.1.4.1.37950.1.1.5.12.2.1.5.1.11
-- 1.3.6.1.4.1.37950.1.1.5.12.2.1.5.1.11
-- 1.3.6.1.4.1.37950.1.1.5.12.2.1.5.1.11
		-- 1.3.6.1.4.1.37950.1.1.5.12.2.1.5.1.11
		maxQueueUSPort OBJECT-TYPE
			SYNTAX INTEGER
			MAX-ACCESS read-only
			STATUS current
			DESCRIPTION
				"Description."
			::= { cap1InfoEntry 11 }

		
--          1.3.6.1.4.1.37950.1.1.5.12.2.1.5.1.12
-- 1.3.6.1.4.1.37950.1.1.5.12.2.1.5.1.12
-- 1.3.6.1.4.1.37950.1.1.5.12.2.1.5.1.12
-- 1.3.6.1.4.1.37950.1.1.5.12.2.1.5.1.12
-- 1.3.6.1.4.1.37950.1.1.5.12.2.1.5.1.12
-- 1.3.6.1.4.1.37950.1.1.5.12.2.1.5.1.12
-- 1.3.6.1.4.1.37950.1.1.5.12.2.1.5.1.12
-- 1.3.6.1.4.1.37950.1.1.5.12.2.1.5.1.12
-- 1.3.6.1.4.1.37950.1.1.5.12.2.1.5.1.12
		-- 1.3.6.1.4.1.37950.1.1.5.12.2.1.5.1.12
		numDSQueues OBJECT-TYPE
			SYNTAX INTEGER
			MAX-ACCESS read-only
			STATUS current
			DESCRIPTION
				"Description."
			::= { cap1InfoEntry 12 }

		
--          1.3.6.1.4.1.37950.1.1.5.12.2.1.5.1.13
-- 1.3.6.1.4.1.37950.1.1.5.12.2.1.5.1.13
-- 1.3.6.1.4.1.37950.1.1.5.12.2.1.5.1.13
-- 1.3.6.1.4.1.37950.1.1.5.12.2.1.5.1.13
-- 1.3.6.1.4.1.37950.1.1.5.12.2.1.5.1.13
-- 1.3.6.1.4.1.37950.1.1.5.12.2.1.5.1.13
-- 1.3.6.1.4.1.37950.1.1.5.12.2.1.5.1.13
-- 1.3.6.1.4.1.37950.1.1.5.12.2.1.5.1.13
-- 1.3.6.1.4.1.37950.1.1.5.12.2.1.5.1.13
		-- 1.3.6.1.4.1.37950.1.1.5.12.2.1.5.1.13
		maxQueueDSPort OBJECT-TYPE
			SYNTAX INTEGER
			MAX-ACCESS read-only
			STATUS current
			DESCRIPTION
				"Description."
			::= { cap1InfoEntry 13 }

		
--          1.3.6.1.4.1.37950.1.1.5.12.2.1.5.1.14
-- 1.3.6.1.4.1.37950.1.1.5.12.2.1.5.1.14
-- 1.3.6.1.4.1.37950.1.1.5.12.2.1.5.1.14
-- 1.3.6.1.4.1.37950.1.1.5.12.2.1.5.1.14
-- 1.3.6.1.4.1.37950.1.1.5.12.2.1.5.1.14
-- 1.3.6.1.4.1.37950.1.1.5.12.2.1.5.1.14
-- 1.3.6.1.4.1.37950.1.1.5.12.2.1.5.1.14
-- 1.3.6.1.4.1.37950.1.1.5.12.2.1.5.1.14
-- 1.3.6.1.4.1.37950.1.1.5.12.2.1.5.1.14
		-- 1.3.6.1.4.1.37950.1.1.5.12.2.1.5.1.14
		batteryBackup OBJECT-TYPE
			SYNTAX INTEGER
			MAX-ACCESS read-only
			STATUS current
			DESCRIPTION
				"Description."
			::= { cap1InfoEntry 14 }

		
--          1.3.6.1.4.1.37950.1.1.5.12.2.1.6
-- 1.3.6.1.4.1.37950.1.1.5.12.2.1.6
-- 1.3.6.1.4.1.37950.1.1.5.12.2.1.6
-- 1.3.6.1.4.1.37950.1.1.5.12.2.1.6
-- 1.3.6.1.4.1.37950.1.1.5.12.2.1.6
-- 1.3.6.1.4.1.37950.1.1.5.12.2.1.6
-- 1.3.6.1.4.1.37950.1.1.5.12.2.1.6
-- 1.3.6.1.4.1.37950.1.1.5.12.2.1.6
-- 1.3.6.1.4.1.37950.1.1.5.12.2.1.6
		-- 1.3.6.1.4.1.37950.1.1.5.12.2.1.6
		cap2InfoTable OBJECT-TYPE
			SYNTAX SEQUENCE OF Cap2InfoEntry
			MAX-ACCESS not-accessible
			STATUS current
			DESCRIPTION
				"Description."
			::= { onuInfo 6 }

		
--          1.3.6.1.4.1.37950.1.1.5.12.2.1.6.1
-- 1.3.6.1.4.1.37950.1.1.5.12.2.1.6.1
-- 1.3.6.1.4.1.37950.1.1.5.12.2.1.6.1
-- 1.3.6.1.4.1.37950.1.1.5.12.2.1.6.1
-- 1.3.6.1.4.1.37950.1.1.5.12.2.1.6.1
-- 1.3.6.1.4.1.37950.1.1.5.12.2.1.6.1
-- 1.3.6.1.4.1.37950.1.1.5.12.2.1.6.1
-- 1.3.6.1.4.1.37950.1.1.5.12.2.1.6.1
-- 1.3.6.1.4.1.37950.1.1.5.12.2.1.6.1
		-- 1.3.6.1.4.1.37950.1.1.5.12.2.1.6.1
		cap2InfoEntry OBJECT-TYPE
			SYNTAX Cap2InfoEntry
			MAX-ACCESS not-accessible
			STATUS current
			DESCRIPTION
				"Description."
			INDEX { cap2InfoPonIndex, cap2InfoOnuIndex }
			::= { cap2InfoTable 1 }

		
		Cap2InfoEntry ::=
			SEQUENCE { 
				cap2InfoPonIndex
					Integer32,
				cap2InfoOnuIndex
					Integer32,
				onuType
					OCTET STRING,
				multiLLID
					OCTET STRING,
				protectionType
					OCTET STRING,
				numPONIf
					INTEGER,
				numSlot
					INTEGER,
				numInterfaceType
					Integer32,
				interfaceTypePorts
					OCTET STRING,
				batBackup
					OCTET STRING
			 }

--          1.3.6.1.4.1.37950.1.1.5.12.2.1.6.1.1
-- 1.3.6.1.4.1.37950.1.1.5.12.2.1.6.1.1
-- 1.3.6.1.4.1.37950.1.1.5.12.2.1.6.1.1
-- 1.3.6.1.4.1.37950.1.1.5.12.2.1.6.1.1
-- 1.3.6.1.4.1.37950.1.1.5.12.2.1.6.1.1
-- 1.3.6.1.4.1.37950.1.1.5.12.2.1.6.1.1
-- 1.3.6.1.4.1.37950.1.1.5.12.2.1.6.1.1
-- 1.3.6.1.4.1.37950.1.1.5.12.2.1.6.1.1
-- 1.3.6.1.4.1.37950.1.1.5.12.2.1.6.1.1
		-- 1.3.6.1.4.1.37950.1.1.5.12.2.1.6.1.1
		cap2InfoPonIndex OBJECT-TYPE
			SYNTAX Integer32
			MAX-ACCESS read-only
			STATUS current
			DESCRIPTION
				"Description."
			::= { cap2InfoEntry 1 }

		
--          1.3.6.1.4.1.37950.1.1.5.12.2.1.6.1.2
-- 1.3.6.1.4.1.37950.1.1.5.12.2.1.6.1.2
-- 1.3.6.1.4.1.37950.1.1.5.12.2.1.6.1.2
-- 1.3.6.1.4.1.37950.1.1.5.12.2.1.6.1.2
-- 1.3.6.1.4.1.37950.1.1.5.12.2.1.6.1.2
-- 1.3.6.1.4.1.37950.1.1.5.12.2.1.6.1.2
-- 1.3.6.1.4.1.37950.1.1.5.12.2.1.6.1.2
-- 1.3.6.1.4.1.37950.1.1.5.12.2.1.6.1.2
-- 1.3.6.1.4.1.37950.1.1.5.12.2.1.6.1.2
		-- 1.3.6.1.4.1.37950.1.1.5.12.2.1.6.1.2
		cap2InfoOnuIndex OBJECT-TYPE
			SYNTAX Integer32
			MAX-ACCESS read-only
			STATUS current
			DESCRIPTION
				"Description."
			::= { cap2InfoEntry 2 }

		
--          1.3.6.1.4.1.37950.1.1.5.12.2.1.6.1.3
-- 1.3.6.1.4.1.37950.1.1.5.12.2.1.6.1.3
-- 1.3.6.1.4.1.37950.1.1.5.12.2.1.6.1.3
-- 1.3.6.1.4.1.37950.1.1.5.12.2.1.6.1.3
-- 1.3.6.1.4.1.37950.1.1.5.12.2.1.6.1.3
-- 1.3.6.1.4.1.37950.1.1.5.12.2.1.6.1.3
-- 1.3.6.1.4.1.37950.1.1.5.12.2.1.6.1.3
-- 1.3.6.1.4.1.37950.1.1.5.12.2.1.6.1.3
-- 1.3.6.1.4.1.37950.1.1.5.12.2.1.6.1.3
		-- 1.3.6.1.4.1.37950.1.1.5.12.2.1.6.1.3
		onuType OBJECT-TYPE
			SYNTAX OCTET STRING
			MAX-ACCESS read-only
			STATUS current
			DESCRIPTION
				"Description."
			::= { cap2InfoEntry 3 }

		
--          1.3.6.1.4.1.37950.1.1.5.12.2.1.6.1.4
-- 1.3.6.1.4.1.37950.1.1.5.12.2.1.6.1.4
-- 1.3.6.1.4.1.37950.1.1.5.12.2.1.6.1.4
-- 1.3.6.1.4.1.37950.1.1.5.12.2.1.6.1.4
-- 1.3.6.1.4.1.37950.1.1.5.12.2.1.6.1.4
-- 1.3.6.1.4.1.37950.1.1.5.12.2.1.6.1.4
-- 1.3.6.1.4.1.37950.1.1.5.12.2.1.6.1.4
-- 1.3.6.1.4.1.37950.1.1.5.12.2.1.6.1.4
-- 1.3.6.1.4.1.37950.1.1.5.12.2.1.6.1.4
		-- 1.3.6.1.4.1.37950.1.1.5.12.2.1.6.1.4
		multiLLID OBJECT-TYPE
			SYNTAX OCTET STRING
			MAX-ACCESS read-only
			STATUS current
			DESCRIPTION
				"Description."
			::= { cap2InfoEntry 4 }

		
--          1.3.6.1.4.1.37950.1.1.5.12.2.1.6.1.5
-- 1.3.6.1.4.1.37950.1.1.5.12.2.1.6.1.5
-- 1.3.6.1.4.1.37950.1.1.5.12.2.1.6.1.5
-- 1.3.6.1.4.1.37950.1.1.5.12.2.1.6.1.5
-- 1.3.6.1.4.1.37950.1.1.5.12.2.1.6.1.5
-- 1.3.6.1.4.1.37950.1.1.5.12.2.1.6.1.5
-- 1.3.6.1.4.1.37950.1.1.5.12.2.1.6.1.5
-- 1.3.6.1.4.1.37950.1.1.5.12.2.1.6.1.5
-- 1.3.6.1.4.1.37950.1.1.5.12.2.1.6.1.5
		-- 1.3.6.1.4.1.37950.1.1.5.12.2.1.6.1.5
		protectionType OBJECT-TYPE
			SYNTAX OCTET STRING
			MAX-ACCESS read-only
			STATUS current
			DESCRIPTION
				"Description."
			::= { cap2InfoEntry 5 }

		
--          1.3.6.1.4.1.37950.1.1.5.12.2.1.6.1.6
-- 1.3.6.1.4.1.37950.1.1.5.12.2.1.6.1.6
-- 1.3.6.1.4.1.37950.1.1.5.12.2.1.6.1.6
-- 1.3.6.1.4.1.37950.1.1.5.12.2.1.6.1.6
-- 1.3.6.1.4.1.37950.1.1.5.12.2.1.6.1.6
-- 1.3.6.1.4.1.37950.1.1.5.12.2.1.6.1.6
-- 1.3.6.1.4.1.37950.1.1.5.12.2.1.6.1.6
-- 1.3.6.1.4.1.37950.1.1.5.12.2.1.6.1.6
-- 1.3.6.1.4.1.37950.1.1.5.12.2.1.6.1.6
		-- 1.3.6.1.4.1.37950.1.1.5.12.2.1.6.1.6
		numPONIf OBJECT-TYPE
			SYNTAX INTEGER
			MAX-ACCESS read-only
			STATUS current
			DESCRIPTION
				"Description."
			::= { cap2InfoEntry 6 }

		
--          1.3.6.1.4.1.37950.1.1.5.12.2.1.6.1.7
-- 1.3.6.1.4.1.37950.1.1.5.12.2.1.6.1.7
-- 1.3.6.1.4.1.37950.1.1.5.12.2.1.6.1.7
-- 1.3.6.1.4.1.37950.1.1.5.12.2.1.6.1.7
-- 1.3.6.1.4.1.37950.1.1.5.12.2.1.6.1.7
-- 1.3.6.1.4.1.37950.1.1.5.12.2.1.6.1.7
-- 1.3.6.1.4.1.37950.1.1.5.12.2.1.6.1.7
-- 1.3.6.1.4.1.37950.1.1.5.12.2.1.6.1.7
-- 1.3.6.1.4.1.37950.1.1.5.12.2.1.6.1.7
		-- 1.3.6.1.4.1.37950.1.1.5.12.2.1.6.1.7
		numSlot OBJECT-TYPE
			SYNTAX INTEGER
			MAX-ACCESS read-only
			STATUS current
			DESCRIPTION
				"Description."
			::= { cap2InfoEntry 7 }

		
--          1.3.6.1.4.1.37950.1.1.5.12.2.1.6.1.8
-- 1.3.6.1.4.1.37950.1.1.5.12.2.1.6.1.8
-- 1.3.6.1.4.1.37950.1.1.5.12.2.1.6.1.8
-- 1.3.6.1.4.1.37950.1.1.5.12.2.1.6.1.8
-- 1.3.6.1.4.1.37950.1.1.5.12.2.1.6.1.8
-- 1.3.6.1.4.1.37950.1.1.5.12.2.1.6.1.8
-- 1.3.6.1.4.1.37950.1.1.5.12.2.1.6.1.8
-- 1.3.6.1.4.1.37950.1.1.5.12.2.1.6.1.8
-- 1.3.6.1.4.1.37950.1.1.5.12.2.1.6.1.8
		-- 1.3.6.1.4.1.37950.1.1.5.12.2.1.6.1.8
		numInterfaceType OBJECT-TYPE
			SYNTAX Integer32
			MAX-ACCESS read-only
			STATUS current
			DESCRIPTION
				"Description."
			::= { cap2InfoEntry 8 }

		
--          1.3.6.1.4.1.37950.1.1.5.12.2.1.6.1.9
-- 1.3.6.1.4.1.37950.1.1.5.12.2.1.6.1.9
-- 1.3.6.1.4.1.37950.1.1.5.12.2.1.6.1.9
-- 1.3.6.1.4.1.37950.1.1.5.12.2.1.6.1.9
-- 1.3.6.1.4.1.37950.1.1.5.12.2.1.6.1.9
-- 1.3.6.1.4.1.37950.1.1.5.12.2.1.6.1.9
-- 1.3.6.1.4.1.37950.1.1.5.12.2.1.6.1.9
-- 1.3.6.1.4.1.37950.1.1.5.12.2.1.6.1.9
-- 1.3.6.1.4.1.37950.1.1.5.12.2.1.6.1.9
		-- 1.3.6.1.4.1.37950.1.1.5.12.2.1.6.1.9
		interfaceTypePorts OBJECT-TYPE
			SYNTAX OCTET STRING
			MAX-ACCESS read-only
			STATUS current
			DESCRIPTION
				"Description."
			::= { cap2InfoEntry 9 }

		
--          1.3.6.1.4.1.37950.1.1.5.12.2.1.6.1.10
-- 1.3.6.1.4.1.37950.1.1.5.12.2.1.6.1.10
-- 1.3.6.1.4.1.37950.1.1.5.12.2.1.6.1.10
-- 1.3.6.1.4.1.37950.1.1.5.12.2.1.6.1.10
-- 1.3.6.1.4.1.37950.1.1.5.12.2.1.6.1.10
-- 1.3.6.1.4.1.37950.1.1.5.12.2.1.6.1.10
-- 1.3.6.1.4.1.37950.1.1.5.12.2.1.6.1.10
-- 1.3.6.1.4.1.37950.1.1.5.12.2.1.6.1.10
-- 1.3.6.1.4.1.37950.1.1.5.12.2.1.6.1.10
		-- 1.3.6.1.4.1.37950.1.1.5.12.2.1.6.1.10
		batBackup OBJECT-TYPE
			SYNTAX OCTET STRING
			MAX-ACCESS read-only
			STATUS current
			DESCRIPTION
				"Description."
			::= { cap2InfoEntry 10 }

		
--          1.3.6.1.4.1.37950.1.1.5.12.2.1.7
-- 1.3.6.1.4.1.37950.1.1.5.12.2.1.7
-- 1.3.6.1.4.1.37950.1.1.5.12.2.1.7
-- 1.3.6.1.4.1.37950.1.1.5.12.2.1.7
-- 1.3.6.1.4.1.37950.1.1.5.12.2.1.7
-- 1.3.6.1.4.1.37950.1.1.5.12.2.1.7
-- 1.3.6.1.4.1.37950.1.1.5.12.2.1.7
-- 1.3.6.1.4.1.37950.1.1.5.12.2.1.7
-- 1.3.6.1.4.1.37950.1.1.5.12.2.1.7
		-- 1.3.6.1.4.1.37950.1.1.5.12.2.1.7
		cap3InfoTable OBJECT-TYPE
			SYNTAX SEQUENCE OF Cap3InfoEntry
			MAX-ACCESS not-accessible
			STATUS current
			DESCRIPTION
				"Description."
			::= { onuInfo 7 }

		
--          1.3.6.1.4.1.37950.1.1.5.12.2.1.7.1
-- 1.3.6.1.4.1.37950.1.1.5.12.2.1.7.1
-- 1.3.6.1.4.1.37950.1.1.5.12.2.1.7.1
-- 1.3.6.1.4.1.37950.1.1.5.12.2.1.7.1
-- 1.3.6.1.4.1.37950.1.1.5.12.2.1.7.1
-- 1.3.6.1.4.1.37950.1.1.5.12.2.1.7.1
-- 1.3.6.1.4.1.37950.1.1.5.12.2.1.7.1
-- 1.3.6.1.4.1.37950.1.1.5.12.2.1.7.1
-- 1.3.6.1.4.1.37950.1.1.5.12.2.1.7.1
		-- 1.3.6.1.4.1.37950.1.1.5.12.2.1.7.1
		cap3InfoEntry OBJECT-TYPE
			SYNTAX Cap3InfoEntry
			MAX-ACCESS not-accessible
			STATUS current
			DESCRIPTION
				"Description."
			INDEX { cap3InfoPonIndex, cap3InfoOnuIndex }
			::= { cap3InfoTable 1 }

		
		Cap3InfoEntry ::=
			SEQUENCE { 
				cap3InfoPonIndex
					Integer32,
				cap3InfoOnuIndex
					Integer32,
				ipv6Support
					INTEGER,
				powerControl
					INTEGER
			 }

--          1.3.6.1.4.1.37950.1.1.5.12.2.1.7.1.1
-- 1.3.6.1.4.1.37950.1.1.5.12.2.1.7.1.1
-- 1.3.6.1.4.1.37950.1.1.5.12.2.1.7.1.1
-- 1.3.6.1.4.1.37950.1.1.5.12.2.1.7.1.1
-- 1.3.6.1.4.1.37950.1.1.5.12.2.1.7.1.1
-- 1.3.6.1.4.1.37950.1.1.5.12.2.1.7.1.1
-- 1.3.6.1.4.1.37950.1.1.5.12.2.1.7.1.1
-- 1.3.6.1.4.1.37950.1.1.5.12.2.1.7.1.1
-- 1.3.6.1.4.1.37950.1.1.5.12.2.1.7.1.1
		-- 1.3.6.1.4.1.37950.1.1.5.12.2.1.7.1.1
		cap3InfoPonIndex OBJECT-TYPE
			SYNTAX Integer32
			MAX-ACCESS read-only
			STATUS current
			DESCRIPTION
				"Description."
			::= { cap3InfoEntry 1 }

		
--          1.3.6.1.4.1.37950.1.1.5.12.2.1.7.1.2
-- 1.3.6.1.4.1.37950.1.1.5.12.2.1.7.1.2
-- 1.3.6.1.4.1.37950.1.1.5.12.2.1.7.1.2
-- 1.3.6.1.4.1.37950.1.1.5.12.2.1.7.1.2
-- 1.3.6.1.4.1.37950.1.1.5.12.2.1.7.1.2
-- 1.3.6.1.4.1.37950.1.1.5.12.2.1.7.1.2
-- 1.3.6.1.4.1.37950.1.1.5.12.2.1.7.1.2
-- 1.3.6.1.4.1.37950.1.1.5.12.2.1.7.1.2
-- 1.3.6.1.4.1.37950.1.1.5.12.2.1.7.1.2
		-- 1.3.6.1.4.1.37950.1.1.5.12.2.1.7.1.2
		cap3InfoOnuIndex OBJECT-TYPE
			SYNTAX Integer32
			MAX-ACCESS read-only
			STATUS current
			DESCRIPTION
				"Description."
			::= { cap3InfoEntry 2 }

		
--          1.3.6.1.4.1.37950.1.1.5.12.2.1.7.1.3
-- 1.3.6.1.4.1.37950.1.1.5.12.2.1.7.1.3
-- 1.3.6.1.4.1.37950.1.1.5.12.2.1.7.1.3
-- 1.3.6.1.4.1.37950.1.1.5.12.2.1.7.1.3
-- 1.3.6.1.4.1.37950.1.1.5.12.2.1.7.1.3
-- 1.3.6.1.4.1.37950.1.1.5.12.2.1.7.1.3
-- 1.3.6.1.4.1.37950.1.1.5.12.2.1.7.1.3
-- 1.3.6.1.4.1.37950.1.1.5.12.2.1.7.1.3
-- 1.3.6.1.4.1.37950.1.1.5.12.2.1.7.1.3
		-- 1.3.6.1.4.1.37950.1.1.5.12.2.1.7.1.3
		ipv6Support OBJECT-TYPE
			SYNTAX INTEGER
				{
				not-support(0),
				support(1)
				}
			MAX-ACCESS read-only
			STATUS current
			DESCRIPTION
				"Description."
			::= { cap3InfoEntry 3 }

		
--          1.3.6.1.4.1.37950.1.1.5.12.2.1.7.1.4
-- 1.3.6.1.4.1.37950.1.1.5.12.2.1.7.1.4
-- 1.3.6.1.4.1.37950.1.1.5.12.2.1.7.1.4
-- 1.3.6.1.4.1.37950.1.1.5.12.2.1.7.1.4
-- 1.3.6.1.4.1.37950.1.1.5.12.2.1.7.1.4
-- 1.3.6.1.4.1.37950.1.1.5.12.2.1.7.1.4
-- 1.3.6.1.4.1.37950.1.1.5.12.2.1.7.1.4
-- 1.3.6.1.4.1.37950.1.1.5.12.2.1.7.1.4
-- 1.3.6.1.4.1.37950.1.1.5.12.2.1.7.1.4
		-- 1.3.6.1.4.1.37950.1.1.5.12.2.1.7.1.4
		powerControl OBJECT-TYPE
			SYNTAX INTEGER
				{
				not-support(0),
				support-onu-tx(1),
				support-onu-tx-and-rx(2)
				}
			MAX-ACCESS read-only
			STATUS current
			DESCRIPTION
				"Description."
			::= { cap3InfoEntry 4 }

		
--          1.3.6.1.4.1.37950.1.1.5.12.2.1.8
-- 1.3.6.1.4.1.37950.1.1.5.12.2.1.8
-- 1.3.6.1.4.1.37950.1.1.5.12.2.1.8
-- 1.3.6.1.4.1.37950.1.1.5.12.2.1.8
-- 1.3.6.1.4.1.37950.1.1.5.12.2.1.8
-- 1.3.6.1.4.1.37950.1.1.5.12.2.1.8
-- 1.3.6.1.4.1.37950.1.1.5.12.2.1.8
-- 1.3.6.1.4.1.37950.1.1.5.12.2.1.8
-- 1.3.6.1.4.1.37950.1.1.5.12.2.1.8
		-- 1.3.6.1.4.1.37950.1.1.5.12.2.1.8
		opmDiagInfoTable OBJECT-TYPE
			SYNTAX SEQUENCE OF OpmDiagInfoEntry
			MAX-ACCESS not-accessible
			STATUS current
			DESCRIPTION
				"Description."
			::= { onuInfo 8 }

		
--          1.3.6.1.4.1.37950.1.1.5.12.2.1.8.1
-- 1.3.6.1.4.1.37950.1.1.5.12.2.1.8.1
-- 1.3.6.1.4.1.37950.1.1.5.12.2.1.8.1
-- 1.3.6.1.4.1.37950.1.1.5.12.2.1.8.1
-- 1.3.6.1.4.1.37950.1.1.5.12.2.1.8.1
-- 1.3.6.1.4.1.37950.1.1.5.12.2.1.8.1
-- 1.3.6.1.4.1.37950.1.1.5.12.2.1.8.1
-- 1.3.6.1.4.1.37950.1.1.5.12.2.1.8.1
-- 1.3.6.1.4.1.37950.1.1.5.12.2.1.8.1
		-- 1.3.6.1.4.1.37950.1.1.5.12.2.1.8.1
		opmDiagInfoEntry OBJECT-TYPE
			SYNTAX OpmDiagInfoEntry
			MAX-ACCESS not-accessible
			STATUS current
			DESCRIPTION
				"Description."
			INDEX { opmDiagInfoPonIndex, opmDiagInfoOnuIndex }
			::= { opmDiagInfoTable 1 }

		
		OpmDiagInfoEntry ::=
			SEQUENCE { 
				opmDiagInfoPonIndex
					Integer32,
				opmDiagInfoOnuIndex
					Integer32,
				temperature
					OCTET STRING,
				supplyVoltage
					OCTET STRING,
				txBias
					OCTET STRING,
				txPower
					OCTET STRING,
				rxPower
					OCTET STRING
			 }

--          1.3.6.1.4.1.37950.1.1.5.12.2.1.8.1.1
-- 1.3.6.1.4.1.37950.1.1.5.12.2.1.8.1.1
-- 1.3.6.1.4.1.37950.1.1.5.12.2.1.8.1.1
-- 1.3.6.1.4.1.37950.1.1.5.12.2.1.8.1.1
-- 1.3.6.1.4.1.37950.1.1.5.12.2.1.8.1.1
-- 1.3.6.1.4.1.37950.1.1.5.12.2.1.8.1.1
-- 1.3.6.1.4.1.37950.1.1.5.12.2.1.8.1.1
-- 1.3.6.1.4.1.37950.1.1.5.12.2.1.8.1.1
-- 1.3.6.1.4.1.37950.1.1.5.12.2.1.8.1.1
		-- 1.3.6.1.4.1.37950.1.1.5.12.2.1.8.1.1
		opmDiagInfoPonIndex OBJECT-TYPE
			SYNTAX Integer32
			MAX-ACCESS read-only
			STATUS current
			DESCRIPTION
				"Description."
			::= { opmDiagInfoEntry 1 }

		
--          1.3.6.1.4.1.37950.1.1.5.12.2.1.8.1.2
-- 1.3.6.1.4.1.37950.1.1.5.12.2.1.8.1.2
-- 1.3.6.1.4.1.37950.1.1.5.12.2.1.8.1.2
-- 1.3.6.1.4.1.37950.1.1.5.12.2.1.8.1.2
-- 1.3.6.1.4.1.37950.1.1.5.12.2.1.8.1.2
-- 1.3.6.1.4.1.37950.1.1.5.12.2.1.8.1.2
-- 1.3.6.1.4.1.37950.1.1.5.12.2.1.8.1.2
-- 1.3.6.1.4.1.37950.1.1.5.12.2.1.8.1.2
-- 1.3.6.1.4.1.37950.1.1.5.12.2.1.8.1.2
		-- 1.3.6.1.4.1.37950.1.1.5.12.2.1.8.1.2
		opmDiagInfoOnuIndex OBJECT-TYPE
			SYNTAX Integer32
			MAX-ACCESS read-only
			STATUS current
			DESCRIPTION
				"Description."
			::= { opmDiagInfoEntry 2 }

		
--          1.3.6.1.4.1.37950.1.1.5.12.2.1.8.1.3
-- 1.3.6.1.4.1.37950.1.1.5.12.2.1.8.1.3
-- 1.3.6.1.4.1.37950.1.1.5.12.2.1.8.1.3
-- 1.3.6.1.4.1.37950.1.1.5.12.2.1.8.1.3
-- 1.3.6.1.4.1.37950.1.1.5.12.2.1.8.1.3
-- 1.3.6.1.4.1.37950.1.1.5.12.2.1.8.1.3
-- 1.3.6.1.4.1.37950.1.1.5.12.2.1.8.1.3
-- 1.3.6.1.4.1.37950.1.1.5.12.2.1.8.1.3
-- 1.3.6.1.4.1.37950.1.1.5.12.2.1.8.1.3
		-- 1.3.6.1.4.1.37950.1.1.5.12.2.1.8.1.3
		temperature OBJECT-TYPE
			SYNTAX OCTET STRING
			MAX-ACCESS read-only
			STATUS current
			DESCRIPTION
				"Description."
			::= { opmDiagInfoEntry 3 }

		
--          1.3.6.1.4.1.37950.1.1.5.12.2.1.8.1.4
-- 1.3.6.1.4.1.37950.1.1.5.12.2.1.8.1.4
-- 1.3.6.1.4.1.37950.1.1.5.12.2.1.8.1.4
-- 1.3.6.1.4.1.37950.1.1.5.12.2.1.8.1.4
-- 1.3.6.1.4.1.37950.1.1.5.12.2.1.8.1.4
-- 1.3.6.1.4.1.37950.1.1.5.12.2.1.8.1.4
-- 1.3.6.1.4.1.37950.1.1.5.12.2.1.8.1.4
-- 1.3.6.1.4.1.37950.1.1.5.12.2.1.8.1.4
-- 1.3.6.1.4.1.37950.1.1.5.12.2.1.8.1.4
		-- 1.3.6.1.4.1.37950.1.1.5.12.2.1.8.1.4
		supplyVoltage OBJECT-TYPE
			SYNTAX OCTET STRING
			MAX-ACCESS read-only
			STATUS current
			DESCRIPTION
				"Description."
			::= { opmDiagInfoEntry 4 }

		
--          1.3.6.1.4.1.37950.1.1.5.12.2.1.8.1.5
-- 1.3.6.1.4.1.37950.1.1.5.12.2.1.8.1.5
-- 1.3.6.1.4.1.37950.1.1.5.12.2.1.8.1.5
-- 1.3.6.1.4.1.37950.1.1.5.12.2.1.8.1.5
-- 1.3.6.1.4.1.37950.1.1.5.12.2.1.8.1.5
-- 1.3.6.1.4.1.37950.1.1.5.12.2.1.8.1.5
-- 1.3.6.1.4.1.37950.1.1.5.12.2.1.8.1.5
-- 1.3.6.1.4.1.37950.1.1.5.12.2.1.8.1.5
-- 1.3.6.1.4.1.37950.1.1.5.12.2.1.8.1.5
		-- 1.3.6.1.4.1.37950.1.1.5.12.2.1.8.1.5
		txBias OBJECT-TYPE
			SYNTAX OCTET STRING
			MAX-ACCESS read-only
			STATUS current
			DESCRIPTION
				"Description."
			::= { opmDiagInfoEntry 5 }

		
--          1.3.6.1.4.1.37950.1.1.5.12.2.1.8.1.6
-- 1.3.6.1.4.1.37950.1.1.5.12.2.1.8.1.6
-- 1.3.6.1.4.1.37950.1.1.5.12.2.1.8.1.6
-- 1.3.6.1.4.1.37950.1.1.5.12.2.1.8.1.6
-- 1.3.6.1.4.1.37950.1.1.5.12.2.1.8.1.6
-- 1.3.6.1.4.1.37950.1.1.5.12.2.1.8.1.6
-- 1.3.6.1.4.1.37950.1.1.5.12.2.1.8.1.6
-- 1.3.6.1.4.1.37950.1.1.5.12.2.1.8.1.6
-- 1.3.6.1.4.1.37950.1.1.5.12.2.1.8.1.6
		-- 1.3.6.1.4.1.37950.1.1.5.12.2.1.8.1.6
		txPower OBJECT-TYPE
			SYNTAX OCTET STRING
			MAX-ACCESS read-only
			STATUS current
			DESCRIPTION
				"Description."
			::= { opmDiagInfoEntry 6 }

		
--          1.3.6.1.4.1.37950.1.1.5.12.2.1.8.1.7
-- 1.3.6.1.4.1.37950.1.1.5.12.2.1.8.1.7
-- 1.3.6.1.4.1.37950.1.1.5.12.2.1.8.1.7
-- 1.3.6.1.4.1.37950.1.1.5.12.2.1.8.1.7
-- 1.3.6.1.4.1.37950.1.1.5.12.2.1.8.1.7
-- 1.3.6.1.4.1.37950.1.1.5.12.2.1.8.1.7
-- 1.3.6.1.4.1.37950.1.1.5.12.2.1.8.1.7
-- 1.3.6.1.4.1.37950.1.1.5.12.2.1.8.1.7
-- 1.3.6.1.4.1.37950.1.1.5.12.2.1.8.1.7
		-- 1.3.6.1.4.1.37950.1.1.5.12.2.1.8.1.7
		rxPower OBJECT-TYPE
			SYNTAX OCTET STRING
			MAX-ACCESS read-only
			STATUS current
			DESCRIPTION
				"Description."
			::= { opmDiagInfoEntry 7 }

		
--          1.3.6.1.4.1.37950.1.1.5.12.2.1.9
-- 1.3.6.1.4.1.37950.1.1.5.12.2.1.9
-- 1.3.6.1.4.1.37950.1.1.5.12.2.1.9
-- 1.3.6.1.4.1.37950.1.1.5.12.2.1.9
-- 1.3.6.1.4.1.37950.1.1.5.12.2.1.9
-- 1.3.6.1.4.1.37950.1.1.5.12.2.1.9
-- 1.3.6.1.4.1.37950.1.1.5.12.2.1.9
-- 1.3.6.1.4.1.37950.1.1.5.12.2.1.9
-- 1.3.6.1.4.1.37950.1.1.5.12.2.1.9
		-- 1.3.6.1.4.1.37950.1.1.5.12.2.1.9
		fecAbilityTable OBJECT-TYPE
			SYNTAX SEQUENCE OF FecAbilityEntry
			MAX-ACCESS not-accessible
			STATUS current
			DESCRIPTION
				"Description."
			::= { onuInfo 9 }

		
--          1.3.6.1.4.1.37950.1.1.5.12.2.1.9.1
-- 1.3.6.1.4.1.37950.1.1.5.12.2.1.9.1
-- 1.3.6.1.4.1.37950.1.1.5.12.2.1.9.1
-- 1.3.6.1.4.1.37950.1.1.5.12.2.1.9.1
-- 1.3.6.1.4.1.37950.1.1.5.12.2.1.9.1
-- 1.3.6.1.4.1.37950.1.1.5.12.2.1.9.1
-- 1.3.6.1.4.1.37950.1.1.5.12.2.1.9.1
-- 1.3.6.1.4.1.37950.1.1.5.12.2.1.9.1
-- 1.3.6.1.4.1.37950.1.1.5.12.2.1.9.1
		-- 1.3.6.1.4.1.37950.1.1.5.12.2.1.9.1
		fecAbilityEntry OBJECT-TYPE
			SYNTAX FecAbilityEntry
			MAX-ACCESS not-accessible
			STATUS current
			DESCRIPTION
				"Description."
			INDEX { fecAbilityPonIndex, fecAbilityOnuIndex }
			::= { fecAbilityTable 1 }

		
		FecAbilityEntry ::=
			SEQUENCE { 
				fecAbilityPonIndex
					Integer32,
				fecAbilityOnuIndex
					Integer32,
				fecAbility
					OCTET STRING,
				fecMode
					INTEGER
			 }

--          1.3.6.1.4.1.37950.1.1.5.12.2.1.9.1.1
-- 1.3.6.1.4.1.37950.1.1.5.12.2.1.9.1.1
-- 1.3.6.1.4.1.37950.1.1.5.12.2.1.9.1.1
-- 1.3.6.1.4.1.37950.1.1.5.12.2.1.9.1.1
-- 1.3.6.1.4.1.37950.1.1.5.12.2.1.9.1.1
-- 1.3.6.1.4.1.37950.1.1.5.12.2.1.9.1.1
-- 1.3.6.1.4.1.37950.1.1.5.12.2.1.9.1.1
-- 1.3.6.1.4.1.37950.1.1.5.12.2.1.9.1.1
-- 1.3.6.1.4.1.37950.1.1.5.12.2.1.9.1.1
		-- 1.3.6.1.4.1.37950.1.1.5.12.2.1.9.1.1
		fecAbilityPonIndex OBJECT-TYPE
			SYNTAX Integer32
			MAX-ACCESS read-only
			STATUS current
			DESCRIPTION
				"Description."
			::= { fecAbilityEntry 1 }

		
--          1.3.6.1.4.1.37950.1.1.5.12.2.1.9.1.2
-- 1.3.6.1.4.1.37950.1.1.5.12.2.1.9.1.2
-- 1.3.6.1.4.1.37950.1.1.5.12.2.1.9.1.2
-- 1.3.6.1.4.1.37950.1.1.5.12.2.1.9.1.2
-- 1.3.6.1.4.1.37950.1.1.5.12.2.1.9.1.2
-- 1.3.6.1.4.1.37950.1.1.5.12.2.1.9.1.2
-- 1.3.6.1.4.1.37950.1.1.5.12.2.1.9.1.2
-- 1.3.6.1.4.1.37950.1.1.5.12.2.1.9.1.2
-- 1.3.6.1.4.1.37950.1.1.5.12.2.1.9.1.2
		-- 1.3.6.1.4.1.37950.1.1.5.12.2.1.9.1.2
		fecAbilityOnuIndex OBJECT-TYPE
			SYNTAX Integer32
			MAX-ACCESS read-only
			STATUS current
			DESCRIPTION
				"Description."
			::= { fecAbilityEntry 2 }

		
--          1.3.6.1.4.1.37950.1.1.5.12.2.1.9.1.3
-- 1.3.6.1.4.1.37950.1.1.5.12.2.1.9.1.3
-- 1.3.6.1.4.1.37950.1.1.5.12.2.1.9.1.3
-- 1.3.6.1.4.1.37950.1.1.5.12.2.1.9.1.3
-- 1.3.6.1.4.1.37950.1.1.5.12.2.1.9.1.3
-- 1.3.6.1.4.1.37950.1.1.5.12.2.1.9.1.3
-- 1.3.6.1.4.1.37950.1.1.5.12.2.1.9.1.3
-- 1.3.6.1.4.1.37950.1.1.5.12.2.1.9.1.3
-- 1.3.6.1.4.1.37950.1.1.5.12.2.1.9.1.3
		-- 1.3.6.1.4.1.37950.1.1.5.12.2.1.9.1.3
		fecAbility OBJECT-TYPE
			SYNTAX OCTET STRING
			MAX-ACCESS read-only
			STATUS current
			DESCRIPTION
				"Description."
			::= { fecAbilityEntry 3 }

		
--          1.3.6.1.4.1.37950.1.1.5.12.2.1.9.1.4
-- 1.3.6.1.4.1.37950.1.1.5.12.2.1.9.1.4
-- 1.3.6.1.4.1.37950.1.1.5.12.2.1.9.1.4
-- 1.3.6.1.4.1.37950.1.1.5.12.2.1.9.1.4
-- 1.3.6.1.4.1.37950.1.1.5.12.2.1.9.1.4
-- 1.3.6.1.4.1.37950.1.1.5.12.2.1.9.1.4
-- 1.3.6.1.4.1.37950.1.1.5.12.2.1.9.1.4
-- 1.3.6.1.4.1.37950.1.1.5.12.2.1.9.1.4
-- 1.3.6.1.4.1.37950.1.1.5.12.2.1.9.1.4
		-- 1.3.6.1.4.1.37950.1.1.5.12.2.1.9.1.4
		fecMode OBJECT-TYPE
			SYNTAX INTEGER
				{
				unknow(1),
				enable(2),
				disable(3)
				}
			MAX-ACCESS read-only
			STATUS current
			DESCRIPTION
				"Description."
			::= { fecAbilityEntry 4 }

		
--          1.3.6.1.4.1.37950.1.1.5.12.2.1.10
-- 1.3.6.1.4.1.37950.1.1.5.12.2.1.10
-- 1.3.6.1.4.1.37950.1.1.5.12.2.1.10
-- 1.3.6.1.4.1.37950.1.1.5.12.2.1.10
-- 1.3.6.1.4.1.37950.1.1.5.12.2.1.10
-- 1.3.6.1.4.1.37950.1.1.5.12.2.1.10
-- 1.3.6.1.4.1.37950.1.1.5.12.2.1.10
-- 1.3.6.1.4.1.37950.1.1.5.12.2.1.10
-- 1.3.6.1.4.1.37950.1.1.5.12.2.1.10
		-- 1.3.6.1.4.1.37950.1.1.5.12.2.1.10
		powerSavingCapTable OBJECT-TYPE
			SYNTAX SEQUENCE OF PowerSavingCapEntry
			MAX-ACCESS not-accessible
			STATUS current
			DESCRIPTION
				"Description."
			::= { onuInfo 10 }

		
--          1.3.6.1.4.1.37950.1.1.5.12.2.1.10.1
-- 1.3.6.1.4.1.37950.1.1.5.12.2.1.10.1
-- 1.3.6.1.4.1.37950.1.1.5.12.2.1.10.1
-- 1.3.6.1.4.1.37950.1.1.5.12.2.1.10.1
-- 1.3.6.1.4.1.37950.1.1.5.12.2.1.10.1
-- 1.3.6.1.4.1.37950.1.1.5.12.2.1.10.1
-- 1.3.6.1.4.1.37950.1.1.5.12.2.1.10.1
-- 1.3.6.1.4.1.37950.1.1.5.12.2.1.10.1
-- 1.3.6.1.4.1.37950.1.1.5.12.2.1.10.1
		-- 1.3.6.1.4.1.37950.1.1.5.12.2.1.10.1
		powerSavingCapEntry OBJECT-TYPE
			SYNTAX PowerSavingCapEntry
			MAX-ACCESS not-accessible
			STATUS current
			DESCRIPTION
				"Description."
			INDEX { powerSavingCapPonIndex, powerSavingCapOnuIndex }
			::= { powerSavingCapTable 1 }

		
		PowerSavingCapEntry ::=
			SEQUENCE { 
				powerSavingCapPonIndex
					Integer32,
				powerSavingCapOnuIndex
					Integer32,
				sleepmode
					OCTET STRING,
				earlywakeup
					OCTET STRING
			 }

--          1.3.6.1.4.1.37950.1.1.5.12.2.1.10.1.1
-- 1.3.6.1.4.1.37950.1.1.5.12.2.1.10.1.1
-- 1.3.6.1.4.1.37950.1.1.5.12.2.1.10.1.1
-- 1.3.6.1.4.1.37950.1.1.5.12.2.1.10.1.1
-- 1.3.6.1.4.1.37950.1.1.5.12.2.1.10.1.1
-- 1.3.6.1.4.1.37950.1.1.5.12.2.1.10.1.1
-- 1.3.6.1.4.1.37950.1.1.5.12.2.1.10.1.1
-- 1.3.6.1.4.1.37950.1.1.5.12.2.1.10.1.1
-- 1.3.6.1.4.1.37950.1.1.5.12.2.1.10.1.1
		-- 1.3.6.1.4.1.37950.1.1.5.12.2.1.10.1.1
		powerSavingCapPonIndex OBJECT-TYPE
			SYNTAX Integer32
			MAX-ACCESS read-only
			STATUS current
			DESCRIPTION
				"Description."
			::= { powerSavingCapEntry 1 }

		
--          1.3.6.1.4.1.37950.1.1.5.12.2.1.10.1.2
-- 1.3.6.1.4.1.37950.1.1.5.12.2.1.10.1.2
-- 1.3.6.1.4.1.37950.1.1.5.12.2.1.10.1.2
-- 1.3.6.1.4.1.37950.1.1.5.12.2.1.10.1.2
-- 1.3.6.1.4.1.37950.1.1.5.12.2.1.10.1.2
-- 1.3.6.1.4.1.37950.1.1.5.12.2.1.10.1.2
-- 1.3.6.1.4.1.37950.1.1.5.12.2.1.10.1.2
-- 1.3.6.1.4.1.37950.1.1.5.12.2.1.10.1.2
-- 1.3.6.1.4.1.37950.1.1.5.12.2.1.10.1.2
		-- 1.3.6.1.4.1.37950.1.1.5.12.2.1.10.1.2
		powerSavingCapOnuIndex OBJECT-TYPE
			SYNTAX Integer32
			MAX-ACCESS read-only
			STATUS current
			DESCRIPTION
				"Description."
			::= { powerSavingCapEntry 2 }

		
--          1.3.6.1.4.1.37950.1.1.5.12.2.1.10.1.3
-- 1.3.6.1.4.1.37950.1.1.5.12.2.1.10.1.3
-- 1.3.6.1.4.1.37950.1.1.5.12.2.1.10.1.3
-- 1.3.6.1.4.1.37950.1.1.5.12.2.1.10.1.3
-- 1.3.6.1.4.1.37950.1.1.5.12.2.1.10.1.3
-- 1.3.6.1.4.1.37950.1.1.5.12.2.1.10.1.3
-- 1.3.6.1.4.1.37950.1.1.5.12.2.1.10.1.3
-- 1.3.6.1.4.1.37950.1.1.5.12.2.1.10.1.3
-- 1.3.6.1.4.1.37950.1.1.5.12.2.1.10.1.3
		-- 1.3.6.1.4.1.37950.1.1.5.12.2.1.10.1.3
		sleepmode OBJECT-TYPE
			SYNTAX OCTET STRING
			MAX-ACCESS read-only
			STATUS current
			DESCRIPTION
				"Description."
			::= { powerSavingCapEntry 3 }

		
--          1.3.6.1.4.1.37950.1.1.5.12.2.1.10.1.4
-- 1.3.6.1.4.1.37950.1.1.5.12.2.1.10.1.4
-- 1.3.6.1.4.1.37950.1.1.5.12.2.1.10.1.4
-- 1.3.6.1.4.1.37950.1.1.5.12.2.1.10.1.4
-- 1.3.6.1.4.1.37950.1.1.5.12.2.1.10.1.4
-- 1.3.6.1.4.1.37950.1.1.5.12.2.1.10.1.4
-- 1.3.6.1.4.1.37950.1.1.5.12.2.1.10.1.4
-- 1.3.6.1.4.1.37950.1.1.5.12.2.1.10.1.4
-- 1.3.6.1.4.1.37950.1.1.5.12.2.1.10.1.4
		-- 1.3.6.1.4.1.37950.1.1.5.12.2.1.10.1.4
		earlywakeup OBJECT-TYPE
			SYNTAX OCTET STRING
			MAX-ACCESS read-only
			STATUS current
			DESCRIPTION
				"Description."
			::= { powerSavingCapEntry 4 }

		
--          1.3.6.1.4.1.37950.1.1.5.12.2.1.11
-- 1.3.6.1.4.1.37950.1.1.5.12.2.1.11
-- 1.3.6.1.4.1.37950.1.1.5.12.2.1.11
-- 1.3.6.1.4.1.37950.1.1.5.12.2.1.11
-- 1.3.6.1.4.1.37950.1.1.5.12.2.1.11
-- 1.3.6.1.4.1.37950.1.1.5.12.2.1.11
-- 1.3.6.1.4.1.37950.1.1.5.12.2.1.11
-- 1.3.6.1.4.1.37950.1.1.5.12.2.1.11
-- 1.3.6.1.4.1.37950.1.1.5.12.2.1.11
		-- 1.3.6.1.4.1.37950.1.1.5.12.2.1.11
		onuSnmpTable OBJECT-TYPE
			SYNTAX SEQUENCE OF OnuSnmpEntry
			MAX-ACCESS not-accessible
			STATUS current
			DESCRIPTION
				"Description."
			::= { onuInfo 11 }

		
--          1.3.6.1.4.1.37950.1.1.5.12.2.1.11.1
-- 1.3.6.1.4.1.37950.1.1.5.12.2.1.11.1
-- 1.3.6.1.4.1.37950.1.1.5.12.2.1.11.1
-- 1.3.6.1.4.1.37950.1.1.5.12.2.1.11.1
-- 1.3.6.1.4.1.37950.1.1.5.12.2.1.11.1
-- 1.3.6.1.4.1.37950.1.1.5.12.2.1.11.1
-- 1.3.6.1.4.1.37950.1.1.5.12.2.1.11.1
-- 1.3.6.1.4.1.37950.1.1.5.12.2.1.11.1
-- 1.3.6.1.4.1.37950.1.1.5.12.2.1.11.1
		-- 1.3.6.1.4.1.37950.1.1.5.12.2.1.11.1
		onuSnmpEntry OBJECT-TYPE
			SYNTAX OnuSnmpEntry
			MAX-ACCESS not-accessible
			STATUS current
			DESCRIPTION
				"Description."
			INDEX { snmpPonNo, snmpOnuNo }
			::= { onuSnmpTable 1 }

		
		OnuSnmpEntry ::=
			SEQUENCE { 
				snmpPonNo
					Integer32,
				snmpOnuNo
					Integer32,
				snmpVer
					INTEGER,
				snmpTrapIPaddr
					IpAddress,
				snmpTrapPort
					Integer32,
				snmpPort
					Integer32,
				snmpSecuritName
					OCTET STRING,
				snmpCommunityRead
					OCTET STRING,
				snmpCommunityWrite
					OCTET STRING
			 }

--          1.3.6.1.4.1.37950.1.1.5.12.2.1.11.1.1
-- 1.3.6.1.4.1.37950.1.1.5.12.2.1.11.1.1
-- 1.3.6.1.4.1.37950.1.1.5.12.2.1.11.1.1
-- 1.3.6.1.4.1.37950.1.1.5.12.2.1.11.1.1
-- 1.3.6.1.4.1.37950.1.1.5.12.2.1.11.1.1
-- 1.3.6.1.4.1.37950.1.1.5.12.2.1.11.1.1
-- 1.3.6.1.4.1.37950.1.1.5.12.2.1.11.1.1
-- 1.3.6.1.4.1.37950.1.1.5.12.2.1.11.1.1
-- 1.3.6.1.4.1.37950.1.1.5.12.2.1.11.1.1
		-- 1.3.6.1.4.1.37950.1.1.5.12.2.1.11.1.1
		snmpPonNo OBJECT-TYPE
			SYNTAX Integer32
			MAX-ACCESS read-only
			STATUS current
			DESCRIPTION
				"Description."
			::= { onuSnmpEntry 1 }

		
--          1.3.6.1.4.1.37950.1.1.5.12.2.1.11.1.2
-- 1.3.6.1.4.1.37950.1.1.5.12.2.1.11.1.2
-- 1.3.6.1.4.1.37950.1.1.5.12.2.1.11.1.2
-- 1.3.6.1.4.1.37950.1.1.5.12.2.1.11.1.2
-- 1.3.6.1.4.1.37950.1.1.5.12.2.1.11.1.2
-- 1.3.6.1.4.1.37950.1.1.5.12.2.1.11.1.2
-- 1.3.6.1.4.1.37950.1.1.5.12.2.1.11.1.2
-- 1.3.6.1.4.1.37950.1.1.5.12.2.1.11.1.2
-- 1.3.6.1.4.1.37950.1.1.5.12.2.1.11.1.2
		-- 1.3.6.1.4.1.37950.1.1.5.12.2.1.11.1.2
		snmpOnuNo OBJECT-TYPE
			SYNTAX Integer32
			MAX-ACCESS read-only
			STATUS current
			DESCRIPTION
				"Description."
			::= { onuSnmpEntry 2 }

		
--          1.3.6.1.4.1.37950.1.1.5.12.2.1.11.1.3
-- 1.3.6.1.4.1.37950.1.1.5.12.2.1.11.1.3
-- 1.3.6.1.4.1.37950.1.1.5.12.2.1.11.1.3
-- 1.3.6.1.4.1.37950.1.1.5.12.2.1.11.1.3
-- 1.3.6.1.4.1.37950.1.1.5.12.2.1.11.1.3
-- 1.3.6.1.4.1.37950.1.1.5.12.2.1.11.1.3
-- 1.3.6.1.4.1.37950.1.1.5.12.2.1.11.1.3
-- 1.3.6.1.4.1.37950.1.1.5.12.2.1.11.1.3
-- 1.3.6.1.4.1.37950.1.1.5.12.2.1.11.1.3
		-- 1.3.6.1.4.1.37950.1.1.5.12.2.1.11.1.3
		snmpVer OBJECT-TYPE
			SYNTAX INTEGER
				{
				snmp-v1(1),
				snmp-v2(2),
				snmp-v3(3)
				}
			MAX-ACCESS read-only
			STATUS current
			DESCRIPTION
				"Description."
			::= { onuSnmpEntry 3 }

		
--          1.3.6.1.4.1.37950.1.1.5.12.2.1.11.1.4
-- 1.3.6.1.4.1.37950.1.1.5.12.2.1.11.1.4
-- 1.3.6.1.4.1.37950.1.1.5.12.2.1.11.1.4
-- 1.3.6.1.4.1.37950.1.1.5.12.2.1.11.1.4
-- 1.3.6.1.4.1.37950.1.1.5.12.2.1.11.1.4
-- 1.3.6.1.4.1.37950.1.1.5.12.2.1.11.1.4
-- 1.3.6.1.4.1.37950.1.1.5.12.2.1.11.1.4
-- 1.3.6.1.4.1.37950.1.1.5.12.2.1.11.1.4
-- 1.3.6.1.4.1.37950.1.1.5.12.2.1.11.1.4
		-- 1.3.6.1.4.1.37950.1.1.5.12.2.1.11.1.4
		snmpTrapIPaddr OBJECT-TYPE
			SYNTAX IpAddress
			MAX-ACCESS read-only
			STATUS current
			DESCRIPTION
				"Description."
			::= { onuSnmpEntry 4 }

		
--          1.3.6.1.4.1.37950.1.1.5.12.2.1.11.1.5
-- 1.3.6.1.4.1.37950.1.1.5.12.2.1.11.1.5
-- 1.3.6.1.4.1.37950.1.1.5.12.2.1.11.1.5
-- 1.3.6.1.4.1.37950.1.1.5.12.2.1.11.1.5
-- 1.3.6.1.4.1.37950.1.1.5.12.2.1.11.1.5
-- 1.3.6.1.4.1.37950.1.1.5.12.2.1.11.1.5
-- 1.3.6.1.4.1.37950.1.1.5.12.2.1.11.1.5
-- 1.3.6.1.4.1.37950.1.1.5.12.2.1.11.1.5
-- 1.3.6.1.4.1.37950.1.1.5.12.2.1.11.1.5
		-- 1.3.6.1.4.1.37950.1.1.5.12.2.1.11.1.5
		snmpTrapPort OBJECT-TYPE
			SYNTAX Integer32
			MAX-ACCESS read-only
			STATUS current
			DESCRIPTION
				"Description."
			::= { onuSnmpEntry 5 }

		
--          1.3.6.1.4.1.37950.1.1.5.12.2.1.11.1.6
-- 1.3.6.1.4.1.37950.1.1.5.12.2.1.11.1.6
-- 1.3.6.1.4.1.37950.1.1.5.12.2.1.11.1.6
-- 1.3.6.1.4.1.37950.1.1.5.12.2.1.11.1.6
-- 1.3.6.1.4.1.37950.1.1.5.12.2.1.11.1.6
-- 1.3.6.1.4.1.37950.1.1.5.12.2.1.11.1.6
-- 1.3.6.1.4.1.37950.1.1.5.12.2.1.11.1.6
-- 1.3.6.1.4.1.37950.1.1.5.12.2.1.11.1.6
-- 1.3.6.1.4.1.37950.1.1.5.12.2.1.11.1.6
		-- 1.3.6.1.4.1.37950.1.1.5.12.2.1.11.1.6
		snmpPort OBJECT-TYPE
			SYNTAX Integer32
			MAX-ACCESS read-only
			STATUS current
			DESCRIPTION
				"Description."
			::= { onuSnmpEntry 6 }

		
--          1.3.6.1.4.1.37950.1.1.5.12.2.1.11.1.7
-- 1.3.6.1.4.1.37950.1.1.5.12.2.1.11.1.7
-- 1.3.6.1.4.1.37950.1.1.5.12.2.1.11.1.7
-- 1.3.6.1.4.1.37950.1.1.5.12.2.1.11.1.7
-- 1.3.6.1.4.1.37950.1.1.5.12.2.1.11.1.7
-- 1.3.6.1.4.1.37950.1.1.5.12.2.1.11.1.7
-- 1.3.6.1.4.1.37950.1.1.5.12.2.1.11.1.7
-- 1.3.6.1.4.1.37950.1.1.5.12.2.1.11.1.7
-- 1.3.6.1.4.1.37950.1.1.5.12.2.1.11.1.7
		-- 1.3.6.1.4.1.37950.1.1.5.12.2.1.11.1.7
		snmpSecuritName OBJECT-TYPE
			SYNTAX OCTET STRING
			MAX-ACCESS read-only
			STATUS current
			DESCRIPTION
				"Description."
			::= { onuSnmpEntry 7 }

		
--          1.3.6.1.4.1.37950.1.1.5.12.2.1.11.1.8
-- 1.3.6.1.4.1.37950.1.1.5.12.2.1.11.1.8
-- 1.3.6.1.4.1.37950.1.1.5.12.2.1.11.1.8
-- 1.3.6.1.4.1.37950.1.1.5.12.2.1.11.1.8
-- 1.3.6.1.4.1.37950.1.1.5.12.2.1.11.1.8
-- 1.3.6.1.4.1.37950.1.1.5.12.2.1.11.1.8
-- 1.3.6.1.4.1.37950.1.1.5.12.2.1.11.1.8
-- 1.3.6.1.4.1.37950.1.1.5.12.2.1.11.1.8
-- 1.3.6.1.4.1.37950.1.1.5.12.2.1.11.1.8
		-- 1.3.6.1.4.1.37950.1.1.5.12.2.1.11.1.8
		snmpCommunityRead OBJECT-TYPE
			SYNTAX OCTET STRING
			MAX-ACCESS read-only
			STATUS current
			DESCRIPTION
				"Description."
			::= { onuSnmpEntry 8 }

		
--          1.3.6.1.4.1.37950.1.1.5.12.2.1.11.1.9
-- 1.3.6.1.4.1.37950.1.1.5.12.2.1.11.1.9
-- 1.3.6.1.4.1.37950.1.1.5.12.2.1.11.1.9
-- 1.3.6.1.4.1.37950.1.1.5.12.2.1.11.1.9
-- 1.3.6.1.4.1.37950.1.1.5.12.2.1.11.1.9
-- 1.3.6.1.4.1.37950.1.1.5.12.2.1.11.1.9
-- 1.3.6.1.4.1.37950.1.1.5.12.2.1.11.1.9
-- 1.3.6.1.4.1.37950.1.1.5.12.2.1.11.1.9
-- 1.3.6.1.4.1.37950.1.1.5.12.2.1.11.1.9
		-- 1.3.6.1.4.1.37950.1.1.5.12.2.1.11.1.9
		snmpCommunityWrite OBJECT-TYPE
			SYNTAX OCTET STRING
			MAX-ACCESS read-only
			STATUS current
			DESCRIPTION
				"Description."
			::= { onuSnmpEntry 9 }

		
--          1.3.6.1.4.1.37950.1.1.5.12.2.1.12
-- 1.3.6.1.4.1.37950.1.1.5.12.2.1.12
-- 1.3.6.1.4.1.37950.1.1.5.12.2.1.12
-- 1.3.6.1.4.1.37950.1.1.5.12.2.1.12
-- 1.3.6.1.4.1.37950.1.1.5.12.2.1.12
-- 1.3.6.1.4.1.37950.1.1.5.12.2.1.12
-- 1.3.6.1.4.1.37950.1.1.5.12.2.1.12
-- 1.3.6.1.4.1.37950.1.1.5.12.2.1.12
-- 1.3.6.1.4.1.37950.1.1.5.12.2.1.12
		-- 1.3.6.1.4.1.37950.1.1.5.12.2.1.12
		onuSlaTable OBJECT-TYPE
			SYNTAX SEQUENCE OF OnuSlaEntry
			MAX-ACCESS not-accessible
			STATUS current
			DESCRIPTION
				"Description."
			::= { onuInfo 12 }

		
--          1.3.6.1.4.1.37950.1.1.5.12.2.1.12.1
-- 1.3.6.1.4.1.37950.1.1.5.12.2.1.12.1
-- 1.3.6.1.4.1.37950.1.1.5.12.2.1.12.1
-- 1.3.6.1.4.1.37950.1.1.5.12.2.1.12.1
-- 1.3.6.1.4.1.37950.1.1.5.12.2.1.12.1
-- 1.3.6.1.4.1.37950.1.1.5.12.2.1.12.1
-- 1.3.6.1.4.1.37950.1.1.5.12.2.1.12.1
-- 1.3.6.1.4.1.37950.1.1.5.12.2.1.12.1
-- 1.3.6.1.4.1.37950.1.1.5.12.2.1.12.1
		-- 1.3.6.1.4.1.37950.1.1.5.12.2.1.12.1
		onuSlaEntry OBJECT-TYPE
			SYNTAX OnuSlaEntry
			MAX-ACCESS not-accessible
			STATUS current
			DESCRIPTION
				"Description."
			INDEX { slaPonNo, slaOnuNo }
			::= { onuSlaTable 1 }

		
		OnuSlaEntry ::=
			SEQUENCE { 
				slaPonNo
					Integer32,
				slaOnuNo
					Integer32,
				slaOperActive
					INTEGER,
				slaScheduleScheme
					INTEGER,
				slaHPriorityBoundary
					INTEGER,
				slaCycleLen
					INTEGER,
				slaNumService
					INTEGER,
				slaQueIdStr
					OCTET STRING,
				slaFixPacketSizeStr
					OCTET STRING,
				slaFixBandwidthStr
					OCTET STRING,
				slaGuarantBwStr
					OCTET STRING,
				slaBestEffortBWStr
					OCTET STRING,
				slaWrrWeightStr
					OCTET STRING
			 }

--          1.3.6.1.4.1.37950.1.1.5.12.2.1.12.1.1
-- 1.3.6.1.4.1.37950.1.1.5.12.2.1.12.1.1
-- 1.3.6.1.4.1.37950.1.1.5.12.2.1.12.1.1
-- 1.3.6.1.4.1.37950.1.1.5.12.2.1.12.1.1
-- 1.3.6.1.4.1.37950.1.1.5.12.2.1.12.1.1
-- 1.3.6.1.4.1.37950.1.1.5.12.2.1.12.1.1
-- 1.3.6.1.4.1.37950.1.1.5.12.2.1.12.1.1
-- 1.3.6.1.4.1.37950.1.1.5.12.2.1.12.1.1
-- 1.3.6.1.4.1.37950.1.1.5.12.2.1.12.1.1
		-- 1.3.6.1.4.1.37950.1.1.5.12.2.1.12.1.1
		slaPonNo OBJECT-TYPE
			SYNTAX Integer32
			MAX-ACCESS read-only
			STATUS current
			DESCRIPTION
				"Description."
			::= { onuSlaEntry 1 }

		
--          1.3.6.1.4.1.37950.1.1.5.12.2.1.12.1.2
-- 1.3.6.1.4.1.37950.1.1.5.12.2.1.12.1.2
-- 1.3.6.1.4.1.37950.1.1.5.12.2.1.12.1.2
-- 1.3.6.1.4.1.37950.1.1.5.12.2.1.12.1.2
-- 1.3.6.1.4.1.37950.1.1.5.12.2.1.12.1.2
-- 1.3.6.1.4.1.37950.1.1.5.12.2.1.12.1.2
-- 1.3.6.1.4.1.37950.1.1.5.12.2.1.12.1.2
-- 1.3.6.1.4.1.37950.1.1.5.12.2.1.12.1.2
-- 1.3.6.1.4.1.37950.1.1.5.12.2.1.12.1.2
		-- 1.3.6.1.4.1.37950.1.1.5.12.2.1.12.1.2
		slaOnuNo OBJECT-TYPE
			SYNTAX Integer32
			MAX-ACCESS read-only
			STATUS current
			DESCRIPTION
				"Description."
			::= { onuSlaEntry 2 }

		
--          1.3.6.1.4.1.37950.1.1.5.12.2.1.12.1.3
-- 1.3.6.1.4.1.37950.1.1.5.12.2.1.12.1.3
-- 1.3.6.1.4.1.37950.1.1.5.12.2.1.12.1.3
-- 1.3.6.1.4.1.37950.1.1.5.12.2.1.12.1.3
-- 1.3.6.1.4.1.37950.1.1.5.12.2.1.12.1.3
-- 1.3.6.1.4.1.37950.1.1.5.12.2.1.12.1.3
-- 1.3.6.1.4.1.37950.1.1.5.12.2.1.12.1.3
-- 1.3.6.1.4.1.37950.1.1.5.12.2.1.12.1.3
-- 1.3.6.1.4.1.37950.1.1.5.12.2.1.12.1.3
		-- 1.3.6.1.4.1.37950.1.1.5.12.2.1.12.1.3
		slaOperActive OBJECT-TYPE
			SYNTAX INTEGER
				{
				deactivate(0),
				active(1)
				}
			MAX-ACCESS read-only
			STATUS current
			DESCRIPTION
				"Description."
			::= { onuSlaEntry 3 }

		
--          1.3.6.1.4.1.37950.1.1.5.12.2.1.12.1.4
-- 1.3.6.1.4.1.37950.1.1.5.12.2.1.12.1.4
-- 1.3.6.1.4.1.37950.1.1.5.12.2.1.12.1.4
-- 1.3.6.1.4.1.37950.1.1.5.12.2.1.12.1.4
-- 1.3.6.1.4.1.37950.1.1.5.12.2.1.12.1.4
-- 1.3.6.1.4.1.37950.1.1.5.12.2.1.12.1.4
-- 1.3.6.1.4.1.37950.1.1.5.12.2.1.12.1.4
-- 1.3.6.1.4.1.37950.1.1.5.12.2.1.12.1.4
-- 1.3.6.1.4.1.37950.1.1.5.12.2.1.12.1.4
		-- 1.3.6.1.4.1.37950.1.1.5.12.2.1.12.1.4
		slaScheduleScheme OBJECT-TYPE
			SYNTAX INTEGER
				{
				sp(0),
				wrr(1),
				sp-wrr(2)
				}
			MAX-ACCESS read-only
			STATUS current
			DESCRIPTION
				"Description."
			::= { onuSlaEntry 4 }

		
--          1.3.6.1.4.1.37950.1.1.5.12.2.1.12.1.5
-- 1.3.6.1.4.1.37950.1.1.5.12.2.1.12.1.5
-- 1.3.6.1.4.1.37950.1.1.5.12.2.1.12.1.5
-- 1.3.6.1.4.1.37950.1.1.5.12.2.1.12.1.5
-- 1.3.6.1.4.1.37950.1.1.5.12.2.1.12.1.5
-- 1.3.6.1.4.1.37950.1.1.5.12.2.1.12.1.5
-- 1.3.6.1.4.1.37950.1.1.5.12.2.1.12.1.5
-- 1.3.6.1.4.1.37950.1.1.5.12.2.1.12.1.5
-- 1.3.6.1.4.1.37950.1.1.5.12.2.1.12.1.5
		-- 1.3.6.1.4.1.37950.1.1.5.12.2.1.12.1.5
		slaHPriorityBoundary OBJECT-TYPE
			SYNTAX INTEGER
			MAX-ACCESS read-only
			STATUS current
			DESCRIPTION
				"Description."
			::= { onuSlaEntry 5 }

		
--          1.3.6.1.4.1.37950.1.1.5.12.2.1.12.1.6
-- 1.3.6.1.4.1.37950.1.1.5.12.2.1.12.1.6
-- 1.3.6.1.4.1.37950.1.1.5.12.2.1.12.1.6
-- 1.3.6.1.4.1.37950.1.1.5.12.2.1.12.1.6
-- 1.3.6.1.4.1.37950.1.1.5.12.2.1.12.1.6
-- 1.3.6.1.4.1.37950.1.1.5.12.2.1.12.1.6
-- 1.3.6.1.4.1.37950.1.1.5.12.2.1.12.1.6
-- 1.3.6.1.4.1.37950.1.1.5.12.2.1.12.1.6
-- 1.3.6.1.4.1.37950.1.1.5.12.2.1.12.1.6
		-- 1.3.6.1.4.1.37950.1.1.5.12.2.1.12.1.6
		slaCycleLen OBJECT-TYPE
			SYNTAX INTEGER
			MAX-ACCESS read-only
			STATUS current
			DESCRIPTION
				"Description."
			::= { onuSlaEntry 6 }

		
--          1.3.6.1.4.1.37950.1.1.5.12.2.1.12.1.7
-- 1.3.6.1.4.1.37950.1.1.5.12.2.1.12.1.7
-- 1.3.6.1.4.1.37950.1.1.5.12.2.1.12.1.7
-- 1.3.6.1.4.1.37950.1.1.5.12.2.1.12.1.7
-- 1.3.6.1.4.1.37950.1.1.5.12.2.1.12.1.7
-- 1.3.6.1.4.1.37950.1.1.5.12.2.1.12.1.7
-- 1.3.6.1.4.1.37950.1.1.5.12.2.1.12.1.7
-- 1.3.6.1.4.1.37950.1.1.5.12.2.1.12.1.7
-- 1.3.6.1.4.1.37950.1.1.5.12.2.1.12.1.7
		-- 1.3.6.1.4.1.37950.1.1.5.12.2.1.12.1.7
		slaNumService OBJECT-TYPE
			SYNTAX INTEGER
			MAX-ACCESS read-only
			STATUS current
			DESCRIPTION
				"Description."
			::= { onuSlaEntry 7 }

		
--          1.3.6.1.4.1.37950.1.1.5.12.2.1.12.1.8
-- 1.3.6.1.4.1.37950.1.1.5.12.2.1.12.1.8
-- 1.3.6.1.4.1.37950.1.1.5.12.2.1.12.1.8
-- 1.3.6.1.4.1.37950.1.1.5.12.2.1.12.1.8
-- 1.3.6.1.4.1.37950.1.1.5.12.2.1.12.1.8
-- 1.3.6.1.4.1.37950.1.1.5.12.2.1.12.1.8
-- 1.3.6.1.4.1.37950.1.1.5.12.2.1.12.1.8
-- 1.3.6.1.4.1.37950.1.1.5.12.2.1.12.1.8
-- 1.3.6.1.4.1.37950.1.1.5.12.2.1.12.1.8
		-- 1.3.6.1.4.1.37950.1.1.5.12.2.1.12.1.8
		slaQueIdStr OBJECT-TYPE
			SYNTAX OCTET STRING
			MAX-ACCESS read-only
			STATUS current
			DESCRIPTION
				"Description."
			::= { onuSlaEntry 8 }

		
--          1.3.6.1.4.1.37950.1.1.5.12.2.1.12.1.9
-- 1.3.6.1.4.1.37950.1.1.5.12.2.1.12.1.9
-- 1.3.6.1.4.1.37950.1.1.5.12.2.1.12.1.9
-- 1.3.6.1.4.1.37950.1.1.5.12.2.1.12.1.9
-- 1.3.6.1.4.1.37950.1.1.5.12.2.1.12.1.9
-- 1.3.6.1.4.1.37950.1.1.5.12.2.1.12.1.9
-- 1.3.6.1.4.1.37950.1.1.5.12.2.1.12.1.9
-- 1.3.6.1.4.1.37950.1.1.5.12.2.1.12.1.9
-- 1.3.6.1.4.1.37950.1.1.5.12.2.1.12.1.9
		-- 1.3.6.1.4.1.37950.1.1.5.12.2.1.12.1.9
		slaFixPacketSizeStr OBJECT-TYPE
			SYNTAX OCTET STRING
			MAX-ACCESS read-only
			STATUS current
			DESCRIPTION
				"Description."
			::= { onuSlaEntry 9 }

		
--          1.3.6.1.4.1.37950.1.1.5.12.2.1.12.1.10
-- 1.3.6.1.4.1.37950.1.1.5.12.2.1.12.1.10
-- 1.3.6.1.4.1.37950.1.1.5.12.2.1.12.1.10
-- 1.3.6.1.4.1.37950.1.1.5.12.2.1.12.1.10
-- 1.3.6.1.4.1.37950.1.1.5.12.2.1.12.1.10
-- 1.3.6.1.4.1.37950.1.1.5.12.2.1.12.1.10
-- 1.3.6.1.4.1.37950.1.1.5.12.2.1.12.1.10
-- 1.3.6.1.4.1.37950.1.1.5.12.2.1.12.1.10
-- 1.3.6.1.4.1.37950.1.1.5.12.2.1.12.1.10
		-- 1.3.6.1.4.1.37950.1.1.5.12.2.1.12.1.10
		slaFixBandwidthStr OBJECT-TYPE
			SYNTAX OCTET STRING
			MAX-ACCESS read-only
			STATUS current
			DESCRIPTION
				"Description."
			::= { onuSlaEntry 10 }

		
--          1.3.6.1.4.1.37950.1.1.5.12.2.1.12.1.11
-- 1.3.6.1.4.1.37950.1.1.5.12.2.1.12.1.11
-- 1.3.6.1.4.1.37950.1.1.5.12.2.1.12.1.11
-- 1.3.6.1.4.1.37950.1.1.5.12.2.1.12.1.11
-- 1.3.6.1.4.1.37950.1.1.5.12.2.1.12.1.11
-- 1.3.6.1.4.1.37950.1.1.5.12.2.1.12.1.11
-- 1.3.6.1.4.1.37950.1.1.5.12.2.1.12.1.11
-- 1.3.6.1.4.1.37950.1.1.5.12.2.1.12.1.11
-- 1.3.6.1.4.1.37950.1.1.5.12.2.1.12.1.11
		-- 1.3.6.1.4.1.37950.1.1.5.12.2.1.12.1.11
		slaGuarantBwStr OBJECT-TYPE
			SYNTAX OCTET STRING
			MAX-ACCESS read-only
			STATUS current
			DESCRIPTION
				"Description."
			::= { onuSlaEntry 11 }

		
--          1.3.6.1.4.1.37950.1.1.5.12.2.1.12.1.12
-- 1.3.6.1.4.1.37950.1.1.5.12.2.1.12.1.12
-- 1.3.6.1.4.1.37950.1.1.5.12.2.1.12.1.12
-- 1.3.6.1.4.1.37950.1.1.5.12.2.1.12.1.12
-- 1.3.6.1.4.1.37950.1.1.5.12.2.1.12.1.12
-- 1.3.6.1.4.1.37950.1.1.5.12.2.1.12.1.12
-- 1.3.6.1.4.1.37950.1.1.5.12.2.1.12.1.12
-- 1.3.6.1.4.1.37950.1.1.5.12.2.1.12.1.12
-- 1.3.6.1.4.1.37950.1.1.5.12.2.1.12.1.12
		-- 1.3.6.1.4.1.37950.1.1.5.12.2.1.12.1.12
		slaBestEffortBWStr OBJECT-TYPE
			SYNTAX OCTET STRING
			MAX-ACCESS read-only
			STATUS current
			DESCRIPTION
				"Description."
			::= { onuSlaEntry 12 }

		
--          1.3.6.1.4.1.37950.1.1.5.12.2.1.12.1.13
-- 1.3.6.1.4.1.37950.1.1.5.12.2.1.12.1.13
-- 1.3.6.1.4.1.37950.1.1.5.12.2.1.12.1.13
-- 1.3.6.1.4.1.37950.1.1.5.12.2.1.12.1.13
-- 1.3.6.1.4.1.37950.1.1.5.12.2.1.12.1.13
-- 1.3.6.1.4.1.37950.1.1.5.12.2.1.12.1.13
-- 1.3.6.1.4.1.37950.1.1.5.12.2.1.12.1.13
-- 1.3.6.1.4.1.37950.1.1.5.12.2.1.12.1.13
-- 1.3.6.1.4.1.37950.1.1.5.12.2.1.12.1.13
		-- 1.3.6.1.4.1.37950.1.1.5.12.2.1.12.1.13
		slaWrrWeightStr OBJECT-TYPE
			SYNTAX OCTET STRING
			MAX-ACCESS read-only
			STATUS current
			DESCRIPTION
				"Description."
			::= { onuSlaEntry 13 }

		
--         1.3.6.1.4.1.37950.1.1.5.12.2.1.13
-- 1.3.6.1.4.1.37950.1.1.5.12.2.1.13
-- 1.3.6.1.4.1.37950.1.1.5.12.2.1.13
-- 1.3.6.1.4.1.37950.1.1.5.12.2.1.13
-- 1.3.6.1.4.1.37950.1.1.5.12.2.1.13
-- 1.3.6.1.4.1.37950.1.1.5.12.2.1.13
-- 1.3.6.1.4.1.37950.1.1.5.12.2.1.13
-- 1.3.6.1.4.1.37950.1.1.5.12.2.1.13
		-- 1.3.6.1.4.1.37950.1.1.5.12.2.1.13
		onuOpmDiagTable OBJECT-TYPE
			SYNTAX SEQUENCE OF OnuOpmDiagEntry
			MAX-ACCESS not-accessible
			STATUS current
			DESCRIPTION
				"Description."
			::= { onuInfo 13 }

		
--         1.3.6.1.4.1.37950.1.1.5.12.2.1.13.1
-- 1.3.6.1.4.1.37950.1.1.5.12.2.1.13.1
-- 1.3.6.1.4.1.37950.1.1.5.12.2.1.13.1
-- 1.3.6.1.4.1.37950.1.1.5.12.2.1.13.1
-- 1.3.6.1.4.1.37950.1.1.5.12.2.1.13.1
-- 1.3.6.1.4.1.37950.1.1.5.12.2.1.13.1
-- 1.3.6.1.4.1.37950.1.1.5.12.2.1.13.1
-- 1.3.6.1.4.1.37950.1.1.5.12.2.1.13.1
		-- 1.3.6.1.4.1.37950.1.1.5.12.2.1.13.1
		onuOpmDiagEntry OBJECT-TYPE
			SYNTAX OnuOpmDiagEntry
			MAX-ACCESS not-accessible
			STATUS current
			DESCRIPTION
				"Description."
			INDEX { onuOpmDiagPonId, onuOpmDiageOnuId }
			::= { onuOpmDiagTable 1 }

		
		OnuOpmDiagEntry ::=
			SEQUENCE { 
				onuOpmDiagPonId
					Integer32,
				onuOpmDiageOnuId
					Integer32,
				onuOpmDiagTemperatue
					OCTET STRING,
				onuOpmDiagVoltage
					OCTET STRING,
				onuOpmDiagTxBias
					OCTET STRING,
				onuOpmDiagTxPower
					OCTET STRING,
				onuOpmDiagRxPower
					OCTET STRING
			 }

--         1.3.6.1.4.1.37950.1.1.5.12.2.1.13.1.1
-- 1.3.6.1.4.1.37950.1.1.5.12.2.1.13.1.1
-- 1.3.6.1.4.1.37950.1.1.5.12.2.1.13.1.1
-- 1.3.6.1.4.1.37950.1.1.5.12.2.1.13.1.1
-- 1.3.6.1.4.1.37950.1.1.5.12.2.1.13.1.1
-- 1.3.6.1.4.1.37950.1.1.5.12.2.1.13.1.1
-- 1.3.6.1.4.1.37950.1.1.5.12.2.1.13.1.1
-- 1.3.6.1.4.1.37950.1.1.5.12.2.1.13.1.1
		-- 1.3.6.1.4.1.37950.1.1.5.12.2.1.13.1.1
		onuOpmDiagPonId OBJECT-TYPE
			SYNTAX Integer32
			MAX-ACCESS read-only
			STATUS current
			DESCRIPTION
				"Description."
			::= { onuOpmDiagEntry 1 }

		
--         1.3.6.1.4.1.37950.1.1.5.12.2.1.13.1.2
-- 1.3.6.1.4.1.37950.1.1.5.12.2.1.13.1.2
-- 1.3.6.1.4.1.37950.1.1.5.12.2.1.13.1.2
-- 1.3.6.1.4.1.37950.1.1.5.12.2.1.13.1.2
-- 1.3.6.1.4.1.37950.1.1.5.12.2.1.13.1.2
-- 1.3.6.1.4.1.37950.1.1.5.12.2.1.13.1.2
-- 1.3.6.1.4.1.37950.1.1.5.12.2.1.13.1.2
-- 1.3.6.1.4.1.37950.1.1.5.12.2.1.13.1.2
		-- 1.3.6.1.4.1.37950.1.1.5.12.2.1.13.1.2
		onuOpmDiageOnuId OBJECT-TYPE
			SYNTAX Integer32
			MAX-ACCESS read-only
			STATUS current
			DESCRIPTION
				"Description."
			::= { onuOpmDiagEntry 2 }

		
--         1.3.6.1.4.1.37950.1.1.5.12.2.1.13.1.3
-- 1.3.6.1.4.1.37950.1.1.5.12.2.1.13.1.3
-- 1.3.6.1.4.1.37950.1.1.5.12.2.1.13.1.3
-- 1.3.6.1.4.1.37950.1.1.5.12.2.1.13.1.3
-- 1.3.6.1.4.1.37950.1.1.5.12.2.1.13.1.3
-- 1.3.6.1.4.1.37950.1.1.5.12.2.1.13.1.3
-- 1.3.6.1.4.1.37950.1.1.5.12.2.1.13.1.3
-- 1.3.6.1.4.1.37950.1.1.5.12.2.1.13.1.3
		-- 1.3.6.1.4.1.37950.1.1.5.12.2.1.13.1.3
		onuOpmDiagTemperatue OBJECT-TYPE
			SYNTAX OCTET STRING
			MAX-ACCESS read-only
			STATUS current
			DESCRIPTION
				"Description."
			::= { onuOpmDiagEntry 3 }

		
--         1.3.6.1.4.1.37950.1.1.5.12.2.1.13.1.4
-- 1.3.6.1.4.1.37950.1.1.5.12.2.1.13.1.4
-- 1.3.6.1.4.1.37950.1.1.5.12.2.1.13.1.4
-- 1.3.6.1.4.1.37950.1.1.5.12.2.1.13.1.4
-- 1.3.6.1.4.1.37950.1.1.5.12.2.1.13.1.4
-- 1.3.6.1.4.1.37950.1.1.5.12.2.1.13.1.4
-- 1.3.6.1.4.1.37950.1.1.5.12.2.1.13.1.4
-- 1.3.6.1.4.1.37950.1.1.5.12.2.1.13.1.4
		-- 1.3.6.1.4.1.37950.1.1.5.12.2.1.13.1.4
		onuOpmDiagVoltage OBJECT-TYPE
			SYNTAX OCTET STRING
			MAX-ACCESS read-only
			STATUS current
			DESCRIPTION
				"Description."
			::= { onuOpmDiagEntry 4 }

		
--         1.3.6.1.4.1.37950.1.1.5.12.2.1.13.1.5
-- 1.3.6.1.4.1.37950.1.1.5.12.2.1.13.1.5
-- 1.3.6.1.4.1.37950.1.1.5.12.2.1.13.1.5
-- 1.3.6.1.4.1.37950.1.1.5.12.2.1.13.1.5
-- 1.3.6.1.4.1.37950.1.1.5.12.2.1.13.1.5
-- 1.3.6.1.4.1.37950.1.1.5.12.2.1.13.1.5
-- 1.3.6.1.4.1.37950.1.1.5.12.2.1.13.1.5
-- 1.3.6.1.4.1.37950.1.1.5.12.2.1.13.1.5
		-- 1.3.6.1.4.1.37950.1.1.5.12.2.1.13.1.5
		onuOpmDiagTxBias OBJECT-TYPE
			SYNTAX OCTET STRING
			MAX-ACCESS read-only
			STATUS current
			DESCRIPTION
				"Description."
			::= { onuOpmDiagEntry 5 }

		
--         1.3.6.1.4.1.37950.1.1.5.12.2.1.13.1.6
-- 1.3.6.1.4.1.37950.1.1.5.12.2.1.13.1.6
-- 1.3.6.1.4.1.37950.1.1.5.12.2.1.13.1.6
-- 1.3.6.1.4.1.37950.1.1.5.12.2.1.13.1.6
-- 1.3.6.1.4.1.37950.1.1.5.12.2.1.13.1.6
-- 1.3.6.1.4.1.37950.1.1.5.12.2.1.13.1.6
-- 1.3.6.1.4.1.37950.1.1.5.12.2.1.13.1.6
-- 1.3.6.1.4.1.37950.1.1.5.12.2.1.13.1.6
		-- 1.3.6.1.4.1.37950.1.1.5.12.2.1.13.1.6
		onuOpmDiagTxPower OBJECT-TYPE
			SYNTAX OCTET STRING
			MAX-ACCESS read-only
			STATUS current
			DESCRIPTION
				"Description."
			::= { onuOpmDiagEntry 6 }

		
--         1.3.6.1.4.1.37950.1.1.5.12.2.1.13.1.7
-- 1.3.6.1.4.1.37950.1.1.5.12.2.1.13.1.7
-- 1.3.6.1.4.1.37950.1.1.5.12.2.1.13.1.7
-- 1.3.6.1.4.1.37950.1.1.5.12.2.1.13.1.7
-- 1.3.6.1.4.1.37950.1.1.5.12.2.1.13.1.7
-- 1.3.6.1.4.1.37950.1.1.5.12.2.1.13.1.7
-- 1.3.6.1.4.1.37950.1.1.5.12.2.1.13.1.7
-- 1.3.6.1.4.1.37950.1.1.5.12.2.1.13.1.7
		-- 1.3.6.1.4.1.37950.1.1.5.12.2.1.13.1.7
		onuOpmDiagRxPower OBJECT-TYPE
			SYNTAX OCTET STRING
			MAX-ACCESS read-only
			STATUS current
			DESCRIPTION
				"Description."
			::= { onuOpmDiagEntry 7 }

		
--         1.3.6.1.4.1.37950.1.1.5.12.2.1.14
-- 1.3.6.1.4.1.37950.1.1.5.12.2.1.14
-- 1.3.6.1.4.1.37950.1.1.5.12.2.1.14
-- 1.3.6.1.4.1.37950.1.1.5.12.2.1.14
-- 1.3.6.1.4.1.37950.1.1.5.12.2.1.14
-- 1.3.6.1.4.1.37950.1.1.5.12.2.1.14
-- 1.3.6.1.4.1.37950.1.1.5.12.2.1.14
-- 1.3.6.1.4.1.37950.1.1.5.12.2.1.14
		-- 1.3.6.1.4.1.37950.1.1.5.12.2.1.14
		onuOpmPowerTable OBJECT-TYPE
			SYNTAX SEQUENCE OF OnuOpmPowerEntry
			MAX-ACCESS not-accessible
			STATUS current
			DESCRIPTION
				"Description."
			::= { onuInfo 14 }

		
--         1.3.6.1.4.1.37950.1.1.5.12.2.1.14.1
-- 1.3.6.1.4.1.37950.1.1.5.12.2.1.14.1
-- 1.3.6.1.4.1.37950.1.1.5.12.2.1.14.1
-- 1.3.6.1.4.1.37950.1.1.5.12.2.1.14.1
-- 1.3.6.1.4.1.37950.1.1.5.12.2.1.14.1
-- 1.3.6.1.4.1.37950.1.1.5.12.2.1.14.1
-- 1.3.6.1.4.1.37950.1.1.5.12.2.1.14.1
-- 1.3.6.1.4.1.37950.1.1.5.12.2.1.14.1
		-- 1.3.6.1.4.1.37950.1.1.5.12.2.1.14.1
		onuOpmPowerEntry OBJECT-TYPE
			SYNTAX OnuOpmPowerEntry
			MAX-ACCESS not-accessible
			STATUS current
			DESCRIPTION
				"Description."
			INDEX { onuOpmPowerIndex }
			::= { onuOpmPowerTable 1 }

		
		OnuOpmPowerEntry ::=
			SEQUENCE { 
				onuOpmPowerIndex
					Integer32,
				onuOpmPowerName
					OCTET STRING,
				onuOpmPowerRx
					INTEGER,
				onuOpmPowerTx
					INTEGER
			 }

--         1.3.6.1.4.1.37950.1.1.5.12.2.1.14.1.1
-- 1.3.6.1.4.1.37950.1.1.5.12.2.1.14.1.1
-- 1.3.6.1.4.1.37950.1.1.5.12.2.1.14.1.1
-- 1.3.6.1.4.1.37950.1.1.5.12.2.1.14.1.1
-- 1.3.6.1.4.1.37950.1.1.5.12.2.1.14.1.1
-- 1.3.6.1.4.1.37950.1.1.5.12.2.1.14.1.1
-- 1.3.6.1.4.1.37950.1.1.5.12.2.1.14.1.1
-- 1.3.6.1.4.1.37950.1.1.5.12.2.1.14.1.1
		-- 1.3.6.1.4.1.37950.1.1.5.12.2.1.14.1.1
		onuOpmPowerIndex OBJECT-TYPE
			SYNTAX Integer32
			MAX-ACCESS read-write
			STATUS current
			DESCRIPTION
				"Description."
			::= { onuOpmPowerEntry 1 }

		
--         1.3.6.1.4.1.37950.1.1.5.12.2.1.14.1.2
-- 1.3.6.1.4.1.37950.1.1.5.12.2.1.14.1.2
-- 1.3.6.1.4.1.37950.1.1.5.12.2.1.14.1.2
-- 1.3.6.1.4.1.37950.1.1.5.12.2.1.14.1.2
-- 1.3.6.1.4.1.37950.1.1.5.12.2.1.14.1.2
-- 1.3.6.1.4.1.37950.1.1.5.12.2.1.14.1.2
-- 1.3.6.1.4.1.37950.1.1.5.12.2.1.14.1.2
-- 1.3.6.1.4.1.37950.1.1.5.12.2.1.14.1.2
		-- 1.3.6.1.4.1.37950.1.1.5.12.2.1.14.1.2
		onuOpmPowerName OBJECT-TYPE
			SYNTAX OCTET STRING
			MAX-ACCESS read-write
			STATUS current
			DESCRIPTION
				"Description."
			::= { onuOpmPowerEntry 2 }

		
--         1.3.6.1.4.1.37950.1.1.5.12.2.1.14.1.3
-- 1.3.6.1.4.1.37950.1.1.5.12.2.1.14.1.3
-- 1.3.6.1.4.1.37950.1.1.5.12.2.1.14.1.3
-- 1.3.6.1.4.1.37950.1.1.5.12.2.1.14.1.3
-- 1.3.6.1.4.1.37950.1.1.5.12.2.1.14.1.3
-- 1.3.6.1.4.1.37950.1.1.5.12.2.1.14.1.3
-- 1.3.6.1.4.1.37950.1.1.5.12.2.1.14.1.3
-- 1.3.6.1.4.1.37950.1.1.5.12.2.1.14.1.3
		-- 1.3.6.1.4.1.37950.1.1.5.12.2.1.14.1.3
		onuOpmPowerRx OBJECT-TYPE
			SYNTAX INTEGER
			MAX-ACCESS read-write
			STATUS current
			DESCRIPTION
				"Description."
			::= { onuOpmPowerEntry 3 }

		
--         1.3.6.1.4.1.37950.1.1.5.12.2.1.14.1.4
-- 1.3.6.1.4.1.37950.1.1.5.12.2.1.14.1.4
-- 1.3.6.1.4.1.37950.1.1.5.12.2.1.14.1.4
-- 1.3.6.1.4.1.37950.1.1.5.12.2.1.14.1.4
-- 1.3.6.1.4.1.37950.1.1.5.12.2.1.14.1.4
-- 1.3.6.1.4.1.37950.1.1.5.12.2.1.14.1.4
-- 1.3.6.1.4.1.37950.1.1.5.12.2.1.14.1.4
-- 1.3.6.1.4.1.37950.1.1.5.12.2.1.14.1.4
		-- 1.3.6.1.4.1.37950.1.1.5.12.2.1.14.1.4
		onuOpmPowerTx OBJECT-TYPE
			SYNTAX INTEGER
			MAX-ACCESS read-write
			STATUS current
			DESCRIPTION
				"Description."
			::= { onuOpmPowerEntry 4 }

		
--          1.3.6.1.4.1.37950.1.1.5.12.2.2
-- 1.3.6.1.4.1.37950.1.1.5.12.2.2
-- 1.3.6.1.4.1.37950.1.1.5.12.2.2
-- 1.3.6.1.4.1.37950.1.1.5.12.2.2
-- 1.3.6.1.4.1.37950.1.1.5.12.2.2
-- 1.3.6.1.4.1.37950.1.1.5.12.2.2
-- 1.3.6.1.4.1.37950.1.1.5.12.2.2
-- 1.3.6.1.4.1.37950.1.1.5.12.2.2
-- 1.3.6.1.4.1.37950.1.1.5.12.2.2
		-- 1.3.6.1.4.1.37950.1.1.5.12.2.2
		onuUpgrade OBJECT IDENTIFIER ::= { onuGlobalCfg 2 }

		
--          1.3.6.1.4.1.37950.1.1.5.12.2.2.1
-- 1.3.6.1.4.1.37950.1.1.5.12.2.2.1
-- 1.3.6.1.4.1.37950.1.1.5.12.2.2.1
-- 1.3.6.1.4.1.37950.1.1.5.12.2.2.1
-- 1.3.6.1.4.1.37950.1.1.5.12.2.2.1
-- 1.3.6.1.4.1.37950.1.1.5.12.2.2.1
-- 1.3.6.1.4.1.37950.1.1.5.12.2.2.1
-- 1.3.6.1.4.1.37950.1.1.5.12.2.2.1
-- 1.3.6.1.4.1.37950.1.1.5.12.2.2.1
		-- 1.3.6.1.4.1.37950.1.1.5.12.2.2.1
		tftpDownloadFile OBJECT IDENTIFIER ::= { onuUpgrade 1 }

		
--          1.3.6.1.4.1.37950.1.1.5.12.2.2.1.1
-- 1.3.6.1.4.1.37950.1.1.5.12.2.2.1.1
-- 1.3.6.1.4.1.37950.1.1.5.12.2.2.1.1
-- 1.3.6.1.4.1.37950.1.1.5.12.2.2.1.1
-- 1.3.6.1.4.1.37950.1.1.5.12.2.2.1.1
-- 1.3.6.1.4.1.37950.1.1.5.12.2.2.1.1
-- 1.3.6.1.4.1.37950.1.1.5.12.2.2.1.1
-- 1.3.6.1.4.1.37950.1.1.5.12.2.2.1.1
-- 1.3.6.1.4.1.37950.1.1.5.12.2.2.1.1
		-- 1.3.6.1.4.1.37950.1.1.5.12.2.2.1.1
		filename OBJECT-TYPE
			SYNTAX OCTET STRING
			MAX-ACCESS read-write
			STATUS current
			DESCRIPTION
				"Description."
			::= { tftpDownloadFile 1 }

		
--          1.3.6.1.4.1.37950.1.1.5.12.2.2.1.2
-- 1.3.6.1.4.1.37950.1.1.5.12.2.2.1.2
-- 1.3.6.1.4.1.37950.1.1.5.12.2.2.1.2
-- 1.3.6.1.4.1.37950.1.1.5.12.2.2.1.2
-- 1.3.6.1.4.1.37950.1.1.5.12.2.2.1.2
-- 1.3.6.1.4.1.37950.1.1.5.12.2.2.1.2
-- 1.3.6.1.4.1.37950.1.1.5.12.2.2.1.2
-- 1.3.6.1.4.1.37950.1.1.5.12.2.2.1.2
-- 1.3.6.1.4.1.37950.1.1.5.12.2.2.1.2
		-- 1.3.6.1.4.1.37950.1.1.5.12.2.2.1.2
		tftpServer OBJECT-TYPE
			SYNTAX OCTET STRING
			MAX-ACCESS read-write
			STATUS current
			DESCRIPTION
				"Description."
			::= { tftpDownloadFile 2 }

		
--          1.3.6.1.4.1.37950.1.1.5.12.2.2.1.3
-- 1.3.6.1.4.1.37950.1.1.5.12.2.2.1.3
-- 1.3.6.1.4.1.37950.1.1.5.12.2.2.1.3
-- 1.3.6.1.4.1.37950.1.1.5.12.2.2.1.3
-- 1.3.6.1.4.1.37950.1.1.5.12.2.2.1.3
-- 1.3.6.1.4.1.37950.1.1.5.12.2.2.1.3
-- 1.3.6.1.4.1.37950.1.1.5.12.2.2.1.3
-- 1.3.6.1.4.1.37950.1.1.5.12.2.2.1.3
-- 1.3.6.1.4.1.37950.1.1.5.12.2.2.1.3
		-- 1.3.6.1.4.1.37950.1.1.5.12.2.2.1.3
		tftpAction OBJECT-TYPE
			SYNTAX INTEGER { commit(1) }
			MAX-ACCESS read-write
			STATUS current
			DESCRIPTION
				"Description."
			::= { tftpDownloadFile 3 }

		
--          1.3.6.1.4.1.37950.1.1.5.12.2.2.2
-- 1.3.6.1.4.1.37950.1.1.5.12.2.2.2
-- 1.3.6.1.4.1.37950.1.1.5.12.2.2.2
-- 1.3.6.1.4.1.37950.1.1.5.12.2.2.2
-- 1.3.6.1.4.1.37950.1.1.5.12.2.2.2
-- 1.3.6.1.4.1.37950.1.1.5.12.2.2.2
-- 1.3.6.1.4.1.37950.1.1.5.12.2.2.2
-- 1.3.6.1.4.1.37950.1.1.5.12.2.2.2
-- 1.3.6.1.4.1.37950.1.1.5.12.2.2.2
		-- 1.3.6.1.4.1.37950.1.1.5.12.2.2.2
		upgradeLoadOnuImg OBJECT IDENTIFIER ::= { onuUpgrade 2 }

		
--          1.3.6.1.4.1.37950.1.1.5.12.2.2.2.1
-- 1.3.6.1.4.1.37950.1.1.5.12.2.2.2.1
-- 1.3.6.1.4.1.37950.1.1.5.12.2.2.2.1
-- 1.3.6.1.4.1.37950.1.1.5.12.2.2.2.1
-- 1.3.6.1.4.1.37950.1.1.5.12.2.2.2.1
-- 1.3.6.1.4.1.37950.1.1.5.12.2.2.2.1
-- 1.3.6.1.4.1.37950.1.1.5.12.2.2.2.1
-- 1.3.6.1.4.1.37950.1.1.5.12.2.2.2.1
-- 1.3.6.1.4.1.37950.1.1.5.12.2.2.2.1
		-- 1.3.6.1.4.1.37950.1.1.5.12.2.2.2.1
		filenameSet OBJECT-TYPE
			SYNTAX OCTET STRING
			MAX-ACCESS read-write
			STATUS current
			DESCRIPTION
				"Description."
			::= { upgradeLoadOnuImg 1 }

		
--          1.3.6.1.4.1.37950.1.1.5.12.2.2.2.2
-- 1.3.6.1.4.1.37950.1.1.5.12.2.2.2.2
-- 1.3.6.1.4.1.37950.1.1.5.12.2.2.2.2
-- 1.3.6.1.4.1.37950.1.1.5.12.2.2.2.2
-- 1.3.6.1.4.1.37950.1.1.5.12.2.2.2.2
-- 1.3.6.1.4.1.37950.1.1.5.12.2.2.2.2
-- 1.3.6.1.4.1.37950.1.1.5.12.2.2.2.2
-- 1.3.6.1.4.1.37950.1.1.5.12.2.2.2.2
-- 1.3.6.1.4.1.37950.1.1.5.12.2.2.2.2
		-- 1.3.6.1.4.1.37950.1.1.5.12.2.2.2.2
		loadAction OBJECT-TYPE
			SYNTAX INTEGER
				{
				commit(1),
				clean(2)
				}
			MAX-ACCESS read-write
			STATUS current
			DESCRIPTION
				"Description."
			::= { upgradeLoadOnuImg 2 }

		
--          1.3.6.1.4.1.37950.1.1.5.12.2.2.3
-- 1.3.6.1.4.1.37950.1.1.5.12.2.2.3
-- 1.3.6.1.4.1.37950.1.1.5.12.2.2.3
-- 1.3.6.1.4.1.37950.1.1.5.12.2.2.3
-- 1.3.6.1.4.1.37950.1.1.5.12.2.2.3
-- 1.3.6.1.4.1.37950.1.1.5.12.2.2.3
-- 1.3.6.1.4.1.37950.1.1.5.12.2.2.3
-- 1.3.6.1.4.1.37950.1.1.5.12.2.2.3
-- 1.3.6.1.4.1.37950.1.1.5.12.2.2.3
		-- 1.3.6.1.4.1.37950.1.1.5.12.2.2.3
		ctcUpgradeCfg OBJECT IDENTIFIER ::= { onuUpgrade 3 }

		
--          1.3.6.1.4.1.37950.1.1.5.12.2.2.3.1
-- 1.3.6.1.4.1.37950.1.1.5.12.2.2.3.1
-- 1.3.6.1.4.1.37950.1.1.5.12.2.2.3.1
-- 1.3.6.1.4.1.37950.1.1.5.12.2.2.3.1
-- 1.3.6.1.4.1.37950.1.1.5.12.2.2.3.1
-- 1.3.6.1.4.1.37950.1.1.5.12.2.2.3.1
-- 1.3.6.1.4.1.37950.1.1.5.12.2.2.3.1
-- 1.3.6.1.4.1.37950.1.1.5.12.2.2.3.1
-- 1.3.6.1.4.1.37950.1.1.5.12.2.2.3.1
		-- 1.3.6.1.4.1.37950.1.1.5.12.2.2.3.1
		upgradePonNo OBJECT-TYPE
			SYNTAX INTEGER (1..16)
			MAX-ACCESS read-write
			STATUS current
			DESCRIPTION
				"Description."
			::= { ctcUpgradeCfg 1 }

		
--          1.3.6.1.4.1.37950.1.1.5.12.2.2.3.2
-- 1.3.6.1.4.1.37950.1.1.5.12.2.2.3.2
-- 1.3.6.1.4.1.37950.1.1.5.12.2.2.3.2
-- 1.3.6.1.4.1.37950.1.1.5.12.2.2.3.2
-- 1.3.6.1.4.1.37950.1.1.5.12.2.2.3.2
-- 1.3.6.1.4.1.37950.1.1.5.12.2.2.3.2
-- 1.3.6.1.4.1.37950.1.1.5.12.2.2.3.2
-- 1.3.6.1.4.1.37950.1.1.5.12.2.2.3.2
-- 1.3.6.1.4.1.37950.1.1.5.12.2.2.3.2
		-- 1.3.6.1.4.1.37950.1.1.5.12.2.2.3.2
		upgradeOnuNo OBJECT-TYPE
			SYNTAX INTEGER (1..65535)
			MAX-ACCESS read-write
			STATUS current
			DESCRIPTION
				"Description."
			::= { ctcUpgradeCfg 2 }

		
--          1.3.6.1.4.1.37950.1.1.5.12.2.2.3.3
-- 1.3.6.1.4.1.37950.1.1.5.12.2.2.3.3
-- 1.3.6.1.4.1.37950.1.1.5.12.2.2.3.3
-- 1.3.6.1.4.1.37950.1.1.5.12.2.2.3.3
-- 1.3.6.1.4.1.37950.1.1.5.12.2.2.3.3
-- 1.3.6.1.4.1.37950.1.1.5.12.2.2.3.3
-- 1.3.6.1.4.1.37950.1.1.5.12.2.2.3.3
-- 1.3.6.1.4.1.37950.1.1.5.12.2.2.3.3
-- 1.3.6.1.4.1.37950.1.1.5.12.2.2.3.3
		-- 1.3.6.1.4.1.37950.1.1.5.12.2.2.3.3
		ctcUpgrade OBJECT-TYPE
			SYNTAX INTEGER
				{
				start(1),
				commit(2)
				}
			MAX-ACCESS read-write
			STATUS current
			DESCRIPTION
				"Description."
			::= { ctcUpgradeCfg 3 }

		
--          1.3.6.1.4.1.37950.1.1.5.12.2.2.4
-- 1.3.6.1.4.1.37950.1.1.5.12.2.2.4
-- 1.3.6.1.4.1.37950.1.1.5.12.2.2.4
-- 1.3.6.1.4.1.37950.1.1.5.12.2.2.4
-- 1.3.6.1.4.1.37950.1.1.5.12.2.2.4
-- 1.3.6.1.4.1.37950.1.1.5.12.2.2.4
-- 1.3.6.1.4.1.37950.1.1.5.12.2.2.4
-- 1.3.6.1.4.1.37950.1.1.5.12.2.2.4
-- 1.3.6.1.4.1.37950.1.1.5.12.2.2.4
		-- 1.3.6.1.4.1.37950.1.1.5.12.2.2.4
		upgradeOnuImage OBJECT IDENTIFIER ::= { onuUpgrade 4 }

		
--          1.3.6.1.4.1.37950.1.1.5.12.2.2.4.1
-- 1.3.6.1.4.1.37950.1.1.5.12.2.2.4.1
-- 1.3.6.1.4.1.37950.1.1.5.12.2.2.4.1
-- 1.3.6.1.4.1.37950.1.1.5.12.2.2.4.1
-- 1.3.6.1.4.1.37950.1.1.5.12.2.2.4.1
-- 1.3.6.1.4.1.37950.1.1.5.12.2.2.4.1
-- 1.3.6.1.4.1.37950.1.1.5.12.2.2.4.1
-- 1.3.6.1.4.1.37950.1.1.5.12.2.2.4.1
-- 1.3.6.1.4.1.37950.1.1.5.12.2.2.4.1
		-- 1.3.6.1.4.1.37950.1.1.5.12.2.2.4.1
		upgradeImage OBJECT-TYPE
			SYNTAX OCTET STRING
			MAX-ACCESS read-write
			STATUS current
			DESCRIPTION
				"Description."
			::= { upgradeOnuImage 1 }

		
--          1.3.6.1.4.1.37950.1.1.5.12.2.2.4.2
-- 1.3.6.1.4.1.37950.1.1.5.12.2.2.4.2
-- 1.3.6.1.4.1.37950.1.1.5.12.2.2.4.2
-- 1.3.6.1.4.1.37950.1.1.5.12.2.2.4.2
-- 1.3.6.1.4.1.37950.1.1.5.12.2.2.4.2
-- 1.3.6.1.4.1.37950.1.1.5.12.2.2.4.2
-- 1.3.6.1.4.1.37950.1.1.5.12.2.2.4.2
-- 1.3.6.1.4.1.37950.1.1.5.12.2.2.4.2
-- 1.3.6.1.4.1.37950.1.1.5.12.2.2.4.2
		-- 1.3.6.1.4.1.37950.1.1.5.12.2.2.4.2
		upgradeIp OBJECT-TYPE
			SYNTAX IpAddress
			MAX-ACCESS read-write
			STATUS current
			DESCRIPTION
				"Description."
			::= { upgradeOnuImage 2 }

		
--          1.3.6.1.4.1.37950.1.1.5.12.2.2.4.3
-- 1.3.6.1.4.1.37950.1.1.5.12.2.2.4.3
-- 1.3.6.1.4.1.37950.1.1.5.12.2.2.4.3
-- 1.3.6.1.4.1.37950.1.1.5.12.2.2.4.3
-- 1.3.6.1.4.1.37950.1.1.5.12.2.2.4.3
-- 1.3.6.1.4.1.37950.1.1.5.12.2.2.4.3
-- 1.3.6.1.4.1.37950.1.1.5.12.2.2.4.3
-- 1.3.6.1.4.1.37950.1.1.5.12.2.2.4.3
-- 1.3.6.1.4.1.37950.1.1.5.12.2.2.4.3
		-- 1.3.6.1.4.1.37950.1.1.5.12.2.2.4.3
		upgradeImageAction OBJECT-TYPE
			SYNTAX INTEGER { commit(1) }
			MAX-ACCESS read-write
			STATUS current
			DESCRIPTION
				"Description."
			::= { upgradeOnuImage 3 }

		
--          1.3.6.1.4.1.37950.1.1.5.12.2.2.5
-- 1.3.6.1.4.1.37950.1.1.5.12.2.2.5
-- 1.3.6.1.4.1.37950.1.1.5.12.2.2.5
-- 1.3.6.1.4.1.37950.1.1.5.12.2.2.5
-- 1.3.6.1.4.1.37950.1.1.5.12.2.2.5
-- 1.3.6.1.4.1.37950.1.1.5.12.2.2.5
-- 1.3.6.1.4.1.37950.1.1.5.12.2.2.5
-- 1.3.6.1.4.1.37950.1.1.5.12.2.2.5
-- 1.3.6.1.4.1.37950.1.1.5.12.2.2.5
		-- 1.3.6.1.4.1.37950.1.1.5.12.2.2.5
		upgradeOnuSelect OBJECT IDENTIFIER ::= { onuUpgrade 5 }

		
--          1.3.6.1.4.1.37950.1.1.5.12.2.2.5.1
-- 1.3.6.1.4.1.37950.1.1.5.12.2.2.5.1
-- 1.3.6.1.4.1.37950.1.1.5.12.2.2.5.1
-- 1.3.6.1.4.1.37950.1.1.5.12.2.2.5.1
-- 1.3.6.1.4.1.37950.1.1.5.12.2.2.5.1
-- 1.3.6.1.4.1.37950.1.1.5.12.2.2.5.1
-- 1.3.6.1.4.1.37950.1.1.5.12.2.2.5.1
-- 1.3.6.1.4.1.37950.1.1.5.12.2.2.5.1
-- 1.3.6.1.4.1.37950.1.1.5.12.2.2.5.1
		-- 1.3.6.1.4.1.37950.1.1.5.12.2.2.5.1
		upgradePon OBJECT-TYPE
			SYNTAX INTEGER (1..16)
			MAX-ACCESS read-write
			STATUS current
			DESCRIPTION
				"Description."
			::= { upgradeOnuSelect 1 }

		
--          1.3.6.1.4.1.37950.1.1.5.12.2.2.5.2
-- 1.3.6.1.4.1.37950.1.1.5.12.2.2.5.2
-- 1.3.6.1.4.1.37950.1.1.5.12.2.2.5.2
-- 1.3.6.1.4.1.37950.1.1.5.12.2.2.5.2
-- 1.3.6.1.4.1.37950.1.1.5.12.2.2.5.2
-- 1.3.6.1.4.1.37950.1.1.5.12.2.2.5.2
-- 1.3.6.1.4.1.37950.1.1.5.12.2.2.5.2
-- 1.3.6.1.4.1.37950.1.1.5.12.2.2.5.2
-- 1.3.6.1.4.1.37950.1.1.5.12.2.2.5.2
		-- 1.3.6.1.4.1.37950.1.1.5.12.2.2.5.2
		upgradeOnu OBJECT-TYPE
			SYNTAX OCTET STRING
			MAX-ACCESS read-write
			STATUS current
			DESCRIPTION
				"Description."
			::= { upgradeOnuSelect 2 }

		
--          1.3.6.1.4.1.37950.1.1.5.12.2.2.5.3
-- 1.3.6.1.4.1.37950.1.1.5.12.2.2.5.3
-- 1.3.6.1.4.1.37950.1.1.5.12.2.2.5.3
-- 1.3.6.1.4.1.37950.1.1.5.12.2.2.5.3
-- 1.3.6.1.4.1.37950.1.1.5.12.2.2.5.3
-- 1.3.6.1.4.1.37950.1.1.5.12.2.2.5.3
-- 1.3.6.1.4.1.37950.1.1.5.12.2.2.5.3
-- 1.3.6.1.4.1.37950.1.1.5.12.2.2.5.3
-- 1.3.6.1.4.1.37950.1.1.5.12.2.2.5.3
		-- 1.3.6.1.4.1.37950.1.1.5.12.2.2.5.3
		upgradeSelectAction OBJECT-TYPE
			SYNTAX INTEGER
				{
				add(1),
				delete(2)
				}
			MAX-ACCESS read-write
			STATUS current
			DESCRIPTION
				"Description."
			::= { upgradeOnuSelect 3 }

		
--          1.3.6.1.4.1.37950.1.1.5.12.2.2.6
-- 1.3.6.1.4.1.37950.1.1.5.12.2.2.6
-- 1.3.6.1.4.1.37950.1.1.5.12.2.2.6
-- 1.3.6.1.4.1.37950.1.1.5.12.2.2.6
-- 1.3.6.1.4.1.37950.1.1.5.12.2.2.6
-- 1.3.6.1.4.1.37950.1.1.5.12.2.2.6
-- 1.3.6.1.4.1.37950.1.1.5.12.2.2.6
-- 1.3.6.1.4.1.37950.1.1.5.12.2.2.6
-- 1.3.6.1.4.1.37950.1.1.5.12.2.2.6
		-- 1.3.6.1.4.1.37950.1.1.5.12.2.2.6
		upgradeOnuSelectTable OBJECT-TYPE
			SYNTAX SEQUENCE OF UpgradeOnuSelectEntry
			MAX-ACCESS not-accessible
			STATUS current
			DESCRIPTION
				"Description."
			::= { onuUpgrade 6 }

		
--          1.3.6.1.4.1.37950.1.1.5.12.2.2.6.1
-- 1.3.6.1.4.1.37950.1.1.5.12.2.2.6.1
-- 1.3.6.1.4.1.37950.1.1.5.12.2.2.6.1
-- 1.3.6.1.4.1.37950.1.1.5.12.2.2.6.1
-- 1.3.6.1.4.1.37950.1.1.5.12.2.2.6.1
-- 1.3.6.1.4.1.37950.1.1.5.12.2.2.6.1
-- 1.3.6.1.4.1.37950.1.1.5.12.2.2.6.1
-- 1.3.6.1.4.1.37950.1.1.5.12.2.2.6.1
-- 1.3.6.1.4.1.37950.1.1.5.12.2.2.6.1
		-- 1.3.6.1.4.1.37950.1.1.5.12.2.2.6.1
		upgradeOnuSelectEntry OBJECT-TYPE
			SYNTAX UpgradeOnuSelectEntry
			MAX-ACCESS not-accessible
			STATUS current
			DESCRIPTION
				"Description."
			INDEX { upgradeOnuPonS }
			::= { upgradeOnuSelectTable 1 }

		
		UpgradeOnuSelectEntry ::=
			SEQUENCE { 
				upgradeOnuPonS
					INTEGER,
				upgradeOnuSelectS
					OCTET STRING
			 }

--          1.3.6.1.4.1.37950.1.1.5.12.2.2.6.1.1
-- 1.3.6.1.4.1.37950.1.1.5.12.2.2.6.1.1
-- 1.3.6.1.4.1.37950.1.1.5.12.2.2.6.1.1
-- 1.3.6.1.4.1.37950.1.1.5.12.2.2.6.1.1
-- 1.3.6.1.4.1.37950.1.1.5.12.2.2.6.1.1
-- 1.3.6.1.4.1.37950.1.1.5.12.2.2.6.1.1
-- 1.3.6.1.4.1.37950.1.1.5.12.2.2.6.1.1
-- 1.3.6.1.4.1.37950.1.1.5.12.2.2.6.1.1
-- 1.3.6.1.4.1.37950.1.1.5.12.2.2.6.1.1
		-- 1.3.6.1.4.1.37950.1.1.5.12.2.2.6.1.1
		upgradeOnuPonS OBJECT-TYPE
			SYNTAX INTEGER (1..16)
			MAX-ACCESS read-only
			STATUS current
			DESCRIPTION
				"Description."
			::= { upgradeOnuSelectEntry 1 }

		
--          1.3.6.1.4.1.37950.1.1.5.12.2.2.6.1.2
-- 1.3.6.1.4.1.37950.1.1.5.12.2.2.6.1.2
-- 1.3.6.1.4.1.37950.1.1.5.12.2.2.6.1.2
-- 1.3.6.1.4.1.37950.1.1.5.12.2.2.6.1.2
-- 1.3.6.1.4.1.37950.1.1.5.12.2.2.6.1.2
-- 1.3.6.1.4.1.37950.1.1.5.12.2.2.6.1.2
-- 1.3.6.1.4.1.37950.1.1.5.12.2.2.6.1.2
-- 1.3.6.1.4.1.37950.1.1.5.12.2.2.6.1.2
-- 1.3.6.1.4.1.37950.1.1.5.12.2.2.6.1.2
		-- 1.3.6.1.4.1.37950.1.1.5.12.2.2.6.1.2
		upgradeOnuSelectS OBJECT-TYPE
			SYNTAX OCTET STRING
			MAX-ACCESS read-only
			STATUS current
			DESCRIPTION
				"Description."
			::= { upgradeOnuSelectEntry 2 }

		
--          1.3.6.1.4.1.37950.1.1.5.12.2.2.7
-- 1.3.6.1.4.1.37950.1.1.5.12.2.2.7
-- 1.3.6.1.4.1.37950.1.1.5.12.2.2.7
-- 1.3.6.1.4.1.37950.1.1.5.12.2.2.7
-- 1.3.6.1.4.1.37950.1.1.5.12.2.2.7
-- 1.3.6.1.4.1.37950.1.1.5.12.2.2.7
-- 1.3.6.1.4.1.37950.1.1.5.12.2.2.7
-- 1.3.6.1.4.1.37950.1.1.5.12.2.2.7
-- 1.3.6.1.4.1.37950.1.1.5.12.2.2.7
		-- 1.3.6.1.4.1.37950.1.1.5.12.2.2.7
		upgreadOnuAction OBJECT IDENTIFIER ::= { onuUpgrade 7 }

		
--          1.3.6.1.4.1.37950.1.1.5.12.2.2.7.1
-- 1.3.6.1.4.1.37950.1.1.5.12.2.2.7.1
-- 1.3.6.1.4.1.37950.1.1.5.12.2.2.7.1
-- 1.3.6.1.4.1.37950.1.1.5.12.2.2.7.1
-- 1.3.6.1.4.1.37950.1.1.5.12.2.2.7.1
-- 1.3.6.1.4.1.37950.1.1.5.12.2.2.7.1
-- 1.3.6.1.4.1.37950.1.1.5.12.2.2.7.1
-- 1.3.6.1.4.1.37950.1.1.5.12.2.2.7.1
-- 1.3.6.1.4.1.37950.1.1.5.12.2.2.7.1
		-- 1.3.6.1.4.1.37950.1.1.5.12.2.2.7.1
		upgreadAction OBJECT-TYPE
			SYNTAX INTEGER
				{
				start(1),
				stop(2)
				}
			MAX-ACCESS read-write
			STATUS current
			DESCRIPTION
				"Description."
			::= { upgreadOnuAction 1 }

		
--          1.3.6.1.4.1.37950.1.1.5.12.2.2.7.2
-- 1.3.6.1.4.1.37950.1.1.5.12.2.2.7.2
-- 1.3.6.1.4.1.37950.1.1.5.12.2.2.7.2
-- 1.3.6.1.4.1.37950.1.1.5.12.2.2.7.2
-- 1.3.6.1.4.1.37950.1.1.5.12.2.2.7.2
-- 1.3.6.1.4.1.37950.1.1.5.12.2.2.7.2
-- 1.3.6.1.4.1.37950.1.1.5.12.2.2.7.2
-- 1.3.6.1.4.1.37950.1.1.5.12.2.2.7.2
-- 1.3.6.1.4.1.37950.1.1.5.12.2.2.7.2
		-- 1.3.6.1.4.1.37950.1.1.5.12.2.2.7.2
		upgradeOver OBJECT-TYPE
			SYNTAX Integer32
			MAX-ACCESS read-only
			STATUS current
			DESCRIPTION
				"Description."
			::= { upgreadOnuAction 2 }

		
--          1.3.6.1.4.1.37950.1.1.5.12.2.2.8
-- 1.3.6.1.4.1.37950.1.1.5.12.2.2.8
-- 1.3.6.1.4.1.37950.1.1.5.12.2.2.8
-- 1.3.6.1.4.1.37950.1.1.5.12.2.2.8
-- 1.3.6.1.4.1.37950.1.1.5.12.2.2.8
-- 1.3.6.1.4.1.37950.1.1.5.12.2.2.8
-- 1.3.6.1.4.1.37950.1.1.5.12.2.2.8
-- 1.3.6.1.4.1.37950.1.1.5.12.2.2.8
-- 1.3.6.1.4.1.37950.1.1.5.12.2.2.8
		-- 1.3.6.1.4.1.37950.1.1.5.12.2.2.8
		upgradeOnuStatusTable OBJECT-TYPE
			SYNTAX SEQUENCE OF UpgradeOnuStatusEntry
			MAX-ACCESS not-accessible
			STATUS current
			DESCRIPTION
				"Description."
			::= { onuUpgrade 8 }

		
--          1.3.6.1.4.1.37950.1.1.5.12.2.2.8.1
-- 1.3.6.1.4.1.37950.1.1.5.12.2.2.8.1
-- 1.3.6.1.4.1.37950.1.1.5.12.2.2.8.1
-- 1.3.6.1.4.1.37950.1.1.5.12.2.2.8.1
-- 1.3.6.1.4.1.37950.1.1.5.12.2.2.8.1
-- 1.3.6.1.4.1.37950.1.1.5.12.2.2.8.1
-- 1.3.6.1.4.1.37950.1.1.5.12.2.2.8.1
-- 1.3.6.1.4.1.37950.1.1.5.12.2.2.8.1
-- 1.3.6.1.4.1.37950.1.1.5.12.2.2.8.1
		-- 1.3.6.1.4.1.37950.1.1.5.12.2.2.8.1
		upgradeOnuStatusEntry OBJECT-TYPE
			SYNTAX UpgradeOnuStatusEntry
			MAX-ACCESS not-accessible
			STATUS current
			DESCRIPTION
				"Description."
			INDEX { upgradeOnuStatusIndex }
			::= { upgradeOnuStatusTable 1 }

		
		UpgradeOnuStatusEntry ::=
			SEQUENCE { 
				upgradeOnuStatusIndex
					Integer32,
				upgreadeStatusPonS
					Integer32,
				upgradeOnuLlid
					Integer32,
				upgradeOnuStatusS
					OCTET STRING,
				upgradeOnuStatusProcess
					OCTET STRING
			 }

--          1.3.6.1.4.1.37950.1.1.5.12.2.2.8.1.1
-- 1.3.6.1.4.1.37950.1.1.5.12.2.2.8.1.1
-- 1.3.6.1.4.1.37950.1.1.5.12.2.2.8.1.1
-- 1.3.6.1.4.1.37950.1.1.5.12.2.2.8.1.1
-- 1.3.6.1.4.1.37950.1.1.5.12.2.2.8.1.1
-- 1.3.6.1.4.1.37950.1.1.5.12.2.2.8.1.1
-- 1.3.6.1.4.1.37950.1.1.5.12.2.2.8.1.1
-- 1.3.6.1.4.1.37950.1.1.5.12.2.2.8.1.1
-- 1.3.6.1.4.1.37950.1.1.5.12.2.2.8.1.1
		-- 1.3.6.1.4.1.37950.1.1.5.12.2.2.8.1.1
		upgradeOnuStatusIndex OBJECT-TYPE
			SYNTAX Integer32
			MAX-ACCESS read-write
			STATUS current
			DESCRIPTION
				"Description."
			::= { upgradeOnuStatusEntry 1 }

		
--          1.3.6.1.4.1.37950.1.1.5.12.2.2.8.1.2
-- 1.3.6.1.4.1.37950.1.1.5.12.2.2.8.1.2
-- 1.3.6.1.4.1.37950.1.1.5.12.2.2.8.1.2
-- 1.3.6.1.4.1.37950.1.1.5.12.2.2.8.1.2
-- 1.3.6.1.4.1.37950.1.1.5.12.2.2.8.1.2
-- 1.3.6.1.4.1.37950.1.1.5.12.2.2.8.1.2
-- 1.3.6.1.4.1.37950.1.1.5.12.2.2.8.1.2
-- 1.3.6.1.4.1.37950.1.1.5.12.2.2.8.1.2
-- 1.3.6.1.4.1.37950.1.1.5.12.2.2.8.1.2
		-- 1.3.6.1.4.1.37950.1.1.5.12.2.2.8.1.2
		upgreadeStatusPonS OBJECT-TYPE
			SYNTAX Integer32
			MAX-ACCESS read-write
			STATUS current
			DESCRIPTION
				"Description."
			::= { upgradeOnuStatusEntry 2 }

		
--          1.3.6.1.4.1.37950.1.1.5.12.2.2.8.1.3
-- 1.3.6.1.4.1.37950.1.1.5.12.2.2.8.1.3
-- 1.3.6.1.4.1.37950.1.1.5.12.2.2.8.1.3
-- 1.3.6.1.4.1.37950.1.1.5.12.2.2.8.1.3
-- 1.3.6.1.4.1.37950.1.1.5.12.2.2.8.1.3
-- 1.3.6.1.4.1.37950.1.1.5.12.2.2.8.1.3
-- 1.3.6.1.4.1.37950.1.1.5.12.2.2.8.1.3
-- 1.3.6.1.4.1.37950.1.1.5.12.2.2.8.1.3
-- 1.3.6.1.4.1.37950.1.1.5.12.2.2.8.1.3
		-- 1.3.6.1.4.1.37950.1.1.5.12.2.2.8.1.3
		upgradeOnuLlid OBJECT-TYPE
			SYNTAX Integer32
			MAX-ACCESS read-write
			STATUS current
			DESCRIPTION
				"Description."
			::= { upgradeOnuStatusEntry 3 }

		
--          1.3.6.1.4.1.37950.1.1.5.12.2.2.8.1.4
-- 1.3.6.1.4.1.37950.1.1.5.12.2.2.8.1.4
-- 1.3.6.1.4.1.37950.1.1.5.12.2.2.8.1.4
-- 1.3.6.1.4.1.37950.1.1.5.12.2.2.8.1.4
-- 1.3.6.1.4.1.37950.1.1.5.12.2.2.8.1.4
-- 1.3.6.1.4.1.37950.1.1.5.12.2.2.8.1.4
-- 1.3.6.1.4.1.37950.1.1.5.12.2.2.8.1.4
-- 1.3.6.1.4.1.37950.1.1.5.12.2.2.8.1.4
-- 1.3.6.1.4.1.37950.1.1.5.12.2.2.8.1.4
		-- 1.3.6.1.4.1.37950.1.1.5.12.2.2.8.1.4
		upgradeOnuStatusS OBJECT-TYPE
			SYNTAX OCTET STRING
			MAX-ACCESS read-write
			STATUS current
			DESCRIPTION
				"Description."
			::= { upgradeOnuStatusEntry 4 }

		
--          1.3.6.1.4.1.37950.1.1.5.12.2.2.8.1.5
-- 1.3.6.1.4.1.37950.1.1.5.12.2.2.8.1.5
-- 1.3.6.1.4.1.37950.1.1.5.12.2.2.8.1.5
-- 1.3.6.1.4.1.37950.1.1.5.12.2.2.8.1.5
-- 1.3.6.1.4.1.37950.1.1.5.12.2.2.8.1.5
-- 1.3.6.1.4.1.37950.1.1.5.12.2.2.8.1.5
-- 1.3.6.1.4.1.37950.1.1.5.12.2.2.8.1.5
-- 1.3.6.1.4.1.37950.1.1.5.12.2.2.8.1.5
-- 1.3.6.1.4.1.37950.1.1.5.12.2.2.8.1.5
		-- 1.3.6.1.4.1.37950.1.1.5.12.2.2.8.1.5
		upgradeOnuStatusProcess OBJECT-TYPE
			SYNTAX OCTET STRING
			MAX-ACCESS read-write
			STATUS current
			DESCRIPTION
				"Description."
			::= { upgradeOnuStatusEntry 5 }

		
--              1.3.6.1.4.1.37950.1.1.5.12.2.2.1
-- 1.3.6.1.4.1.37950.1.1.5.12.2.2.9
-- 1.3.6.1.4.1.37950.1.1.5.12.2.2.9
-- 1.3.6.1.4.1.37950.1.1.5.12.2.2.9
-- 1.3.6.1.4.1.37950.1.1.5.12.2.2.9
-- 1.3.6.1.4.1.37950.1.1.5.12.2.2.9
-- 1.3.6.1.4.1.37950.1.1.5.12.2.2.9
-- 1.3.6.1.4.1.37950.1.1.5.12.2.2.9
-- 1.3.6.1.4.1.37950.1.1.5.12.2.2.9
		-- 1.3.6.1.4.1.37950.1.1.5.12.2.2.9
		autoUpgrade OBJECT IDENTIFIER ::= { onuUpgrade 9 }

		
--              1.3.6.1.4.1.37950.1.1.5.12.2.2.1
-- 1.3.6.1.4.1.37950.1.1.5.12.2.2.9.1
-- 1.3.6.1.4.1.37950.1.1.5.12.2.2.9.1
-- 1.3.6.1.4.1.37950.1.1.5.12.2.2.9.1
-- 1.3.6.1.4.1.37950.1.1.5.12.2.2.9.1
-- 1.3.6.1.4.1.37950.1.1.5.12.2.2.9.1
-- 1.3.6.1.4.1.37950.1.1.5.12.2.2.9.1
-- 1.3.6.1.4.1.37950.1.1.5.12.2.2.9.1
-- 1.3.6.1.4.1.37950.1.1.5.12.2.2.9.1
		-- 1.3.6.1.4.1.37950.1.1.5.12.2.2.9.1
		autoUpgradeCreate OBJECT IDENTIFIER ::= { autoUpgrade 1 }

		
--              1.3.6.1.4.1.37950.1.1.5.12.2.2.1.1
-- 1.3.6.1.4.1.37950.1.1.5.12.2.2.9.1.1
-- 1.3.6.1.4.1.37950.1.1.5.12.2.2.9.1.1
-- 1.3.6.1.4.1.37950.1.1.5.12.2.2.9.1.1
-- 1.3.6.1.4.1.37950.1.1.5.12.2.2.9.1.1
-- 1.3.6.1.4.1.37950.1.1.5.12.2.2.9.1.1
-- 1.3.6.1.4.1.37950.1.1.5.12.2.2.9.1.1
-- 1.3.6.1.4.1.37950.1.1.5.12.2.2.9.1.1
-- 1.3.6.1.4.1.37950.1.1.5.12.2.2.9.1.1
		-- 1.3.6.1.4.1.37950.1.1.5.12.2.2.9.1.1
		autoForceMode OBJECT-TYPE
			SYNTAX INTEGER
				{
				disable(0),
				enable(1),
				match(2)
				}
			MAX-ACCESS read-write
			STATUS current
			DESCRIPTION
				"Description."
			::= { autoUpgradeCreate 1 }

		
--              1.3.6.1.4.1.37950.1.1.5.12.2.2.1.2
-- 1.3.6.1.4.1.37950.1.1.5.12.2.2.9.1.2
-- 1.3.6.1.4.1.37950.1.1.5.12.2.2.9.1.2
-- 1.3.6.1.4.1.37950.1.1.5.12.2.2.9.1.2
-- 1.3.6.1.4.1.37950.1.1.5.12.2.2.9.1.2
-- 1.3.6.1.4.1.37950.1.1.5.12.2.2.9.1.2
-- 1.3.6.1.4.1.37950.1.1.5.12.2.2.9.1.2
-- 1.3.6.1.4.1.37950.1.1.5.12.2.2.9.1.2
-- 1.3.6.1.4.1.37950.1.1.5.12.2.2.9.1.2
		-- 1.3.6.1.4.1.37950.1.1.5.12.2.2.9.1.2
		autoVendorID OBJECT-TYPE
			SYNTAX OCTET STRING (SIZE (1..4))
			MAX-ACCESS read-write
			STATUS current
			DESCRIPTION
				"Description."
			::= { autoUpgradeCreate 2 }

		
--              1.3.6.1.4.1.37950.1.1.5.12.2.2.1.3
-- 1.3.6.1.4.1.37950.1.1.5.12.2.2.9.1.3
-- 1.3.6.1.4.1.37950.1.1.5.12.2.2.9.1.3
-- 1.3.6.1.4.1.37950.1.1.5.12.2.2.9.1.3
-- 1.3.6.1.4.1.37950.1.1.5.12.2.2.9.1.3
-- 1.3.6.1.4.1.37950.1.1.5.12.2.2.9.1.3
-- 1.3.6.1.4.1.37950.1.1.5.12.2.2.9.1.3
-- 1.3.6.1.4.1.37950.1.1.5.12.2.2.9.1.3
-- 1.3.6.1.4.1.37950.1.1.5.12.2.2.9.1.3
		-- 1.3.6.1.4.1.37950.1.1.5.12.2.2.9.1.3
		autoModelID OBJECT-TYPE
			SYNTAX OCTET STRING (SIZE (1..4))
			MAX-ACCESS read-write
			STATUS current
			DESCRIPTION
				"Description."
			::= { autoUpgradeCreate 3 }

		
--              1.3.6.1.4.1.37950.1.1.5.12.2.2.1.1
-- 1.3.6.1.4.1.37950.1.1.5.12.2.2.9.1.4
-- 1.3.6.1.4.1.37950.1.1.5.12.2.2.9.1.4
-- 1.3.6.1.4.1.37950.1.1.5.12.2.2.9.1.4
-- 1.3.6.1.4.1.37950.1.1.5.12.2.2.9.1.4
-- 1.3.6.1.4.1.37950.1.1.5.12.2.2.9.1.4
-- 1.3.6.1.4.1.37950.1.1.5.12.2.2.9.1.4
-- 1.3.6.1.4.1.37950.1.1.5.12.2.2.9.1.4
-- 1.3.6.1.4.1.37950.1.1.5.12.2.2.9.1.4
		-- 1.3.6.1.4.1.37950.1.1.5.12.2.2.9.1.4
		autoSoftwareVersion OBJECT-TYPE
			SYNTAX OCTET STRING (SIZE (1..16))
			MAX-ACCESS read-write
			STATUS current
			DESCRIPTION
				"Description."
			::= { autoUpgradeCreate 4 }

		
--              1.3.6.1.4.1.37950.1.1.5.12.2.2.1.1
-- 1.3.6.1.4.1.37950.1.1.5.12.2.2.9.1.5
-- 1.3.6.1.4.1.37950.1.1.5.12.2.2.9.1.5
-- 1.3.6.1.4.1.37950.1.1.5.12.2.2.9.1.5
-- 1.3.6.1.4.1.37950.1.1.5.12.2.2.9.1.5
-- 1.3.6.1.4.1.37950.1.1.5.12.2.2.9.1.5
-- 1.3.6.1.4.1.37950.1.1.5.12.2.2.9.1.5
-- 1.3.6.1.4.1.37950.1.1.5.12.2.2.9.1.5
-- 1.3.6.1.4.1.37950.1.1.5.12.2.2.9.1.5
		-- 1.3.6.1.4.1.37950.1.1.5.12.2.2.9.1.5
		autoImageName OBJECT-TYPE
			SYNTAX OCTET STRING (SIZE (1..64))
			MAX-ACCESS read-write
			STATUS current
			DESCRIPTION
				"Description."
			::= { autoUpgradeCreate 5 }

		
--              1.3.6.1.4.1.37950.1.1.5.12.2.2.1.1
-- 1.3.6.1.4.1.37950.1.1.5.12.2.2.9.1.6
-- 1.3.6.1.4.1.37950.1.1.5.12.2.2.9.1.6
-- 1.3.6.1.4.1.37950.1.1.5.12.2.2.9.1.6
-- 1.3.6.1.4.1.37950.1.1.5.12.2.2.9.1.6
-- 1.3.6.1.4.1.37950.1.1.5.12.2.2.9.1.6
-- 1.3.6.1.4.1.37950.1.1.5.12.2.2.9.1.6
-- 1.3.6.1.4.1.37950.1.1.5.12.2.2.9.1.6
-- 1.3.6.1.4.1.37950.1.1.5.12.2.2.9.1.6
		-- 1.3.6.1.4.1.37950.1.1.5.12.2.2.9.1.6
		autoTftpServerIP OBJECT-TYPE
			SYNTAX OCTET STRING (SIZE (1..64))
			MAX-ACCESS read-write
			STATUS current
			DESCRIPTION
				"Description."
			::= { autoUpgradeCreate 6 }

		
--              1.3.6.1.4.1.37950.1.1.5.12.2.2.1.1
-- 1.3.6.1.4.1.37950.1.1.5.12.2.2.9.1.7
-- 1.3.6.1.4.1.37950.1.1.5.12.2.2.9.1.7
-- 1.3.6.1.4.1.37950.1.1.5.12.2.2.9.1.7
-- 1.3.6.1.4.1.37950.1.1.5.12.2.2.9.1.7
-- 1.3.6.1.4.1.37950.1.1.5.12.2.2.9.1.7
-- 1.3.6.1.4.1.37950.1.1.5.12.2.2.9.1.7
-- 1.3.6.1.4.1.37950.1.1.5.12.2.2.9.1.7
-- 1.3.6.1.4.1.37950.1.1.5.12.2.2.9.1.7
		-- 1.3.6.1.4.1.37950.1.1.5.12.2.2.9.1.7
		autoCreateAction OBJECT-TYPE
			SYNTAX INTEGER { submit(1) }
			MAX-ACCESS read-write
			STATUS current
			DESCRIPTION
				"Description."
			::= { autoUpgradeCreate 7 }

		
--       1.3.6.1.4.1.37950.1.1.5.12.2.2.9.1.8
-- 1.3.6.1.4.1.37950.1.1.5.12.2.2.9.1.8
-- 1.3.6.1.4.1.37950.1.1.5.12.2.2.9.1.8
-- 1.3.6.1.4.1.37950.1.1.5.12.2.2.9.1.8
-- 1.3.6.1.4.1.37950.1.1.5.12.2.2.9.1.8
-- 1.3.6.1.4.1.37950.1.1.5.12.2.2.9.1.8
		-- 1.3.6.1.4.1.37950.1.1.5.12.2.2.9.1.8
		autoOui1 OBJECT-TYPE
			SYNTAX OCTET STRING
			MAX-ACCESS read-write
			STATUS current
			DESCRIPTION
				"Description."
			DEFVAL { "0" }
			::= { autoUpgradeCreate 8 }

		
--       1.3.6.1.4.1.37950.1.1.5.12.2.2.9.1.9
-- 1.3.6.1.4.1.37950.1.1.5.12.2.2.9.1.9
-- 1.3.6.1.4.1.37950.1.1.5.12.2.2.9.1.9
-- 1.3.6.1.4.1.37950.1.1.5.12.2.2.9.1.9
-- 1.3.6.1.4.1.37950.1.1.5.12.2.2.9.1.9
-- 1.3.6.1.4.1.37950.1.1.5.12.2.2.9.1.9
		-- 1.3.6.1.4.1.37950.1.1.5.12.2.2.9.1.9
		autoOui2 OBJECT-TYPE
			SYNTAX OCTET STRING
			MAX-ACCESS read-write
			STATUS current
			DESCRIPTION
				"Description."
			DEFVAL { "0" }
			::= { autoUpgradeCreate 9 }

		
--       1.3.6.1.4.1.37950.1.1.5.12.2.2.9.1.10
-- 1.3.6.1.4.1.37950.1.1.5.12.2.2.9.1.10
-- 1.3.6.1.4.1.37950.1.1.5.12.2.2.9.1.10
-- 1.3.6.1.4.1.37950.1.1.5.12.2.2.9.1.10
-- 1.3.6.1.4.1.37950.1.1.5.12.2.2.9.1.10
-- 1.3.6.1.4.1.37950.1.1.5.12.2.2.9.1.10
		-- 1.3.6.1.4.1.37950.1.1.5.12.2.2.9.1.10
		autoOui3 OBJECT-TYPE
			SYNTAX OCTET STRING
			MAX-ACCESS read-write
			STATUS current
			DESCRIPTION
				"Description."
			DEFVAL { "0" }
			::= { autoUpgradeCreate 10 }

		
--       1.3.6.1.4.1.37950.1.1.5.12.2.2.9.1.11
-- 1.3.6.1.4.1.37950.1.1.5.12.2.2.9.1.11
-- 1.3.6.1.4.1.37950.1.1.5.12.2.2.9.1.11
-- 1.3.6.1.4.1.37950.1.1.5.12.2.2.9.1.11
-- 1.3.6.1.4.1.37950.1.1.5.12.2.2.9.1.11
-- 1.3.6.1.4.1.37950.1.1.5.12.2.2.9.1.11
		-- 1.3.6.1.4.1.37950.1.1.5.12.2.2.9.1.11
		autoSourceVersion1 OBJECT-TYPE
			SYNTAX OCTET STRING
			MAX-ACCESS read-write
			STATUS current
			DESCRIPTION
				"Description."
			DEFVAL { "0" }
			::= { autoUpgradeCreate 11 }

		
--       1.3.6.1.4.1.37950.1.1.5.12.2.2.9.1.12
-- 1.3.6.1.4.1.37950.1.1.5.12.2.2.9.1.12
-- 1.3.6.1.4.1.37950.1.1.5.12.2.2.9.1.12
-- 1.3.6.1.4.1.37950.1.1.5.12.2.2.9.1.12
-- 1.3.6.1.4.1.37950.1.1.5.12.2.2.9.1.12
-- 1.3.6.1.4.1.37950.1.1.5.12.2.2.9.1.12
		-- 1.3.6.1.4.1.37950.1.1.5.12.2.2.9.1.12
		autoSourceVersion2 OBJECT-TYPE
			SYNTAX OCTET STRING
			MAX-ACCESS read-write
			STATUS current
			DESCRIPTION
				"Description."
			DEFVAL { "0" }
			::= { autoUpgradeCreate 12 }

		
--       1.3.6.1.4.1.37950.1.1.5.12.2.2.9.1.13
-- 1.3.6.1.4.1.37950.1.1.5.12.2.2.9.1.13
-- 1.3.6.1.4.1.37950.1.1.5.12.2.2.9.1.13
-- 1.3.6.1.4.1.37950.1.1.5.12.2.2.9.1.13
-- 1.3.6.1.4.1.37950.1.1.5.12.2.2.9.1.13
-- 1.3.6.1.4.1.37950.1.1.5.12.2.2.9.1.13
		-- 1.3.6.1.4.1.37950.1.1.5.12.2.2.9.1.13
		autoSourceVersion3 OBJECT-TYPE
			SYNTAX OCTET STRING
			MAX-ACCESS read-write
			STATUS current
			DESCRIPTION
				"Description."
			DEFVAL { "0" }
			::= { autoUpgradeCreate 13 }

		
--              1.3.6.1.4.1.37950.1.1.5.12.2.2.1
-- 1.3.6.1.4.1.37950.1.1.5.12.2.2.9.2
-- 1.3.6.1.4.1.37950.1.1.5.12.2.2.9.2
-- 1.3.6.1.4.1.37950.1.1.5.12.2.2.9.2
-- 1.3.6.1.4.1.37950.1.1.5.12.2.2.9.2
-- 1.3.6.1.4.1.37950.1.1.5.12.2.2.9.2
-- 1.3.6.1.4.1.37950.1.1.5.12.2.2.9.2
-- 1.3.6.1.4.1.37950.1.1.5.12.2.2.9.2
-- 1.3.6.1.4.1.37950.1.1.5.12.2.2.9.2
		-- 1.3.6.1.4.1.37950.1.1.5.12.2.2.9.2
		autoUpgradeDelete OBJECT IDENTIFIER ::= { autoUpgrade 2 }

		
--              1.3.6.1.4.1.37950.1.1.5.12.2.2.1.2
-- 1.3.6.1.4.1.37950.1.1.5.12.2.2.9.2.1
-- 1.3.6.1.4.1.37950.1.1.5.12.2.2.9.2.1
-- 1.3.6.1.4.1.37950.1.1.5.12.2.2.9.2.1
-- 1.3.6.1.4.1.37950.1.1.5.12.2.2.9.2.1
-- 1.3.6.1.4.1.37950.1.1.5.12.2.2.9.2.1
-- 1.3.6.1.4.1.37950.1.1.5.12.2.2.9.2.1
-- 1.3.6.1.4.1.37950.1.1.5.12.2.2.9.2.1
-- 1.3.6.1.4.1.37950.1.1.5.12.2.2.9.2.1
		-- 1.3.6.1.4.1.37950.1.1.5.12.2.2.9.2.1
		deleteVendorID OBJECT-TYPE
			SYNTAX OCTET STRING (SIZE (1..4))
			MAX-ACCESS read-write
			STATUS current
			DESCRIPTION
				"Description."
			::= { autoUpgradeDelete 1 }

		
--              1.3.6.1.4.1.37950.1.1.5.12.2.2.1.3
-- 1.3.6.1.4.1.37950.1.1.5.12.2.2.9.2.2
-- 1.3.6.1.4.1.37950.1.1.5.12.2.2.9.2.2
-- 1.3.6.1.4.1.37950.1.1.5.12.2.2.9.2.2
-- 1.3.6.1.4.1.37950.1.1.5.12.2.2.9.2.2
-- 1.3.6.1.4.1.37950.1.1.5.12.2.2.9.2.2
-- 1.3.6.1.4.1.37950.1.1.5.12.2.2.9.2.2
-- 1.3.6.1.4.1.37950.1.1.5.12.2.2.9.2.2
-- 1.3.6.1.4.1.37950.1.1.5.12.2.2.9.2.2
		-- 1.3.6.1.4.1.37950.1.1.5.12.2.2.9.2.2
		deleteModelID OBJECT-TYPE
			SYNTAX OCTET STRING (SIZE (1..4))
			MAX-ACCESS read-write
			STATUS current
			DESCRIPTION
				"Description."
			::= { autoUpgradeDelete 2 }

		
--              1.3.6.1.4.1.37950.1.1.5.12.2.2.1.1
-- 1.3.6.1.4.1.37950.1.1.5.12.2.2.9.2.3
-- 1.3.6.1.4.1.37950.1.1.5.12.2.2.9.2.3
-- 1.3.6.1.4.1.37950.1.1.5.12.2.2.9.2.3
-- 1.3.6.1.4.1.37950.1.1.5.12.2.2.9.2.3
-- 1.3.6.1.4.1.37950.1.1.5.12.2.2.9.2.3
-- 1.3.6.1.4.1.37950.1.1.5.12.2.2.9.2.3
-- 1.3.6.1.4.1.37950.1.1.5.12.2.2.9.2.3
-- 1.3.6.1.4.1.37950.1.1.5.12.2.2.9.2.3
		-- 1.3.6.1.4.1.37950.1.1.5.12.2.2.9.2.3
		autoDeleteAction OBJECT-TYPE
			SYNTAX INTEGER { delete(1) }
			MAX-ACCESS read-write
			STATUS current
			DESCRIPTION
				"Description."
			::= { autoUpgradeDelete 3 }

		
--       1.3.6.1.4.1.37950.1.1.5.12.2.2.9.2.4
-- 1.3.6.1.4.1.37950.1.1.5.12.2.2.9.2.4
-- 1.3.6.1.4.1.37950.1.1.5.12.2.2.9.2.4
-- 1.3.6.1.4.1.37950.1.1.5.12.2.2.9.2.4
-- 1.3.6.1.4.1.37950.1.1.5.12.2.2.9.2.4
-- 1.3.6.1.4.1.37950.1.1.5.12.2.2.9.2.4
		-- 1.3.6.1.4.1.37950.1.1.5.12.2.2.9.2.4
		deleteForce OBJECT-TYPE
			SYNTAX OCTET STRING
			MAX-ACCESS read-write
			STATUS current
			DESCRIPTION
				"Description."
			::= { autoUpgradeDelete 4 }

		
--       1.3.6.1.4.1.37950.1.1.5.12.2.2.9.2.5
-- 1.3.6.1.4.1.37950.1.1.5.12.2.2.9.2.5
-- 1.3.6.1.4.1.37950.1.1.5.12.2.2.9.2.5
-- 1.3.6.1.4.1.37950.1.1.5.12.2.2.9.2.5
-- 1.3.6.1.4.1.37950.1.1.5.12.2.2.9.2.5
-- 1.3.6.1.4.1.37950.1.1.5.12.2.2.9.2.5
		-- 1.3.6.1.4.1.37950.1.1.5.12.2.2.9.2.5
		deleteSourceVersion OBJECT-TYPE
			SYNTAX OCTET STRING
			MAX-ACCESS read-write
			STATUS current
			DESCRIPTION
				"Description."
			::= { autoUpgradeDelete 5 }

		
--              1.3.6.1.4.1.37950.1.1.5.12.2.2.8
-- 1.3.6.1.4.1.37950.1.1.5.12.2.2.9.3
-- 1.3.6.1.4.1.37950.1.1.5.12.2.2.9.3
-- 1.3.6.1.4.1.37950.1.1.5.12.2.2.9.3
-- 1.3.6.1.4.1.37950.1.1.5.12.2.2.9.3
-- 1.3.6.1.4.1.37950.1.1.5.12.2.2.9.3
-- 1.3.6.1.4.1.37950.1.1.5.12.2.2.9.3
-- 1.3.6.1.4.1.37950.1.1.5.12.2.2.9.3
-- 1.3.6.1.4.1.37950.1.1.5.12.2.2.9.3
		-- 1.3.6.1.4.1.37950.1.1.5.12.2.2.9.3
		autoUpgradeTable OBJECT-TYPE
			SYNTAX SEQUENCE OF AutoUpgradeEntry
			MAX-ACCESS not-accessible
			STATUS current
			DESCRIPTION
				"Description."
			::= { autoUpgrade 3 }

		
--              1.3.6.1.4.1.37950.1.1.5.12.2.2.8.1
-- 1.3.6.1.4.1.37950.1.1.5.12.2.2.9.3.1
-- 1.3.6.1.4.1.37950.1.1.5.12.2.2.9.3.1
-- 1.3.6.1.4.1.37950.1.1.5.12.2.2.9.3.1
-- 1.3.6.1.4.1.37950.1.1.5.12.2.2.9.3.1
-- 1.3.6.1.4.1.37950.1.1.5.12.2.2.9.3.1
-- 1.3.6.1.4.1.37950.1.1.5.12.2.2.9.3.1
-- 1.3.6.1.4.1.37950.1.1.5.12.2.2.9.3.1
-- 1.3.6.1.4.1.37950.1.1.5.12.2.2.9.3.1
		-- 1.3.6.1.4.1.37950.1.1.5.12.2.2.9.3.1
		autoUpgradeEntry OBJECT-TYPE
			SYNTAX AutoUpgradeEntry
			MAX-ACCESS not-accessible
			STATUS current
			DESCRIPTION
				"Description."
			INDEX { autoUpgradeIndex }
			::= { autoUpgradeTable 1 }

		
		AutoUpgradeEntry ::=
			SEQUENCE { 
				autoUpgradeIndex
					Integer32,
				autoForceModeS
					INTEGER,
				autoVendorIDS
					OCTET STRING,
				autoModelIDS
					OCTET STRING,
				autoSoftwareVersionS
					OCTET STRING,
				autoImageNameS
					OCTET STRING,
				autoTftpServerIPS
					OCTET STRING,
				autoOuisS
					OCTET STRING,
				autoSourceVersionS
					OCTET STRING
			 }

--              1.3.6.1.4.1.37950.1.1.5.12.2.2.8.1.1
-- 1.3.6.1.4.1.37950.1.1.5.12.2.2.9.3.1.1
-- 1.3.6.1.4.1.37950.1.1.5.12.2.2.9.3.1.1
-- 1.3.6.1.4.1.37950.1.1.5.12.2.2.9.3.1.1
-- 1.3.6.1.4.1.37950.1.1.5.12.2.2.9.3.1.1
-- 1.3.6.1.4.1.37950.1.1.5.12.2.2.9.3.1.1
-- 1.3.6.1.4.1.37950.1.1.5.12.2.2.9.3.1.1
-- 1.3.6.1.4.1.37950.1.1.5.12.2.2.9.3.1.1
-- 1.3.6.1.4.1.37950.1.1.5.12.2.2.9.3.1.1
		-- 1.3.6.1.4.1.37950.1.1.5.12.2.2.9.3.1.1
		autoUpgradeIndex OBJECT-TYPE
			SYNTAX Integer32 (1..64)
			MAX-ACCESS read-only
			STATUS current
			DESCRIPTION
				"Description."
			::= { autoUpgradeEntry 1 }

		
--              1.3.6.1.4.1.37950.1.1.5.12.2.2.8.1.1
-- 1.3.6.1.4.1.37950.1.1.5.12.2.2.9.3.1.2
-- 1.3.6.1.4.1.37950.1.1.5.12.2.2.9.3.1.2
-- 1.3.6.1.4.1.37950.1.1.5.12.2.2.9.3.1.2
-- 1.3.6.1.4.1.37950.1.1.5.12.2.2.9.3.1.2
-- 1.3.6.1.4.1.37950.1.1.5.12.2.2.9.3.1.2
-- 1.3.6.1.4.1.37950.1.1.5.12.2.2.9.3.1.2
-- 1.3.6.1.4.1.37950.1.1.5.12.2.2.9.3.1.2
-- 1.3.6.1.4.1.37950.1.1.5.12.2.2.9.3.1.2
		-- 1.3.6.1.4.1.37950.1.1.5.12.2.2.9.3.1.2
		autoForceModeS OBJECT-TYPE
			SYNTAX INTEGER
				{
				disable(0),
				enable(1),
				match(2)
				}
			MAX-ACCESS read-only
			STATUS current
			DESCRIPTION
				"Description."
			::= { autoUpgradeEntry 2 }

		
--              1.3.6.1.4.1.37950.1.1.5.12.2.2.8.1.2
-- 1.3.6.1.4.1.37950.1.1.5.12.2.2.9.3.1.3
-- 1.3.6.1.4.1.37950.1.1.5.12.2.2.9.3.1.3
-- 1.3.6.1.4.1.37950.1.1.5.12.2.2.9.3.1.3
-- 1.3.6.1.4.1.37950.1.1.5.12.2.2.9.3.1.3
-- 1.3.6.1.4.1.37950.1.1.5.12.2.2.9.3.1.3
-- 1.3.6.1.4.1.37950.1.1.5.12.2.2.9.3.1.3
-- 1.3.6.1.4.1.37950.1.1.5.12.2.2.9.3.1.3
-- 1.3.6.1.4.1.37950.1.1.5.12.2.2.9.3.1.3
		-- 1.3.6.1.4.1.37950.1.1.5.12.2.2.9.3.1.3
		autoVendorIDS OBJECT-TYPE
			SYNTAX OCTET STRING (SIZE (1..4))
			MAX-ACCESS read-only
			STATUS current
			DESCRIPTION
				"Description."
			::= { autoUpgradeEntry 3 }

		
--              1.3.6.1.4.1.37950.1.1.5.12.2.2.8.1.3
-- 1.3.6.1.4.1.37950.1.1.5.12.2.2.9.3.1.4
-- 1.3.6.1.4.1.37950.1.1.5.12.2.2.9.3.1.4
-- 1.3.6.1.4.1.37950.1.1.5.12.2.2.9.3.1.4
-- 1.3.6.1.4.1.37950.1.1.5.12.2.2.9.3.1.4
-- 1.3.6.1.4.1.37950.1.1.5.12.2.2.9.3.1.4
-- 1.3.6.1.4.1.37950.1.1.5.12.2.2.9.3.1.4
-- 1.3.6.1.4.1.37950.1.1.5.12.2.2.9.3.1.4
-- 1.3.6.1.4.1.37950.1.1.5.12.2.2.9.3.1.4
		-- 1.3.6.1.4.1.37950.1.1.5.12.2.2.9.3.1.4
		autoModelIDS OBJECT-TYPE
			SYNTAX OCTET STRING (SIZE (1..4))
			MAX-ACCESS read-only
			STATUS current
			DESCRIPTION
				"Description."
			::= { autoUpgradeEntry 4 }

		
--              1.3.6.1.4.1.37950.1.1.5.12.2.2.8.1.4
-- 1.3.6.1.4.1.37950.1.1.5.12.2.2.9.3.1.5
-- 1.3.6.1.4.1.37950.1.1.5.12.2.2.9.3.1.5
-- 1.3.6.1.4.1.37950.1.1.5.12.2.2.9.3.1.5
-- 1.3.6.1.4.1.37950.1.1.5.12.2.2.9.3.1.5
-- 1.3.6.1.4.1.37950.1.1.5.12.2.2.9.3.1.5
-- 1.3.6.1.4.1.37950.1.1.5.12.2.2.9.3.1.5
-- 1.3.6.1.4.1.37950.1.1.5.12.2.2.9.3.1.5
-- 1.3.6.1.4.1.37950.1.1.5.12.2.2.9.3.1.5
		-- 1.3.6.1.4.1.37950.1.1.5.12.2.2.9.3.1.5
		autoSoftwareVersionS OBJECT-TYPE
			SYNTAX OCTET STRING (SIZE (1..16))
			MAX-ACCESS read-only
			STATUS current
			DESCRIPTION
				"Description."
			::= { autoUpgradeEntry 5 }

		
--              1.3.6.1.4.1.37950.1.1.5.12.2.2.8.1.5
-- 1.3.6.1.4.1.37950.1.1.5.12.2.2.9.3.1.6
-- 1.3.6.1.4.1.37950.1.1.5.12.2.2.9.3.1.6
-- 1.3.6.1.4.1.37950.1.1.5.12.2.2.9.3.1.6
-- 1.3.6.1.4.1.37950.1.1.5.12.2.2.9.3.1.6
-- 1.3.6.1.4.1.37950.1.1.5.12.2.2.9.3.1.6
-- 1.3.6.1.4.1.37950.1.1.5.12.2.2.9.3.1.6
-- 1.3.6.1.4.1.37950.1.1.5.12.2.2.9.3.1.6
-- 1.3.6.1.4.1.37950.1.1.5.12.2.2.9.3.1.6
		-- 1.3.6.1.4.1.37950.1.1.5.12.2.2.9.3.1.6
		autoImageNameS OBJECT-TYPE
			SYNTAX OCTET STRING (SIZE (1..64))
			MAX-ACCESS read-only
			STATUS current
			DESCRIPTION
				"Description."
			::= { autoUpgradeEntry 6 }

		
--              1.3.6.1.4.1.37950.1.1.5.12.2.2.8.1.5
-- 1.3.6.1.4.1.37950.1.1.5.12.2.2.9.3.1.7
-- 1.3.6.1.4.1.37950.1.1.5.12.2.2.9.3.1.7
-- 1.3.6.1.4.1.37950.1.1.5.12.2.2.9.3.1.7
-- 1.3.6.1.4.1.37950.1.1.5.12.2.2.9.3.1.7
-- 1.3.6.1.4.1.37950.1.1.5.12.2.2.9.3.1.7
-- 1.3.6.1.4.1.37950.1.1.5.12.2.2.9.3.1.7
-- 1.3.6.1.4.1.37950.1.1.5.12.2.2.9.3.1.7
-- 1.3.6.1.4.1.37950.1.1.5.12.2.2.9.3.1.7
		-- 1.3.6.1.4.1.37950.1.1.5.12.2.2.9.3.1.7
		autoTftpServerIPS OBJECT-TYPE
			SYNTAX OCTET STRING (SIZE (1..64))
			MAX-ACCESS read-only
			STATUS current
			DESCRIPTION
				"Description."
			::= { autoUpgradeEntry 7 }

		
--       1.3.6.1.4.1.37950.1.1.5.12.2.2.9.3.1.8
-- 1.3.6.1.4.1.37950.1.1.5.12.2.2.9.3.1.8
-- 1.3.6.1.4.1.37950.1.1.5.12.2.2.9.3.1.8
-- 1.3.6.1.4.1.37950.1.1.5.12.2.2.9.3.1.8
-- 1.3.6.1.4.1.37950.1.1.5.12.2.2.9.3.1.8
-- 1.3.6.1.4.1.37950.1.1.5.12.2.2.9.3.1.8
		-- 1.3.6.1.4.1.37950.1.1.5.12.2.2.9.3.1.8
		autoOuisS OBJECT-TYPE
			SYNTAX OCTET STRING
			MAX-ACCESS read-write
			STATUS current
			DESCRIPTION
				"Description."
			::= { autoUpgradeEntry 8 }

		
--       1.3.6.1.4.1.37950.1.1.5.12.2.2.9.3.1.9
-- 1.3.6.1.4.1.37950.1.1.5.12.2.2.9.3.1.9
-- 1.3.6.1.4.1.37950.1.1.5.12.2.2.9.3.1.9
-- 1.3.6.1.4.1.37950.1.1.5.12.2.2.9.3.1.9
-- 1.3.6.1.4.1.37950.1.1.5.12.2.2.9.3.1.9
-- 1.3.6.1.4.1.37950.1.1.5.12.2.2.9.3.1.9
		-- 1.3.6.1.4.1.37950.1.1.5.12.2.2.9.3.1.9
		autoSourceVersionS OBJECT-TYPE
			SYNTAX OCTET STRING
			MAX-ACCESS read-write
			STATUS current
			DESCRIPTION
				"Description."
			::= { autoUpgradeEntry 9 }

		
--          1.3.6.1.4.1.37950.1.1.5.12.2.2.9.4
-- 1.3.6.1.4.1.37950.1.1.5.12.2.2.9.4
-- 1.3.6.1.4.1.37950.1.1.5.12.2.2.9.4
-- 1.3.6.1.4.1.37950.1.1.5.12.2.2.9.4
-- 1.3.6.1.4.1.37950.1.1.5.12.2.2.9.4
-- 1.3.6.1.4.1.37950.1.1.5.12.2.2.9.4
-- 1.3.6.1.4.1.37950.1.1.5.12.2.2.9.4
-- 1.3.6.1.4.1.37950.1.1.5.12.2.2.9.4
-- 1.3.6.1.4.1.37950.1.1.5.12.2.2.9.4
		-- 1.3.6.1.4.1.37950.1.1.5.12.2.2.9.4
		autoUpgradeStatus OBJECT-TYPE
			SYNTAX OCTET STRING
			MAX-ACCESS read-only
			STATUS current
			DESCRIPTION
				"Description."
			::= { autoUpgrade 4 }

		
--          1.3.6.1.4.1.37950.1.1.5.12.2.3
-- 1.3.6.1.4.1.37950.1.1.5.12.2.3
-- 1.3.6.1.4.1.37950.1.1.5.12.2.3
-- 1.3.6.1.4.1.37950.1.1.5.12.2.3
-- 1.3.6.1.4.1.37950.1.1.5.12.2.3
-- 1.3.6.1.4.1.37950.1.1.5.12.2.3
-- 1.3.6.1.4.1.37950.1.1.5.12.2.3
-- 1.3.6.1.4.1.37950.1.1.5.12.2.3
-- 1.3.6.1.4.1.37950.1.1.5.12.2.3
		-- 1.3.6.1.4.1.37950.1.1.5.12.2.3
		onuManagementIp OBJECT IDENTIFIER ::= { onuGlobalCfg 3 }

		
--          1.3.6.1.4.1.37950.1.1.5.12.2.3.1
-- 1.3.6.1.4.1.37950.1.1.5.12.2.3.1
-- 1.3.6.1.4.1.37950.1.1.5.12.2.3.1
-- 1.3.6.1.4.1.37950.1.1.5.12.2.3.1
-- 1.3.6.1.4.1.37950.1.1.5.12.2.3.1
-- 1.3.6.1.4.1.37950.1.1.5.12.2.3.1
-- 1.3.6.1.4.1.37950.1.1.5.12.2.3.1
-- 1.3.6.1.4.1.37950.1.1.5.12.2.3.1
-- 1.3.6.1.4.1.37950.1.1.5.12.2.3.1
		-- 1.3.6.1.4.1.37950.1.1.5.12.2.3.1
		mgmtIpPonNo OBJECT-TYPE
			SYNTAX INTEGER (1..16)
			MAX-ACCESS read-write
			STATUS current
			DESCRIPTION
				"Description."
			::= { onuManagementIp 1 }

		
--          1.3.6.1.4.1.37950.1.1.5.12.2.3.2
-- 1.3.6.1.4.1.37950.1.1.5.12.2.3.2
-- 1.3.6.1.4.1.37950.1.1.5.12.2.3.2
-- 1.3.6.1.4.1.37950.1.1.5.12.2.3.2
-- 1.3.6.1.4.1.37950.1.1.5.12.2.3.2
-- 1.3.6.1.4.1.37950.1.1.5.12.2.3.2
-- 1.3.6.1.4.1.37950.1.1.5.12.2.3.2
-- 1.3.6.1.4.1.37950.1.1.5.12.2.3.2
-- 1.3.6.1.4.1.37950.1.1.5.12.2.3.2
		-- 1.3.6.1.4.1.37950.1.1.5.12.2.3.2
		mgmtIpOnuNo OBJECT-TYPE
			SYNTAX INTEGER (1..65535)
			MAX-ACCESS read-write
			STATUS current
			DESCRIPTION
				"Description."
			::= { onuManagementIp 2 }

		
--          1.3.6.1.4.1.37950.1.1.5.12.2.3.3
-- 1.3.6.1.4.1.37950.1.1.5.12.2.3.3
-- 1.3.6.1.4.1.37950.1.1.5.12.2.3.3
-- 1.3.6.1.4.1.37950.1.1.5.12.2.3.3
-- 1.3.6.1.4.1.37950.1.1.5.12.2.3.3
-- 1.3.6.1.4.1.37950.1.1.5.12.2.3.3
-- 1.3.6.1.4.1.37950.1.1.5.12.2.3.3
-- 1.3.6.1.4.1.37950.1.1.5.12.2.3.3
-- 1.3.6.1.4.1.37950.1.1.5.12.2.3.3
		-- 1.3.6.1.4.1.37950.1.1.5.12.2.3.3
		mgmtIp OBJECT-TYPE
			SYNTAX IpAddress
			MAX-ACCESS read-write
			STATUS current
			DESCRIPTION
				"Description."
			::= { onuManagementIp 3 }

		
--          1.3.6.1.4.1.37950.1.1.5.12.2.3.4
-- 1.3.6.1.4.1.37950.1.1.5.12.2.3.4
-- 1.3.6.1.4.1.37950.1.1.5.12.2.3.4
-- 1.3.6.1.4.1.37950.1.1.5.12.2.3.4
-- 1.3.6.1.4.1.37950.1.1.5.12.2.3.4
-- 1.3.6.1.4.1.37950.1.1.5.12.2.3.4
-- 1.3.6.1.4.1.37950.1.1.5.12.2.3.4
-- 1.3.6.1.4.1.37950.1.1.5.12.2.3.4
-- 1.3.6.1.4.1.37950.1.1.5.12.2.3.4
		-- 1.3.6.1.4.1.37950.1.1.5.12.2.3.4
		mgmtIpMask OBJECT-TYPE
			SYNTAX IpAddress
			MAX-ACCESS read-write
			STATUS current
			DESCRIPTION
				"Description."
			::= { onuManagementIp 4 }

		
--          1.3.6.1.4.1.37950.1.1.5.12.2.3.5
-- 1.3.6.1.4.1.37950.1.1.5.12.2.3.5
-- 1.3.6.1.4.1.37950.1.1.5.12.2.3.5
-- 1.3.6.1.4.1.37950.1.1.5.12.2.3.5
-- 1.3.6.1.4.1.37950.1.1.5.12.2.3.5
-- 1.3.6.1.4.1.37950.1.1.5.12.2.3.5
-- 1.3.6.1.4.1.37950.1.1.5.12.2.3.5
-- 1.3.6.1.4.1.37950.1.1.5.12.2.3.5
-- 1.3.6.1.4.1.37950.1.1.5.12.2.3.5
		-- 1.3.6.1.4.1.37950.1.1.5.12.2.3.5
		mgmtIpGw OBJECT-TYPE
			SYNTAX IpAddress
			MAX-ACCESS read-write
			STATUS current
			DESCRIPTION
				"Description."
			::= { onuManagementIp 5 }

		
--          1.3.6.1.4.1.37950.1.1.5.12.2.3.6
-- 1.3.6.1.4.1.37950.1.1.5.12.2.3.6
-- 1.3.6.1.4.1.37950.1.1.5.12.2.3.6
-- 1.3.6.1.4.1.37950.1.1.5.12.2.3.6
-- 1.3.6.1.4.1.37950.1.1.5.12.2.3.6
-- 1.3.6.1.4.1.37950.1.1.5.12.2.3.6
-- 1.3.6.1.4.1.37950.1.1.5.12.2.3.6
-- 1.3.6.1.4.1.37950.1.1.5.12.2.3.6
-- 1.3.6.1.4.1.37950.1.1.5.12.2.3.6
		-- 1.3.6.1.4.1.37950.1.1.5.12.2.3.6
		mgmtIpCVlan OBJECT-TYPE
			SYNTAX INTEGER (0..4095)
			MAX-ACCESS read-write
			STATUS current
			DESCRIPTION
				"Description."
			::= { onuManagementIp 6 }

		
--          1.3.6.1.4.1.37950.1.1.5.12.2.3.7
-- 1.3.6.1.4.1.37950.1.1.5.12.2.3.7
-- 1.3.6.1.4.1.37950.1.1.5.12.2.3.7
-- 1.3.6.1.4.1.37950.1.1.5.12.2.3.7
-- 1.3.6.1.4.1.37950.1.1.5.12.2.3.7
-- 1.3.6.1.4.1.37950.1.1.5.12.2.3.7
-- 1.3.6.1.4.1.37950.1.1.5.12.2.3.7
-- 1.3.6.1.4.1.37950.1.1.5.12.2.3.7
-- 1.3.6.1.4.1.37950.1.1.5.12.2.3.7
		-- 1.3.6.1.4.1.37950.1.1.5.12.2.3.7
		mgmtIpSVlan OBJECT-TYPE
			SYNTAX INTEGER (0..4095)
			MAX-ACCESS read-write
			STATUS current
			DESCRIPTION
				"Description."
			::= { onuManagementIp 7 }

		
--          1.3.6.1.4.1.37950.1.1.5.12.2.3.8
-- 1.3.6.1.4.1.37950.1.1.5.12.2.3.8
-- 1.3.6.1.4.1.37950.1.1.5.12.2.3.8
-- 1.3.6.1.4.1.37950.1.1.5.12.2.3.8
-- 1.3.6.1.4.1.37950.1.1.5.12.2.3.8
-- 1.3.6.1.4.1.37950.1.1.5.12.2.3.8
-- 1.3.6.1.4.1.37950.1.1.5.12.2.3.8
-- 1.3.6.1.4.1.37950.1.1.5.12.2.3.8
-- 1.3.6.1.4.1.37950.1.1.5.12.2.3.8
		-- 1.3.6.1.4.1.37950.1.1.5.12.2.3.8
		mgmtIpPri OBJECT-TYPE
			SYNTAX INTEGER (0..7)
			MAX-ACCESS read-write
			STATUS current
			DESCRIPTION
				"Description."
			::= { onuManagementIp 8 }

		
--          1.3.6.1.4.1.37950.1.1.5.12.2.3.9
-- 1.3.6.1.4.1.37950.1.1.5.12.2.3.9
-- 1.3.6.1.4.1.37950.1.1.5.12.2.3.9
-- 1.3.6.1.4.1.37950.1.1.5.12.2.3.9
-- 1.3.6.1.4.1.37950.1.1.5.12.2.3.9
-- 1.3.6.1.4.1.37950.1.1.5.12.2.3.9
-- 1.3.6.1.4.1.37950.1.1.5.12.2.3.9
-- 1.3.6.1.4.1.37950.1.1.5.12.2.3.9
-- 1.3.6.1.4.1.37950.1.1.5.12.2.3.9
		-- 1.3.6.1.4.1.37950.1.1.5.12.2.3.9
		mgmtIPAction OBJECT-TYPE
			SYNTAX INTEGER
				{
				commit(1),
				delete(2)
				}
			MAX-ACCESS read-write
			STATUS current
			DESCRIPTION
				"Description."
			::= { onuManagementIp 9 }

		
--          1.3.6.1.4.1.37950.1.1.5.12.2.3.10
-- 1.3.6.1.4.1.37950.1.1.5.12.2.3.10
-- 1.3.6.1.4.1.37950.1.1.5.12.2.3.10
-- 1.3.6.1.4.1.37950.1.1.5.12.2.3.10
-- 1.3.6.1.4.1.37950.1.1.5.12.2.3.10
-- 1.3.6.1.4.1.37950.1.1.5.12.2.3.10
-- 1.3.6.1.4.1.37950.1.1.5.12.2.3.10
-- 1.3.6.1.4.1.37950.1.1.5.12.2.3.10
-- 1.3.6.1.4.1.37950.1.1.5.12.2.3.10
		-- 1.3.6.1.4.1.37950.1.1.5.12.2.3.10
		onuManagementIpTable OBJECT-TYPE
			SYNTAX SEQUENCE OF OnuManagementIpEntry
			MAX-ACCESS not-accessible
			STATUS current
			DESCRIPTION
				"Description."
			::= { onuManagementIp 10 }

		
--          1.3.6.1.4.1.37950.1.1.5.12.2.3.10.1
-- 1.3.6.1.4.1.37950.1.1.5.12.2.3.10.1
-- 1.3.6.1.4.1.37950.1.1.5.12.2.3.10.1
-- 1.3.6.1.4.1.37950.1.1.5.12.2.3.10.1
-- 1.3.6.1.4.1.37950.1.1.5.12.2.3.10.1
-- 1.3.6.1.4.1.37950.1.1.5.12.2.3.10.1
-- 1.3.6.1.4.1.37950.1.1.5.12.2.3.10.1
-- 1.3.6.1.4.1.37950.1.1.5.12.2.3.10.1
-- 1.3.6.1.4.1.37950.1.1.5.12.2.3.10.1
		-- 1.3.6.1.4.1.37950.1.1.5.12.2.3.10.1
		onuManagementIpEntry OBJECT-TYPE
			SYNTAX OnuManagementIpEntry
			MAX-ACCESS not-accessible
			STATUS current
			DESCRIPTION
				"Description."
			INDEX { mgmtIPPonNo, mgmtIPOnuNo }
			::= { onuManagementIpTable 1 }

		
		OnuManagementIpEntry ::=
			SEQUENCE { 
				mgmtIPPonNo
					Integer32,
				mgmtIPOnuNo
					Integer32,
				mgmtIP
					IpAddress,
				mgmtIPMask
					IpAddress,
				mgmtIPGw
					IpAddress,
				mgmtIPCvlan
					Integer32,
				mgmtIPSvlan
					Integer32,
				mgmtIPPri
					Integer32
			 }

--          1.3.6.1.4.1.37950.1.1.5.12.2.3.10.1.1
-- 1.3.6.1.4.1.37950.1.1.5.12.2.3.10.1.1
-- 1.3.6.1.4.1.37950.1.1.5.12.2.3.10.1.1
-- 1.3.6.1.4.1.37950.1.1.5.12.2.3.10.1.1
-- 1.3.6.1.4.1.37950.1.1.5.12.2.3.10.1.1
-- 1.3.6.1.4.1.37950.1.1.5.12.2.3.10.1.1
-- 1.3.6.1.4.1.37950.1.1.5.12.2.3.10.1.1
-- 1.3.6.1.4.1.37950.1.1.5.12.2.3.10.1.1
-- 1.3.6.1.4.1.37950.1.1.5.12.2.3.10.1.1
		-- 1.3.6.1.4.1.37950.1.1.5.12.2.3.10.1.1
		mgmtIPPonNo OBJECT-TYPE
			SYNTAX Integer32 (1..16)
			MAX-ACCESS read-only
			STATUS current
			DESCRIPTION
				"Description."
			::= { onuManagementIpEntry 1 }

		
--          1.3.6.1.4.1.37950.1.1.5.12.2.3.10.1.2
-- 1.3.6.1.4.1.37950.1.1.5.12.2.3.10.1.2
-- 1.3.6.1.4.1.37950.1.1.5.12.2.3.10.1.2
-- 1.3.6.1.4.1.37950.1.1.5.12.2.3.10.1.2
-- 1.3.6.1.4.1.37950.1.1.5.12.2.3.10.1.2
-- 1.3.6.1.4.1.37950.1.1.5.12.2.3.10.1.2
-- 1.3.6.1.4.1.37950.1.1.5.12.2.3.10.1.2
-- 1.3.6.1.4.1.37950.1.1.5.12.2.3.10.1.2
-- 1.3.6.1.4.1.37950.1.1.5.12.2.3.10.1.2
		-- 1.3.6.1.4.1.37950.1.1.5.12.2.3.10.1.2
		mgmtIPOnuNo OBJECT-TYPE
			SYNTAX Integer32 (1..65535)
			MAX-ACCESS read-only
			STATUS current
			DESCRIPTION
				"Description."
			::= { onuManagementIpEntry 2 }

		
--          1.3.6.1.4.1.37950.1.1.5.12.2.3.10.1.3
-- 1.3.6.1.4.1.37950.1.1.5.12.2.3.10.1.3
-- 1.3.6.1.4.1.37950.1.1.5.12.2.3.10.1.3
-- 1.3.6.1.4.1.37950.1.1.5.12.2.3.10.1.3
-- 1.3.6.1.4.1.37950.1.1.5.12.2.3.10.1.3
-- 1.3.6.1.4.1.37950.1.1.5.12.2.3.10.1.3
-- 1.3.6.1.4.1.37950.1.1.5.12.2.3.10.1.3
-- 1.3.6.1.4.1.37950.1.1.5.12.2.3.10.1.3
-- 1.3.6.1.4.1.37950.1.1.5.12.2.3.10.1.3
		-- 1.3.6.1.4.1.37950.1.1.5.12.2.3.10.1.3
		mgmtIP OBJECT-TYPE
			SYNTAX IpAddress
			MAX-ACCESS read-only
			STATUS current
			DESCRIPTION
				"Description."
			::= { onuManagementIpEntry 3 }

		
--          1.3.6.1.4.1.37950.1.1.5.12.2.3.10.1.4
-- 1.3.6.1.4.1.37950.1.1.5.12.2.3.10.1.4
-- 1.3.6.1.4.1.37950.1.1.5.12.2.3.10.1.4
-- 1.3.6.1.4.1.37950.1.1.5.12.2.3.10.1.4
-- 1.3.6.1.4.1.37950.1.1.5.12.2.3.10.1.4
-- 1.3.6.1.4.1.37950.1.1.5.12.2.3.10.1.4
-- 1.3.6.1.4.1.37950.1.1.5.12.2.3.10.1.4
-- 1.3.6.1.4.1.37950.1.1.5.12.2.3.10.1.4
-- 1.3.6.1.4.1.37950.1.1.5.12.2.3.10.1.4
		-- 1.3.6.1.4.1.37950.1.1.5.12.2.3.10.1.4
		mgmtIPMask OBJECT-TYPE
			SYNTAX IpAddress
			MAX-ACCESS read-only
			STATUS current
			DESCRIPTION
				"Description."
			::= { onuManagementIpEntry 4 }

		
--          1.3.6.1.4.1.37950.1.1.5.12.2.3.10.1.5
-- 1.3.6.1.4.1.37950.1.1.5.12.2.3.10.1.5
-- 1.3.6.1.4.1.37950.1.1.5.12.2.3.10.1.5
-- 1.3.6.1.4.1.37950.1.1.5.12.2.3.10.1.5
-- 1.3.6.1.4.1.37950.1.1.5.12.2.3.10.1.5
-- 1.3.6.1.4.1.37950.1.1.5.12.2.3.10.1.5
-- 1.3.6.1.4.1.37950.1.1.5.12.2.3.10.1.5
-- 1.3.6.1.4.1.37950.1.1.5.12.2.3.10.1.5
-- 1.3.6.1.4.1.37950.1.1.5.12.2.3.10.1.5
		-- 1.3.6.1.4.1.37950.1.1.5.12.2.3.10.1.5
		mgmtIPGw OBJECT-TYPE
			SYNTAX IpAddress
			MAX-ACCESS read-only
			STATUS current
			DESCRIPTION
				"Description."
			::= { onuManagementIpEntry 5 }

		
--          1.3.6.1.4.1.37950.1.1.5.12.2.3.10.1.6
-- 1.3.6.1.4.1.37950.1.1.5.12.2.3.10.1.6
-- 1.3.6.1.4.1.37950.1.1.5.12.2.3.10.1.6
-- 1.3.6.1.4.1.37950.1.1.5.12.2.3.10.1.6
-- 1.3.6.1.4.1.37950.1.1.5.12.2.3.10.1.6
-- 1.3.6.1.4.1.37950.1.1.5.12.2.3.10.1.6
-- 1.3.6.1.4.1.37950.1.1.5.12.2.3.10.1.6
-- 1.3.6.1.4.1.37950.1.1.5.12.2.3.10.1.6
-- 1.3.6.1.4.1.37950.1.1.5.12.2.3.10.1.6
		-- 1.3.6.1.4.1.37950.1.1.5.12.2.3.10.1.6
		mgmtIPCvlan OBJECT-TYPE
			SYNTAX Integer32 (0..4095)
			MAX-ACCESS read-only
			STATUS current
			DESCRIPTION
				"Description."
			::= { onuManagementIpEntry 6 }

		
--          1.3.6.1.4.1.37950.1.1.5.12.2.3.10.1.7
-- 1.3.6.1.4.1.37950.1.1.5.12.2.3.10.1.7
-- 1.3.6.1.4.1.37950.1.1.5.12.2.3.10.1.7
-- 1.3.6.1.4.1.37950.1.1.5.12.2.3.10.1.7
-- 1.3.6.1.4.1.37950.1.1.5.12.2.3.10.1.7
-- 1.3.6.1.4.1.37950.1.1.5.12.2.3.10.1.7
-- 1.3.6.1.4.1.37950.1.1.5.12.2.3.10.1.7
-- 1.3.6.1.4.1.37950.1.1.5.12.2.3.10.1.7
-- 1.3.6.1.4.1.37950.1.1.5.12.2.3.10.1.7
		-- 1.3.6.1.4.1.37950.1.1.5.12.2.3.10.1.7
		mgmtIPSvlan OBJECT-TYPE
			SYNTAX Integer32 (0..4095)
			MAX-ACCESS read-only
			STATUS current
			DESCRIPTION
				"Description."
			::= { onuManagementIpEntry 7 }

		
--          1.3.6.1.4.1.37950.1.1.5.12.2.3.10.1.8
-- 1.3.6.1.4.1.37950.1.1.5.12.2.3.10.1.8
-- 1.3.6.1.4.1.37950.1.1.5.12.2.3.10.1.8
-- 1.3.6.1.4.1.37950.1.1.5.12.2.3.10.1.8
-- 1.3.6.1.4.1.37950.1.1.5.12.2.3.10.1.8
-- 1.3.6.1.4.1.37950.1.1.5.12.2.3.10.1.8
-- 1.3.6.1.4.1.37950.1.1.5.12.2.3.10.1.8
-- 1.3.6.1.4.1.37950.1.1.5.12.2.3.10.1.8
-- 1.3.6.1.4.1.37950.1.1.5.12.2.3.10.1.8
		-- 1.3.6.1.4.1.37950.1.1.5.12.2.3.10.1.8
		mgmtIPPri OBJECT-TYPE
			SYNTAX Integer32 (0..7)
			MAX-ACCESS read-only
			STATUS current
			DESCRIPTION
				"Description."
			::= { onuManagementIpEntry 8 }

		
--          1.3.6.1.4.1.37950.1.1.5.12.2.4
-- 1.3.6.1.4.1.37950.1.1.5.12.2.4
-- 1.3.6.1.4.1.37950.1.1.5.12.2.4
-- 1.3.6.1.4.1.37950.1.1.5.12.2.4
-- 1.3.6.1.4.1.37950.1.1.5.12.2.4
-- 1.3.6.1.4.1.37950.1.1.5.12.2.4
-- 1.3.6.1.4.1.37950.1.1.5.12.2.4
-- 1.3.6.1.4.1.37950.1.1.5.12.2.4
-- 1.3.6.1.4.1.37950.1.1.5.12.2.4
		-- 1.3.6.1.4.1.37950.1.1.5.12.2.4
		onuSnmpCfg OBJECT IDENTIFIER ::= { onuGlobalCfg 4 }

		
--          1.3.6.1.4.1.37950.1.1.5.12.2.4.1
-- 1.3.6.1.4.1.37950.1.1.5.12.2.4.1
-- 1.3.6.1.4.1.37950.1.1.5.12.2.4.1
-- 1.3.6.1.4.1.37950.1.1.5.12.2.4.1
-- 1.3.6.1.4.1.37950.1.1.5.12.2.4.1
-- 1.3.6.1.4.1.37950.1.1.5.12.2.4.1
-- 1.3.6.1.4.1.37950.1.1.5.12.2.4.1
-- 1.3.6.1.4.1.37950.1.1.5.12.2.4.1
-- 1.3.6.1.4.1.37950.1.1.5.12.2.4.1
		-- 1.3.6.1.4.1.37950.1.1.5.12.2.4.1
		onuSnmpPonNo OBJECT-TYPE
			SYNTAX INTEGER (1..16)
			MAX-ACCESS read-write
			STATUS current
			DESCRIPTION
				"Description."
			::= { onuSnmpCfg 1 }

		
--          1.3.6.1.4.1.37950.1.1.5.12.2.4.2
-- 1.3.6.1.4.1.37950.1.1.5.12.2.4.2
-- 1.3.6.1.4.1.37950.1.1.5.12.2.4.2
-- 1.3.6.1.4.1.37950.1.1.5.12.2.4.2
-- 1.3.6.1.4.1.37950.1.1.5.12.2.4.2
-- 1.3.6.1.4.1.37950.1.1.5.12.2.4.2
-- 1.3.6.1.4.1.37950.1.1.5.12.2.4.2
-- 1.3.6.1.4.1.37950.1.1.5.12.2.4.2
-- 1.3.6.1.4.1.37950.1.1.5.12.2.4.2
		-- 1.3.6.1.4.1.37950.1.1.5.12.2.4.2
		onuSnmpOnuNo OBJECT-TYPE
			SYNTAX INTEGER (1..65535)
			MAX-ACCESS read-write
			STATUS current
			DESCRIPTION
				"Description."
			::= { onuSnmpCfg 2 }

		
--          1.3.6.1.4.1.37950.1.1.5.12.2.4.3
-- 1.3.6.1.4.1.37950.1.1.5.12.2.4.3
-- 1.3.6.1.4.1.37950.1.1.5.12.2.4.3
-- 1.3.6.1.4.1.37950.1.1.5.12.2.4.3
-- 1.3.6.1.4.1.37950.1.1.5.12.2.4.3
-- 1.3.6.1.4.1.37950.1.1.5.12.2.4.3
-- 1.3.6.1.4.1.37950.1.1.5.12.2.4.3
-- 1.3.6.1.4.1.37950.1.1.5.12.2.4.3
-- 1.3.6.1.4.1.37950.1.1.5.12.2.4.3
		-- 1.3.6.1.4.1.37950.1.1.5.12.2.4.3
		onuSnmpTrapHostIp OBJECT-TYPE
			SYNTAX IpAddress
			MAX-ACCESS read-write
			STATUS current
			DESCRIPTION
				"Description."
			::= { onuSnmpCfg 3 }

		
--          1.3.6.1.4.1.37950.1.1.5.12.2.4.4
-- 1.3.6.1.4.1.37950.1.1.5.12.2.4.4
-- 1.3.6.1.4.1.37950.1.1.5.12.2.4.4
-- 1.3.6.1.4.1.37950.1.1.5.12.2.4.4
-- 1.3.6.1.4.1.37950.1.1.5.12.2.4.4
-- 1.3.6.1.4.1.37950.1.1.5.12.2.4.4
-- 1.3.6.1.4.1.37950.1.1.5.12.2.4.4
-- 1.3.6.1.4.1.37950.1.1.5.12.2.4.4
-- 1.3.6.1.4.1.37950.1.1.5.12.2.4.4
		-- 1.3.6.1.4.1.37950.1.1.5.12.2.4.4
		onuSnmpTrapUdpPort OBJECT-TYPE
			SYNTAX INTEGER (0..65535)
			MAX-ACCESS read-write
			STATUS current
			DESCRIPTION
				"Description."
			::= { onuSnmpCfg 4 }

		
--          1.3.6.1.4.1.37950.1.1.5.12.2.4.5
-- 1.3.6.1.4.1.37950.1.1.5.12.2.4.5
-- 1.3.6.1.4.1.37950.1.1.5.12.2.4.5
-- 1.3.6.1.4.1.37950.1.1.5.12.2.4.5
-- 1.3.6.1.4.1.37950.1.1.5.12.2.4.5
-- 1.3.6.1.4.1.37950.1.1.5.12.2.4.5
-- 1.3.6.1.4.1.37950.1.1.5.12.2.4.5
-- 1.3.6.1.4.1.37950.1.1.5.12.2.4.5
-- 1.3.6.1.4.1.37950.1.1.5.12.2.4.5
		-- 1.3.6.1.4.1.37950.1.1.5.12.2.4.5
		onuSnmpPort OBJECT-TYPE
			SYNTAX INTEGER (0..65535)
			MAX-ACCESS read-write
			STATUS current
			DESCRIPTION
				"Description."
			::= { onuSnmpCfg 5 }

		
--          1.3.6.1.4.1.37950.1.1.5.12.2.4.6
-- 1.3.6.1.4.1.37950.1.1.5.12.2.4.6
-- 1.3.6.1.4.1.37950.1.1.5.12.2.4.6
-- 1.3.6.1.4.1.37950.1.1.5.12.2.4.6
-- 1.3.6.1.4.1.37950.1.1.5.12.2.4.6
-- 1.3.6.1.4.1.37950.1.1.5.12.2.4.6
-- 1.3.6.1.4.1.37950.1.1.5.12.2.4.6
-- 1.3.6.1.4.1.37950.1.1.5.12.2.4.6
-- 1.3.6.1.4.1.37950.1.1.5.12.2.4.6
		-- 1.3.6.1.4.1.37950.1.1.5.12.2.4.6
		onuCommunityName OBJECT-TYPE
			SYNTAX OCTET STRING
			MAX-ACCESS read-write
			STATUS current
			DESCRIPTION
				"Description."
			::= { onuSnmpCfg 6 }

		
--          1.3.6.1.4.1.37950.1.1.5.12.2.4.7
-- 1.3.6.1.4.1.37950.1.1.5.12.2.4.7
-- 1.3.6.1.4.1.37950.1.1.5.12.2.4.7
-- 1.3.6.1.4.1.37950.1.1.5.12.2.4.7
-- 1.3.6.1.4.1.37950.1.1.5.12.2.4.7
-- 1.3.6.1.4.1.37950.1.1.5.12.2.4.7
-- 1.3.6.1.4.1.37950.1.1.5.12.2.4.7
-- 1.3.6.1.4.1.37950.1.1.5.12.2.4.7
-- 1.3.6.1.4.1.37950.1.1.5.12.2.4.7
		-- 1.3.6.1.4.1.37950.1.1.5.12.2.4.7
		onuRoCommunityName OBJECT-TYPE
			SYNTAX OCTET STRING
			MAX-ACCESS read-write
			STATUS current
			DESCRIPTION
				"Description."
			::= { onuSnmpCfg 7 }

		
--          1.3.6.1.4.1.37950.1.1.5.12.2.4.8
-- 1.3.6.1.4.1.37950.1.1.5.12.2.4.8
-- 1.3.6.1.4.1.37950.1.1.5.12.2.4.8
-- 1.3.6.1.4.1.37950.1.1.5.12.2.4.8
-- 1.3.6.1.4.1.37950.1.1.5.12.2.4.8
-- 1.3.6.1.4.1.37950.1.1.5.12.2.4.8
-- 1.3.6.1.4.1.37950.1.1.5.12.2.4.8
-- 1.3.6.1.4.1.37950.1.1.5.12.2.4.8
-- 1.3.6.1.4.1.37950.1.1.5.12.2.4.8
		-- 1.3.6.1.4.1.37950.1.1.5.12.2.4.8
		onuRwCommunityName OBJECT-TYPE
			SYNTAX OCTET STRING
			MAX-ACCESS read-write
			STATUS current
			DESCRIPTION
				"Description."
			::= { onuSnmpCfg 8 }

		
--          1.3.6.1.4.1.37950.1.1.5.12.2.4.9
-- 1.3.6.1.4.1.37950.1.1.5.12.2.4.9
-- 1.3.6.1.4.1.37950.1.1.5.12.2.4.9
-- 1.3.6.1.4.1.37950.1.1.5.12.2.4.9
-- 1.3.6.1.4.1.37950.1.1.5.12.2.4.9
-- 1.3.6.1.4.1.37950.1.1.5.12.2.4.9
-- 1.3.6.1.4.1.37950.1.1.5.12.2.4.9
-- 1.3.6.1.4.1.37950.1.1.5.12.2.4.9
-- 1.3.6.1.4.1.37950.1.1.5.12.2.4.9
		-- 1.3.6.1.4.1.37950.1.1.5.12.2.4.9
		onuCommunityAction OBJECT-TYPE
			SYNTAX INTEGER
				{
				add(1),
				delete(2)
				}
			MAX-ACCESS read-write
			STATUS current
			DESCRIPTION
				"Description."
			::= { onuSnmpCfg 9 }

		
--          1.3.6.1.4.1.37950.1.1.5.12.2.5
-- 1.3.6.1.4.1.37950.1.1.5.12.2.5
-- 1.3.6.1.4.1.37950.1.1.5.12.2.5
-- 1.3.6.1.4.1.37950.1.1.5.12.2.5
-- 1.3.6.1.4.1.37950.1.1.5.12.2.5
-- 1.3.6.1.4.1.37950.1.1.5.12.2.5
-- 1.3.6.1.4.1.37950.1.1.5.12.2.5
-- 1.3.6.1.4.1.37950.1.1.5.12.2.5
-- 1.3.6.1.4.1.37950.1.1.5.12.2.5
		-- 1.3.6.1.4.1.37950.1.1.5.12.2.5
		onuMultiLlid OBJECT IDENTIFIER ::= { onuGlobalCfg 5 }

		
--          1.3.6.1.4.1.37950.1.1.5.12.2.5.1
-- 1.3.6.1.4.1.37950.1.1.5.12.2.5.1
-- 1.3.6.1.4.1.37950.1.1.5.12.2.5.1
-- 1.3.6.1.4.1.37950.1.1.5.12.2.5.1
-- 1.3.6.1.4.1.37950.1.1.5.12.2.5.1
-- 1.3.6.1.4.1.37950.1.1.5.12.2.5.1
-- 1.3.6.1.4.1.37950.1.1.5.12.2.5.1
-- 1.3.6.1.4.1.37950.1.1.5.12.2.5.1
-- 1.3.6.1.4.1.37950.1.1.5.12.2.5.1
		-- 1.3.6.1.4.1.37950.1.1.5.12.2.5.1
		llidPonNo OBJECT-TYPE
			SYNTAX INTEGER (1..16)
			MAX-ACCESS read-write
			STATUS current
			DESCRIPTION
				"Description."
			::= { onuMultiLlid 1 }

		
--          1.3.6.1.4.1.37950.1.1.5.12.2.5.2
-- 1.3.6.1.4.1.37950.1.1.5.12.2.5.2
-- 1.3.6.1.4.1.37950.1.1.5.12.2.5.2
-- 1.3.6.1.4.1.37950.1.1.5.12.2.5.2
-- 1.3.6.1.4.1.37950.1.1.5.12.2.5.2
-- 1.3.6.1.4.1.37950.1.1.5.12.2.5.2
-- 1.3.6.1.4.1.37950.1.1.5.12.2.5.2
-- 1.3.6.1.4.1.37950.1.1.5.12.2.5.2
-- 1.3.6.1.4.1.37950.1.1.5.12.2.5.2
		-- 1.3.6.1.4.1.37950.1.1.5.12.2.5.2
		llidOnuNo OBJECT-TYPE
			SYNTAX INTEGER (1..65535)
			MAX-ACCESS read-write
			STATUS current
			DESCRIPTION
				"Description."
			::= { onuMultiLlid 2 }

		
--          1.3.6.1.4.1.37950.1.1.5.12.2.5.3
-- 1.3.6.1.4.1.37950.1.1.5.12.2.5.3
-- 1.3.6.1.4.1.37950.1.1.5.12.2.5.3
-- 1.3.6.1.4.1.37950.1.1.5.12.2.5.3
-- 1.3.6.1.4.1.37950.1.1.5.12.2.5.3
-- 1.3.6.1.4.1.37950.1.1.5.12.2.5.3
-- 1.3.6.1.4.1.37950.1.1.5.12.2.5.3
-- 1.3.6.1.4.1.37950.1.1.5.12.2.5.3
-- 1.3.6.1.4.1.37950.1.1.5.12.2.5.3
		-- 1.3.6.1.4.1.37950.1.1.5.12.2.5.3
		llidNo OBJECT-TYPE
			SYNTAX INTEGER (0..8)
			MAX-ACCESS read-write
			STATUS current
			DESCRIPTION
				"Description."
			::= { onuMultiLlid 3 }

		
--          1.3.6.1.4.1.37950.1.1.5.12.2.6
-- 1.3.6.1.4.1.37950.1.1.5.12.2.6
-- 1.3.6.1.4.1.37950.1.1.5.12.2.6
-- 1.3.6.1.4.1.37950.1.1.5.12.2.6
-- 1.3.6.1.4.1.37950.1.1.5.12.2.6
-- 1.3.6.1.4.1.37950.1.1.5.12.2.6
-- 1.3.6.1.4.1.37950.1.1.5.12.2.6
-- 1.3.6.1.4.1.37950.1.1.5.12.2.6
-- 1.3.6.1.4.1.37950.1.1.5.12.2.6
		-- 1.3.6.1.4.1.37950.1.1.5.12.2.6
		onuMainPonCfg OBJECT IDENTIFIER ::= { onuGlobalCfg 6 }

		
--          1.3.6.1.4.1.37950.1.1.5.12.2.6.1
-- 1.3.6.1.4.1.37950.1.1.5.12.2.6.1
-- 1.3.6.1.4.1.37950.1.1.5.12.2.6.1
-- 1.3.6.1.4.1.37950.1.1.5.12.2.6.1
-- 1.3.6.1.4.1.37950.1.1.5.12.2.6.1
-- 1.3.6.1.4.1.37950.1.1.5.12.2.6.1
-- 1.3.6.1.4.1.37950.1.1.5.12.2.6.1
-- 1.3.6.1.4.1.37950.1.1.5.12.2.6.1
-- 1.3.6.1.4.1.37950.1.1.5.12.2.6.1
		-- 1.3.6.1.4.1.37950.1.1.5.12.2.6.1
		ponNumber OBJECT-TYPE
			SYNTAX INTEGER (1..16)
			MAX-ACCESS read-write
			STATUS current
			DESCRIPTION
				"Description."
			::= { onuMainPonCfg 1 }

		
--          1.3.6.1.4.1.37950.1.1.5.12.2.6.2
-- 1.3.6.1.4.1.37950.1.1.5.12.2.6.2
-- 1.3.6.1.4.1.37950.1.1.5.12.2.6.2
-- 1.3.6.1.4.1.37950.1.1.5.12.2.6.2
-- 1.3.6.1.4.1.37950.1.1.5.12.2.6.2
-- 1.3.6.1.4.1.37950.1.1.5.12.2.6.2
-- 1.3.6.1.4.1.37950.1.1.5.12.2.6.2
-- 1.3.6.1.4.1.37950.1.1.5.12.2.6.2
-- 1.3.6.1.4.1.37950.1.1.5.12.2.6.2
		-- 1.3.6.1.4.1.37950.1.1.5.12.2.6.2
		onuNumber OBJECT-TYPE
			SYNTAX INTEGER (1..65535)
			MAX-ACCESS read-write
			STATUS current
			DESCRIPTION
				"Description."
			::= { onuMainPonCfg 2 }

		
--          1.3.6.1.4.1.37950.1.1.5.12.2.6.3
-- 1.3.6.1.4.1.37950.1.1.5.12.2.6.3
-- 1.3.6.1.4.1.37950.1.1.5.12.2.6.3
-- 1.3.6.1.4.1.37950.1.1.5.12.2.6.3
-- 1.3.6.1.4.1.37950.1.1.5.12.2.6.3
-- 1.3.6.1.4.1.37950.1.1.5.12.2.6.3
-- 1.3.6.1.4.1.37950.1.1.5.12.2.6.3
-- 1.3.6.1.4.1.37950.1.1.5.12.2.6.3
-- 1.3.6.1.4.1.37950.1.1.5.12.2.6.3
		-- 1.3.6.1.4.1.37950.1.1.5.12.2.6.3
		onuMainPonNo OBJECT-TYPE
			SYNTAX INTEGER (1..8)
			MAX-ACCESS read-write
			STATUS current
			DESCRIPTION
				"Description."
			::= { onuMainPonCfg 3 }

		
--          1.3.6.1.4.1.37950.1.1.5.12.2.7
-- 1.3.6.1.4.1.37950.1.1.5.12.2.7
-- 1.3.6.1.4.1.37950.1.1.5.12.2.7
-- 1.3.6.1.4.1.37950.1.1.5.12.2.7
-- 1.3.6.1.4.1.37950.1.1.5.12.2.7
-- 1.3.6.1.4.1.37950.1.1.5.12.2.7
-- 1.3.6.1.4.1.37950.1.1.5.12.2.7
-- 1.3.6.1.4.1.37950.1.1.5.12.2.7
-- 1.3.6.1.4.1.37950.1.1.5.12.2.7
		-- 1.3.6.1.4.1.37950.1.1.5.12.2.7
		onuFecCfg OBJECT IDENTIFIER ::= { onuGlobalCfg 7 }

		
--          1.3.6.1.4.1.37950.1.1.5.12.2.7.1
-- 1.3.6.1.4.1.37950.1.1.5.12.2.7.1
-- 1.3.6.1.4.1.37950.1.1.5.12.2.7.1
-- 1.3.6.1.4.1.37950.1.1.5.12.2.7.1
-- 1.3.6.1.4.1.37950.1.1.5.12.2.7.1
-- 1.3.6.1.4.1.37950.1.1.5.12.2.7.1
-- 1.3.6.1.4.1.37950.1.1.5.12.2.7.1
-- 1.3.6.1.4.1.37950.1.1.5.12.2.7.1
-- 1.3.6.1.4.1.37950.1.1.5.12.2.7.1
		-- 1.3.6.1.4.1.37950.1.1.5.12.2.7.1
		onuFecPonNo OBJECT-TYPE
			SYNTAX INTEGER (1..16)
			MAX-ACCESS read-write
			STATUS current
			DESCRIPTION
				"Description."
			::= { onuFecCfg 1 }

		
--          1.3.6.1.4.1.37950.1.1.5.12.2.7.2
-- 1.3.6.1.4.1.37950.1.1.5.12.2.7.2
-- 1.3.6.1.4.1.37950.1.1.5.12.2.7.2
-- 1.3.6.1.4.1.37950.1.1.5.12.2.7.2
-- 1.3.6.1.4.1.37950.1.1.5.12.2.7.2
-- 1.3.6.1.4.1.37950.1.1.5.12.2.7.2
-- 1.3.6.1.4.1.37950.1.1.5.12.2.7.2
-- 1.3.6.1.4.1.37950.1.1.5.12.2.7.2
-- 1.3.6.1.4.1.37950.1.1.5.12.2.7.2
		-- 1.3.6.1.4.1.37950.1.1.5.12.2.7.2
		onuFecOnuNo OBJECT-TYPE
			SYNTAX INTEGER (1..65535)
			MAX-ACCESS read-write
			STATUS current
			DESCRIPTION
				"Description."
			::= { onuFecCfg 2 }

		
--          1.3.6.1.4.1.37950.1.1.5.12.2.7.3
-- 1.3.6.1.4.1.37950.1.1.5.12.2.7.3
-- 1.3.6.1.4.1.37950.1.1.5.12.2.7.3
-- 1.3.6.1.4.1.37950.1.1.5.12.2.7.3
-- 1.3.6.1.4.1.37950.1.1.5.12.2.7.3
-- 1.3.6.1.4.1.37950.1.1.5.12.2.7.3
-- 1.3.6.1.4.1.37950.1.1.5.12.2.7.3
-- 1.3.6.1.4.1.37950.1.1.5.12.2.7.3
-- 1.3.6.1.4.1.37950.1.1.5.12.2.7.3
		-- 1.3.6.1.4.1.37950.1.1.5.12.2.7.3
		onuFecEn OBJECT-TYPE
			SYNTAX INTEGER
				{
				disable(0),
				enable(1)
				}
			MAX-ACCESS read-write
			STATUS current
			DESCRIPTION
				"Description."
			::= { onuFecCfg 3 }

		
--          1.3.6.1.4.1.37950.1.1.5.12.2.8
-- 1.3.6.1.4.1.37950.1.1.5.12.2.8
-- 1.3.6.1.4.1.37950.1.1.5.12.2.8
-- 1.3.6.1.4.1.37950.1.1.5.12.2.8
-- 1.3.6.1.4.1.37950.1.1.5.12.2.8
-- 1.3.6.1.4.1.37950.1.1.5.12.2.8
-- 1.3.6.1.4.1.37950.1.1.5.12.2.8
-- 1.3.6.1.4.1.37950.1.1.5.12.2.8
-- 1.3.6.1.4.1.37950.1.1.5.12.2.8
		-- 1.3.6.1.4.1.37950.1.1.5.12.2.8
		onuHoldoverCfg OBJECT IDENTIFIER ::= { onuGlobalCfg 8 }

		
--          1.3.6.1.4.1.37950.1.1.5.12.2.8.1
-- 1.3.6.1.4.1.37950.1.1.5.12.2.8.1
-- 1.3.6.1.4.1.37950.1.1.5.12.2.8.1
-- 1.3.6.1.4.1.37950.1.1.5.12.2.8.1
-- 1.3.6.1.4.1.37950.1.1.5.12.2.8.1
-- 1.3.6.1.4.1.37950.1.1.5.12.2.8.1
-- 1.3.6.1.4.1.37950.1.1.5.12.2.8.1
-- 1.3.6.1.4.1.37950.1.1.5.12.2.8.1
-- 1.3.6.1.4.1.37950.1.1.5.12.2.8.1
		-- 1.3.6.1.4.1.37950.1.1.5.12.2.8.1
		holdoverPonNo OBJECT-TYPE
			SYNTAX INTEGER (1..16)
			MAX-ACCESS read-write
			STATUS current
			DESCRIPTION
				"Description."
			::= { onuHoldoverCfg 1 }

		
--          1.3.6.1.4.1.37950.1.1.5.12.2.8.2
-- 1.3.6.1.4.1.37950.1.1.5.12.2.8.2
-- 1.3.6.1.4.1.37950.1.1.5.12.2.8.2
-- 1.3.6.1.4.1.37950.1.1.5.12.2.8.2
-- 1.3.6.1.4.1.37950.1.1.5.12.2.8.2
-- 1.3.6.1.4.1.37950.1.1.5.12.2.8.2
-- 1.3.6.1.4.1.37950.1.1.5.12.2.8.2
-- 1.3.6.1.4.1.37950.1.1.5.12.2.8.2
-- 1.3.6.1.4.1.37950.1.1.5.12.2.8.2
		-- 1.3.6.1.4.1.37950.1.1.5.12.2.8.2
		holdoverOnuNo OBJECT-TYPE
			SYNTAX INTEGER (1..65535)
			MAX-ACCESS read-write
			STATUS current
			DESCRIPTION
				"Description."
			::= { onuHoldoverCfg 2 }

		
--          1.3.6.1.4.1.37950.1.1.5.12.2.8.3
-- 1.3.6.1.4.1.37950.1.1.5.12.2.8.3
-- 1.3.6.1.4.1.37950.1.1.5.12.2.8.3
-- 1.3.6.1.4.1.37950.1.1.5.12.2.8.3
-- 1.3.6.1.4.1.37950.1.1.5.12.2.8.3
-- 1.3.6.1.4.1.37950.1.1.5.12.2.8.3
-- 1.3.6.1.4.1.37950.1.1.5.12.2.8.3
-- 1.3.6.1.4.1.37950.1.1.5.12.2.8.3
-- 1.3.6.1.4.1.37950.1.1.5.12.2.8.3
		-- 1.3.6.1.4.1.37950.1.1.5.12.2.8.3
		holdover OBJECT-TYPE
			SYNTAX INTEGER (0..65535)
			MAX-ACCESS read-write
			STATUS current
			DESCRIPTION
				"Description."
			::= { onuHoldoverCfg 3 }

		
--          1.3.6.1.4.1.37950.1.1.5.12.2.9
-- 1.3.6.1.4.1.37950.1.1.5.12.2.9
-- 1.3.6.1.4.1.37950.1.1.5.12.2.9
-- 1.3.6.1.4.1.37950.1.1.5.12.2.9
-- 1.3.6.1.4.1.37950.1.1.5.12.2.9
-- 1.3.6.1.4.1.37950.1.1.5.12.2.9
-- 1.3.6.1.4.1.37950.1.1.5.12.2.9
-- 1.3.6.1.4.1.37950.1.1.5.12.2.9
-- 1.3.6.1.4.1.37950.1.1.5.12.2.9
		-- 1.3.6.1.4.1.37950.1.1.5.12.2.9
		onuSlaCfg OBJECT IDENTIFIER ::= { onuGlobalCfg 9 }

		
--          1.3.6.1.4.1.37950.1.1.5.12.2.9.1
-- 1.3.6.1.4.1.37950.1.1.5.12.2.9.1
-- 1.3.6.1.4.1.37950.1.1.5.12.2.9.1
-- 1.3.6.1.4.1.37950.1.1.5.12.2.9.1
-- 1.3.6.1.4.1.37950.1.1.5.12.2.9.1
-- 1.3.6.1.4.1.37950.1.1.5.12.2.9.1
-- 1.3.6.1.4.1.37950.1.1.5.12.2.9.1
-- 1.3.6.1.4.1.37950.1.1.5.12.2.9.1
-- 1.3.6.1.4.1.37950.1.1.5.12.2.9.1
		-- 1.3.6.1.4.1.37950.1.1.5.12.2.9.1
		onuSlaPonNo OBJECT-TYPE
			SYNTAX INTEGER (1..16)
			MAX-ACCESS read-write
			STATUS current
			DESCRIPTION
				"Description."
			::= { onuSlaCfg 1 }

		
--          1.3.6.1.4.1.37950.1.1.5.12.2.9.2
-- 1.3.6.1.4.1.37950.1.1.5.12.2.9.2
-- 1.3.6.1.4.1.37950.1.1.5.12.2.9.2
-- 1.3.6.1.4.1.37950.1.1.5.12.2.9.2
-- 1.3.6.1.4.1.37950.1.1.5.12.2.9.2
-- 1.3.6.1.4.1.37950.1.1.5.12.2.9.2
-- 1.3.6.1.4.1.37950.1.1.5.12.2.9.2
-- 1.3.6.1.4.1.37950.1.1.5.12.2.9.2
-- 1.3.6.1.4.1.37950.1.1.5.12.2.9.2
		-- 1.3.6.1.4.1.37950.1.1.5.12.2.9.2
		onuSlaOnuNo OBJECT-TYPE
			SYNTAX INTEGER (1..65535)
			MAX-ACCESS read-write
			STATUS current
			DESCRIPTION
				"Description."
			::= { onuSlaCfg 2 }

		
--          1.3.6.1.4.1.37950.1.1.5.12.2.9.3
-- 1.3.6.1.4.1.37950.1.1.5.12.2.9.3
-- 1.3.6.1.4.1.37950.1.1.5.12.2.9.3
-- 1.3.6.1.4.1.37950.1.1.5.12.2.9.3
-- 1.3.6.1.4.1.37950.1.1.5.12.2.9.3
-- 1.3.6.1.4.1.37950.1.1.5.12.2.9.3
-- 1.3.6.1.4.1.37950.1.1.5.12.2.9.3
-- 1.3.6.1.4.1.37950.1.1.5.12.2.9.3
-- 1.3.6.1.4.1.37950.1.1.5.12.2.9.3
		-- 1.3.6.1.4.1.37950.1.1.5.12.2.9.3
		onuSlaEn OBJECT-TYPE
			SYNTAX INTEGER
				{
				disable(0),
				enable(1)
				}
			MAX-ACCESS read-write
			STATUS current
			DESCRIPTION
				"Description."
			::= { onuSlaCfg 3 }

		
--          1.3.6.1.4.1.37950.1.1.5.12.2.9.4
-- 1.3.6.1.4.1.37950.1.1.5.12.2.9.4
-- 1.3.6.1.4.1.37950.1.1.5.12.2.9.4
-- 1.3.6.1.4.1.37950.1.1.5.12.2.9.4
-- 1.3.6.1.4.1.37950.1.1.5.12.2.9.4
-- 1.3.6.1.4.1.37950.1.1.5.12.2.9.4
-- 1.3.6.1.4.1.37950.1.1.5.12.2.9.4
-- 1.3.6.1.4.1.37950.1.1.5.12.2.9.4
-- 1.3.6.1.4.1.37950.1.1.5.12.2.9.4
		-- 1.3.6.1.4.1.37950.1.1.5.12.2.9.4
		onuSlaMode OBJECT-TYPE
			SYNTAX INTEGER
				{
				sp-basic(1),
				wrr(2),
				sp-wrr(3)
				}
			MAX-ACCESS read-write
			STATUS current
			DESCRIPTION
				"Description."
			::= { onuSlaCfg 4 }

		
--          1.3.6.1.4.1.37950.1.1.5.12.2.9.5
-- 1.3.6.1.4.1.37950.1.1.5.12.2.9.5
-- 1.3.6.1.4.1.37950.1.1.5.12.2.9.5
-- 1.3.6.1.4.1.37950.1.1.5.12.2.9.5
-- 1.3.6.1.4.1.37950.1.1.5.12.2.9.5
-- 1.3.6.1.4.1.37950.1.1.5.12.2.9.5
-- 1.3.6.1.4.1.37950.1.1.5.12.2.9.5
-- 1.3.6.1.4.1.37950.1.1.5.12.2.9.5
-- 1.3.6.1.4.1.37950.1.1.5.12.2.9.5
		-- 1.3.6.1.4.1.37950.1.1.5.12.2.9.5
		highPriBoundary OBJECT-TYPE
			SYNTAX Integer32 (0..255)
			MAX-ACCESS read-write
			STATUS current
			DESCRIPTION
				"Description."
			::= { onuSlaCfg 5 }

		
--          1.3.6.1.4.1.37950.1.1.5.12.2.9.6
-- 1.3.6.1.4.1.37950.1.1.5.12.2.9.6
-- 1.3.6.1.4.1.37950.1.1.5.12.2.9.6
-- 1.3.6.1.4.1.37950.1.1.5.12.2.9.6
-- 1.3.6.1.4.1.37950.1.1.5.12.2.9.6
-- 1.3.6.1.4.1.37950.1.1.5.12.2.9.6
-- 1.3.6.1.4.1.37950.1.1.5.12.2.9.6
-- 1.3.6.1.4.1.37950.1.1.5.12.2.9.6
-- 1.3.6.1.4.1.37950.1.1.5.12.2.9.6
		-- 1.3.6.1.4.1.37950.1.1.5.12.2.9.6
		cycleLength OBJECT-TYPE
			SYNTAX Integer32
			MAX-ACCESS read-write
			STATUS current
			DESCRIPTION
				"Description."
			::= { onuSlaCfg 6 }

		
--          1.3.6.1.4.1.37950.1.1.5.12.2.9.7
-- 1.3.6.1.4.1.37950.1.1.5.12.2.9.7
-- 1.3.6.1.4.1.37950.1.1.5.12.2.9.7
-- 1.3.6.1.4.1.37950.1.1.5.12.2.9.7
-- 1.3.6.1.4.1.37950.1.1.5.12.2.9.7
-- 1.3.6.1.4.1.37950.1.1.5.12.2.9.7
-- 1.3.6.1.4.1.37950.1.1.5.12.2.9.7
-- 1.3.6.1.4.1.37950.1.1.5.12.2.9.7
-- 1.3.6.1.4.1.37950.1.1.5.12.2.9.7
		-- 1.3.6.1.4.1.37950.1.1.5.12.2.9.7
		numServices OBJECT-TYPE
			SYNTAX Integer32 (1..8)
			MAX-ACCESS read-write
			STATUS current
			DESCRIPTION
				"Description."
			::= { onuSlaCfg 7 }

		
--          1.3.6.1.4.1.37950.1.1.5.12.2.9.8
-- 1.3.6.1.4.1.37950.1.1.5.12.2.9.8
-- 1.3.6.1.4.1.37950.1.1.5.12.2.9.8
-- 1.3.6.1.4.1.37950.1.1.5.12.2.9.8
-- 1.3.6.1.4.1.37950.1.1.5.12.2.9.8
-- 1.3.6.1.4.1.37950.1.1.5.12.2.9.8
-- 1.3.6.1.4.1.37950.1.1.5.12.2.9.8
-- 1.3.6.1.4.1.37950.1.1.5.12.2.9.8
-- 1.3.6.1.4.1.37950.1.1.5.12.2.9.8
		-- 1.3.6.1.4.1.37950.1.1.5.12.2.9.8
		queueIdListStr OBJECT-TYPE
			SYNTAX OCTET STRING
			MAX-ACCESS read-write
			STATUS current
			DESCRIPTION
				"Description."
			::= { onuSlaCfg 8 }

		
--          1.3.6.1.4.1.37950.1.1.5.12.2.9.9
-- 1.3.6.1.4.1.37950.1.1.5.12.2.9.9
-- 1.3.6.1.4.1.37950.1.1.5.12.2.9.9
-- 1.3.6.1.4.1.37950.1.1.5.12.2.9.9
-- 1.3.6.1.4.1.37950.1.1.5.12.2.9.9
-- 1.3.6.1.4.1.37950.1.1.5.12.2.9.9
-- 1.3.6.1.4.1.37950.1.1.5.12.2.9.9
-- 1.3.6.1.4.1.37950.1.1.5.12.2.9.9
-- 1.3.6.1.4.1.37950.1.1.5.12.2.9.9
		-- 1.3.6.1.4.1.37950.1.1.5.12.2.9.9
		fixPacketSizeListStr OBJECT-TYPE
			SYNTAX OCTET STRING
			MAX-ACCESS read-write
			STATUS current
			DESCRIPTION
				"Description."
			::= { onuSlaCfg 9 }

		
--          1.3.6.1.4.1.37950.1.1.5.12.2.9.10
-- 1.3.6.1.4.1.37950.1.1.5.12.2.9.10
-- 1.3.6.1.4.1.37950.1.1.5.12.2.9.10
-- 1.3.6.1.4.1.37950.1.1.5.12.2.9.10
-- 1.3.6.1.4.1.37950.1.1.5.12.2.9.10
-- 1.3.6.1.4.1.37950.1.1.5.12.2.9.10
-- 1.3.6.1.4.1.37950.1.1.5.12.2.9.10
-- 1.3.6.1.4.1.37950.1.1.5.12.2.9.10
-- 1.3.6.1.4.1.37950.1.1.5.12.2.9.10
		-- 1.3.6.1.4.1.37950.1.1.5.12.2.9.10
		queweightListStr OBJECT-TYPE
			SYNTAX OCTET STRING
			MAX-ACCESS read-write
			STATUS current
			DESCRIPTION
				"Description."
			::= { onuSlaCfg 10 }

		
--          1.3.6.1.4.1.37950.1.1.5.12.2.9.11
-- 1.3.6.1.4.1.37950.1.1.5.12.2.9.11
-- 1.3.6.1.4.1.37950.1.1.5.12.2.9.11
-- 1.3.6.1.4.1.37950.1.1.5.12.2.9.11
-- 1.3.6.1.4.1.37950.1.1.5.12.2.9.11
-- 1.3.6.1.4.1.37950.1.1.5.12.2.9.11
-- 1.3.6.1.4.1.37950.1.1.5.12.2.9.11
-- 1.3.6.1.4.1.37950.1.1.5.12.2.9.11
-- 1.3.6.1.4.1.37950.1.1.5.12.2.9.11
		-- 1.3.6.1.4.1.37950.1.1.5.12.2.9.11
		fixBandwidthListStr OBJECT-TYPE
			SYNTAX OCTET STRING
			MAX-ACCESS read-write
			STATUS current
			DESCRIPTION
				"Description."
			::= { onuSlaCfg 11 }

		
--          1.3.6.1.4.1.37950.1.1.5.12.2.9.12
-- 1.3.6.1.4.1.37950.1.1.5.12.2.9.12
-- 1.3.6.1.4.1.37950.1.1.5.12.2.9.12
-- 1.3.6.1.4.1.37950.1.1.5.12.2.9.12
-- 1.3.6.1.4.1.37950.1.1.5.12.2.9.12
-- 1.3.6.1.4.1.37950.1.1.5.12.2.9.12
-- 1.3.6.1.4.1.37950.1.1.5.12.2.9.12
-- 1.3.6.1.4.1.37950.1.1.5.12.2.9.12
-- 1.3.6.1.4.1.37950.1.1.5.12.2.9.12
		-- 1.3.6.1.4.1.37950.1.1.5.12.2.9.12
		guaranteedBandwidthListStr OBJECT-TYPE
			SYNTAX OCTET STRING
			MAX-ACCESS read-write
			STATUS current
			DESCRIPTION
				"Description."
			::= { onuSlaCfg 12 }

		
--          1.3.6.1.4.1.37950.1.1.5.12.2.9.13
-- 1.3.6.1.4.1.37950.1.1.5.12.2.9.13
-- 1.3.6.1.4.1.37950.1.1.5.12.2.9.13
-- 1.3.6.1.4.1.37950.1.1.5.12.2.9.13
-- 1.3.6.1.4.1.37950.1.1.5.12.2.9.13
-- 1.3.6.1.4.1.37950.1.1.5.12.2.9.13
-- 1.3.6.1.4.1.37950.1.1.5.12.2.9.13
-- 1.3.6.1.4.1.37950.1.1.5.12.2.9.13
-- 1.3.6.1.4.1.37950.1.1.5.12.2.9.13
		-- 1.3.6.1.4.1.37950.1.1.5.12.2.9.13
		besteffortBandwithListStr OBJECT-TYPE
			SYNTAX OCTET STRING
			MAX-ACCESS read-write
			STATUS current
			DESCRIPTION
				"Description."
			::= { onuSlaCfg 13 }

		
--          1.3.6.1.4.1.37950.1.1.5.12.2.9.56
-- 1.3.6.1.4.1.37950.1.1.5.12.2.9.56
-- 1.3.6.1.4.1.37950.1.1.5.12.2.9.56
-- 1.3.6.1.4.1.37950.1.1.5.12.2.9.56
-- 1.3.6.1.4.1.37950.1.1.5.12.2.9.56
-- 1.3.6.1.4.1.37950.1.1.5.12.2.9.56
-- 1.3.6.1.4.1.37950.1.1.5.12.2.9.56
-- 1.3.6.1.4.1.37950.1.1.5.12.2.9.56
-- 1.3.6.1.4.1.37950.1.1.5.12.2.9.56
		-- 1.3.6.1.4.1.37950.1.1.5.12.2.9.56
		slaAction OBJECT-TYPE
			SYNTAX INTEGER { commit(1) }
			MAX-ACCESS read-write
			STATUS current
			DESCRIPTION
				"Description."
			::= { onuSlaCfg 56 }

		
--          1.3.6.1.4.1.37950.1.1.5.12.2.10
-- 1.3.6.1.4.1.37950.1.1.5.12.2.10
-- 1.3.6.1.4.1.37950.1.1.5.12.2.10
-- 1.3.6.1.4.1.37950.1.1.5.12.2.10
-- 1.3.6.1.4.1.37950.1.1.5.12.2.10
-- 1.3.6.1.4.1.37950.1.1.5.12.2.10
-- 1.3.6.1.4.1.37950.1.1.5.12.2.10
-- 1.3.6.1.4.1.37950.1.1.5.12.2.10
-- 1.3.6.1.4.1.37950.1.1.5.12.2.10
		-- 1.3.6.1.4.1.37950.1.1.5.12.2.10
		onuIgmpCfg OBJECT IDENTIFIER ::= { onuGlobalCfg 10 }

		
--          1.3.6.1.4.1.37950.1.1.5.12.2.10.1
-- 1.3.6.1.4.1.37950.1.1.5.12.2.10.1
-- 1.3.6.1.4.1.37950.1.1.5.12.2.10.1
-- 1.3.6.1.4.1.37950.1.1.5.12.2.10.1
-- 1.3.6.1.4.1.37950.1.1.5.12.2.10.1
-- 1.3.6.1.4.1.37950.1.1.5.12.2.10.1
-- 1.3.6.1.4.1.37950.1.1.5.12.2.10.1
-- 1.3.6.1.4.1.37950.1.1.5.12.2.10.1
-- 1.3.6.1.4.1.37950.1.1.5.12.2.10.1
		-- 1.3.6.1.4.1.37950.1.1.5.12.2.10.1
		igmpMode OBJECT IDENTIFIER ::= { onuIgmpCfg 1 }

		
--          1.3.6.1.4.1.37950.1.1.5.12.2.10.1.1
-- 1.3.6.1.4.1.37950.1.1.5.12.2.10.1.1
-- 1.3.6.1.4.1.37950.1.1.5.12.2.10.1.1
-- 1.3.6.1.4.1.37950.1.1.5.12.2.10.1.1
-- 1.3.6.1.4.1.37950.1.1.5.12.2.10.1.1
-- 1.3.6.1.4.1.37950.1.1.5.12.2.10.1.1
-- 1.3.6.1.4.1.37950.1.1.5.12.2.10.1.1
-- 1.3.6.1.4.1.37950.1.1.5.12.2.10.1.1
-- 1.3.6.1.4.1.37950.1.1.5.12.2.10.1.1
		-- 1.3.6.1.4.1.37950.1.1.5.12.2.10.1.1
		igmpModePonNo OBJECT-TYPE
			SYNTAX INTEGER (1..16)
			MAX-ACCESS read-write
			STATUS current
			DESCRIPTION
				"Description."
			::= { igmpMode 1 }

		
--          1.3.6.1.4.1.37950.1.1.5.12.2.10.1.2
-- 1.3.6.1.4.1.37950.1.1.5.12.2.10.1.2
-- 1.3.6.1.4.1.37950.1.1.5.12.2.10.1.2
-- 1.3.6.1.4.1.37950.1.1.5.12.2.10.1.2
-- 1.3.6.1.4.1.37950.1.1.5.12.2.10.1.2
-- 1.3.6.1.4.1.37950.1.1.5.12.2.10.1.2
-- 1.3.6.1.4.1.37950.1.1.5.12.2.10.1.2
-- 1.3.6.1.4.1.37950.1.1.5.12.2.10.1.2
-- 1.3.6.1.4.1.37950.1.1.5.12.2.10.1.2
		-- 1.3.6.1.4.1.37950.1.1.5.12.2.10.1.2
		igmpModeOnuNo OBJECT-TYPE
			SYNTAX INTEGER (1..65535)
			MAX-ACCESS read-write
			STATUS current
			DESCRIPTION
				"Description."
			::= { igmpMode 2 }

		
--          1.3.6.1.4.1.37950.1.1.5.12.2.10.1.3
-- 1.3.6.1.4.1.37950.1.1.5.12.2.10.1.3
-- 1.3.6.1.4.1.37950.1.1.5.12.2.10.1.3
-- 1.3.6.1.4.1.37950.1.1.5.12.2.10.1.3
-- 1.3.6.1.4.1.37950.1.1.5.12.2.10.1.3
-- 1.3.6.1.4.1.37950.1.1.5.12.2.10.1.3
-- 1.3.6.1.4.1.37950.1.1.5.12.2.10.1.3
-- 1.3.6.1.4.1.37950.1.1.5.12.2.10.1.3
-- 1.3.6.1.4.1.37950.1.1.5.12.2.10.1.3
		-- 1.3.6.1.4.1.37950.1.1.5.12.2.10.1.3
		onuIgmpMode OBJECT-TYPE
			SYNTAX INTEGER
				{
				snooping(1),
				control(2)
				}
			MAX-ACCESS read-write
			STATUS current
			DESCRIPTION
				"Description."
			::= { igmpMode 3 }

		
--          1.3.6.1.4.1.37950.1.1.5.12.2.10.2
-- 1.3.6.1.4.1.37950.1.1.5.12.2.10.2
-- 1.3.6.1.4.1.37950.1.1.5.12.2.10.2
-- 1.3.6.1.4.1.37950.1.1.5.12.2.10.2
-- 1.3.6.1.4.1.37950.1.1.5.12.2.10.2
-- 1.3.6.1.4.1.37950.1.1.5.12.2.10.2
-- 1.3.6.1.4.1.37950.1.1.5.12.2.10.2
-- 1.3.6.1.4.1.37950.1.1.5.12.2.10.2
-- 1.3.6.1.4.1.37950.1.1.5.12.2.10.2
		-- 1.3.6.1.4.1.37950.1.1.5.12.2.10.2
		igmpFastLeave OBJECT IDENTIFIER ::= { onuIgmpCfg 2 }

		
--          1.3.6.1.4.1.37950.1.1.5.12.2.10.2.1
-- 1.3.6.1.4.1.37950.1.1.5.12.2.10.2.1
-- 1.3.6.1.4.1.37950.1.1.5.12.2.10.2.1
-- 1.3.6.1.4.1.37950.1.1.5.12.2.10.2.1
-- 1.3.6.1.4.1.37950.1.1.5.12.2.10.2.1
-- 1.3.6.1.4.1.37950.1.1.5.12.2.10.2.1
-- 1.3.6.1.4.1.37950.1.1.5.12.2.10.2.1
-- 1.3.6.1.4.1.37950.1.1.5.12.2.10.2.1
-- 1.3.6.1.4.1.37950.1.1.5.12.2.10.2.1
		-- 1.3.6.1.4.1.37950.1.1.5.12.2.10.2.1
		igmpFastPonNo OBJECT-TYPE
			SYNTAX INTEGER (1..16)
			MAX-ACCESS read-write
			STATUS current
			DESCRIPTION
				"Description."
			::= { igmpFastLeave 1 }

		
--          1.3.6.1.4.1.37950.1.1.5.12.2.10.2.2
-- 1.3.6.1.4.1.37950.1.1.5.12.2.10.2.2
-- 1.3.6.1.4.1.37950.1.1.5.12.2.10.2.2
-- 1.3.6.1.4.1.37950.1.1.5.12.2.10.2.2
-- 1.3.6.1.4.1.37950.1.1.5.12.2.10.2.2
-- 1.3.6.1.4.1.37950.1.1.5.12.2.10.2.2
-- 1.3.6.1.4.1.37950.1.1.5.12.2.10.2.2
-- 1.3.6.1.4.1.37950.1.1.5.12.2.10.2.2
-- 1.3.6.1.4.1.37950.1.1.5.12.2.10.2.2
		-- 1.3.6.1.4.1.37950.1.1.5.12.2.10.2.2
		igmpFastOnuNo OBJECT-TYPE
			SYNTAX INTEGER (1..65535)
			MAX-ACCESS read-write
			STATUS current
			DESCRIPTION
				"Description."
			::= { igmpFastLeave 2 }

		
--          1.3.6.1.4.1.37950.1.1.5.12.2.10.2.3
-- 1.3.6.1.4.1.37950.1.1.5.12.2.10.2.3
-- 1.3.6.1.4.1.37950.1.1.5.12.2.10.2.3
-- 1.3.6.1.4.1.37950.1.1.5.12.2.10.2.3
-- 1.3.6.1.4.1.37950.1.1.5.12.2.10.2.3
-- 1.3.6.1.4.1.37950.1.1.5.12.2.10.2.3
-- 1.3.6.1.4.1.37950.1.1.5.12.2.10.2.3
-- 1.3.6.1.4.1.37950.1.1.5.12.2.10.2.3
-- 1.3.6.1.4.1.37950.1.1.5.12.2.10.2.3
		-- 1.3.6.1.4.1.37950.1.1.5.12.2.10.2.3
		onuIgmpFastLeave OBJECT-TYPE
			SYNTAX INTEGER
				{
				disable(1),
				enable(2)
				}
			MAX-ACCESS read-write
			STATUS current
			DESCRIPTION
				"Description."
			::= { igmpFastLeave 3 }

		
--          1.3.6.1.4.1.37950.1.1.5.12.2.10.3
-- 1.3.6.1.4.1.37950.1.1.5.12.2.10.3
-- 1.3.6.1.4.1.37950.1.1.5.12.2.10.3
-- 1.3.6.1.4.1.37950.1.1.5.12.2.10.3
-- 1.3.6.1.4.1.37950.1.1.5.12.2.10.3
-- 1.3.6.1.4.1.37950.1.1.5.12.2.10.3
-- 1.3.6.1.4.1.37950.1.1.5.12.2.10.3
-- 1.3.6.1.4.1.37950.1.1.5.12.2.10.3
-- 1.3.6.1.4.1.37950.1.1.5.12.2.10.3
		-- 1.3.6.1.4.1.37950.1.1.5.12.2.10.3
		igmpCfgTable OBJECT-TYPE
			SYNTAX SEQUENCE OF IgmpCfgEntry
			MAX-ACCESS not-accessible
			STATUS current
			DESCRIPTION
				"Description."
			::= { onuIgmpCfg 3 }

		
--          1.3.6.1.4.1.37950.1.1.5.12.2.10.3.1
-- 1.3.6.1.4.1.37950.1.1.5.12.2.10.3.1
-- 1.3.6.1.4.1.37950.1.1.5.12.2.10.3.1
-- 1.3.6.1.4.1.37950.1.1.5.12.2.10.3.1
-- 1.3.6.1.4.1.37950.1.1.5.12.2.10.3.1
-- 1.3.6.1.4.1.37950.1.1.5.12.2.10.3.1
-- 1.3.6.1.4.1.37950.1.1.5.12.2.10.3.1
-- 1.3.6.1.4.1.37950.1.1.5.12.2.10.3.1
-- 1.3.6.1.4.1.37950.1.1.5.12.2.10.3.1
		-- 1.3.6.1.4.1.37950.1.1.5.12.2.10.3.1
		igmpCfgEntry OBJECT-TYPE
			SYNTAX IgmpCfgEntry
			MAX-ACCESS not-accessible
			STATUS current
			DESCRIPTION
				"Description."
			INDEX { igmpCfgPonNo, igmpCfgOnuNo }
			::= { igmpCfgTable 1 }

		
		IgmpCfgEntry ::=
			SEQUENCE { 
				igmpCfgPonNo
					Integer32,
				igmpCfgOnuNo
					Integer32,
				igmpCfgMode
					INTEGER,
				igmpCfgFastLeave
					INTEGER
			 }

--          1.3.6.1.4.1.37950.1.1.5.12.2.10.3.1.1
-- 1.3.6.1.4.1.37950.1.1.5.12.2.10.3.1.1
-- 1.3.6.1.4.1.37950.1.1.5.12.2.10.3.1.1
-- 1.3.6.1.4.1.37950.1.1.5.12.2.10.3.1.1
-- 1.3.6.1.4.1.37950.1.1.5.12.2.10.3.1.1
-- 1.3.6.1.4.1.37950.1.1.5.12.2.10.3.1.1
-- 1.3.6.1.4.1.37950.1.1.5.12.2.10.3.1.1
-- 1.3.6.1.4.1.37950.1.1.5.12.2.10.3.1.1
-- 1.3.6.1.4.1.37950.1.1.5.12.2.10.3.1.1
		-- 1.3.6.1.4.1.37950.1.1.5.12.2.10.3.1.1
		igmpCfgPonNo OBJECT-TYPE
			SYNTAX Integer32
			MAX-ACCESS read-only
			STATUS current
			DESCRIPTION
				"Description."
			::= { igmpCfgEntry 1 }

		
--          1.3.6.1.4.1.37950.1.1.5.12.2.10.3.1.2
-- 1.3.6.1.4.1.37950.1.1.5.12.2.10.3.1.2
-- 1.3.6.1.4.1.37950.1.1.5.12.2.10.3.1.2
-- 1.3.6.1.4.1.37950.1.1.5.12.2.10.3.1.2
-- 1.3.6.1.4.1.37950.1.1.5.12.2.10.3.1.2
-- 1.3.6.1.4.1.37950.1.1.5.12.2.10.3.1.2
-- 1.3.6.1.4.1.37950.1.1.5.12.2.10.3.1.2
-- 1.3.6.1.4.1.37950.1.1.5.12.2.10.3.1.2
-- 1.3.6.1.4.1.37950.1.1.5.12.2.10.3.1.2
		-- 1.3.6.1.4.1.37950.1.1.5.12.2.10.3.1.2
		igmpCfgOnuNo OBJECT-TYPE
			SYNTAX Integer32
			MAX-ACCESS read-only
			STATUS current
			DESCRIPTION
				"Description."
			::= { igmpCfgEntry 2 }

		
--          1.3.6.1.4.1.37950.1.1.5.12.2.10.3.1.3
-- 1.3.6.1.4.1.37950.1.1.5.12.2.10.3.1.3
-- 1.3.6.1.4.1.37950.1.1.5.12.2.10.3.1.3
-- 1.3.6.1.4.1.37950.1.1.5.12.2.10.3.1.3
-- 1.3.6.1.4.1.37950.1.1.5.12.2.10.3.1.3
-- 1.3.6.1.4.1.37950.1.1.5.12.2.10.3.1.3
-- 1.3.6.1.4.1.37950.1.1.5.12.2.10.3.1.3
-- 1.3.6.1.4.1.37950.1.1.5.12.2.10.3.1.3
-- 1.3.6.1.4.1.37950.1.1.5.12.2.10.3.1.3
		-- 1.3.6.1.4.1.37950.1.1.5.12.2.10.3.1.3
		igmpCfgMode OBJECT-TYPE
			SYNTAX INTEGER
				{
				snooping(1),
				ctc(2)
				}
			MAX-ACCESS read-only
			STATUS current
			DESCRIPTION
				"Description."
			::= { igmpCfgEntry 3 }

		
--          1.3.6.1.4.1.37950.1.1.5.12.2.10.3.1.4
-- 1.3.6.1.4.1.37950.1.1.5.12.2.10.3.1.4
-- 1.3.6.1.4.1.37950.1.1.5.12.2.10.3.1.4
-- 1.3.6.1.4.1.37950.1.1.5.12.2.10.3.1.4
-- 1.3.6.1.4.1.37950.1.1.5.12.2.10.3.1.4
-- 1.3.6.1.4.1.37950.1.1.5.12.2.10.3.1.4
-- 1.3.6.1.4.1.37950.1.1.5.12.2.10.3.1.4
-- 1.3.6.1.4.1.37950.1.1.5.12.2.10.3.1.4
-- 1.3.6.1.4.1.37950.1.1.5.12.2.10.3.1.4
		-- 1.3.6.1.4.1.37950.1.1.5.12.2.10.3.1.4
		igmpCfgFastLeave OBJECT-TYPE
			SYNTAX INTEGER
				{
				enable(1),
				disable(2)
				}
			MAX-ACCESS read-only
			STATUS current
			DESCRIPTION
				"Description."
			::= { igmpCfgEntry 4 }

		
--          1.3.6.1.4.1.37950.1.1.5.12.2.11
-- 1.3.6.1.4.1.37950.1.1.5.12.2.11
-- 1.3.6.1.4.1.37950.1.1.5.12.2.11
-- 1.3.6.1.4.1.37950.1.1.5.12.2.11
-- 1.3.6.1.4.1.37950.1.1.5.12.2.11
-- 1.3.6.1.4.1.37950.1.1.5.12.2.11
-- 1.3.6.1.4.1.37950.1.1.5.12.2.11
-- 1.3.6.1.4.1.37950.1.1.5.12.2.11
-- 1.3.6.1.4.1.37950.1.1.5.12.2.11
		-- 1.3.6.1.4.1.37950.1.1.5.12.2.11
		onuReset OBJECT IDENTIFIER ::= { onuGlobalCfg 11 }

		
--          1.3.6.1.4.1.37950.1.1.5.12.2.11.1
-- 1.3.6.1.4.1.37950.1.1.5.12.2.11.1
-- 1.3.6.1.4.1.37950.1.1.5.12.2.11.1
-- 1.3.6.1.4.1.37950.1.1.5.12.2.11.1
-- 1.3.6.1.4.1.37950.1.1.5.12.2.11.1
-- 1.3.6.1.4.1.37950.1.1.5.12.2.11.1
-- 1.3.6.1.4.1.37950.1.1.5.12.2.11.1
-- 1.3.6.1.4.1.37950.1.1.5.12.2.11.1
-- 1.3.6.1.4.1.37950.1.1.5.12.2.11.1
		-- 1.3.6.1.4.1.37950.1.1.5.12.2.11.1
		onuResetPonNo OBJECT-TYPE
			SYNTAX INTEGER (1..16)
			MAX-ACCESS read-write
			STATUS current
			DESCRIPTION
				"Description."
			::= { onuReset 1 }

		
--          1.3.6.1.4.1.37950.1.1.5.12.2.11.2
-- 1.3.6.1.4.1.37950.1.1.5.12.2.11.2
-- 1.3.6.1.4.1.37950.1.1.5.12.2.11.2
-- 1.3.6.1.4.1.37950.1.1.5.12.2.11.2
-- 1.3.6.1.4.1.37950.1.1.5.12.2.11.2
-- 1.3.6.1.4.1.37950.1.1.5.12.2.11.2
-- 1.3.6.1.4.1.37950.1.1.5.12.2.11.2
-- 1.3.6.1.4.1.37950.1.1.5.12.2.11.2
-- 1.3.6.1.4.1.37950.1.1.5.12.2.11.2
		-- 1.3.6.1.4.1.37950.1.1.5.12.2.11.2
		onuResetOnuNo OBJECT-TYPE
			SYNTAX INTEGER (1..65535)
			MAX-ACCESS read-write
			STATUS current
			DESCRIPTION
				"Description."
			::= { onuReset 2 }

		
--          1.3.6.1.4.1.37950.1.1.5.12.2.11.3
-- 1.3.6.1.4.1.37950.1.1.5.12.2.11.3
-- 1.3.6.1.4.1.37950.1.1.5.12.2.11.3
-- 1.3.6.1.4.1.37950.1.1.5.12.2.11.3
-- 1.3.6.1.4.1.37950.1.1.5.12.2.11.3
-- 1.3.6.1.4.1.37950.1.1.5.12.2.11.3
-- 1.3.6.1.4.1.37950.1.1.5.12.2.11.3
-- 1.3.6.1.4.1.37950.1.1.5.12.2.11.3
-- 1.3.6.1.4.1.37950.1.1.5.12.2.11.3
		-- 1.3.6.1.4.1.37950.1.1.5.12.2.11.3
		onuResetAction OBJECT-TYPE
			SYNTAX INTEGER { enable(1) }
			MAX-ACCESS read-write
			STATUS current
			DESCRIPTION
				"Description."
			::= { onuReset 3 }

		
--          1.3.6.1.4.1.37950.1.1.5.12.2.12
-- 1.3.6.1.4.1.37950.1.1.5.12.2.12
-- 1.3.6.1.4.1.37950.1.1.5.12.2.12
-- 1.3.6.1.4.1.37950.1.1.5.12.2.12
-- 1.3.6.1.4.1.37950.1.1.5.12.2.12
-- 1.3.6.1.4.1.37950.1.1.5.12.2.12
-- 1.3.6.1.4.1.37950.1.1.5.12.2.12
-- 1.3.6.1.4.1.37950.1.1.5.12.2.12
-- 1.3.6.1.4.1.37950.1.1.5.12.2.12
		-- 1.3.6.1.4.1.37950.1.1.5.12.2.12
		onuPowerSavingCfg OBJECT IDENTIFIER ::= { onuGlobalCfg 12 }

		
--          1.3.6.1.4.1.37950.1.1.5.12.2.12.1
-- 1.3.6.1.4.1.37950.1.1.5.12.2.12.1
-- 1.3.6.1.4.1.37950.1.1.5.12.2.12.1
-- 1.3.6.1.4.1.37950.1.1.5.12.2.12.1
-- 1.3.6.1.4.1.37950.1.1.5.12.2.12.1
-- 1.3.6.1.4.1.37950.1.1.5.12.2.12.1
-- 1.3.6.1.4.1.37950.1.1.5.12.2.12.1
-- 1.3.6.1.4.1.37950.1.1.5.12.2.12.1
-- 1.3.6.1.4.1.37950.1.1.5.12.2.12.1
		-- 1.3.6.1.4.1.37950.1.1.5.12.2.12.1
		onuPowerSavPonNo OBJECT-TYPE
			SYNTAX INTEGER (1..16)
			MAX-ACCESS read-write
			STATUS current
			DESCRIPTION
				"Description."
			::= { onuPowerSavingCfg 1 }

		
--          1.3.6.1.4.1.37950.1.1.5.12.2.12.2
-- 1.3.6.1.4.1.37950.1.1.5.12.2.12.2
-- 1.3.6.1.4.1.37950.1.1.5.12.2.12.2
-- 1.3.6.1.4.1.37950.1.1.5.12.2.12.2
-- 1.3.6.1.4.1.37950.1.1.5.12.2.12.2
-- 1.3.6.1.4.1.37950.1.1.5.12.2.12.2
-- 1.3.6.1.4.1.37950.1.1.5.12.2.12.2
-- 1.3.6.1.4.1.37950.1.1.5.12.2.12.2
-- 1.3.6.1.4.1.37950.1.1.5.12.2.12.2
		-- 1.3.6.1.4.1.37950.1.1.5.12.2.12.2
		onuPowerSavOnuNo OBJECT-TYPE
			SYNTAX INTEGER (1..65535)
			MAX-ACCESS read-write
			STATUS current
			DESCRIPTION
				"Description."
			::= { onuPowerSavingCfg 2 }

		
--          1.3.6.1.4.1.37950.1.1.5.12.2.12.3
-- 1.3.6.1.4.1.37950.1.1.5.12.2.12.3
-- 1.3.6.1.4.1.37950.1.1.5.12.2.12.3
-- 1.3.6.1.4.1.37950.1.1.5.12.2.12.3
-- 1.3.6.1.4.1.37950.1.1.5.12.2.12.3
-- 1.3.6.1.4.1.37950.1.1.5.12.2.12.3
-- 1.3.6.1.4.1.37950.1.1.5.12.2.12.3
-- 1.3.6.1.4.1.37950.1.1.5.12.2.12.3
-- 1.3.6.1.4.1.37950.1.1.5.12.2.12.3
		-- 1.3.6.1.4.1.37950.1.1.5.12.2.12.3
		earlyWakeupEn OBJECT-TYPE
			SYNTAX INTEGER
				{
				disable(0),
				enable(1)
				}
			MAX-ACCESS read-write
			STATUS current
			DESCRIPTION
				"Description."
			::= { onuPowerSavingCfg 3 }

		
--          1.3.6.1.4.1.37950.1.1.5.12.2.12.4
-- 1.3.6.1.4.1.37950.1.1.5.12.2.12.4
-- 1.3.6.1.4.1.37950.1.1.5.12.2.12.4
-- 1.3.6.1.4.1.37950.1.1.5.12.2.12.4
-- 1.3.6.1.4.1.37950.1.1.5.12.2.12.4
-- 1.3.6.1.4.1.37950.1.1.5.12.2.12.4
-- 1.3.6.1.4.1.37950.1.1.5.12.2.12.4
-- 1.3.6.1.4.1.37950.1.1.5.12.2.12.4
-- 1.3.6.1.4.1.37950.1.1.5.12.2.12.4
		-- 1.3.6.1.4.1.37950.1.1.5.12.2.12.4
		sleepDurationMax OBJECT-TYPE
			SYNTAX INTEGER (0..65535)
			MAX-ACCESS read-write
			STATUS current
			DESCRIPTION
				"Description."
			::= { onuPowerSavingCfg 4 }

		
--          1.3.6.1.4.1.37950.1.1.5.12.2.12.5
-- 1.3.6.1.4.1.37950.1.1.5.12.2.12.5
-- 1.3.6.1.4.1.37950.1.1.5.12.2.12.5
-- 1.3.6.1.4.1.37950.1.1.5.12.2.12.5
-- 1.3.6.1.4.1.37950.1.1.5.12.2.12.5
-- 1.3.6.1.4.1.37950.1.1.5.12.2.12.5
-- 1.3.6.1.4.1.37950.1.1.5.12.2.12.5
-- 1.3.6.1.4.1.37950.1.1.5.12.2.12.5
-- 1.3.6.1.4.1.37950.1.1.5.12.2.12.5
		-- 1.3.6.1.4.1.37950.1.1.5.12.2.12.5
		powerSavAction OBJECT-TYPE
			SYNTAX INTEGER { commit(1) }
			MAX-ACCESS read-write
			STATUS current
			DESCRIPTION
				"Description."
			::= { onuPowerSavingCfg 5 }

		
--          1.3.6.1.4.1.37950.1.1.5.12.2.13
-- 1.3.6.1.4.1.37950.1.1.5.12.2.13
-- 1.3.6.1.4.1.37950.1.1.5.12.2.13
-- 1.3.6.1.4.1.37950.1.1.5.12.2.13
-- 1.3.6.1.4.1.37950.1.1.5.12.2.13
-- 1.3.6.1.4.1.37950.1.1.5.12.2.13
-- 1.3.6.1.4.1.37950.1.1.5.12.2.13
-- 1.3.6.1.4.1.37950.1.1.5.12.2.13
-- 1.3.6.1.4.1.37950.1.1.5.12.2.13
		-- 1.3.6.1.4.1.37950.1.1.5.12.2.13
		onuPowerSavParameter OBJECT IDENTIFIER ::= { onuGlobalCfg 13 }

		
--          1.3.6.1.4.1.37950.1.1.5.12.2.13.1
-- 1.3.6.1.4.1.37950.1.1.5.12.2.13.1
-- 1.3.6.1.4.1.37950.1.1.5.12.2.13.1
-- 1.3.6.1.4.1.37950.1.1.5.12.2.13.1
-- 1.3.6.1.4.1.37950.1.1.5.12.2.13.1
-- 1.3.6.1.4.1.37950.1.1.5.12.2.13.1
-- 1.3.6.1.4.1.37950.1.1.5.12.2.13.1
-- 1.3.6.1.4.1.37950.1.1.5.12.2.13.1
-- 1.3.6.1.4.1.37950.1.1.5.12.2.13.1
		-- 1.3.6.1.4.1.37950.1.1.5.12.2.13.1
		onuPwSavPonNo OBJECT-TYPE
			SYNTAX INTEGER (1..16)
			MAX-ACCESS read-write
			STATUS current
			DESCRIPTION
				"Description."
			::= { onuPowerSavParameter 1 }

		
--          1.3.6.1.4.1.37950.1.1.5.12.2.13.2
-- 1.3.6.1.4.1.37950.1.1.5.12.2.13.2
-- 1.3.6.1.4.1.37950.1.1.5.12.2.13.2
-- 1.3.6.1.4.1.37950.1.1.5.12.2.13.2
-- 1.3.6.1.4.1.37950.1.1.5.12.2.13.2
-- 1.3.6.1.4.1.37950.1.1.5.12.2.13.2
-- 1.3.6.1.4.1.37950.1.1.5.12.2.13.2
-- 1.3.6.1.4.1.37950.1.1.5.12.2.13.2
-- 1.3.6.1.4.1.37950.1.1.5.12.2.13.2
		-- 1.3.6.1.4.1.37950.1.1.5.12.2.13.2
		onuPwSavOnuNo OBJECT-TYPE
			SYNTAX INTEGER (1..65535)
			MAX-ACCESS read-write
			STATUS current
			DESCRIPTION
				"Description."
			::= { onuPowerSavParameter 2 }

		
--          1.3.6.1.4.1.37950.1.1.5.12.2.13.3
-- 1.3.6.1.4.1.37950.1.1.5.12.2.13.3
-- 1.3.6.1.4.1.37950.1.1.5.12.2.13.3
-- 1.3.6.1.4.1.37950.1.1.5.12.2.13.3
-- 1.3.6.1.4.1.37950.1.1.5.12.2.13.3
-- 1.3.6.1.4.1.37950.1.1.5.12.2.13.3
-- 1.3.6.1.4.1.37950.1.1.5.12.2.13.3
-- 1.3.6.1.4.1.37950.1.1.5.12.2.13.3
-- 1.3.6.1.4.1.37950.1.1.5.12.2.13.3
		-- 1.3.6.1.4.1.37950.1.1.5.12.2.13.3
		sleepDuration OBJECT-TYPE
			SYNTAX INTEGER (0..65535)
			MAX-ACCESS read-write
			STATUS current
			DESCRIPTION
				"Description."
			::= { onuPowerSavParameter 3 }

		
--          1.3.6.1.4.1.37950.1.1.5.12.2.13.4
-- 1.3.6.1.4.1.37950.1.1.5.12.2.13.4
-- 1.3.6.1.4.1.37950.1.1.5.12.2.13.4
-- 1.3.6.1.4.1.37950.1.1.5.12.2.13.4
-- 1.3.6.1.4.1.37950.1.1.5.12.2.13.4
-- 1.3.6.1.4.1.37950.1.1.5.12.2.13.4
-- 1.3.6.1.4.1.37950.1.1.5.12.2.13.4
-- 1.3.6.1.4.1.37950.1.1.5.12.2.13.4
-- 1.3.6.1.4.1.37950.1.1.5.12.2.13.4
		-- 1.3.6.1.4.1.37950.1.1.5.12.2.13.4
		wakeDuration OBJECT-TYPE
			SYNTAX INTEGER (0..65535)
			MAX-ACCESS read-write
			STATUS current
			DESCRIPTION
				"Description."
			::= { onuPowerSavParameter 4 }

		
--          1.3.6.1.4.1.37950.1.1.5.12.2.13.5
-- 1.3.6.1.4.1.37950.1.1.5.12.2.13.5
-- 1.3.6.1.4.1.37950.1.1.5.12.2.13.5
-- 1.3.6.1.4.1.37950.1.1.5.12.2.13.5
-- 1.3.6.1.4.1.37950.1.1.5.12.2.13.5
-- 1.3.6.1.4.1.37950.1.1.5.12.2.13.5
-- 1.3.6.1.4.1.37950.1.1.5.12.2.13.5
-- 1.3.6.1.4.1.37950.1.1.5.12.2.13.5
-- 1.3.6.1.4.1.37950.1.1.5.12.2.13.5
		-- 1.3.6.1.4.1.37950.1.1.5.12.2.13.5
		sleepFlag OBJECT-TYPE
			SYNTAX INTEGER
				{
				off(1),
				on(2),
				change(3)
				}
			MAX-ACCESS read-write
			STATUS current
			DESCRIPTION
				"Description."
			::= { onuPowerSavParameter 5 }

		
--          1.3.6.1.4.1.37950.1.1.5.12.2.13.6
-- 1.3.6.1.4.1.37950.1.1.5.12.2.13.6
-- 1.3.6.1.4.1.37950.1.1.5.12.2.13.6
-- 1.3.6.1.4.1.37950.1.1.5.12.2.13.6
-- 1.3.6.1.4.1.37950.1.1.5.12.2.13.6
-- 1.3.6.1.4.1.37950.1.1.5.12.2.13.6
-- 1.3.6.1.4.1.37950.1.1.5.12.2.13.6
-- 1.3.6.1.4.1.37950.1.1.5.12.2.13.6
-- 1.3.6.1.4.1.37950.1.1.5.12.2.13.6
		-- 1.3.6.1.4.1.37950.1.1.5.12.2.13.6
		sleepMode OBJECT-TYPE
			SYNTAX INTEGER
				{
				none(1),
				txSleepOnly(2),
				txAndRxSleep(3)
				}
			MAX-ACCESS read-write
			STATUS current
			DESCRIPTION
				"Description."
			::= { onuPowerSavParameter 6 }

		
--          1.3.6.1.4.1.37950.1.1.5.12.2.13.7
-- 1.3.6.1.4.1.37950.1.1.5.12.2.13.7
-- 1.3.6.1.4.1.37950.1.1.5.12.2.13.7
-- 1.3.6.1.4.1.37950.1.1.5.12.2.13.7
-- 1.3.6.1.4.1.37950.1.1.5.12.2.13.7
-- 1.3.6.1.4.1.37950.1.1.5.12.2.13.7
-- 1.3.6.1.4.1.37950.1.1.5.12.2.13.7
-- 1.3.6.1.4.1.37950.1.1.5.12.2.13.7
-- 1.3.6.1.4.1.37950.1.1.5.12.2.13.7
		-- 1.3.6.1.4.1.37950.1.1.5.12.2.13.7
		onuPwSaveAction OBJECT-TYPE
			SYNTAX INTEGER { commit(1) }
			MAX-ACCESS read-write
			STATUS current
			DESCRIPTION
				"Description."
			::= { onuPowerSavParameter 7 }

		
--          1.3.6.1.4.1.37950.1.1.5.12.2.14
-- 1.3.6.1.4.1.37950.1.1.5.12.2.14
-- 1.3.6.1.4.1.37950.1.1.5.12.2.14
-- 1.3.6.1.4.1.37950.1.1.5.12.2.14
-- 1.3.6.1.4.1.37950.1.1.5.12.2.14
-- 1.3.6.1.4.1.37950.1.1.5.12.2.14
-- 1.3.6.1.4.1.37950.1.1.5.12.2.14
-- 1.3.6.1.4.1.37950.1.1.5.12.2.14
-- 1.3.6.1.4.1.37950.1.1.5.12.2.14
		-- 1.3.6.1.4.1.37950.1.1.5.12.2.14
		onuPonProtectCfg OBJECT IDENTIFIER ::= { onuGlobalCfg 14 }

		
--          1.3.6.1.4.1.37950.1.1.5.12.2.14.1
-- 1.3.6.1.4.1.37950.1.1.5.12.2.14.1
-- 1.3.6.1.4.1.37950.1.1.5.12.2.14.1
-- 1.3.6.1.4.1.37950.1.1.5.12.2.14.1
-- 1.3.6.1.4.1.37950.1.1.5.12.2.14.1
-- 1.3.6.1.4.1.37950.1.1.5.12.2.14.1
-- 1.3.6.1.4.1.37950.1.1.5.12.2.14.1
-- 1.3.6.1.4.1.37950.1.1.5.12.2.14.1
-- 1.3.6.1.4.1.37950.1.1.5.12.2.14.1
		-- 1.3.6.1.4.1.37950.1.1.5.12.2.14.1
		ponProtectPonNo OBJECT-TYPE
			SYNTAX INTEGER (1..16)
			MAX-ACCESS read-write
			STATUS current
			DESCRIPTION
				"Description."
			::= { onuPonProtectCfg 1 }

		
--          1.3.6.1.4.1.37950.1.1.5.12.2.14.2
-- 1.3.6.1.4.1.37950.1.1.5.12.2.14.2
-- 1.3.6.1.4.1.37950.1.1.5.12.2.14.2
-- 1.3.6.1.4.1.37950.1.1.5.12.2.14.2
-- 1.3.6.1.4.1.37950.1.1.5.12.2.14.2
-- 1.3.6.1.4.1.37950.1.1.5.12.2.14.2
-- 1.3.6.1.4.1.37950.1.1.5.12.2.14.2
-- 1.3.6.1.4.1.37950.1.1.5.12.2.14.2
-- 1.3.6.1.4.1.37950.1.1.5.12.2.14.2
		-- 1.3.6.1.4.1.37950.1.1.5.12.2.14.2
		ponProtectOnuNo OBJECT-TYPE
			SYNTAX INTEGER (1..65535)
			MAX-ACCESS read-write
			STATUS current
			DESCRIPTION
				"Description."
			::= { onuPonProtectCfg 2 }

		
--          1.3.6.1.4.1.37950.1.1.5.12.2.14.3
-- 1.3.6.1.4.1.37950.1.1.5.12.2.14.3
-- 1.3.6.1.4.1.37950.1.1.5.12.2.14.3
-- 1.3.6.1.4.1.37950.1.1.5.12.2.14.3
-- 1.3.6.1.4.1.37950.1.1.5.12.2.14.3
-- 1.3.6.1.4.1.37950.1.1.5.12.2.14.3
-- 1.3.6.1.4.1.37950.1.1.5.12.2.14.3
-- 1.3.6.1.4.1.37950.1.1.5.12.2.14.3
-- 1.3.6.1.4.1.37950.1.1.5.12.2.14.3
		-- 1.3.6.1.4.1.37950.1.1.5.12.2.14.3
		losOptical OBJECT-TYPE
			SYNTAX INTEGER (0..65535)
			MAX-ACCESS read-write
			STATUS current
			DESCRIPTION
				"Description."
			::= { onuPonProtectCfg 3 }

		
--          1.3.6.1.4.1.37950.1.1.5.12.2.14.4
-- 1.3.6.1.4.1.37950.1.1.5.12.2.14.4
-- 1.3.6.1.4.1.37950.1.1.5.12.2.14.4
-- 1.3.6.1.4.1.37950.1.1.5.12.2.14.4
-- 1.3.6.1.4.1.37950.1.1.5.12.2.14.4
-- 1.3.6.1.4.1.37950.1.1.5.12.2.14.4
-- 1.3.6.1.4.1.37950.1.1.5.12.2.14.4
-- 1.3.6.1.4.1.37950.1.1.5.12.2.14.4
-- 1.3.6.1.4.1.37950.1.1.5.12.2.14.4
		-- 1.3.6.1.4.1.37950.1.1.5.12.2.14.4
		losMpcp OBJECT-TYPE
			SYNTAX INTEGER (0..65535)
			MAX-ACCESS read-write
			STATUS current
			DESCRIPTION
				"Description."
			::= { onuPonProtectCfg 4 }

		
--          1.3.6.1.4.1.37950.1.1.5.12.2.14.5
-- 1.3.6.1.4.1.37950.1.1.5.12.2.14.5
-- 1.3.6.1.4.1.37950.1.1.5.12.2.14.5
-- 1.3.6.1.4.1.37950.1.1.5.12.2.14.5
-- 1.3.6.1.4.1.37950.1.1.5.12.2.14.5
-- 1.3.6.1.4.1.37950.1.1.5.12.2.14.5
-- 1.3.6.1.4.1.37950.1.1.5.12.2.14.5
-- 1.3.6.1.4.1.37950.1.1.5.12.2.14.5
-- 1.3.6.1.4.1.37950.1.1.5.12.2.14.5
		-- 1.3.6.1.4.1.37950.1.1.5.12.2.14.5
		ponProtectAction OBJECT-TYPE
			SYNTAX INTEGER { commit(1) }
			MAX-ACCESS read-write
			STATUS current
			DESCRIPTION
				"Description."
			::= { onuPonProtectCfg 5 }

		
--          1.3.6.1.4.1.37950.1.1.5.12.2.14.6
-- 1.3.6.1.4.1.37950.1.1.5.12.2.14.6
-- 1.3.6.1.4.1.37950.1.1.5.12.2.14.6
-- 1.3.6.1.4.1.37950.1.1.5.12.2.14.6
-- 1.3.6.1.4.1.37950.1.1.5.12.2.14.6
-- 1.3.6.1.4.1.37950.1.1.5.12.2.14.6
-- 1.3.6.1.4.1.37950.1.1.5.12.2.14.6
-- 1.3.6.1.4.1.37950.1.1.5.12.2.14.6
-- 1.3.6.1.4.1.37950.1.1.5.12.2.14.6
		-- 1.3.6.1.4.1.37950.1.1.5.12.2.14.6
		onuPonProtectTable OBJECT-TYPE
			SYNTAX SEQUENCE OF OnuPonProtectEntry
			MAX-ACCESS not-accessible
			STATUS current
			DESCRIPTION
				"Description."
			::= { onuPonProtectCfg 6 }

		
--          1.3.6.1.4.1.37950.1.1.5.12.2.14.6.1
-- 1.3.6.1.4.1.37950.1.1.5.12.2.14.6.1
-- 1.3.6.1.4.1.37950.1.1.5.12.2.14.6.1
-- 1.3.6.1.4.1.37950.1.1.5.12.2.14.6.1
-- 1.3.6.1.4.1.37950.1.1.5.12.2.14.6.1
-- 1.3.6.1.4.1.37950.1.1.5.12.2.14.6.1
-- 1.3.6.1.4.1.37950.1.1.5.12.2.14.6.1
-- 1.3.6.1.4.1.37950.1.1.5.12.2.14.6.1
-- 1.3.6.1.4.1.37950.1.1.5.12.2.14.6.1
		-- 1.3.6.1.4.1.37950.1.1.5.12.2.14.6.1
		onuPonProtectEntry OBJECT-TYPE
			SYNTAX OnuPonProtectEntry
			MAX-ACCESS not-accessible
			STATUS current
			DESCRIPTION
				"Description."
			INDEX { protectPonNo, protectPonOnuNo }
			::= { onuPonProtectTable 1 }

		
		OnuPonProtectEntry ::=
			SEQUENCE { 
				protectPonNo
					Integer32,
				protectPonOnuNo
					Integer32,
				protectLostOptical
					Integer32,
				protectLostMpcp
					Integer32
			 }

--          1.3.6.1.4.1.37950.1.1.5.12.2.14.6.1.1
-- 1.3.6.1.4.1.37950.1.1.5.12.2.14.6.1.1
-- 1.3.6.1.4.1.37950.1.1.5.12.2.14.6.1.1
-- 1.3.6.1.4.1.37950.1.1.5.12.2.14.6.1.1
-- 1.3.6.1.4.1.37950.1.1.5.12.2.14.6.1.1
-- 1.3.6.1.4.1.37950.1.1.5.12.2.14.6.1.1
-- 1.3.6.1.4.1.37950.1.1.5.12.2.14.6.1.1
-- 1.3.6.1.4.1.37950.1.1.5.12.2.14.6.1.1
-- 1.3.6.1.4.1.37950.1.1.5.12.2.14.6.1.1
		-- 1.3.6.1.4.1.37950.1.1.5.12.2.14.6.1.1
		protectPonNo OBJECT-TYPE
			SYNTAX Integer32
			MAX-ACCESS read-only
			STATUS current
			DESCRIPTION
				"Description."
			::= { onuPonProtectEntry 1 }

		
--          1.3.6.1.4.1.37950.1.1.5.12.2.14.6.1.2
-- 1.3.6.1.4.1.37950.1.1.5.12.2.14.6.1.2
-- 1.3.6.1.4.1.37950.1.1.5.12.2.14.6.1.2
-- 1.3.6.1.4.1.37950.1.1.5.12.2.14.6.1.2
-- 1.3.6.1.4.1.37950.1.1.5.12.2.14.6.1.2
-- 1.3.6.1.4.1.37950.1.1.5.12.2.14.6.1.2
-- 1.3.6.1.4.1.37950.1.1.5.12.2.14.6.1.2
-- 1.3.6.1.4.1.37950.1.1.5.12.2.14.6.1.2
-- 1.3.6.1.4.1.37950.1.1.5.12.2.14.6.1.2
		-- 1.3.6.1.4.1.37950.1.1.5.12.2.14.6.1.2
		protectPonOnuNo OBJECT-TYPE
			SYNTAX Integer32
			MAX-ACCESS read-only
			STATUS current
			DESCRIPTION
				"Description."
			::= { onuPonProtectEntry 2 }

		
--          1.3.6.1.4.1.37950.1.1.5.12.2.14.6.1.3
-- 1.3.6.1.4.1.37950.1.1.5.12.2.14.6.1.3
-- 1.3.6.1.4.1.37950.1.1.5.12.2.14.6.1.3
-- 1.3.6.1.4.1.37950.1.1.5.12.2.14.6.1.3
-- 1.3.6.1.4.1.37950.1.1.5.12.2.14.6.1.3
-- 1.3.6.1.4.1.37950.1.1.5.12.2.14.6.1.3
-- 1.3.6.1.4.1.37950.1.1.5.12.2.14.6.1.3
-- 1.3.6.1.4.1.37950.1.1.5.12.2.14.6.1.3
-- 1.3.6.1.4.1.37950.1.1.5.12.2.14.6.1.3
		-- 1.3.6.1.4.1.37950.1.1.5.12.2.14.6.1.3
		protectLostOptical OBJECT-TYPE
			SYNTAX Integer32
			MAX-ACCESS read-only
			STATUS current
			DESCRIPTION
				"Description."
			::= { onuPonProtectEntry 3 }

		
--          1.3.6.1.4.1.37950.1.1.5.12.2.14.6.1.4
-- 1.3.6.1.4.1.37950.1.1.5.12.2.14.6.1.4
-- 1.3.6.1.4.1.37950.1.1.5.12.2.14.6.1.4
-- 1.3.6.1.4.1.37950.1.1.5.12.2.14.6.1.4
-- 1.3.6.1.4.1.37950.1.1.5.12.2.14.6.1.4
-- 1.3.6.1.4.1.37950.1.1.5.12.2.14.6.1.4
-- 1.3.6.1.4.1.37950.1.1.5.12.2.14.6.1.4
-- 1.3.6.1.4.1.37950.1.1.5.12.2.14.6.1.4
-- 1.3.6.1.4.1.37950.1.1.5.12.2.14.6.1.4
		-- 1.3.6.1.4.1.37950.1.1.5.12.2.14.6.1.4
		protectLostMpcp OBJECT-TYPE
			SYNTAX Integer32
			MAX-ACCESS read-only
			STATUS current
			DESCRIPTION
				"Description."
			::= { onuPonProtectEntry 4 }

		
--          1.3.6.1.4.1.37950.1.1.5.12.2.15
-- 1.3.6.1.4.1.37950.1.1.5.12.2.15
-- 1.3.6.1.4.1.37950.1.1.5.12.2.15
-- 1.3.6.1.4.1.37950.1.1.5.12.2.15
-- 1.3.6.1.4.1.37950.1.1.5.12.2.15
-- 1.3.6.1.4.1.37950.1.1.5.12.2.15
-- 1.3.6.1.4.1.37950.1.1.5.12.2.15
-- 1.3.6.1.4.1.37950.1.1.5.12.2.15
-- 1.3.6.1.4.1.37950.1.1.5.12.2.15
		-- 1.3.6.1.4.1.37950.1.1.5.12.2.15
		onuPonPowerOnOff OBJECT IDENTIFIER ::= { onuGlobalCfg 15 }

		
--          1.3.6.1.4.1.37950.1.1.5.12.2.15.1
-- 1.3.6.1.4.1.37950.1.1.5.12.2.15.1
-- 1.3.6.1.4.1.37950.1.1.5.12.2.15.1
-- 1.3.6.1.4.1.37950.1.1.5.12.2.15.1
-- 1.3.6.1.4.1.37950.1.1.5.12.2.15.1
-- 1.3.6.1.4.1.37950.1.1.5.12.2.15.1
-- 1.3.6.1.4.1.37950.1.1.5.12.2.15.1
-- 1.3.6.1.4.1.37950.1.1.5.12.2.15.1
-- 1.3.6.1.4.1.37950.1.1.5.12.2.15.1
		-- 1.3.6.1.4.1.37950.1.1.5.12.2.15.1
		onOffPonNo OBJECT-TYPE
			SYNTAX INTEGER (1..16)
			MAX-ACCESS read-write
			STATUS current
			DESCRIPTION
				"Description."
			::= { onuPonPowerOnOff 1 }

		
--          1.3.6.1.4.1.37950.1.1.5.12.2.15.2
-- 1.3.6.1.4.1.37950.1.1.5.12.2.15.2
-- 1.3.6.1.4.1.37950.1.1.5.12.2.15.2
-- 1.3.6.1.4.1.37950.1.1.5.12.2.15.2
-- 1.3.6.1.4.1.37950.1.1.5.12.2.15.2
-- 1.3.6.1.4.1.37950.1.1.5.12.2.15.2
-- 1.3.6.1.4.1.37950.1.1.5.12.2.15.2
-- 1.3.6.1.4.1.37950.1.1.5.12.2.15.2
-- 1.3.6.1.4.1.37950.1.1.5.12.2.15.2
		-- 1.3.6.1.4.1.37950.1.1.5.12.2.15.2
		onOffOnuNo OBJECT-TYPE
			SYNTAX INTEGER (1..65535)
			MAX-ACCESS read-write
			STATUS current
			DESCRIPTION
				"Description."
			::= { onuPonPowerOnOff 2 }

		
--          1.3.6.1.4.1.37950.1.1.5.12.2.15.3
-- 1.3.6.1.4.1.37950.1.1.5.12.2.15.3
-- 1.3.6.1.4.1.37950.1.1.5.12.2.15.3
-- 1.3.6.1.4.1.37950.1.1.5.12.2.15.3
-- 1.3.6.1.4.1.37950.1.1.5.12.2.15.3
-- 1.3.6.1.4.1.37950.1.1.5.12.2.15.3
-- 1.3.6.1.4.1.37950.1.1.5.12.2.15.3
-- 1.3.6.1.4.1.37950.1.1.5.12.2.15.3
-- 1.3.6.1.4.1.37950.1.1.5.12.2.15.3
		-- 1.3.6.1.4.1.37950.1.1.5.12.2.15.3
		laserAction OBJECT-TYPE
			SYNTAX INTEGER (0..65535)
			MAX-ACCESS read-write
			STATUS current
			DESCRIPTION
				"Description."
			::= { onuPonPowerOnOff 3 }

		
--          1.3.6.1.4.1.37950.1.1.5.12.2.15.4
-- 1.3.6.1.4.1.37950.1.1.5.12.2.15.4
-- 1.3.6.1.4.1.37950.1.1.5.12.2.15.4
-- 1.3.6.1.4.1.37950.1.1.5.12.2.15.4
-- 1.3.6.1.4.1.37950.1.1.5.12.2.15.4
-- 1.3.6.1.4.1.37950.1.1.5.12.2.15.4
-- 1.3.6.1.4.1.37950.1.1.5.12.2.15.4
-- 1.3.6.1.4.1.37950.1.1.5.12.2.15.4
-- 1.3.6.1.4.1.37950.1.1.5.12.2.15.4
		-- 1.3.6.1.4.1.37950.1.1.5.12.2.15.4
		ponMac OBJECT-TYPE
			SYNTAX OCTET STRING
			MAX-ACCESS read-write
			STATUS current
			DESCRIPTION
				"Description."
			::= { onuPonPowerOnOff 4 }

		
--          1.3.6.1.4.1.37950.1.1.5.12.2.15.5
-- 1.3.6.1.4.1.37950.1.1.5.12.2.15.5
-- 1.3.6.1.4.1.37950.1.1.5.12.2.15.5
-- 1.3.6.1.4.1.37950.1.1.5.12.2.15.5
-- 1.3.6.1.4.1.37950.1.1.5.12.2.15.5
-- 1.3.6.1.4.1.37950.1.1.5.12.2.15.5
-- 1.3.6.1.4.1.37950.1.1.5.12.2.15.5
-- 1.3.6.1.4.1.37950.1.1.5.12.2.15.5
-- 1.3.6.1.4.1.37950.1.1.5.12.2.15.5
		-- 1.3.6.1.4.1.37950.1.1.5.12.2.15.5
		transmitter OBJECT-TYPE
			SYNTAX INTEGER
				{
				major(1),
				standby(2),
				both(3)
				}
			MAX-ACCESS read-write
			STATUS current
			DESCRIPTION
				"Description."
			::= { onuPonPowerOnOff 5 }

		
--          1.3.6.1.4.1.37950.1.1.5.12.2.15.6
-- 1.3.6.1.4.1.37950.1.1.5.12.2.15.6
-- 1.3.6.1.4.1.37950.1.1.5.12.2.15.6
-- 1.3.6.1.4.1.37950.1.1.5.12.2.15.6
-- 1.3.6.1.4.1.37950.1.1.5.12.2.15.6
-- 1.3.6.1.4.1.37950.1.1.5.12.2.15.6
-- 1.3.6.1.4.1.37950.1.1.5.12.2.15.6
-- 1.3.6.1.4.1.37950.1.1.5.12.2.15.6
-- 1.3.6.1.4.1.37950.1.1.5.12.2.15.6
		-- 1.3.6.1.4.1.37950.1.1.5.12.2.15.6
		onOffAction OBJECT-TYPE
			SYNTAX INTEGER { commit(1) }
			MAX-ACCESS read-write
			STATUS current
			DESCRIPTION
				"Description."
			::= { onuPonPowerOnOff 6 }

		
--          1.3.6.1.4.1.37950.1.1.5.12.2.16
-- 1.3.6.1.4.1.37950.1.1.5.12.2.16
-- 1.3.6.1.4.1.37950.1.1.5.12.2.16
-- 1.3.6.1.4.1.37950.1.1.5.12.2.16
-- 1.3.6.1.4.1.37950.1.1.5.12.2.16
-- 1.3.6.1.4.1.37950.1.1.5.12.2.16
-- 1.3.6.1.4.1.37950.1.1.5.12.2.16
-- 1.3.6.1.4.1.37950.1.1.5.12.2.16
-- 1.3.6.1.4.1.37950.1.1.5.12.2.16
		-- 1.3.6.1.4.1.37950.1.1.5.12.2.16
		onuMacAgingTime OBJECT IDENTIFIER ::= { onuGlobalCfg 16 }

		
--          1.3.6.1.4.1.37950.1.1.5.12.2.16.1
-- 1.3.6.1.4.1.37950.1.1.5.12.2.16.1
-- 1.3.6.1.4.1.37950.1.1.5.12.2.16.1
-- 1.3.6.1.4.1.37950.1.1.5.12.2.16.1
-- 1.3.6.1.4.1.37950.1.1.5.12.2.16.1
-- 1.3.6.1.4.1.37950.1.1.5.12.2.16.1
-- 1.3.6.1.4.1.37950.1.1.5.12.2.16.1
-- 1.3.6.1.4.1.37950.1.1.5.12.2.16.1
-- 1.3.6.1.4.1.37950.1.1.5.12.2.16.1
		-- 1.3.6.1.4.1.37950.1.1.5.12.2.16.1
		agingTimePonNo OBJECT-TYPE
			SYNTAX INTEGER (1..16)
			MAX-ACCESS read-write
			STATUS current
			DESCRIPTION
				"Description."
			::= { onuMacAgingTime 1 }

		
--          1.3.6.1.4.1.37950.1.1.5.12.2.16.2
-- 1.3.6.1.4.1.37950.1.1.5.12.2.16.2
-- 1.3.6.1.4.1.37950.1.1.5.12.2.16.2
-- 1.3.6.1.4.1.37950.1.1.5.12.2.16.2
-- 1.3.6.1.4.1.37950.1.1.5.12.2.16.2
-- 1.3.6.1.4.1.37950.1.1.5.12.2.16.2
-- 1.3.6.1.4.1.37950.1.1.5.12.2.16.2
-- 1.3.6.1.4.1.37950.1.1.5.12.2.16.2
-- 1.3.6.1.4.1.37950.1.1.5.12.2.16.2
		-- 1.3.6.1.4.1.37950.1.1.5.12.2.16.2
		agingTimeOnuNo OBJECT-TYPE
			SYNTAX INTEGER (1..65535)
			MAX-ACCESS read-write
			STATUS current
			DESCRIPTION
				"Description."
			::= { onuMacAgingTime 2 }

		
--          1.3.6.1.4.1.37950.1.1.5.12.2.16.3
-- 1.3.6.1.4.1.37950.1.1.5.12.2.16.3
-- 1.3.6.1.4.1.37950.1.1.5.12.2.16.3
-- 1.3.6.1.4.1.37950.1.1.5.12.2.16.3
-- 1.3.6.1.4.1.37950.1.1.5.12.2.16.3
-- 1.3.6.1.4.1.37950.1.1.5.12.2.16.3
-- 1.3.6.1.4.1.37950.1.1.5.12.2.16.3
-- 1.3.6.1.4.1.37950.1.1.5.12.2.16.3
-- 1.3.6.1.4.1.37950.1.1.5.12.2.16.3
		-- 1.3.6.1.4.1.37950.1.1.5.12.2.16.3
		macAgetime OBJECT-TYPE
			SYNTAX INTEGER (0..65535)
			MAX-ACCESS read-write
			STATUS current
			DESCRIPTION
				"Description."
			::= { onuMacAgingTime 3 }

		
--          1.3.6.1.4.1.37950.1.1.5.12.2.17
-- 1.3.6.1.4.1.37950.1.1.5.12.2.17
-- 1.3.6.1.4.1.37950.1.1.5.12.2.17
-- 1.3.6.1.4.1.37950.1.1.5.12.2.17
-- 1.3.6.1.4.1.37950.1.1.5.12.2.17
-- 1.3.6.1.4.1.37950.1.1.5.12.2.17
-- 1.3.6.1.4.1.37950.1.1.5.12.2.17
-- 1.3.6.1.4.1.37950.1.1.5.12.2.17
-- 1.3.6.1.4.1.37950.1.1.5.12.2.17
		-- 1.3.6.1.4.1.37950.1.1.5.12.2.17
		onuInfoTable OBJECT-TYPE
			SYNTAX SEQUENCE OF OnuInfoEntry
			MAX-ACCESS not-accessible
			STATUS current
			DESCRIPTION
				"Description."
			::= { onuGlobalCfg 17 }

		
--          1.3.6.1.4.1.37950.1.1.5.12.2.17.1
-- 1.3.6.1.4.1.37950.1.1.5.12.2.17.1
-- 1.3.6.1.4.1.37950.1.1.5.12.2.17.1
-- 1.3.6.1.4.1.37950.1.1.5.12.2.17.1
-- 1.3.6.1.4.1.37950.1.1.5.12.2.17.1
-- 1.3.6.1.4.1.37950.1.1.5.12.2.17.1
-- 1.3.6.1.4.1.37950.1.1.5.12.2.17.1
-- 1.3.6.1.4.1.37950.1.1.5.12.2.17.1
-- 1.3.6.1.4.1.37950.1.1.5.12.2.17.1
		-- 1.3.6.1.4.1.37950.1.1.5.12.2.17.1
		onuInfoEntry OBJECT-TYPE
			SYNTAX OnuInfoEntry
			MAX-ACCESS not-accessible
			STATUS current
			DESCRIPTION
				"Description."
			INDEX { onuInfoPonNo, onuInfoOnuNo }
			::= { onuInfoTable 1 }

		
		OnuInfoEntry ::=
			SEQUENCE { 
				onuInfoPonNo
					Integer32,
				onuInfoOnuNo
					Integer32,
				onuInfoMacAgingTime
					Integer32,
				onuInfoHoldOver
					Integer32,
				onuInfoMainPon
					Integer32
			 }

--          1.3.6.1.4.1.37950.1.1.5.12.2.17.1.1
-- 1.3.6.1.4.1.37950.1.1.5.12.2.17.1.1
-- 1.3.6.1.4.1.37950.1.1.5.12.2.17.1.1
-- 1.3.6.1.4.1.37950.1.1.5.12.2.17.1.1
-- 1.3.6.1.4.1.37950.1.1.5.12.2.17.1.1
-- 1.3.6.1.4.1.37950.1.1.5.12.2.17.1.1
-- 1.3.6.1.4.1.37950.1.1.5.12.2.17.1.1
-- 1.3.6.1.4.1.37950.1.1.5.12.2.17.1.1
-- 1.3.6.1.4.1.37950.1.1.5.12.2.17.1.1
		-- 1.3.6.1.4.1.37950.1.1.5.12.2.17.1.1
		onuInfoPonNo OBJECT-TYPE
			SYNTAX Integer32
			MAX-ACCESS read-only
			STATUS current
			DESCRIPTION
				"Description."
			::= { onuInfoEntry 1 }

		
--          1.3.6.1.4.1.37950.1.1.5.12.2.17.1.2
-- 1.3.6.1.4.1.37950.1.1.5.12.2.17.1.2
-- 1.3.6.1.4.1.37950.1.1.5.12.2.17.1.2
-- 1.3.6.1.4.1.37950.1.1.5.12.2.17.1.2
-- 1.3.6.1.4.1.37950.1.1.5.12.2.17.1.2
-- 1.3.6.1.4.1.37950.1.1.5.12.2.17.1.2
-- 1.3.6.1.4.1.37950.1.1.5.12.2.17.1.2
-- 1.3.6.1.4.1.37950.1.1.5.12.2.17.1.2
-- 1.3.6.1.4.1.37950.1.1.5.12.2.17.1.2
		-- 1.3.6.1.4.1.37950.1.1.5.12.2.17.1.2
		onuInfoOnuNo OBJECT-TYPE
			SYNTAX Integer32
			MAX-ACCESS read-only
			STATUS current
			DESCRIPTION
				"Description."
			::= { onuInfoEntry 2 }

		
--          1.3.6.1.4.1.37950.1.1.5.12.2.17.1.3
-- 1.3.6.1.4.1.37950.1.1.5.12.2.17.1.3
-- 1.3.6.1.4.1.37950.1.1.5.12.2.17.1.3
-- 1.3.6.1.4.1.37950.1.1.5.12.2.17.1.3
-- 1.3.6.1.4.1.37950.1.1.5.12.2.17.1.3
-- 1.3.6.1.4.1.37950.1.1.5.12.2.17.1.3
-- 1.3.6.1.4.1.37950.1.1.5.12.2.17.1.3
-- 1.3.6.1.4.1.37950.1.1.5.12.2.17.1.3
-- 1.3.6.1.4.1.37950.1.1.5.12.2.17.1.3
		-- 1.3.6.1.4.1.37950.1.1.5.12.2.17.1.3
		onuInfoMacAgingTime OBJECT-TYPE
			SYNTAX Integer32
			MAX-ACCESS read-only
			STATUS current
			DESCRIPTION
				"Description."
			::= { onuInfoEntry 3 }

		
--          1.3.6.1.4.1.37950.1.1.5.12.2.17.1.4
-- 1.3.6.1.4.1.37950.1.1.5.12.2.17.1.4
-- 1.3.6.1.4.1.37950.1.1.5.12.2.17.1.4
-- 1.3.6.1.4.1.37950.1.1.5.12.2.17.1.4
-- 1.3.6.1.4.1.37950.1.1.5.12.2.17.1.4
-- 1.3.6.1.4.1.37950.1.1.5.12.2.17.1.4
-- 1.3.6.1.4.1.37950.1.1.5.12.2.17.1.4
-- 1.3.6.1.4.1.37950.1.1.5.12.2.17.1.4
-- 1.3.6.1.4.1.37950.1.1.5.12.2.17.1.4
		-- 1.3.6.1.4.1.37950.1.1.5.12.2.17.1.4
		onuInfoHoldOver OBJECT-TYPE
			SYNTAX Integer32
			MAX-ACCESS read-only
			STATUS current
			DESCRIPTION
				"Description."
			::= { onuInfoEntry 4 }

		
--          1.3.6.1.4.1.37950.1.1.5.12.2.17.1.5
-- 1.3.6.1.4.1.37950.1.1.5.12.2.17.1.5
-- 1.3.6.1.4.1.37950.1.1.5.12.2.17.1.5
-- 1.3.6.1.4.1.37950.1.1.5.12.2.17.1.5
-- 1.3.6.1.4.1.37950.1.1.5.12.2.17.1.5
-- 1.3.6.1.4.1.37950.1.1.5.12.2.17.1.5
-- 1.3.6.1.4.1.37950.1.1.5.12.2.17.1.5
-- 1.3.6.1.4.1.37950.1.1.5.12.2.17.1.5
-- 1.3.6.1.4.1.37950.1.1.5.12.2.17.1.5
		-- 1.3.6.1.4.1.37950.1.1.5.12.2.17.1.5
		onuInfoMainPon OBJECT-TYPE
			SYNTAX Integer32
			MAX-ACCESS read-only
			STATUS current
			DESCRIPTION
				"Description."
			::= { onuInfoEntry 5 }

		
--          1.3.6.1.4.1.37950.1.1.5.12.2.18
-- 1.3.6.1.4.1.37950.1.1.5.12.2.18
-- 1.3.6.1.4.1.37950.1.1.5.12.2.18
-- 1.3.6.1.4.1.37950.1.1.5.12.2.18
-- 1.3.6.1.4.1.37950.1.1.5.12.2.18
-- 1.3.6.1.4.1.37950.1.1.5.12.2.18
-- 1.3.6.1.4.1.37950.1.1.5.12.2.18
-- 1.3.6.1.4.1.37950.1.1.5.12.2.18
-- 1.3.6.1.4.1.37950.1.1.5.12.2.18
		-- 1.3.6.1.4.1.37950.1.1.5.12.2.18
		powerSavingTable OBJECT-TYPE
			SYNTAX SEQUENCE OF PowerSavingEntry
			MAX-ACCESS not-accessible
			STATUS current
			DESCRIPTION
				"Description."
			::= { onuGlobalCfg 18 }

		
--          1.3.6.1.4.1.37950.1.1.5.12.2.18.1
-- 1.3.6.1.4.1.37950.1.1.5.12.2.18.1
-- 1.3.6.1.4.1.37950.1.1.5.12.2.18.1
-- 1.3.6.1.4.1.37950.1.1.5.12.2.18.1
-- 1.3.6.1.4.1.37950.1.1.5.12.2.18.1
-- 1.3.6.1.4.1.37950.1.1.5.12.2.18.1
-- 1.3.6.1.4.1.37950.1.1.5.12.2.18.1
-- 1.3.6.1.4.1.37950.1.1.5.12.2.18.1
-- 1.3.6.1.4.1.37950.1.1.5.12.2.18.1
		-- 1.3.6.1.4.1.37950.1.1.5.12.2.18.1
		powerSavingEntry OBJECT-TYPE
			SYNTAX PowerSavingEntry
			MAX-ACCESS not-accessible
			STATUS current
			DESCRIPTION
				"Description."
			INDEX { pSPonNo, pSOnuNo }
			::= { powerSavingTable 1 }

		
		PowerSavingEntry ::=
			SEQUENCE { 
				pSPonNo
					Integer32,
				pSOnuNo
					Integer32,
				pSEarlyWakeupEn
					INTEGER,
				pSSleepDurationMax
					INTEGER
			 }

--          1.3.6.1.4.1.37950.1.1.5.12.2.18.1.1
-- 1.3.6.1.4.1.37950.1.1.5.12.2.18.1.1
-- 1.3.6.1.4.1.37950.1.1.5.12.2.18.1.1
-- 1.3.6.1.4.1.37950.1.1.5.12.2.18.1.1
-- 1.3.6.1.4.1.37950.1.1.5.12.2.18.1.1
-- 1.3.6.1.4.1.37950.1.1.5.12.2.18.1.1
-- 1.3.6.1.4.1.37950.1.1.5.12.2.18.1.1
-- 1.3.6.1.4.1.37950.1.1.5.12.2.18.1.1
-- 1.3.6.1.4.1.37950.1.1.5.12.2.18.1.1
		-- 1.3.6.1.4.1.37950.1.1.5.12.2.18.1.1
		pSPonNo OBJECT-TYPE
			SYNTAX Integer32
			MAX-ACCESS read-only
			STATUS current
			DESCRIPTION
				"Description."
			::= { powerSavingEntry 1 }

		
--          1.3.6.1.4.1.37950.1.1.5.12.2.18.1.2
-- 1.3.6.1.4.1.37950.1.1.5.12.2.18.1.2
-- 1.3.6.1.4.1.37950.1.1.5.12.2.18.1.2
-- 1.3.6.1.4.1.37950.1.1.5.12.2.18.1.2
-- 1.3.6.1.4.1.37950.1.1.5.12.2.18.1.2
-- 1.3.6.1.4.1.37950.1.1.5.12.2.18.1.2
-- 1.3.6.1.4.1.37950.1.1.5.12.2.18.1.2
-- 1.3.6.1.4.1.37950.1.1.5.12.2.18.1.2
-- 1.3.6.1.4.1.37950.1.1.5.12.2.18.1.2
		-- 1.3.6.1.4.1.37950.1.1.5.12.2.18.1.2
		pSOnuNo OBJECT-TYPE
			SYNTAX Integer32
			MAX-ACCESS read-only
			STATUS current
			DESCRIPTION
				"Description."
			::= { powerSavingEntry 2 }

		
--          1.3.6.1.4.1.37950.1.1.5.12.2.18.1.3
-- 1.3.6.1.4.1.37950.1.1.5.12.2.18.1.3
-- 1.3.6.1.4.1.37950.1.1.5.12.2.18.1.3
-- 1.3.6.1.4.1.37950.1.1.5.12.2.18.1.3
-- 1.3.6.1.4.1.37950.1.1.5.12.2.18.1.3
-- 1.3.6.1.4.1.37950.1.1.5.12.2.18.1.3
-- 1.3.6.1.4.1.37950.1.1.5.12.2.18.1.3
-- 1.3.6.1.4.1.37950.1.1.5.12.2.18.1.3
-- 1.3.6.1.4.1.37950.1.1.5.12.2.18.1.3
		-- 1.3.6.1.4.1.37950.1.1.5.12.2.18.1.3
		pSEarlyWakeupEn OBJECT-TYPE
			SYNTAX INTEGER
				{
				enableWakeUp(0),
				disableWakeUp(1)
				}
			MAX-ACCESS read-only
			STATUS current
			DESCRIPTION
				"Description."
			::= { powerSavingEntry 3 }

		
--          1.3.6.1.4.1.37950.1.1.5.12.2.18.1.4
-- 1.3.6.1.4.1.37950.1.1.5.12.2.18.1.4
-- 1.3.6.1.4.1.37950.1.1.5.12.2.18.1.4
-- 1.3.6.1.4.1.37950.1.1.5.12.2.18.1.4
-- 1.3.6.1.4.1.37950.1.1.5.12.2.18.1.4
-- 1.3.6.1.4.1.37950.1.1.5.12.2.18.1.4
-- 1.3.6.1.4.1.37950.1.1.5.12.2.18.1.4
-- 1.3.6.1.4.1.37950.1.1.5.12.2.18.1.4
-- 1.3.6.1.4.1.37950.1.1.5.12.2.18.1.4
		-- 1.3.6.1.4.1.37950.1.1.5.12.2.18.1.4
		pSSleepDurationMax OBJECT-TYPE
			SYNTAX INTEGER
				{
				enableWakeUp(0),
				disableWakeUp(1)
				}
			MAX-ACCESS read-only
			STATUS current
			DESCRIPTION
				"Description."
			::= { powerSavingEntry 4 }

		
--          1.3.6.1.4.1.37950.1.1.5.12.2.19
-- 1.3.6.1.4.1.37950.1.1.5.12.2.19
-- 1.3.6.1.4.1.37950.1.1.5.12.2.19
-- 1.3.6.1.4.1.37950.1.1.5.12.2.19
-- 1.3.6.1.4.1.37950.1.1.5.12.2.19
-- 1.3.6.1.4.1.37950.1.1.5.12.2.19
-- 1.3.6.1.4.1.37950.1.1.5.12.2.19
-- 1.3.6.1.4.1.37950.1.1.5.12.2.19
-- 1.3.6.1.4.1.37950.1.1.5.12.2.19
		-- 1.3.6.1.4.1.37950.1.1.5.12.2.19
		onuSleepControlTable OBJECT-TYPE
			SYNTAX SEQUENCE OF OnuSleepControlEntry
			MAX-ACCESS not-accessible
			STATUS current
			DESCRIPTION
				"Description."
			::= { onuGlobalCfg 19 }

		
--          1.3.6.1.4.1.37950.1.1.5.12.2.19.1
-- 1.3.6.1.4.1.37950.1.1.5.12.2.19.1
-- 1.3.6.1.4.1.37950.1.1.5.12.2.19.1
-- 1.3.6.1.4.1.37950.1.1.5.12.2.19.1
-- 1.3.6.1.4.1.37950.1.1.5.12.2.19.1
-- 1.3.6.1.4.1.37950.1.1.5.12.2.19.1
-- 1.3.6.1.4.1.37950.1.1.5.12.2.19.1
-- 1.3.6.1.4.1.37950.1.1.5.12.2.19.1
-- 1.3.6.1.4.1.37950.1.1.5.12.2.19.1
		-- 1.3.6.1.4.1.37950.1.1.5.12.2.19.1
		onuSleepControlEntry OBJECT-TYPE
			SYNTAX OnuSleepControlEntry
			MAX-ACCESS not-accessible
			STATUS current
			DESCRIPTION
				"Description."
			INDEX { sleepCtlPonNo, sleepCtlOnuNo }
			::= { onuSleepControlTable 1 }

		
		OnuSleepControlEntry ::=
			SEQUENCE { 
				sleepCtlPonNo
					Integer32,
				sleepCtlOnuNo
					Integer32,
				scSleepDuration
					Integer32,
				scWakeDuration
					Integer32,
				scSleepFlag
					Integer32,
				scSleepMode
					Integer32
			 }

--          1.3.6.1.4.1.37950.1.1.5.12.2.19.1.1
-- 1.3.6.1.4.1.37950.1.1.5.12.2.19.1.1
-- 1.3.6.1.4.1.37950.1.1.5.12.2.19.1.1
-- 1.3.6.1.4.1.37950.1.1.5.12.2.19.1.1
-- 1.3.6.1.4.1.37950.1.1.5.12.2.19.1.1
-- 1.3.6.1.4.1.37950.1.1.5.12.2.19.1.1
-- 1.3.6.1.4.1.37950.1.1.5.12.2.19.1.1
-- 1.3.6.1.4.1.37950.1.1.5.12.2.19.1.1
-- 1.3.6.1.4.1.37950.1.1.5.12.2.19.1.1
		-- 1.3.6.1.4.1.37950.1.1.5.12.2.19.1.1
		sleepCtlPonNo OBJECT-TYPE
			SYNTAX Integer32
			MAX-ACCESS read-only
			STATUS current
			DESCRIPTION
				"Description."
			::= { onuSleepControlEntry 1 }

		
--          1.3.6.1.4.1.37950.1.1.5.12.2.19.1.2
-- 1.3.6.1.4.1.37950.1.1.5.12.2.19.1.2
-- 1.3.6.1.4.1.37950.1.1.5.12.2.19.1.2
-- 1.3.6.1.4.1.37950.1.1.5.12.2.19.1.2
-- 1.3.6.1.4.1.37950.1.1.5.12.2.19.1.2
-- 1.3.6.1.4.1.37950.1.1.5.12.2.19.1.2
-- 1.3.6.1.4.1.37950.1.1.5.12.2.19.1.2
-- 1.3.6.1.4.1.37950.1.1.5.12.2.19.1.2
-- 1.3.6.1.4.1.37950.1.1.5.12.2.19.1.2
		-- 1.3.6.1.4.1.37950.1.1.5.12.2.19.1.2
		sleepCtlOnuNo OBJECT-TYPE
			SYNTAX Integer32
			MAX-ACCESS read-only
			STATUS current
			DESCRIPTION
				"Description."
			::= { onuSleepControlEntry 2 }

		
--          1.3.6.1.4.1.37950.1.1.5.12.2.19.1.3
-- 1.3.6.1.4.1.37950.1.1.5.12.2.19.1.3
-- 1.3.6.1.4.1.37950.1.1.5.12.2.19.1.3
-- 1.3.6.1.4.1.37950.1.1.5.12.2.19.1.3
-- 1.3.6.1.4.1.37950.1.1.5.12.2.19.1.3
-- 1.3.6.1.4.1.37950.1.1.5.12.2.19.1.3
-- 1.3.6.1.4.1.37950.1.1.5.12.2.19.1.3
-- 1.3.6.1.4.1.37950.1.1.5.12.2.19.1.3
-- 1.3.6.1.4.1.37950.1.1.5.12.2.19.1.3
		-- 1.3.6.1.4.1.37950.1.1.5.12.2.19.1.3
		scSleepDuration OBJECT-TYPE
			SYNTAX Integer32
			MAX-ACCESS read-only
			STATUS current
			DESCRIPTION
				"Description."
			::= { onuSleepControlEntry 3 }

		
--          1.3.6.1.4.1.37950.1.1.5.12.2.19.1.4
-- 1.3.6.1.4.1.37950.1.1.5.12.2.19.1.4
-- 1.3.6.1.4.1.37950.1.1.5.12.2.19.1.4
-- 1.3.6.1.4.1.37950.1.1.5.12.2.19.1.4
-- 1.3.6.1.4.1.37950.1.1.5.12.2.19.1.4
-- 1.3.6.1.4.1.37950.1.1.5.12.2.19.1.4
-- 1.3.6.1.4.1.37950.1.1.5.12.2.19.1.4
-- 1.3.6.1.4.1.37950.1.1.5.12.2.19.1.4
-- 1.3.6.1.4.1.37950.1.1.5.12.2.19.1.4
		-- 1.3.6.1.4.1.37950.1.1.5.12.2.19.1.4
		scWakeDuration OBJECT-TYPE
			SYNTAX Integer32
			MAX-ACCESS read-only
			STATUS current
			DESCRIPTION
				"Description."
			::= { onuSleepControlEntry 4 }

		
--          1.3.6.1.4.1.37950.1.1.5.12.2.19.1.5
-- 1.3.6.1.4.1.37950.1.1.5.12.2.19.1.5
-- 1.3.6.1.4.1.37950.1.1.5.12.2.19.1.5
-- 1.3.6.1.4.1.37950.1.1.5.12.2.19.1.5
-- 1.3.6.1.4.1.37950.1.1.5.12.2.19.1.5
-- 1.3.6.1.4.1.37950.1.1.5.12.2.19.1.5
-- 1.3.6.1.4.1.37950.1.1.5.12.2.19.1.5
-- 1.3.6.1.4.1.37950.1.1.5.12.2.19.1.5
-- 1.3.6.1.4.1.37950.1.1.5.12.2.19.1.5
		-- 1.3.6.1.4.1.37950.1.1.5.12.2.19.1.5
		scSleepFlag OBJECT-TYPE
			SYNTAX Integer32
			MAX-ACCESS read-only
			STATUS current
			DESCRIPTION
				"Description."
			::= { onuSleepControlEntry 5 }

		
--          1.3.6.1.4.1.37950.1.1.5.12.2.19.1.6
-- 1.3.6.1.4.1.37950.1.1.5.12.2.19.1.6
-- 1.3.6.1.4.1.37950.1.1.5.12.2.19.1.6
-- 1.3.6.1.4.1.37950.1.1.5.12.2.19.1.6
-- 1.3.6.1.4.1.37950.1.1.5.12.2.19.1.6
-- 1.3.6.1.4.1.37950.1.1.5.12.2.19.1.6
-- 1.3.6.1.4.1.37950.1.1.5.12.2.19.1.6
-- 1.3.6.1.4.1.37950.1.1.5.12.2.19.1.6
-- 1.3.6.1.4.1.37950.1.1.5.12.2.19.1.6
		-- 1.3.6.1.4.1.37950.1.1.5.12.2.19.1.6
		scSleepMode OBJECT-TYPE
			SYNTAX Integer32
			MAX-ACCESS read-only
			STATUS current
			DESCRIPTION
				"Description."
			::= { onuSleepControlEntry 6 }

		
--          1.3.6.1.4.1.37950.1.1.5.12.3
-- 1.3.6.1.4.1.37950.1.1.5.12.3
-- 1.3.6.1.4.1.37950.1.1.5.12.3
-- 1.3.6.1.4.1.37950.1.1.5.12.3
-- 1.3.6.1.4.1.37950.1.1.5.12.3
-- 1.3.6.1.4.1.37950.1.1.5.12.3
-- 1.3.6.1.4.1.37950.1.1.5.12.3
-- 1.3.6.1.4.1.37950.1.1.5.12.3
-- 1.3.6.1.4.1.37950.1.1.5.12.3
		-- 1.3.6.1.4.1.37950.1.1.5.12.3
		onuPriGlobal OBJECT IDENTIFIER ::= { v1600dOnuMgmt 3 }

		
--          1.3.6.1.4.1.37950.1.1.5.12.3.1
-- 1.3.6.1.4.1.37950.1.1.5.12.3.1
-- 1.3.6.1.4.1.37950.1.1.5.12.3.1
-- 1.3.6.1.4.1.37950.1.1.5.12.3.1
-- 1.3.6.1.4.1.37950.1.1.5.12.3.1
-- 1.3.6.1.4.1.37950.1.1.5.12.3.1
-- 1.3.6.1.4.1.37950.1.1.5.12.3.1
-- 1.3.6.1.4.1.37950.1.1.5.12.3.1
-- 1.3.6.1.4.1.37950.1.1.5.12.3.1
		-- 1.3.6.1.4.1.37950.1.1.5.12.3.1
		onuPriGlobalCfg OBJECT IDENTIFIER ::= { onuPriGlobal 1 }

		
--          1.3.6.1.4.1.37950.1.1.5.12.3.1.1
-- 1.3.6.1.4.1.37950.1.1.5.12.3.1.1
-- 1.3.6.1.4.1.37950.1.1.5.12.3.1.1
-- 1.3.6.1.4.1.37950.1.1.5.12.3.1.1
-- 1.3.6.1.4.1.37950.1.1.5.12.3.1.1
-- 1.3.6.1.4.1.37950.1.1.5.12.3.1.1
-- 1.3.6.1.4.1.37950.1.1.5.12.3.1.1
-- 1.3.6.1.4.1.37950.1.1.5.12.3.1.1
-- 1.3.6.1.4.1.37950.1.1.5.12.3.1.1
		-- 1.3.6.1.4.1.37950.1.1.5.12.3.1.1
		onuPriIgmpAdmin OBJECT IDENTIFIER ::= { onuPriGlobalCfg 1 }

		
--          1.3.6.1.4.1.37950.1.1.5.12.3.1.1.1
-- 1.3.6.1.4.1.37950.1.1.5.12.3.1.1.1
-- 1.3.6.1.4.1.37950.1.1.5.12.3.1.1.1
-- 1.3.6.1.4.1.37950.1.1.5.12.3.1.1.1
-- 1.3.6.1.4.1.37950.1.1.5.12.3.1.1.1
-- 1.3.6.1.4.1.37950.1.1.5.12.3.1.1.1
-- 1.3.6.1.4.1.37950.1.1.5.12.3.1.1.1
-- 1.3.6.1.4.1.37950.1.1.5.12.3.1.1.1
-- 1.3.6.1.4.1.37950.1.1.5.12.3.1.1.1
		-- 1.3.6.1.4.1.37950.1.1.5.12.3.1.1.1
		priIgmpAdminPon OBJECT-TYPE
			SYNTAX INTEGER (1..16)
			MAX-ACCESS read-write
			STATUS current
			DESCRIPTION
				"Description."
			::= { onuPriIgmpAdmin 1 }

		
--          1.3.6.1.4.1.37950.1.1.5.12.3.1.1.2
-- 1.3.6.1.4.1.37950.1.1.5.12.3.1.1.2
-- 1.3.6.1.4.1.37950.1.1.5.12.3.1.1.2
-- 1.3.6.1.4.1.37950.1.1.5.12.3.1.1.2
-- 1.3.6.1.4.1.37950.1.1.5.12.3.1.1.2
-- 1.3.6.1.4.1.37950.1.1.5.12.3.1.1.2
-- 1.3.6.1.4.1.37950.1.1.5.12.3.1.1.2
-- 1.3.6.1.4.1.37950.1.1.5.12.3.1.1.2
-- 1.3.6.1.4.1.37950.1.1.5.12.3.1.1.2
		-- 1.3.6.1.4.1.37950.1.1.5.12.3.1.1.2
		priIgmpAdminOnu OBJECT-TYPE
			SYNTAX INTEGER (1..65565)
			MAX-ACCESS read-write
			STATUS current
			DESCRIPTION
				"Description."
			::= { onuPriIgmpAdmin 2 }

		
--          1.3.6.1.4.1.37950.1.1.5.12.3.1.1.3
-- 1.3.6.1.4.1.37950.1.1.5.12.3.1.1.3
-- 1.3.6.1.4.1.37950.1.1.5.12.3.1.1.3
-- 1.3.6.1.4.1.37950.1.1.5.12.3.1.1.3
-- 1.3.6.1.4.1.37950.1.1.5.12.3.1.1.3
-- 1.3.6.1.4.1.37950.1.1.5.12.3.1.1.3
-- 1.3.6.1.4.1.37950.1.1.5.12.3.1.1.3
-- 1.3.6.1.4.1.37950.1.1.5.12.3.1.1.3
-- 1.3.6.1.4.1.37950.1.1.5.12.3.1.1.3
		-- 1.3.6.1.4.1.37950.1.1.5.12.3.1.1.3
		priIgmpAdmin OBJECT-TYPE
			SYNTAX INTEGER
				{
				disable(0),
				enable(1)
				}
			MAX-ACCESS read-write
			STATUS current
			DESCRIPTION
				"Description."
			::= { onuPriIgmpAdmin 3 }

		
--          1.3.6.1.4.1.37950.1.1.5.12.3.1.1.4
-- 1.3.6.1.4.1.37950.1.1.5.12.3.1.1.4
-- 1.3.6.1.4.1.37950.1.1.5.12.3.1.1.4
-- 1.3.6.1.4.1.37950.1.1.5.12.3.1.1.4
-- 1.3.6.1.4.1.37950.1.1.5.12.3.1.1.4
-- 1.3.6.1.4.1.37950.1.1.5.12.3.1.1.4
-- 1.3.6.1.4.1.37950.1.1.5.12.3.1.1.4
-- 1.3.6.1.4.1.37950.1.1.5.12.3.1.1.4
-- 1.3.6.1.4.1.37950.1.1.5.12.3.1.1.4
		-- 1.3.6.1.4.1.37950.1.1.5.12.3.1.1.4
		priIgmpAdminAction OBJECT-TYPE
			SYNTAX INTEGER
				{
				commit(1),
				remove(2)
				}
			MAX-ACCESS read-write
			STATUS current
			DESCRIPTION
				"Description."
			::= { onuPriIgmpAdmin 4 }

		
--          1.3.6.1.4.1.37950.1.1.5.12.3.1.2
-- 1.3.6.1.4.1.37950.1.1.5.12.3.1.2
-- 1.3.6.1.4.1.37950.1.1.5.12.3.1.2
-- 1.3.6.1.4.1.37950.1.1.5.12.3.1.2
-- 1.3.6.1.4.1.37950.1.1.5.12.3.1.2
-- 1.3.6.1.4.1.37950.1.1.5.12.3.1.2
-- 1.3.6.1.4.1.37950.1.1.5.12.3.1.2
-- 1.3.6.1.4.1.37950.1.1.5.12.3.1.2
-- 1.3.6.1.4.1.37950.1.1.5.12.3.1.2
		-- 1.3.6.1.4.1.37950.1.1.5.12.3.1.2
		onuPriCatvEnable OBJECT IDENTIFIER ::= { onuPriGlobalCfg 2 }

		
--          1.3.6.1.4.1.37950.1.1.5.12.3.1.2.1
-- 1.3.6.1.4.1.37950.1.1.5.12.3.1.2.1
-- 1.3.6.1.4.1.37950.1.1.5.12.3.1.2.1
-- 1.3.6.1.4.1.37950.1.1.5.12.3.1.2.1
-- 1.3.6.1.4.1.37950.1.1.5.12.3.1.2.1
-- 1.3.6.1.4.1.37950.1.1.5.12.3.1.2.1
-- 1.3.6.1.4.1.37950.1.1.5.12.3.1.2.1
-- 1.3.6.1.4.1.37950.1.1.5.12.3.1.2.1
-- 1.3.6.1.4.1.37950.1.1.5.12.3.1.2.1
		-- 1.3.6.1.4.1.37950.1.1.5.12.3.1.2.1
		priCatvEnablePon OBJECT-TYPE
			SYNTAX INTEGER (1..16)
			MAX-ACCESS read-write
			STATUS current
			DESCRIPTION
				"Description."
			::= { onuPriCatvEnable 1 }

		
--          1.3.6.1.4.1.37950.1.1.5.12.3.1.2.2
-- 1.3.6.1.4.1.37950.1.1.5.12.3.1.2.2
-- 1.3.6.1.4.1.37950.1.1.5.12.3.1.2.2
-- 1.3.6.1.4.1.37950.1.1.5.12.3.1.2.2
-- 1.3.6.1.4.1.37950.1.1.5.12.3.1.2.2
-- 1.3.6.1.4.1.37950.1.1.5.12.3.1.2.2
-- 1.3.6.1.4.1.37950.1.1.5.12.3.1.2.2
-- 1.3.6.1.4.1.37950.1.1.5.12.3.1.2.2
-- 1.3.6.1.4.1.37950.1.1.5.12.3.1.2.2
		-- 1.3.6.1.4.1.37950.1.1.5.12.3.1.2.2
		priCatvEnableOnu OBJECT-TYPE
			SYNTAX INTEGER (1..65535)
			MAX-ACCESS read-write
			STATUS current
			DESCRIPTION
				"Description."
			::= { onuPriCatvEnable 2 }

		
--          1.3.6.1.4.1.37950.1.1.5.12.3.1.2.3
-- 1.3.6.1.4.1.37950.1.1.5.12.3.1.2.3
-- 1.3.6.1.4.1.37950.1.1.5.12.3.1.2.3
-- 1.3.6.1.4.1.37950.1.1.5.12.3.1.2.3
-- 1.3.6.1.4.1.37950.1.1.5.12.3.1.2.3
-- 1.3.6.1.4.1.37950.1.1.5.12.3.1.2.3
-- 1.3.6.1.4.1.37950.1.1.5.12.3.1.2.3
-- 1.3.6.1.4.1.37950.1.1.5.12.3.1.2.3
-- 1.3.6.1.4.1.37950.1.1.5.12.3.1.2.3
		-- 1.3.6.1.4.1.37950.1.1.5.12.3.1.2.3
		priCatvEnable OBJECT-TYPE
			SYNTAX INTEGER
				{
				disable(0),
				enable(1)
				}
			MAX-ACCESS read-write
			STATUS current
			DESCRIPTION
				"Description."
			::= { onuPriCatvEnable 3 }

		
--          1.3.6.1.4.1.37950.1.1.5.12.3.1.2.4
-- 1.3.6.1.4.1.37950.1.1.5.12.3.1.2.4
-- 1.3.6.1.4.1.37950.1.1.5.12.3.1.2.4
-- 1.3.6.1.4.1.37950.1.1.5.12.3.1.2.4
-- 1.3.6.1.4.1.37950.1.1.5.12.3.1.2.4
-- 1.3.6.1.4.1.37950.1.1.5.12.3.1.2.4
-- 1.3.6.1.4.1.37950.1.1.5.12.3.1.2.4
-- 1.3.6.1.4.1.37950.1.1.5.12.3.1.2.4
-- 1.3.6.1.4.1.37950.1.1.5.12.3.1.2.4
		-- 1.3.6.1.4.1.37950.1.1.5.12.3.1.2.4
		priCatvAction OBJECT-TYPE
			SYNTAX INTEGER
				{
				commit(1),
				remove(2)
				}
			MAX-ACCESS read-write
			STATUS current
			DESCRIPTION
				"Description."
			::= { onuPriCatvEnable 4 }

		
--          1.3.6.1.4.1.37950.1.1.5.12.3.1.3
-- 1.3.6.1.4.1.37950.1.1.5.12.3.1.3
-- 1.3.6.1.4.1.37950.1.1.5.12.3.1.3
-- 1.3.6.1.4.1.37950.1.1.5.12.3.1.3
-- 1.3.6.1.4.1.37950.1.1.5.12.3.1.3
-- 1.3.6.1.4.1.37950.1.1.5.12.3.1.3
-- 1.3.6.1.4.1.37950.1.1.5.12.3.1.3
-- 1.3.6.1.4.1.37950.1.1.5.12.3.1.3
-- 1.3.6.1.4.1.37950.1.1.5.12.3.1.3
		-- 1.3.6.1.4.1.37950.1.1.5.12.3.1.3
		onuPriCtcoamSkip OBJECT IDENTIFIER ::= { onuPriGlobalCfg 3 }

		
--          1.3.6.1.4.1.37950.1.1.5.12.3.1.3.1
-- 1.3.6.1.4.1.37950.1.1.5.12.3.1.3.1
-- 1.3.6.1.4.1.37950.1.1.5.12.3.1.3.1
-- 1.3.6.1.4.1.37950.1.1.5.12.3.1.3.1
-- 1.3.6.1.4.1.37950.1.1.5.12.3.1.3.1
-- 1.3.6.1.4.1.37950.1.1.5.12.3.1.3.1
-- 1.3.6.1.4.1.37950.1.1.5.12.3.1.3.1
-- 1.3.6.1.4.1.37950.1.1.5.12.3.1.3.1
-- 1.3.6.1.4.1.37950.1.1.5.12.3.1.3.1
		-- 1.3.6.1.4.1.37950.1.1.5.12.3.1.3.1
		priCtcoamSkipPon OBJECT-TYPE
			SYNTAX INTEGER (1..16)
			MAX-ACCESS read-write
			STATUS current
			DESCRIPTION
				"Description."
			::= { onuPriCtcoamSkip 1 }

		
--          1.3.6.1.4.1.37950.1.1.5.12.3.1.3.2
-- 1.3.6.1.4.1.37950.1.1.5.12.3.1.3.2
-- 1.3.6.1.4.1.37950.1.1.5.12.3.1.3.2
-- 1.3.6.1.4.1.37950.1.1.5.12.3.1.3.2
-- 1.3.6.1.4.1.37950.1.1.5.12.3.1.3.2
-- 1.3.6.1.4.1.37950.1.1.5.12.3.1.3.2
-- 1.3.6.1.4.1.37950.1.1.5.12.3.1.3.2
-- 1.3.6.1.4.1.37950.1.1.5.12.3.1.3.2
-- 1.3.6.1.4.1.37950.1.1.5.12.3.1.3.2
		-- 1.3.6.1.4.1.37950.1.1.5.12.3.1.3.2
		priCtcoamSkipOnu OBJECT-TYPE
			SYNTAX INTEGER (1..65535)
			MAX-ACCESS read-write
			STATUS current
			DESCRIPTION
				"Description."
			::= { onuPriCtcoamSkip 2 }

		
--          1.3.6.1.4.1.37950.1.1.5.12.3.1.3.3
-- 1.3.6.1.4.1.37950.1.1.5.12.3.1.3.3
-- 1.3.6.1.4.1.37950.1.1.5.12.3.1.3.3
-- 1.3.6.1.4.1.37950.1.1.5.12.3.1.3.3
-- 1.3.6.1.4.1.37950.1.1.5.12.3.1.3.3
-- 1.3.6.1.4.1.37950.1.1.5.12.3.1.3.3
-- 1.3.6.1.4.1.37950.1.1.5.12.3.1.3.3
-- 1.3.6.1.4.1.37950.1.1.5.12.3.1.3.3
-- 1.3.6.1.4.1.37950.1.1.5.12.3.1.3.3
		-- 1.3.6.1.4.1.37950.1.1.5.12.3.1.3.3
		priCtcoamSkip OBJECT-TYPE
			SYNTAX INTEGER
				{
				disable(0),
				enable(1)
				}
			MAX-ACCESS read-write
			STATUS current
			DESCRIPTION
				"Description."
			::= { onuPriCtcoamSkip 3 }

		
--          1.3.6.1.4.1.37950.1.1.5.12.3.1.3.4
-- 1.3.6.1.4.1.37950.1.1.5.12.3.1.3.4
-- 1.3.6.1.4.1.37950.1.1.5.12.3.1.3.4
-- 1.3.6.1.4.1.37950.1.1.5.12.3.1.3.4
-- 1.3.6.1.4.1.37950.1.1.5.12.3.1.3.4
-- 1.3.6.1.4.1.37950.1.1.5.12.3.1.3.4
-- 1.3.6.1.4.1.37950.1.1.5.12.3.1.3.4
-- 1.3.6.1.4.1.37950.1.1.5.12.3.1.3.4
-- 1.3.6.1.4.1.37950.1.1.5.12.3.1.3.4
		-- 1.3.6.1.4.1.37950.1.1.5.12.3.1.3.4
		priCtcoamSkipAction OBJECT-TYPE
			SYNTAX INTEGER
				{
				commit(1),
				remove(2)
				}
			MAX-ACCESS read-write
			STATUS current
			DESCRIPTION
				"Description."
			::= { onuPriCtcoamSkip 4 }

		
--          1.3.6.1.4.1.37950.1.1.5.12.3.1.4
-- 1.3.6.1.4.1.37950.1.1.5.12.3.1.4
-- 1.3.6.1.4.1.37950.1.1.5.12.3.1.4
-- 1.3.6.1.4.1.37950.1.1.5.12.3.1.4
-- 1.3.6.1.4.1.37950.1.1.5.12.3.1.4
-- 1.3.6.1.4.1.37950.1.1.5.12.3.1.4
-- 1.3.6.1.4.1.37950.1.1.5.12.3.1.4
-- 1.3.6.1.4.1.37950.1.1.5.12.3.1.4
-- 1.3.6.1.4.1.37950.1.1.5.12.3.1.4
		-- 1.3.6.1.4.1.37950.1.1.5.12.3.1.4
		onuPriWifiSwitch OBJECT IDENTIFIER ::= { onuPriGlobalCfg 4 }

		
--          1.3.6.1.4.1.37950.1.1.5.12.3.1.4.1
-- 1.3.6.1.4.1.37950.1.1.5.12.3.1.4.1
-- 1.3.6.1.4.1.37950.1.1.5.12.3.1.4.1
-- 1.3.6.1.4.1.37950.1.1.5.12.3.1.4.1
-- 1.3.6.1.4.1.37950.1.1.5.12.3.1.4.1
-- 1.3.6.1.4.1.37950.1.1.5.12.3.1.4.1
-- 1.3.6.1.4.1.37950.1.1.5.12.3.1.4.1
-- 1.3.6.1.4.1.37950.1.1.5.12.3.1.4.1
-- 1.3.6.1.4.1.37950.1.1.5.12.3.1.4.1
		-- 1.3.6.1.4.1.37950.1.1.5.12.3.1.4.1
		priWifiSwitchPon OBJECT-TYPE
			SYNTAX INTEGER (1..16)
			MAX-ACCESS read-write
			STATUS current
			DESCRIPTION
				"Description."
			::= { onuPriWifiSwitch 1 }

		
--          1.3.6.1.4.1.37950.1.1.5.12.3.1.4.2
-- 1.3.6.1.4.1.37950.1.1.5.12.3.1.4.2
-- 1.3.6.1.4.1.37950.1.1.5.12.3.1.4.2
-- 1.3.6.1.4.1.37950.1.1.5.12.3.1.4.2
-- 1.3.6.1.4.1.37950.1.1.5.12.3.1.4.2
-- 1.3.6.1.4.1.37950.1.1.5.12.3.1.4.2
-- 1.3.6.1.4.1.37950.1.1.5.12.3.1.4.2
-- 1.3.6.1.4.1.37950.1.1.5.12.3.1.4.2
-- 1.3.6.1.4.1.37950.1.1.5.12.3.1.4.2
		-- 1.3.6.1.4.1.37950.1.1.5.12.3.1.4.2
		priWifiSwitchOnu OBJECT-TYPE
			SYNTAX INTEGER (1..65535)
			MAX-ACCESS read-write
			STATUS current
			DESCRIPTION
				"Description."
			::= { onuPriWifiSwitch 2 }

		
--          1.3.6.1.4.1.37950.1.1.5.12.3.1.4.3
-- 1.3.6.1.4.1.37950.1.1.5.12.3.1.4.3
-- 1.3.6.1.4.1.37950.1.1.5.12.3.1.4.3
-- 1.3.6.1.4.1.37950.1.1.5.12.3.1.4.3
-- 1.3.6.1.4.1.37950.1.1.5.12.3.1.4.3
-- 1.3.6.1.4.1.37950.1.1.5.12.3.1.4.3
-- 1.3.6.1.4.1.37950.1.1.5.12.3.1.4.3
-- 1.3.6.1.4.1.37950.1.1.5.12.3.1.4.3
-- 1.3.6.1.4.1.37950.1.1.5.12.3.1.4.3
		-- 1.3.6.1.4.1.37950.1.1.5.12.3.1.4.3
		priWifiApModule OBJECT-TYPE
			SYNTAX INTEGER
				{
				disable(0),
				enable(1)
				}
			MAX-ACCESS read-write
			STATUS current
			DESCRIPTION
				"Description."
			::= { onuPriWifiSwitch 3 }

		
--          1.3.6.1.4.1.37950.1.1.5.12.3.1.4.4
-- 1.3.6.1.4.1.37950.1.1.5.12.3.1.4.4
-- 1.3.6.1.4.1.37950.1.1.5.12.3.1.4.4
-- 1.3.6.1.4.1.37950.1.1.5.12.3.1.4.4
-- 1.3.6.1.4.1.37950.1.1.5.12.3.1.4.4
-- 1.3.6.1.4.1.37950.1.1.5.12.3.1.4.4
-- 1.3.6.1.4.1.37950.1.1.5.12.3.1.4.4
-- 1.3.6.1.4.1.37950.1.1.5.12.3.1.4.4
-- 1.3.6.1.4.1.37950.1.1.5.12.3.1.4.4
		-- 1.3.6.1.4.1.37950.1.1.5.12.3.1.4.4
		priWifiContry OBJECT-TYPE
			SYNTAX INTEGER
				{
				etsi(0),
				fcc(1),
				ic(2),
				spain(3),
				france(4),
				mkk(5),
				isreal(6),
				mkk2(7),
				mkk3(8),
				russian(9),
				cn(10),
				global(11),
				world-wide(12),
				mkk1(13),
				ncc(14)
				}
			MAX-ACCESS read-write
			STATUS current
			DESCRIPTION
				"Description."
			::= { onuPriWifiSwitch 4 }

		
--          1.3.6.1.4.1.37950.1.1.5.12.3.1.4.5
-- 1.3.6.1.4.1.37950.1.1.5.12.3.1.4.5
-- 1.3.6.1.4.1.37950.1.1.5.12.3.1.4.5
-- 1.3.6.1.4.1.37950.1.1.5.12.3.1.4.5
-- 1.3.6.1.4.1.37950.1.1.5.12.3.1.4.5
-- 1.3.6.1.4.1.37950.1.1.5.12.3.1.4.5
-- 1.3.6.1.4.1.37950.1.1.5.12.3.1.4.5
-- 1.3.6.1.4.1.37950.1.1.5.12.3.1.4.5
-- 1.3.6.1.4.1.37950.1.1.5.12.3.1.4.5
		-- 1.3.6.1.4.1.37950.1.1.5.12.3.1.4.5
		priWifiChannel OBJECT-TYPE
			SYNTAX INTEGER (0..13)
			MAX-ACCESS read-write
			STATUS current
			DESCRIPTION
				"Description."
			::= { onuPriWifiSwitch 5 }

		
--          1.3.6.1.4.1.37950.1.1.5.12.3.1.4.6
-- 1.3.6.1.4.1.37950.1.1.5.12.3.1.4.6
-- 1.3.6.1.4.1.37950.1.1.5.12.3.1.4.6
-- 1.3.6.1.4.1.37950.1.1.5.12.3.1.4.6
-- 1.3.6.1.4.1.37950.1.1.5.12.3.1.4.6
-- 1.3.6.1.4.1.37950.1.1.5.12.3.1.4.6
-- 1.3.6.1.4.1.37950.1.1.5.12.3.1.4.6
-- 1.3.6.1.4.1.37950.1.1.5.12.3.1.4.6
-- 1.3.6.1.4.1.37950.1.1.5.12.3.1.4.6
		-- 1.3.6.1.4.1.37950.1.1.5.12.3.1.4.6
		priWifiStandard OBJECT-TYPE
			SYNTAX INTEGER
				{
				s80211b(0),
				s80211g(1),
				s80211bg(2),
				s80211n(3),
				s80211bgn(4),
				s80211ax(5),
				s80211bgnax(6)
				}
			MAX-ACCESS read-write
			STATUS current
			DESCRIPTION
				"Description."
			::= { onuPriWifiSwitch 6 }

		
--          1.3.6.1.4.1.37950.1.1.5.12.3.1.4.7
-- 1.3.6.1.4.1.37950.1.1.5.12.3.1.4.7
-- 1.3.6.1.4.1.37950.1.1.5.12.3.1.4.7
-- 1.3.6.1.4.1.37950.1.1.5.12.3.1.4.7
-- 1.3.6.1.4.1.37950.1.1.5.12.3.1.4.7
-- 1.3.6.1.4.1.37950.1.1.5.12.3.1.4.7
-- 1.3.6.1.4.1.37950.1.1.5.12.3.1.4.7
-- 1.3.6.1.4.1.37950.1.1.5.12.3.1.4.7
-- 1.3.6.1.4.1.37950.1.1.5.12.3.1.4.7
		-- 1.3.6.1.4.1.37950.1.1.5.12.3.1.4.7
		priWifiPower OBJECT-TYPE
			SYNTAX INTEGER (0..20)
			MAX-ACCESS read-write
			STATUS current
			DESCRIPTION
				"Description."
			::= { onuPriWifiSwitch 7 }

		
--          1.3.6.1.4.1.37950.1.1.5.12.3.1.4.8
-- 1.3.6.1.4.1.37950.1.1.5.12.3.1.4.8
-- 1.3.6.1.4.1.37950.1.1.5.12.3.1.4.8
-- 1.3.6.1.4.1.37950.1.1.5.12.3.1.4.8
-- 1.3.6.1.4.1.37950.1.1.5.12.3.1.4.8
-- 1.3.6.1.4.1.37950.1.1.5.12.3.1.4.8
-- 1.3.6.1.4.1.37950.1.1.5.12.3.1.4.8
-- 1.3.6.1.4.1.37950.1.1.5.12.3.1.4.8
-- 1.3.6.1.4.1.37950.1.1.5.12.3.1.4.8
		-- 1.3.6.1.4.1.37950.1.1.5.12.3.1.4.8
		priWifiSwitchAction OBJECT-TYPE
			SYNTAX INTEGER
				{
				commit(1),
				remove(2)
				}
			MAX-ACCESS read-write
			STATUS current
			DESCRIPTION
				"Description."
			::= { onuPriWifiSwitch 8 }

		
--         1.3.6.1.4.1.37950.1.1.5.12.3.1.4.9
-- 1.3.6.1.4.1.37950.1.1.5.12.3.1.4.9
-- 1.3.6.1.4.1.37950.1.1.5.12.3.1.4.9
-- 1.3.6.1.4.1.37950.1.1.5.12.3.1.4.9
-- 1.3.6.1.4.1.37950.1.1.5.12.3.1.4.9
-- 1.3.6.1.4.1.37950.1.1.5.12.3.1.4.9
-- 1.3.6.1.4.1.37950.1.1.5.12.3.1.4.9
-- 1.3.6.1.4.1.37950.1.1.5.12.3.1.4.9
		-- 1.3.6.1.4.1.37950.1.1.5.12.3.1.4.9
		priWifiChannelWidth OBJECT-TYPE
			SYNTAX INTEGER
				{
				s20(0),
				s40(1),
				s20-40(3)
				}
			MAX-ACCESS read-write
			STATUS current
			DESCRIPTION
				"Description."
			::= { onuPriWifiSwitch 9 }

		
--          1.3.6.1.4.1.37950.1.1.5.12.3.1.5
-- 1.3.6.1.4.1.37950.1.1.5.12.3.1.5
-- 1.3.6.1.4.1.37950.1.1.5.12.3.1.5
-- 1.3.6.1.4.1.37950.1.1.5.12.3.1.5
-- 1.3.6.1.4.1.37950.1.1.5.12.3.1.5
-- 1.3.6.1.4.1.37950.1.1.5.12.3.1.5
-- 1.3.6.1.4.1.37950.1.1.5.12.3.1.5
-- 1.3.6.1.4.1.37950.1.1.5.12.3.1.5
-- 1.3.6.1.4.1.37950.1.1.5.12.3.1.5
		-- 1.3.6.1.4.1.37950.1.1.5.12.3.1.5
		onuPriWifiSsid OBJECT IDENTIFIER ::= { onuPriGlobalCfg 5 }

		
--          1.3.6.1.4.1.37950.1.1.5.12.3.1.5.1
-- 1.3.6.1.4.1.37950.1.1.5.12.3.1.5.1
-- 1.3.6.1.4.1.37950.1.1.5.12.3.1.5.1
-- 1.3.6.1.4.1.37950.1.1.5.12.3.1.5.1
-- 1.3.6.1.4.1.37950.1.1.5.12.3.1.5.1
-- 1.3.6.1.4.1.37950.1.1.5.12.3.1.5.1
-- 1.3.6.1.4.1.37950.1.1.5.12.3.1.5.1
-- 1.3.6.1.4.1.37950.1.1.5.12.3.1.5.1
-- 1.3.6.1.4.1.37950.1.1.5.12.3.1.5.1
		-- 1.3.6.1.4.1.37950.1.1.5.12.3.1.5.1
		priSsidPon OBJECT-TYPE
			SYNTAX INTEGER (1..16)
			MAX-ACCESS read-write
			STATUS current
			DESCRIPTION
				"Description."
			::= { onuPriWifiSsid 1 }

		
--          1.3.6.1.4.1.37950.1.1.5.12.3.1.5.2
-- 1.3.6.1.4.1.37950.1.1.5.12.3.1.5.2
-- 1.3.6.1.4.1.37950.1.1.5.12.3.1.5.2
-- 1.3.6.1.4.1.37950.1.1.5.12.3.1.5.2
-- 1.3.6.1.4.1.37950.1.1.5.12.3.1.5.2
-- 1.3.6.1.4.1.37950.1.1.5.12.3.1.5.2
-- 1.3.6.1.4.1.37950.1.1.5.12.3.1.5.2
-- 1.3.6.1.4.1.37950.1.1.5.12.3.1.5.2
-- 1.3.6.1.4.1.37950.1.1.5.12.3.1.5.2
		-- 1.3.6.1.4.1.37950.1.1.5.12.3.1.5.2
		proSsidOnu OBJECT-TYPE
			SYNTAX INTEGER (1..65535)
			MAX-ACCESS read-write
			STATUS current
			DESCRIPTION
				"Description."
			::= { onuPriWifiSsid 2 }

		
--          1.3.6.1.4.1.37950.1.1.5.12.3.1.5.3
-- 1.3.6.1.4.1.37950.1.1.5.12.3.1.5.3
-- 1.3.6.1.4.1.37950.1.1.5.12.3.1.5.3
-- 1.3.6.1.4.1.37950.1.1.5.12.3.1.5.3
-- 1.3.6.1.4.1.37950.1.1.5.12.3.1.5.3
-- 1.3.6.1.4.1.37950.1.1.5.12.3.1.5.3
-- 1.3.6.1.4.1.37950.1.1.5.12.3.1.5.3
-- 1.3.6.1.4.1.37950.1.1.5.12.3.1.5.3
-- 1.3.6.1.4.1.37950.1.1.5.12.3.1.5.3
		-- 1.3.6.1.4.1.37950.1.1.5.12.3.1.5.3
		priSsidId OBJECT-TYPE
			SYNTAX INTEGER (1..10)
			MAX-ACCESS read-write
			STATUS current
			DESCRIPTION
				"Description."
			::= { onuPriWifiSsid 3 }

		
--          1.3.6.1.4.1.37950.1.1.5.12.3.1.5.4
-- 1.3.6.1.4.1.37950.1.1.5.12.3.1.5.4
-- 1.3.6.1.4.1.37950.1.1.5.12.3.1.5.4
-- 1.3.6.1.4.1.37950.1.1.5.12.3.1.5.4
-- 1.3.6.1.4.1.37950.1.1.5.12.3.1.5.4
-- 1.3.6.1.4.1.37950.1.1.5.12.3.1.5.4
-- 1.3.6.1.4.1.37950.1.1.5.12.3.1.5.4
-- 1.3.6.1.4.1.37950.1.1.5.12.3.1.5.4
-- 1.3.6.1.4.1.37950.1.1.5.12.3.1.5.4
		-- 1.3.6.1.4.1.37950.1.1.5.12.3.1.5.4
		priSsidName OBJECT-TYPE
			SYNTAX OCTET STRING
			MAX-ACCESS read-write
			STATUS current
			DESCRIPTION
				"Description."
			::= { onuPriWifiSsid 4 }

		
--          1.3.6.1.4.1.37950.1.1.5.12.3.1.5.5
-- 1.3.6.1.4.1.37950.1.1.5.12.3.1.5.5
-- 1.3.6.1.4.1.37950.1.1.5.12.3.1.5.5
-- 1.3.6.1.4.1.37950.1.1.5.12.3.1.5.5
-- 1.3.6.1.4.1.37950.1.1.5.12.3.1.5.5
-- 1.3.6.1.4.1.37950.1.1.5.12.3.1.5.5
-- 1.3.6.1.4.1.37950.1.1.5.12.3.1.5.5
-- 1.3.6.1.4.1.37950.1.1.5.12.3.1.5.5
-- 1.3.6.1.4.1.37950.1.1.5.12.3.1.5.5
		-- 1.3.6.1.4.1.37950.1.1.5.12.3.1.5.5
		priSsidEnable OBJECT-TYPE
			SYNTAX INTEGER
				{
				disable(0),
				enable(1)
				}
			MAX-ACCESS read-write
			STATUS current
			DESCRIPTION
				"Description."
			::= { onuPriWifiSsid 5 }

		
--          1.3.6.1.4.1.37950.1.1.5.12.3.1.5.6
-- 1.3.6.1.4.1.37950.1.1.5.12.3.1.5.6
-- 1.3.6.1.4.1.37950.1.1.5.12.3.1.5.6
-- 1.3.6.1.4.1.37950.1.1.5.12.3.1.5.6
-- 1.3.6.1.4.1.37950.1.1.5.12.3.1.5.6
-- 1.3.6.1.4.1.37950.1.1.5.12.3.1.5.6
-- 1.3.6.1.4.1.37950.1.1.5.12.3.1.5.6
-- 1.3.6.1.4.1.37950.1.1.5.12.3.1.5.6
-- 1.3.6.1.4.1.37950.1.1.5.12.3.1.5.6
		-- 1.3.6.1.4.1.37950.1.1.5.12.3.1.5.6
		priSsidHide OBJECT-TYPE
			SYNTAX INTEGER
				{
				disable(0),
				enable(1)
				}
			MAX-ACCESS read-write
			STATUS current
			DESCRIPTION
				"Description."
			::= { onuPriWifiSsid 6 }

		
--          1.3.6.1.4.1.37950.1.1.5.12.3.1.5.7
-- 1.3.6.1.4.1.37950.1.1.5.12.3.1.5.7
-- 1.3.6.1.4.1.37950.1.1.5.12.3.1.5.7
-- 1.3.6.1.4.1.37950.1.1.5.12.3.1.5.7
-- 1.3.6.1.4.1.37950.1.1.5.12.3.1.5.7
-- 1.3.6.1.4.1.37950.1.1.5.12.3.1.5.7
-- 1.3.6.1.4.1.37950.1.1.5.12.3.1.5.7
-- 1.3.6.1.4.1.37950.1.1.5.12.3.1.5.7
-- 1.3.6.1.4.1.37950.1.1.5.12.3.1.5.7
		-- 1.3.6.1.4.1.37950.1.1.5.12.3.1.5.7
		priSsidAuthMode OBJECT-TYPE
			SYNTAX INTEGER
				{
				open(1),
				shared(2),
				wepauto(3),
				wpapsk(4),
				wpa(5),
				wpa2psk(6),
				wpa2(7),
				wpa-wpa2(8),
				wpapsk-wpa2psk(9),
				wpa3psk(10),
				wpa2psk-wpa3psk(11)
				}
			MAX-ACCESS read-write
			STATUS current
			DESCRIPTION
				"Description."
			::= { onuPriWifiSsid 7 }

		
--          1.3.6.1.4.1.37950.1.1.5.12.3.1.5.8
-- 1.3.6.1.4.1.37950.1.1.5.12.3.1.5.8
-- 1.3.6.1.4.1.37950.1.1.5.12.3.1.5.8
-- 1.3.6.1.4.1.37950.1.1.5.12.3.1.5.8
-- 1.3.6.1.4.1.37950.1.1.5.12.3.1.5.8
-- 1.3.6.1.4.1.37950.1.1.5.12.3.1.5.8
-- 1.3.6.1.4.1.37950.1.1.5.12.3.1.5.8
-- 1.3.6.1.4.1.37950.1.1.5.12.3.1.5.8
-- 1.3.6.1.4.1.37950.1.1.5.12.3.1.5.8
		-- 1.3.6.1.4.1.37950.1.1.5.12.3.1.5.8
		priSsidEncrypTpye OBJECT-TYPE
			SYNTAX INTEGER
				{
				none(1),
				wep(2),
				tkip(3),
				aes(4),
				tkipaes(5)
				}
			MAX-ACCESS read-write
			STATUS current
			DESCRIPTION
				"Description."
			::= { onuPriWifiSsid 8 }

		
--          1.3.6.1.4.1.37950.1.1.5.12.3.1.5.9
-- 1.3.6.1.4.1.37950.1.1.5.12.3.1.5.9
-- 1.3.6.1.4.1.37950.1.1.5.12.3.1.5.9
-- 1.3.6.1.4.1.37950.1.1.5.12.3.1.5.9
-- 1.3.6.1.4.1.37950.1.1.5.12.3.1.5.9
-- 1.3.6.1.4.1.37950.1.1.5.12.3.1.5.9
-- 1.3.6.1.4.1.37950.1.1.5.12.3.1.5.9
-- 1.3.6.1.4.1.37950.1.1.5.12.3.1.5.9
-- 1.3.6.1.4.1.37950.1.1.5.12.3.1.5.9
		-- 1.3.6.1.4.1.37950.1.1.5.12.3.1.5.9
		priSsidPresharedKey OBJECT-TYPE
			SYNTAX OCTET STRING
			MAX-ACCESS read-write
			STATUS current
			DESCRIPTION
				"Description."
			::= { onuPriWifiSsid 9 }

		
--          1.3.6.1.4.1.37950.1.1.5.12.3.1.5.10
-- 1.3.6.1.4.1.37950.1.1.5.12.3.1.5.10
-- 1.3.6.1.4.1.37950.1.1.5.12.3.1.5.10
-- 1.3.6.1.4.1.37950.1.1.5.12.3.1.5.10
-- 1.3.6.1.4.1.37950.1.1.5.12.3.1.5.10
-- 1.3.6.1.4.1.37950.1.1.5.12.3.1.5.10
-- 1.3.6.1.4.1.37950.1.1.5.12.3.1.5.10
-- 1.3.6.1.4.1.37950.1.1.5.12.3.1.5.10
-- 1.3.6.1.4.1.37950.1.1.5.12.3.1.5.10
		-- 1.3.6.1.4.1.37950.1.1.5.12.3.1.5.10
		priSsidPrekeyInterval OBJECT-TYPE
			SYNTAX INTEGER (0..4194303)
			MAX-ACCESS read-write
			STATUS current
			DESCRIPTION
				"Description."
			::= { onuPriWifiSsid 10 }

		
--          1.3.6.1.4.1.37950.1.1.5.12.3.1.5.11
-- 1.3.6.1.4.1.37950.1.1.5.12.3.1.5.11
-- 1.3.6.1.4.1.37950.1.1.5.12.3.1.5.11
-- 1.3.6.1.4.1.37950.1.1.5.12.3.1.5.11
-- 1.3.6.1.4.1.37950.1.1.5.12.3.1.5.11
-- 1.3.6.1.4.1.37950.1.1.5.12.3.1.5.11
-- 1.3.6.1.4.1.37950.1.1.5.12.3.1.5.11
-- 1.3.6.1.4.1.37950.1.1.5.12.3.1.5.11
-- 1.3.6.1.4.1.37950.1.1.5.12.3.1.5.11
		-- 1.3.6.1.4.1.37950.1.1.5.12.3.1.5.11
		priSsidRadiusSeripType OBJECT-TYPE
			SYNTAX INTEGER
				{
				ipv4(1),
				ipv6(2),
				ipv4z(3),
				ipv6z(4),
				dns(16)
				}
			MAX-ACCESS read-write
			STATUS current
			DESCRIPTION
				"Description."
			::= { onuPriWifiSsid 11 }

		
--          1.3.6.1.4.1.37950.1.1.5.12.3.1.5.12
-- 1.3.6.1.4.1.37950.1.1.5.12.3.1.5.12
-- 1.3.6.1.4.1.37950.1.1.5.12.3.1.5.12
-- 1.3.6.1.4.1.37950.1.1.5.12.3.1.5.12
-- 1.3.6.1.4.1.37950.1.1.5.12.3.1.5.12
-- 1.3.6.1.4.1.37950.1.1.5.12.3.1.5.12
-- 1.3.6.1.4.1.37950.1.1.5.12.3.1.5.12
-- 1.3.6.1.4.1.37950.1.1.5.12.3.1.5.12
-- 1.3.6.1.4.1.37950.1.1.5.12.3.1.5.12
		-- 1.3.6.1.4.1.37950.1.1.5.12.3.1.5.12
		priSsidRadiusSerip OBJECT-TYPE
			SYNTAX OCTET STRING
			MAX-ACCESS read-write
			STATUS current
			DESCRIPTION
				"Description."
			::= { onuPriWifiSsid 12 }

		
--          1.3.6.1.4.1.37950.1.1.5.12.3.1.5.13
-- 1.3.6.1.4.1.37950.1.1.5.12.3.1.5.13
-- 1.3.6.1.4.1.37950.1.1.5.12.3.1.5.13
-- 1.3.6.1.4.1.37950.1.1.5.12.3.1.5.13
-- 1.3.6.1.4.1.37950.1.1.5.12.3.1.5.13
-- 1.3.6.1.4.1.37950.1.1.5.12.3.1.5.13
-- 1.3.6.1.4.1.37950.1.1.5.12.3.1.5.13
-- 1.3.6.1.4.1.37950.1.1.5.12.3.1.5.13
-- 1.3.6.1.4.1.37950.1.1.5.12.3.1.5.13
		-- 1.3.6.1.4.1.37950.1.1.5.12.3.1.5.13
		priSsidRadiusServipPrefixLen OBJECT-TYPE
			SYNTAX INTEGER (0..255)
			MAX-ACCESS read-write
			STATUS current
			DESCRIPTION
				"Description."
			::= { onuPriWifiSsid 13 }

		
--          1.3.6.1.4.1.37950.1.1.5.12.3.1.5.14
-- 1.3.6.1.4.1.37950.1.1.5.12.3.1.5.14
-- 1.3.6.1.4.1.37950.1.1.5.12.3.1.5.14
-- 1.3.6.1.4.1.37950.1.1.5.12.3.1.5.14
-- 1.3.6.1.4.1.37950.1.1.5.12.3.1.5.14
-- 1.3.6.1.4.1.37950.1.1.5.12.3.1.5.14
-- 1.3.6.1.4.1.37950.1.1.5.12.3.1.5.14
-- 1.3.6.1.4.1.37950.1.1.5.12.3.1.5.14
-- 1.3.6.1.4.1.37950.1.1.5.12.3.1.5.14
		-- 1.3.6.1.4.1.37950.1.1.5.12.3.1.5.14
		priSsidRadiusPort OBJECT-TYPE
			SYNTAX INTEGER (0..65535)
			MAX-ACCESS read-write
			STATUS current
			DESCRIPTION
				"Description."
			::= { onuPriWifiSsid 14 }

		
--          1.3.6.1.4.1.37950.1.1.5.12.3.1.5.15
-- 1.3.6.1.4.1.37950.1.1.5.12.3.1.5.15
-- 1.3.6.1.4.1.37950.1.1.5.12.3.1.5.15
-- 1.3.6.1.4.1.37950.1.1.5.12.3.1.5.15
-- 1.3.6.1.4.1.37950.1.1.5.12.3.1.5.15
-- 1.3.6.1.4.1.37950.1.1.5.12.3.1.5.15
-- 1.3.6.1.4.1.37950.1.1.5.12.3.1.5.15
-- 1.3.6.1.4.1.37950.1.1.5.12.3.1.5.15
-- 1.3.6.1.4.1.37950.1.1.5.12.3.1.5.15
		-- 1.3.6.1.4.1.37950.1.1.5.12.3.1.5.15
		priSsidRadiusKey OBJECT-TYPE
			SYNTAX OCTET STRING (SIZE (0..32))
			MAX-ACCESS read-write
			STATUS current
			DESCRIPTION
				"Description."
			::= { onuPriWifiSsid 15 }

		
--          1.3.6.1.4.1.37950.1.1.5.12.3.1.5.16
-- 1.3.6.1.4.1.37950.1.1.5.12.3.1.5.16
-- 1.3.6.1.4.1.37950.1.1.5.12.3.1.5.16
-- 1.3.6.1.4.1.37950.1.1.5.12.3.1.5.16
-- 1.3.6.1.4.1.37950.1.1.5.12.3.1.5.16
-- 1.3.6.1.4.1.37950.1.1.5.12.3.1.5.16
-- 1.3.6.1.4.1.37950.1.1.5.12.3.1.5.16
-- 1.3.6.1.4.1.37950.1.1.5.12.3.1.5.16
-- 1.3.6.1.4.1.37950.1.1.5.12.3.1.5.16
		-- 1.3.6.1.4.1.37950.1.1.5.12.3.1.5.16
		priSsidWepEncrytionLevel OBJECT-TYPE
			SYNTAX INTEGER
				{
				s64bit(1),
				s128bit(2)
				}
			MAX-ACCESS read-write
			STATUS current
			DESCRIPTION
				"Description."
			::= { onuPriWifiSsid 16 }

		
--          1.3.6.1.4.1.37950.1.1.5.12.3.1.5.17
-- 1.3.6.1.4.1.37950.1.1.5.12.3.1.5.17
-- 1.3.6.1.4.1.37950.1.1.5.12.3.1.5.17
-- 1.3.6.1.4.1.37950.1.1.5.12.3.1.5.17
-- 1.3.6.1.4.1.37950.1.1.5.12.3.1.5.17
-- 1.3.6.1.4.1.37950.1.1.5.12.3.1.5.17
-- 1.3.6.1.4.1.37950.1.1.5.12.3.1.5.17
-- 1.3.6.1.4.1.37950.1.1.5.12.3.1.5.17
-- 1.3.6.1.4.1.37950.1.1.5.12.3.1.5.17
		-- 1.3.6.1.4.1.37950.1.1.5.12.3.1.5.17
		priSsidWepKeyIndex OBJECT-TYPE
			SYNTAX INTEGER (1..4)
			MAX-ACCESS read-write
			STATUS current
			DESCRIPTION
				"Description."
			::= { onuPriWifiSsid 17 }

		
--          1.3.6.1.4.1.37950.1.1.5.12.3.1.5.18
-- 1.3.6.1.4.1.37950.1.1.5.12.3.1.5.18
-- 1.3.6.1.4.1.37950.1.1.5.12.3.1.5.18
-- 1.3.6.1.4.1.37950.1.1.5.12.3.1.5.18
-- 1.3.6.1.4.1.37950.1.1.5.12.3.1.5.18
-- 1.3.6.1.4.1.37950.1.1.5.12.3.1.5.18
-- 1.3.6.1.4.1.37950.1.1.5.12.3.1.5.18
-- 1.3.6.1.4.1.37950.1.1.5.12.3.1.5.18
-- 1.3.6.1.4.1.37950.1.1.5.12.3.1.5.18
		-- 1.3.6.1.4.1.37950.1.1.5.12.3.1.5.18
		priSsidWepKey1 OBJECT-TYPE
			SYNTAX OCTET STRING
			MAX-ACCESS read-write
			STATUS current
			DESCRIPTION
				"Description."
			::= { onuPriWifiSsid 18 }

		
--          1.3.6.1.4.1.37950.1.1.5.12.3.1.5.19
-- 1.3.6.1.4.1.37950.1.1.5.12.3.1.5.19
-- 1.3.6.1.4.1.37950.1.1.5.12.3.1.5.19
-- 1.3.6.1.4.1.37950.1.1.5.12.3.1.5.19
-- 1.3.6.1.4.1.37950.1.1.5.12.3.1.5.19
-- 1.3.6.1.4.1.37950.1.1.5.12.3.1.5.19
-- 1.3.6.1.4.1.37950.1.1.5.12.3.1.5.19
-- 1.3.6.1.4.1.37950.1.1.5.12.3.1.5.19
-- 1.3.6.1.4.1.37950.1.1.5.12.3.1.5.19
		-- 1.3.6.1.4.1.37950.1.1.5.12.3.1.5.19
		priSsidWepKey2 OBJECT-TYPE
			SYNTAX OCTET STRING
			MAX-ACCESS read-write
			STATUS current
			DESCRIPTION
				"Description."
			::= { onuPriWifiSsid 19 }

		
--          1.3.6.1.4.1.37950.1.1.5.12.3.1.5.20
-- 1.3.6.1.4.1.37950.1.1.5.12.3.1.5.20
-- 1.3.6.1.4.1.37950.1.1.5.12.3.1.5.20
-- 1.3.6.1.4.1.37950.1.1.5.12.3.1.5.20
-- 1.3.6.1.4.1.37950.1.1.5.12.3.1.5.20
-- 1.3.6.1.4.1.37950.1.1.5.12.3.1.5.20
-- 1.3.6.1.4.1.37950.1.1.5.12.3.1.5.20
-- 1.3.6.1.4.1.37950.1.1.5.12.3.1.5.20
-- 1.3.6.1.4.1.37950.1.1.5.12.3.1.5.20
		-- 1.3.6.1.4.1.37950.1.1.5.12.3.1.5.20
		priSsidWepKey3 OBJECT-TYPE
			SYNTAX OCTET STRING
			MAX-ACCESS read-write
			STATUS current
			DESCRIPTION
				"Description."
			::= { onuPriWifiSsid 20 }

		
--          1.3.6.1.4.1.37950.1.1.5.12.3.1.5.21
-- 1.3.6.1.4.1.37950.1.1.5.12.3.1.5.21
-- 1.3.6.1.4.1.37950.1.1.5.12.3.1.5.21
-- 1.3.6.1.4.1.37950.1.1.5.12.3.1.5.21
-- 1.3.6.1.4.1.37950.1.1.5.12.3.1.5.21
-- 1.3.6.1.4.1.37950.1.1.5.12.3.1.5.21
-- 1.3.6.1.4.1.37950.1.1.5.12.3.1.5.21
-- 1.3.6.1.4.1.37950.1.1.5.12.3.1.5.21
-- 1.3.6.1.4.1.37950.1.1.5.12.3.1.5.21
		-- 1.3.6.1.4.1.37950.1.1.5.12.3.1.5.21
		priSsidWepKey4 OBJECT-TYPE
			SYNTAX OCTET STRING
			MAX-ACCESS read-write
			STATUS current
			DESCRIPTION
				"Description."
			::= { onuPriWifiSsid 21 }

		
--          1.3.6.1.4.1.37950.1.1.5.12.3.1.5.22
-- 1.3.6.1.4.1.37950.1.1.5.12.3.1.5.22
-- 1.3.6.1.4.1.37950.1.1.5.12.3.1.5.22
-- 1.3.6.1.4.1.37950.1.1.5.12.3.1.5.22
-- 1.3.6.1.4.1.37950.1.1.5.12.3.1.5.22
-- 1.3.6.1.4.1.37950.1.1.5.12.3.1.5.22
-- 1.3.6.1.4.1.37950.1.1.5.12.3.1.5.22
-- 1.3.6.1.4.1.37950.1.1.5.12.3.1.5.22
-- 1.3.6.1.4.1.37950.1.1.5.12.3.1.5.22
		-- 1.3.6.1.4.1.37950.1.1.5.12.3.1.5.22
		priSsidAction OBJECT-TYPE
			SYNTAX INTEGER
				{
				commit(1),
				remove(2)
				}
			MAX-ACCESS read-write
			STATUS current
			DESCRIPTION
				"Description."
			::= { onuPriWifiSsid 22 }

		
--          1.3.6.1.4.1.37950.1.1.5.12.3.1.6
-- 1.3.6.1.4.1.37950.1.1.5.12.3.1.6
-- 1.3.6.1.4.1.37950.1.1.5.12.3.1.6
-- 1.3.6.1.4.1.37950.1.1.5.12.3.1.6
-- 1.3.6.1.4.1.37950.1.1.5.12.3.1.6
-- 1.3.6.1.4.1.37950.1.1.5.12.3.1.6
-- 1.3.6.1.4.1.37950.1.1.5.12.3.1.6
-- 1.3.6.1.4.1.37950.1.1.5.12.3.1.6
-- 1.3.6.1.4.1.37950.1.1.5.12.3.1.6
		-- 1.3.6.1.4.1.37950.1.1.5.12.3.1.6
		onuPriWanConn OBJECT IDENTIFIER ::= { onuPriGlobalCfg 6 }

		
--          1.3.6.1.4.1.37950.1.1.5.12.3.1.6.1
-- 1.3.6.1.4.1.37950.1.1.5.12.3.1.6.1
-- 1.3.6.1.4.1.37950.1.1.5.12.3.1.6.1
-- 1.3.6.1.4.1.37950.1.1.5.12.3.1.6.1
-- 1.3.6.1.4.1.37950.1.1.5.12.3.1.6.1
-- 1.3.6.1.4.1.37950.1.1.5.12.3.1.6.1
-- 1.3.6.1.4.1.37950.1.1.5.12.3.1.6.1
-- 1.3.6.1.4.1.37950.1.1.5.12.3.1.6.1
-- 1.3.6.1.4.1.37950.1.1.5.12.3.1.6.1
		-- 1.3.6.1.4.1.37950.1.1.5.12.3.1.6.1
		priWanConnAdd OBJECT IDENTIFIER ::= { onuPriWanConn 1 }

		
--          1.3.6.1.4.1.37950.1.1.5.12.3.1.6.1.1
-- 1.3.6.1.4.1.37950.1.1.5.12.3.1.6.1.1
-- 1.3.6.1.4.1.37950.1.1.5.12.3.1.6.1.1
-- 1.3.6.1.4.1.37950.1.1.5.12.3.1.6.1.1
-- 1.3.6.1.4.1.37950.1.1.5.12.3.1.6.1.1
-- 1.3.6.1.4.1.37950.1.1.5.12.3.1.6.1.1
-- 1.3.6.1.4.1.37950.1.1.5.12.3.1.6.1.1
-- 1.3.6.1.4.1.37950.1.1.5.12.3.1.6.1.1
-- 1.3.6.1.4.1.37950.1.1.5.12.3.1.6.1.1
		-- 1.3.6.1.4.1.37950.1.1.5.12.3.1.6.1.1
		priWanAddPon OBJECT-TYPE
			SYNTAX INTEGER (1..16)
			MAX-ACCESS read-write
			STATUS current
			DESCRIPTION
				"Description."
			::= { priWanConnAdd 1 }

		
--          1.3.6.1.4.1.37950.1.1.5.12.3.1.6.1.2
-- 1.3.6.1.4.1.37950.1.1.5.12.3.1.6.1.2
-- 1.3.6.1.4.1.37950.1.1.5.12.3.1.6.1.2
-- 1.3.6.1.4.1.37950.1.1.5.12.3.1.6.1.2
-- 1.3.6.1.4.1.37950.1.1.5.12.3.1.6.1.2
-- 1.3.6.1.4.1.37950.1.1.5.12.3.1.6.1.2
-- 1.3.6.1.4.1.37950.1.1.5.12.3.1.6.1.2
-- 1.3.6.1.4.1.37950.1.1.5.12.3.1.6.1.2
-- 1.3.6.1.4.1.37950.1.1.5.12.3.1.6.1.2
		-- 1.3.6.1.4.1.37950.1.1.5.12.3.1.6.1.2
		priWanAddOnu OBJECT-TYPE
			SYNTAX INTEGER (1..65535)
			MAX-ACCESS read-write
			STATUS current
			DESCRIPTION
				"Description."
			::= { priWanConnAdd 2 }

		
--          1.3.6.1.4.1.37950.1.1.5.12.3.1.6.1.3
-- 1.3.6.1.4.1.37950.1.1.5.12.3.1.6.1.3
-- 1.3.6.1.4.1.37950.1.1.5.12.3.1.6.1.3
-- 1.3.6.1.4.1.37950.1.1.5.12.3.1.6.1.3
-- 1.3.6.1.4.1.37950.1.1.5.12.3.1.6.1.3
-- 1.3.6.1.4.1.37950.1.1.5.12.3.1.6.1.3
-- 1.3.6.1.4.1.37950.1.1.5.12.3.1.6.1.3
-- 1.3.6.1.4.1.37950.1.1.5.12.3.1.6.1.3
-- 1.3.6.1.4.1.37950.1.1.5.12.3.1.6.1.3
		-- 1.3.6.1.4.1.37950.1.1.5.12.3.1.6.1.3
		priConnType OBJECT-TYPE
			SYNTAX INTEGER
				{
				bridge(0),
				route(1)
				}
			MAX-ACCESS read-write
			STATUS current
			DESCRIPTION
				"Description."
			::= { priWanConnAdd 3 }

		
--          1.3.6.1.4.1.37950.1.1.5.12.3.1.6.1.4
-- 1.3.6.1.4.1.37950.1.1.5.12.3.1.6.1.4
-- 1.3.6.1.4.1.37950.1.1.5.12.3.1.6.1.4
-- 1.3.6.1.4.1.37950.1.1.5.12.3.1.6.1.4
-- 1.3.6.1.4.1.37950.1.1.5.12.3.1.6.1.4
-- 1.3.6.1.4.1.37950.1.1.5.12.3.1.6.1.4
-- 1.3.6.1.4.1.37950.1.1.5.12.3.1.6.1.4
-- 1.3.6.1.4.1.37950.1.1.5.12.3.1.6.1.4
-- 1.3.6.1.4.1.37950.1.1.5.12.3.1.6.1.4
		-- 1.3.6.1.4.1.37950.1.1.5.12.3.1.6.1.4
		priConnAddAction OBJECT-TYPE
			SYNTAX INTEGER { add(1) }
			MAX-ACCESS read-write
			STATUS current
			DESCRIPTION
				"Description."
			::= { priWanConnAdd 4 }

		
--          1.3.6.1.4.1.37950.1.1.5.12.3.1.6.2
-- 1.3.6.1.4.1.37950.1.1.5.12.3.1.6.2
-- 1.3.6.1.4.1.37950.1.1.5.12.3.1.6.2
-- 1.3.6.1.4.1.37950.1.1.5.12.3.1.6.2
-- 1.3.6.1.4.1.37950.1.1.5.12.3.1.6.2
-- 1.3.6.1.4.1.37950.1.1.5.12.3.1.6.2
-- 1.3.6.1.4.1.37950.1.1.5.12.3.1.6.2
-- 1.3.6.1.4.1.37950.1.1.5.12.3.1.6.2
-- 1.3.6.1.4.1.37950.1.1.5.12.3.1.6.2
		-- 1.3.6.1.4.1.37950.1.1.5.12.3.1.6.2
		priWanConnDelete OBJECT IDENTIFIER ::= { onuPriWanConn 2 }

		
--          1.3.6.1.4.1.37950.1.1.5.12.3.1.6.2.1
-- 1.3.6.1.4.1.37950.1.1.5.12.3.1.6.2.1
-- 1.3.6.1.4.1.37950.1.1.5.12.3.1.6.2.1
-- 1.3.6.1.4.1.37950.1.1.5.12.3.1.6.2.1
-- 1.3.6.1.4.1.37950.1.1.5.12.3.1.6.2.1
-- 1.3.6.1.4.1.37950.1.1.5.12.3.1.6.2.1
-- 1.3.6.1.4.1.37950.1.1.5.12.3.1.6.2.1
-- 1.3.6.1.4.1.37950.1.1.5.12.3.1.6.2.1
-- 1.3.6.1.4.1.37950.1.1.5.12.3.1.6.2.1
		-- 1.3.6.1.4.1.37950.1.1.5.12.3.1.6.2.1
		priWanDeletePon OBJECT-TYPE
			SYNTAX INTEGER (1..16)
			MAX-ACCESS read-write
			STATUS current
			DESCRIPTION
				"Description."
			::= { priWanConnDelete 1 }

		
--          1.3.6.1.4.1.37950.1.1.5.12.3.1.6.2.2
-- 1.3.6.1.4.1.37950.1.1.5.12.3.1.6.2.2
-- 1.3.6.1.4.1.37950.1.1.5.12.3.1.6.2.2
-- 1.3.6.1.4.1.37950.1.1.5.12.3.1.6.2.2
-- 1.3.6.1.4.1.37950.1.1.5.12.3.1.6.2.2
-- 1.3.6.1.4.1.37950.1.1.5.12.3.1.6.2.2
-- 1.3.6.1.4.1.37950.1.1.5.12.3.1.6.2.2
-- 1.3.6.1.4.1.37950.1.1.5.12.3.1.6.2.2
-- 1.3.6.1.4.1.37950.1.1.5.12.3.1.6.2.2
		-- 1.3.6.1.4.1.37950.1.1.5.12.3.1.6.2.2
		priWanDeleteOnu OBJECT-TYPE
			SYNTAX INTEGER (1..65535)
			MAX-ACCESS read-write
			STATUS current
			DESCRIPTION
				"Description."
			::= { priWanConnDelete 2 }

		
--          1.3.6.1.4.1.37950.1.1.5.12.3.1.6.2.3
-- 1.3.6.1.4.1.37950.1.1.5.12.3.1.6.2.3
-- 1.3.6.1.4.1.37950.1.1.5.12.3.1.6.2.3
-- 1.3.6.1.4.1.37950.1.1.5.12.3.1.6.2.3
-- 1.3.6.1.4.1.37950.1.1.5.12.3.1.6.2.3
-- 1.3.6.1.4.1.37950.1.1.5.12.3.1.6.2.3
-- 1.3.6.1.4.1.37950.1.1.5.12.3.1.6.2.3
-- 1.3.6.1.4.1.37950.1.1.5.12.3.1.6.2.3
-- 1.3.6.1.4.1.37950.1.1.5.12.3.1.6.2.3
		-- 1.3.6.1.4.1.37950.1.1.5.12.3.1.6.2.3
		priConnIndexD OBJECT-TYPE
			SYNTAX Integer32 (1..8)
			MAX-ACCESS read-write
			STATUS current
			DESCRIPTION
				"Description."
			::= { priWanConnDelete 3 }

		
--          1.3.6.1.4.1.37950.1.1.5.12.3.1.6.2.4
-- 1.3.6.1.4.1.37950.1.1.5.12.3.1.6.2.4
-- 1.3.6.1.4.1.37950.1.1.5.12.3.1.6.2.4
-- 1.3.6.1.4.1.37950.1.1.5.12.3.1.6.2.4
-- 1.3.6.1.4.1.37950.1.1.5.12.3.1.6.2.4
-- 1.3.6.1.4.1.37950.1.1.5.12.3.1.6.2.4
-- 1.3.6.1.4.1.37950.1.1.5.12.3.1.6.2.4
-- 1.3.6.1.4.1.37950.1.1.5.12.3.1.6.2.4
-- 1.3.6.1.4.1.37950.1.1.5.12.3.1.6.2.4
		-- 1.3.6.1.4.1.37950.1.1.5.12.3.1.6.2.4
		priConnDeleteAction OBJECT-TYPE
			SYNTAX INTEGER { delete(1) }
			MAX-ACCESS read-write
			STATUS current
			DESCRIPTION
				"Description."
			::= { priWanConnDelete 4 }

		
--          1.3.6.1.4.1.37950.1.1.5.12.3.1.6.3
-- 1.3.6.1.4.1.37950.1.1.5.12.3.1.6.3
-- 1.3.6.1.4.1.37950.1.1.5.12.3.1.6.3
-- 1.3.6.1.4.1.37950.1.1.5.12.3.1.6.3
-- 1.3.6.1.4.1.37950.1.1.5.12.3.1.6.3
-- 1.3.6.1.4.1.37950.1.1.5.12.3.1.6.3
-- 1.3.6.1.4.1.37950.1.1.5.12.3.1.6.3
-- 1.3.6.1.4.1.37950.1.1.5.12.3.1.6.3
-- 1.3.6.1.4.1.37950.1.1.5.12.3.1.6.3
		-- 1.3.6.1.4.1.37950.1.1.5.12.3.1.6.3
		priWanConnCfg OBJECT IDENTIFIER ::= { onuPriWanConn 3 }

		
--          1.3.6.1.4.1.37950.1.1.5.12.3.1.6.3.1
-- 1.3.6.1.4.1.37950.1.1.5.12.3.1.6.3.1
-- 1.3.6.1.4.1.37950.1.1.5.12.3.1.6.3.1
-- 1.3.6.1.4.1.37950.1.1.5.12.3.1.6.3.1
-- 1.3.6.1.4.1.37950.1.1.5.12.3.1.6.3.1
-- 1.3.6.1.4.1.37950.1.1.5.12.3.1.6.3.1
-- 1.3.6.1.4.1.37950.1.1.5.12.3.1.6.3.1
-- 1.3.6.1.4.1.37950.1.1.5.12.3.1.6.3.1
-- 1.3.6.1.4.1.37950.1.1.5.12.3.1.6.3.1
		-- 1.3.6.1.4.1.37950.1.1.5.12.3.1.6.3.1
		priConnPon OBJECT-TYPE
			SYNTAX INTEGER (1..16)
			MAX-ACCESS read-write
			STATUS current
			DESCRIPTION
				"Description."
			::= { priWanConnCfg 1 }

		
--          1.3.6.1.4.1.37950.1.1.5.12.3.1.6.3.2
-- 1.3.6.1.4.1.37950.1.1.5.12.3.1.6.3.2
-- 1.3.6.1.4.1.37950.1.1.5.12.3.1.6.3.2
-- 1.3.6.1.4.1.37950.1.1.5.12.3.1.6.3.2
-- 1.3.6.1.4.1.37950.1.1.5.12.3.1.6.3.2
-- 1.3.6.1.4.1.37950.1.1.5.12.3.1.6.3.2
-- 1.3.6.1.4.1.37950.1.1.5.12.3.1.6.3.2
-- 1.3.6.1.4.1.37950.1.1.5.12.3.1.6.3.2
-- 1.3.6.1.4.1.37950.1.1.5.12.3.1.6.3.2
		-- 1.3.6.1.4.1.37950.1.1.5.12.3.1.6.3.2
		priConnOnu OBJECT-TYPE
			SYNTAX INTEGER (1..65535)
			MAX-ACCESS read-write
			STATUS current
			DESCRIPTION
				"Description."
			::= { priWanConnCfg 2 }

		
--          1.3.6.1.4.1.37950.1.1.5.12.3.1.6.3.3
-- 1.3.6.1.4.1.37950.1.1.5.12.3.1.6.3.3
-- 1.3.6.1.4.1.37950.1.1.5.12.3.1.6.3.3
-- 1.3.6.1.4.1.37950.1.1.5.12.3.1.6.3.3
-- 1.3.6.1.4.1.37950.1.1.5.12.3.1.6.3.3
-- 1.3.6.1.4.1.37950.1.1.5.12.3.1.6.3.3
-- 1.3.6.1.4.1.37950.1.1.5.12.3.1.6.3.3
-- 1.3.6.1.4.1.37950.1.1.5.12.3.1.6.3.3
-- 1.3.6.1.4.1.37950.1.1.5.12.3.1.6.3.3
		-- 1.3.6.1.4.1.37950.1.1.5.12.3.1.6.3.3
		priConnIndex OBJECT-TYPE
			SYNTAX INTEGER (1..8)
			MAX-ACCESS read-write
			STATUS current
			DESCRIPTION
				"Description."
			::= { priWanConnCfg 3 }

		
--          1.3.6.1.4.1.37950.1.1.5.12.3.1.6.3.4
-- 1.3.6.1.4.1.37950.1.1.5.12.3.1.6.3.4
-- 1.3.6.1.4.1.37950.1.1.5.12.3.1.6.3.4
-- 1.3.6.1.4.1.37950.1.1.5.12.3.1.6.3.4
-- 1.3.6.1.4.1.37950.1.1.5.12.3.1.6.3.4
-- 1.3.6.1.4.1.37950.1.1.5.12.3.1.6.3.4
-- 1.3.6.1.4.1.37950.1.1.5.12.3.1.6.3.4
-- 1.3.6.1.4.1.37950.1.1.5.12.3.1.6.3.4
-- 1.3.6.1.4.1.37950.1.1.5.12.3.1.6.3.4
		-- 1.3.6.1.4.1.37950.1.1.5.12.3.1.6.3.4
		priConnBindLan OBJECT-TYPE
			SYNTAX INTEGER (0..15)
			MAX-ACCESS read-write
			STATUS current
			DESCRIPTION
				"Description."
			::= { priWanConnCfg 4 }

		
--          1.3.6.1.4.1.37950.1.1.5.12.3.1.6.3.5
-- 1.3.6.1.4.1.37950.1.1.5.12.3.1.6.3.5
-- 1.3.6.1.4.1.37950.1.1.5.12.3.1.6.3.5
-- 1.3.6.1.4.1.37950.1.1.5.12.3.1.6.3.5
-- 1.3.6.1.4.1.37950.1.1.5.12.3.1.6.3.5
-- 1.3.6.1.4.1.37950.1.1.5.12.3.1.6.3.5
-- 1.3.6.1.4.1.37950.1.1.5.12.3.1.6.3.5
-- 1.3.6.1.4.1.37950.1.1.5.12.3.1.6.3.5
-- 1.3.6.1.4.1.37950.1.1.5.12.3.1.6.3.5
		-- 1.3.6.1.4.1.37950.1.1.5.12.3.1.6.3.5
		priConnBindSsid OBJECT-TYPE
			SYNTAX INTEGER (0..65535)
			MAX-ACCESS read-write
			STATUS current
			DESCRIPTION
				"Description."
			::= { priWanConnCfg 5 }

		
--          1.3.6.1.4.1.37950.1.1.5.12.3.1.6.3.6
-- 1.3.6.1.4.1.37950.1.1.5.12.3.1.6.3.6
-- 1.3.6.1.4.1.37950.1.1.5.12.3.1.6.3.6
-- 1.3.6.1.4.1.37950.1.1.5.12.3.1.6.3.6
-- 1.3.6.1.4.1.37950.1.1.5.12.3.1.6.3.6
-- 1.3.6.1.4.1.37950.1.1.5.12.3.1.6.3.6
-- 1.3.6.1.4.1.37950.1.1.5.12.3.1.6.3.6
-- 1.3.6.1.4.1.37950.1.1.5.12.3.1.6.3.6
-- 1.3.6.1.4.1.37950.1.1.5.12.3.1.6.3.6
		-- 1.3.6.1.4.1.37950.1.1.5.12.3.1.6.3.6
		priWanMode OBJECT-TYPE
			SYNTAX INTEGER
				{
				internet(0),
				multicast(1),
				tr069(2),
				tr069-internet(3),
				tr069-voip(4),
				voip-internet(5),
				tr069-voip-internet(6),
				other(100)
				}
			MAX-ACCESS read-write
			STATUS current
			DESCRIPTION
				"Description."
			::= { priWanConnCfg 6 }

		
--          1.3.6.1.4.1.37950.1.1.5.12.3.1.6.3.7
-- 1.3.6.1.4.1.37950.1.1.5.12.3.1.6.3.7
-- 1.3.6.1.4.1.37950.1.1.5.12.3.1.6.3.7
-- 1.3.6.1.4.1.37950.1.1.5.12.3.1.6.3.7
-- 1.3.6.1.4.1.37950.1.1.5.12.3.1.6.3.7
-- 1.3.6.1.4.1.37950.1.1.5.12.3.1.6.3.7
-- 1.3.6.1.4.1.37950.1.1.5.12.3.1.6.3.7
-- 1.3.6.1.4.1.37950.1.1.5.12.3.1.6.3.7
-- 1.3.6.1.4.1.37950.1.1.5.12.3.1.6.3.7
		-- 1.3.6.1.4.1.37950.1.1.5.12.3.1.6.3.7
		priConnTypeCfg OBJECT-TYPE
			SYNTAX INTEGER
				{
				bridge(0),
				route(1)
				}
			MAX-ACCESS read-write
			STATUS current
			DESCRIPTION
				"Description."
			::= { priWanConnCfg 7 }

		
--          1.3.6.1.4.1.37950.1.1.5.12.3.1.6.3.8
-- 1.3.6.1.4.1.37950.1.1.5.12.3.1.6.3.8
-- 1.3.6.1.4.1.37950.1.1.5.12.3.1.6.3.8
-- 1.3.6.1.4.1.37950.1.1.5.12.3.1.6.3.8
-- 1.3.6.1.4.1.37950.1.1.5.12.3.1.6.3.8
-- 1.3.6.1.4.1.37950.1.1.5.12.3.1.6.3.8
-- 1.3.6.1.4.1.37950.1.1.5.12.3.1.6.3.8
-- 1.3.6.1.4.1.37950.1.1.5.12.3.1.6.3.8
-- 1.3.6.1.4.1.37950.1.1.5.12.3.1.6.3.8
		-- 1.3.6.1.4.1.37950.1.1.5.12.3.1.6.3.8
		priConnVlanId OBJECT-TYPE
			SYNTAX Integer32 (0..4095)
			MAX-ACCESS read-write
			STATUS current
			DESCRIPTION
				"Description."
			::= { priWanConnCfg 8 }

		
--          1.3.6.1.4.1.37950.1.1.5.12.3.1.6.3.9
-- 1.3.6.1.4.1.37950.1.1.5.12.3.1.6.3.9
-- 1.3.6.1.4.1.37950.1.1.5.12.3.1.6.3.9
-- 1.3.6.1.4.1.37950.1.1.5.12.3.1.6.3.9
-- 1.3.6.1.4.1.37950.1.1.5.12.3.1.6.3.9
-- 1.3.6.1.4.1.37950.1.1.5.12.3.1.6.3.9
-- 1.3.6.1.4.1.37950.1.1.5.12.3.1.6.3.9
-- 1.3.6.1.4.1.37950.1.1.5.12.3.1.6.3.9
-- 1.3.6.1.4.1.37950.1.1.5.12.3.1.6.3.9
		-- 1.3.6.1.4.1.37950.1.1.5.12.3.1.6.3.9
		priConnCos OBJECT-TYPE
			SYNTAX INTEGER (0..7)
			MAX-ACCESS read-write
			STATUS current
			DESCRIPTION
				"Description."
			::= { priWanConnCfg 9 }

		
--          1.3.6.1.4.1.37950.1.1.5.12.3.1.6.3.10
-- 1.3.6.1.4.1.37950.1.1.5.12.3.1.6.3.10
-- 1.3.6.1.4.1.37950.1.1.5.12.3.1.6.3.10
-- 1.3.6.1.4.1.37950.1.1.5.12.3.1.6.3.10
-- 1.3.6.1.4.1.37950.1.1.5.12.3.1.6.3.10
-- 1.3.6.1.4.1.37950.1.1.5.12.3.1.6.3.10
-- 1.3.6.1.4.1.37950.1.1.5.12.3.1.6.3.10
-- 1.3.6.1.4.1.37950.1.1.5.12.3.1.6.3.10
-- 1.3.6.1.4.1.37950.1.1.5.12.3.1.6.3.10
		-- 1.3.6.1.4.1.37950.1.1.5.12.3.1.6.3.10
		priConnNatEnable OBJECT-TYPE
			SYNTAX INTEGER
				{
				disable(0),
				enable(1)
				}
			MAX-ACCESS read-write
			STATUS current
			DESCRIPTION
				"Description."
			::= { priWanConnCfg 10 }

		
--          1.3.6.1.4.1.37950.1.1.5.12.3.1.6.3.11
-- 1.3.6.1.4.1.37950.1.1.5.12.3.1.6.3.11
-- 1.3.6.1.4.1.37950.1.1.5.12.3.1.6.3.11
-- 1.3.6.1.4.1.37950.1.1.5.12.3.1.6.3.11
-- 1.3.6.1.4.1.37950.1.1.5.12.3.1.6.3.11
-- 1.3.6.1.4.1.37950.1.1.5.12.3.1.6.3.11
-- 1.3.6.1.4.1.37950.1.1.5.12.3.1.6.3.11
-- 1.3.6.1.4.1.37950.1.1.5.12.3.1.6.3.11
-- 1.3.6.1.4.1.37950.1.1.5.12.3.1.6.3.11
		-- 1.3.6.1.4.1.37950.1.1.5.12.3.1.6.3.11
		priConnModeCfg OBJECT-TYPE
			SYNTAX INTEGER
				{
				dhcp(0),
				static(1),
				pppoe(2)
				}
			MAX-ACCESS read-write
			STATUS current
			DESCRIPTION
				"Description."
			::= { priWanConnCfg 11 }

		
--          1.3.6.1.4.1.37950.1.1.5.12.3.1.6.3.12
-- 1.3.6.1.4.1.37950.1.1.5.12.3.1.6.3.12
-- 1.3.6.1.4.1.37950.1.1.5.12.3.1.6.3.12
-- 1.3.6.1.4.1.37950.1.1.5.12.3.1.6.3.12
-- 1.3.6.1.4.1.37950.1.1.5.12.3.1.6.3.12
-- 1.3.6.1.4.1.37950.1.1.5.12.3.1.6.3.12
-- 1.3.6.1.4.1.37950.1.1.5.12.3.1.6.3.12
-- 1.3.6.1.4.1.37950.1.1.5.12.3.1.6.3.12
-- 1.3.6.1.4.1.37950.1.1.5.12.3.1.6.3.12
		-- 1.3.6.1.4.1.37950.1.1.5.12.3.1.6.3.12
		priConnIpAddress OBJECT-TYPE
			SYNTAX IpAddress
			MAX-ACCESS read-write
			STATUS current
			DESCRIPTION
				"Description."
			::= { priWanConnCfg 12 }

		
--          1.3.6.1.4.1.37950.1.1.5.12.3.1.6.3.13
-- 1.3.6.1.4.1.37950.1.1.5.12.3.1.6.3.13
-- 1.3.6.1.4.1.37950.1.1.5.12.3.1.6.3.13
-- 1.3.6.1.4.1.37950.1.1.5.12.3.1.6.3.13
-- 1.3.6.1.4.1.37950.1.1.5.12.3.1.6.3.13
-- 1.3.6.1.4.1.37950.1.1.5.12.3.1.6.3.13
-- 1.3.6.1.4.1.37950.1.1.5.12.3.1.6.3.13
-- 1.3.6.1.4.1.37950.1.1.5.12.3.1.6.3.13
-- 1.3.6.1.4.1.37950.1.1.5.12.3.1.6.3.13
		-- 1.3.6.1.4.1.37950.1.1.5.12.3.1.6.3.13
		priConnIpMask OBJECT-TYPE
			SYNTAX IpAddress
			MAX-ACCESS read-write
			STATUS current
			DESCRIPTION
				"Description."
			::= { priWanConnCfg 13 }

		
--          1.3.6.1.4.1.37950.1.1.5.12.3.1.6.3.14
-- 1.3.6.1.4.1.37950.1.1.5.12.3.1.6.3.14
-- 1.3.6.1.4.1.37950.1.1.5.12.3.1.6.3.14
-- 1.3.6.1.4.1.37950.1.1.5.12.3.1.6.3.14
-- 1.3.6.1.4.1.37950.1.1.5.12.3.1.6.3.14
-- 1.3.6.1.4.1.37950.1.1.5.12.3.1.6.3.14
-- 1.3.6.1.4.1.37950.1.1.5.12.3.1.6.3.14
-- 1.3.6.1.4.1.37950.1.1.5.12.3.1.6.3.14
-- 1.3.6.1.4.1.37950.1.1.5.12.3.1.6.3.14
		-- 1.3.6.1.4.1.37950.1.1.5.12.3.1.6.3.14
		priConnGateway OBJECT-TYPE
			SYNTAX IpAddress
			MAX-ACCESS read-write
			STATUS current
			DESCRIPTION
				"Description."
			::= { priWanConnCfg 14 }

		
--          1.3.6.1.4.1.37950.1.1.5.12.3.1.6.3.15
-- 1.3.6.1.4.1.37950.1.1.5.12.3.1.6.3.15
-- 1.3.6.1.4.1.37950.1.1.5.12.3.1.6.3.15
-- 1.3.6.1.4.1.37950.1.1.5.12.3.1.6.3.15
-- 1.3.6.1.4.1.37950.1.1.5.12.3.1.6.3.15
-- 1.3.6.1.4.1.37950.1.1.5.12.3.1.6.3.15
-- 1.3.6.1.4.1.37950.1.1.5.12.3.1.6.3.15
-- 1.3.6.1.4.1.37950.1.1.5.12.3.1.6.3.15
-- 1.3.6.1.4.1.37950.1.1.5.12.3.1.6.3.15
		-- 1.3.6.1.4.1.37950.1.1.5.12.3.1.6.3.15
		priConnMasterDns OBJECT-TYPE
			SYNTAX IpAddress
			MAX-ACCESS read-write
			STATUS current
			DESCRIPTION
				"Description."
			::= { priWanConnCfg 15 }

		
--          1.3.6.1.4.1.37950.1.1.5.12.3.1.6.3.16
-- 1.3.6.1.4.1.37950.1.1.5.12.3.1.6.3.16
-- 1.3.6.1.4.1.37950.1.1.5.12.3.1.6.3.16
-- 1.3.6.1.4.1.37950.1.1.5.12.3.1.6.3.16
-- 1.3.6.1.4.1.37950.1.1.5.12.3.1.6.3.16
-- 1.3.6.1.4.1.37950.1.1.5.12.3.1.6.3.16
-- 1.3.6.1.4.1.37950.1.1.5.12.3.1.6.3.16
-- 1.3.6.1.4.1.37950.1.1.5.12.3.1.6.3.16
-- 1.3.6.1.4.1.37950.1.1.5.12.3.1.6.3.16
		-- 1.3.6.1.4.1.37950.1.1.5.12.3.1.6.3.16
		priConnSlaveDns OBJECT-TYPE
			SYNTAX IpAddress
			MAX-ACCESS read-write
			STATUS current
			DESCRIPTION
				"Description."
			::= { priWanConnCfg 16 }

		
--          1.3.6.1.4.1.37950.1.1.5.12.3.1.6.3.17
-- 1.3.6.1.4.1.37950.1.1.5.12.3.1.6.3.17
-- 1.3.6.1.4.1.37950.1.1.5.12.3.1.6.3.17
-- 1.3.6.1.4.1.37950.1.1.5.12.3.1.6.3.17
-- 1.3.6.1.4.1.37950.1.1.5.12.3.1.6.3.17
-- 1.3.6.1.4.1.37950.1.1.5.12.3.1.6.3.17
-- 1.3.6.1.4.1.37950.1.1.5.12.3.1.6.3.17
-- 1.3.6.1.4.1.37950.1.1.5.12.3.1.6.3.17
-- 1.3.6.1.4.1.37950.1.1.5.12.3.1.6.3.17
		-- 1.3.6.1.4.1.37950.1.1.5.12.3.1.6.3.17
		priConnPppoeProxy OBJECT-TYPE
			SYNTAX INTEGER
				{
				disable(0),
				enable(1)
				}
			MAX-ACCESS read-write
			STATUS current
			DESCRIPTION
				"Description."
			::= { priWanConnCfg 17 }

		
--          1.3.6.1.4.1.37950.1.1.5.12.3.1.6.3.18
-- 1.3.6.1.4.1.37950.1.1.5.12.3.1.6.3.18
-- 1.3.6.1.4.1.37950.1.1.5.12.3.1.6.3.18
-- 1.3.6.1.4.1.37950.1.1.5.12.3.1.6.3.18
-- 1.3.6.1.4.1.37950.1.1.5.12.3.1.6.3.18
-- 1.3.6.1.4.1.37950.1.1.5.12.3.1.6.3.18
-- 1.3.6.1.4.1.37950.1.1.5.12.3.1.6.3.18
-- 1.3.6.1.4.1.37950.1.1.5.12.3.1.6.3.18
-- 1.3.6.1.4.1.37950.1.1.5.12.3.1.6.3.18
		-- 1.3.6.1.4.1.37950.1.1.5.12.3.1.6.3.18
		priConnPppoeUsername OBJECT-TYPE
			SYNTAX OCTET STRING
			MAX-ACCESS read-write
			STATUS current
			DESCRIPTION
				"Description."
			::= { priWanConnCfg 18 }

		
--          1.3.6.1.4.1.37950.1.1.5.12.3.1.6.3.19
-- 1.3.6.1.4.1.37950.1.1.5.12.3.1.6.3.19
-- 1.3.6.1.4.1.37950.1.1.5.12.3.1.6.3.19
-- 1.3.6.1.4.1.37950.1.1.5.12.3.1.6.3.19
-- 1.3.6.1.4.1.37950.1.1.5.12.3.1.6.3.19
-- 1.3.6.1.4.1.37950.1.1.5.12.3.1.6.3.19
-- 1.3.6.1.4.1.37950.1.1.5.12.3.1.6.3.19
-- 1.3.6.1.4.1.37950.1.1.5.12.3.1.6.3.19
-- 1.3.6.1.4.1.37950.1.1.5.12.3.1.6.3.19
		-- 1.3.6.1.4.1.37950.1.1.5.12.3.1.6.3.19
		priConnPppoePassword OBJECT-TYPE
			SYNTAX OCTET STRING
			MAX-ACCESS read-write
			STATUS current
			DESCRIPTION
				"Description."
			::= { priWanConnCfg 19 }

		
--          1.3.6.1.4.1.37950.1.1.5.12.3.1.6.3.20
-- 1.3.6.1.4.1.37950.1.1.5.12.3.1.6.3.20
-- 1.3.6.1.4.1.37950.1.1.5.12.3.1.6.3.20
-- 1.3.6.1.4.1.37950.1.1.5.12.3.1.6.3.20
-- 1.3.6.1.4.1.37950.1.1.5.12.3.1.6.3.20
-- 1.3.6.1.4.1.37950.1.1.5.12.3.1.6.3.20
-- 1.3.6.1.4.1.37950.1.1.5.12.3.1.6.3.20
-- 1.3.6.1.4.1.37950.1.1.5.12.3.1.6.3.20
-- 1.3.6.1.4.1.37950.1.1.5.12.3.1.6.3.20
		-- 1.3.6.1.4.1.37950.1.1.5.12.3.1.6.3.20
		priConnPppoeSerName OBJECT-TYPE
			SYNTAX OCTET STRING
			MAX-ACCESS read-write
			STATUS current
			DESCRIPTION
				"Description."
			::= { priWanConnCfg 20 }

		
--          1.3.6.1.4.1.37950.1.1.5.12.3.1.6.3.21
-- 1.3.6.1.4.1.37950.1.1.5.12.3.1.6.3.21
-- 1.3.6.1.4.1.37950.1.1.5.12.3.1.6.3.21
-- 1.3.6.1.4.1.37950.1.1.5.12.3.1.6.3.21
-- 1.3.6.1.4.1.37950.1.1.5.12.3.1.6.3.21
-- 1.3.6.1.4.1.37950.1.1.5.12.3.1.6.3.21
-- 1.3.6.1.4.1.37950.1.1.5.12.3.1.6.3.21
-- 1.3.6.1.4.1.37950.1.1.5.12.3.1.6.3.21
-- 1.3.6.1.4.1.37950.1.1.5.12.3.1.6.3.21
		-- 1.3.6.1.4.1.37950.1.1.5.12.3.1.6.3.21
		priConnPppoeMode OBJECT-TYPE
			SYNTAX INTEGER
				{
				autoConnect(0),
				connecWhenPayload(1)
				}
			MAX-ACCESS read-write
			STATUS current
			DESCRIPTION
				"Description."
			::= { priWanConnCfg 21 }

		
--          1.3.6.1.4.1.37950.1.1.5.12.3.1.6.3.22
-- 1.3.6.1.4.1.37950.1.1.5.12.3.1.6.3.22
-- 1.3.6.1.4.1.37950.1.1.5.12.3.1.6.3.22
-- 1.3.6.1.4.1.37950.1.1.5.12.3.1.6.3.22
-- 1.3.6.1.4.1.37950.1.1.5.12.3.1.6.3.22
-- 1.3.6.1.4.1.37950.1.1.5.12.3.1.6.3.22
-- 1.3.6.1.4.1.37950.1.1.5.12.3.1.6.3.22
-- 1.3.6.1.4.1.37950.1.1.5.12.3.1.6.3.22
-- 1.3.6.1.4.1.37950.1.1.5.12.3.1.6.3.22
		-- 1.3.6.1.4.1.37950.1.1.5.12.3.1.6.3.22
		priConnQosEnable OBJECT-TYPE
			SYNTAX INTEGER
				{
				disable(0),
				enable(1)
				}
			MAX-ACCESS read-write
			STATUS current
			DESCRIPTION
				"Description."
			::= { priWanConnCfg 22 }

		
--          1.3.6.1.4.1.37950.1.1.5.12.3.1.6.3.23
-- 1.3.6.1.4.1.37950.1.1.5.12.3.1.6.3.23
-- 1.3.6.1.4.1.37950.1.1.5.12.3.1.6.3.23
-- 1.3.6.1.4.1.37950.1.1.5.12.3.1.6.3.23
-- 1.3.6.1.4.1.37950.1.1.5.12.3.1.6.3.23
-- 1.3.6.1.4.1.37950.1.1.5.12.3.1.6.3.23
-- 1.3.6.1.4.1.37950.1.1.5.12.3.1.6.3.23
-- 1.3.6.1.4.1.37950.1.1.5.12.3.1.6.3.23
-- 1.3.6.1.4.1.37950.1.1.5.12.3.1.6.3.23
		-- 1.3.6.1.4.1.37950.1.1.5.12.3.1.6.3.23
		priConnVlanMode OBJECT-TYPE
			SYNTAX INTEGER
				{
				disable(0),
				tag(1),
				transparent(2)
				}
			MAX-ACCESS read-write
			STATUS current
			DESCRIPTION
				"Description."
			::= { priWanConnCfg 23 }

		
--          1.3.6.1.4.1.37950.1.1.5.12.3.1.6.3.24
-- 1.3.6.1.4.1.37950.1.1.5.12.3.1.6.3.24
-- 1.3.6.1.4.1.37950.1.1.5.12.3.1.6.3.24
-- 1.3.6.1.4.1.37950.1.1.5.12.3.1.6.3.24
-- 1.3.6.1.4.1.37950.1.1.5.12.3.1.6.3.24
-- 1.3.6.1.4.1.37950.1.1.5.12.3.1.6.3.24
-- 1.3.6.1.4.1.37950.1.1.5.12.3.1.6.3.24
-- 1.3.6.1.4.1.37950.1.1.5.12.3.1.6.3.24
-- 1.3.6.1.4.1.37950.1.1.5.12.3.1.6.3.24
		-- 1.3.6.1.4.1.37950.1.1.5.12.3.1.6.3.24
		priConnTranslationEnable OBJECT-TYPE
			SYNTAX INTEGER
				{
				disable(0),
				enable(1)
				}
			MAX-ACCESS read-write
			STATUS current
			DESCRIPTION
				"Description."
			::= { priWanConnCfg 24 }

		
--          1.3.6.1.4.1.37950.1.1.5.12.3.1.6.3.25
-- 1.3.6.1.4.1.37950.1.1.5.12.3.1.6.3.25
-- 1.3.6.1.4.1.37950.1.1.5.12.3.1.6.3.25
-- 1.3.6.1.4.1.37950.1.1.5.12.3.1.6.3.25
-- 1.3.6.1.4.1.37950.1.1.5.12.3.1.6.3.25
-- 1.3.6.1.4.1.37950.1.1.5.12.3.1.6.3.25
-- 1.3.6.1.4.1.37950.1.1.5.12.3.1.6.3.25
-- 1.3.6.1.4.1.37950.1.1.5.12.3.1.6.3.25
-- 1.3.6.1.4.1.37950.1.1.5.12.3.1.6.3.25
		-- 1.3.6.1.4.1.37950.1.1.5.12.3.1.6.3.25
		priConnTranslationVlan OBJECT-TYPE
			SYNTAX INTEGER (0..4095)
			MAX-ACCESS read-write
			STATUS current
			DESCRIPTION
				"Description."
			::= { priWanConnCfg 25 }

		
--          1.3.6.1.4.1.37950.1.1.5.12.3.1.6.3.26
-- 1.3.6.1.4.1.37950.1.1.5.12.3.1.6.3.26
-- 1.3.6.1.4.1.37950.1.1.5.12.3.1.6.3.26
-- 1.3.6.1.4.1.37950.1.1.5.12.3.1.6.3.26
-- 1.3.6.1.4.1.37950.1.1.5.12.3.1.6.3.26
-- 1.3.6.1.4.1.37950.1.1.5.12.3.1.6.3.26
-- 1.3.6.1.4.1.37950.1.1.5.12.3.1.6.3.26
-- 1.3.6.1.4.1.37950.1.1.5.12.3.1.6.3.26
-- 1.3.6.1.4.1.37950.1.1.5.12.3.1.6.3.26
		-- 1.3.6.1.4.1.37950.1.1.5.12.3.1.6.3.26
		priConnTranslationCos OBJECT-TYPE
			SYNTAX INTEGER (0..7)
			MAX-ACCESS read-write
			STATUS current
			DESCRIPTION
				"Description."
			::= { priWanConnCfg 26 }

		
--          1.3.6.1.4.1.37950.1.1.5.12.3.1.6.3.27
-- 1.3.6.1.4.1.37950.1.1.5.12.3.1.6.3.27
-- 1.3.6.1.4.1.37950.1.1.5.12.3.1.6.3.27
-- 1.3.6.1.4.1.37950.1.1.5.12.3.1.6.3.27
-- 1.3.6.1.4.1.37950.1.1.5.12.3.1.6.3.27
-- 1.3.6.1.4.1.37950.1.1.5.12.3.1.6.3.27
-- 1.3.6.1.4.1.37950.1.1.5.12.3.1.6.3.27
-- 1.3.6.1.4.1.37950.1.1.5.12.3.1.6.3.27
-- 1.3.6.1.4.1.37950.1.1.5.12.3.1.6.3.27
		-- 1.3.6.1.4.1.37950.1.1.5.12.3.1.6.3.27
		priConnQinqEnable OBJECT-TYPE
			SYNTAX INTEGER
				{
				disable(0),
				enable(1)
				}
			MAX-ACCESS read-write
			STATUS current
			DESCRIPTION
				"Description."
			::= { priWanConnCfg 27 }

		
--          1.3.6.1.4.1.37950.1.1.5.12.3.1.6.3.28
-- 1.3.6.1.4.1.37950.1.1.5.12.3.1.6.3.28
-- 1.3.6.1.4.1.37950.1.1.5.12.3.1.6.3.28
-- 1.3.6.1.4.1.37950.1.1.5.12.3.1.6.3.28
-- 1.3.6.1.4.1.37950.1.1.5.12.3.1.6.3.28
-- 1.3.6.1.4.1.37950.1.1.5.12.3.1.6.3.28
-- 1.3.6.1.4.1.37950.1.1.5.12.3.1.6.3.28
-- 1.3.6.1.4.1.37950.1.1.5.12.3.1.6.3.28
-- 1.3.6.1.4.1.37950.1.1.5.12.3.1.6.3.28
		-- 1.3.6.1.4.1.37950.1.1.5.12.3.1.6.3.28
		priConnQinqTpid OBJECT-TYPE
			SYNTAX Integer32 (0..65534)
			MAX-ACCESS read-write
			STATUS current
			DESCRIPTION
				"Description."
			::= { priWanConnCfg 28 }

		
--          1.3.6.1.4.1.37950.1.1.5.12.3.1.6.3.29
-- 1.3.6.1.4.1.37950.1.1.5.12.3.1.6.3.29
-- 1.3.6.1.4.1.37950.1.1.5.12.3.1.6.3.29
-- 1.3.6.1.4.1.37950.1.1.5.12.3.1.6.3.29
-- 1.3.6.1.4.1.37950.1.1.5.12.3.1.6.3.29
-- 1.3.6.1.4.1.37950.1.1.5.12.3.1.6.3.29
-- 1.3.6.1.4.1.37950.1.1.5.12.3.1.6.3.29
-- 1.3.6.1.4.1.37950.1.1.5.12.3.1.6.3.29
-- 1.3.6.1.4.1.37950.1.1.5.12.3.1.6.3.29
		-- 1.3.6.1.4.1.37950.1.1.5.12.3.1.6.3.29
		priConnWanSvlan OBJECT-TYPE
			SYNTAX INTEGER (0..4095)
			MAX-ACCESS read-write
			STATUS current
			DESCRIPTION
				"Description."
			::= { priWanConnCfg 29 }

		
--          1.3.6.1.4.1.37950.1.1.5.12.3.1.6.3.30
-- 1.3.6.1.4.1.37950.1.1.5.12.3.1.6.3.30
-- 1.3.6.1.4.1.37950.1.1.5.12.3.1.6.3.30
-- 1.3.6.1.4.1.37950.1.1.5.12.3.1.6.3.30
-- 1.3.6.1.4.1.37950.1.1.5.12.3.1.6.3.30
-- 1.3.6.1.4.1.37950.1.1.5.12.3.1.6.3.30
-- 1.3.6.1.4.1.37950.1.1.5.12.3.1.6.3.30
-- 1.3.6.1.4.1.37950.1.1.5.12.3.1.6.3.30
-- 1.3.6.1.4.1.37950.1.1.5.12.3.1.6.3.30
		-- 1.3.6.1.4.1.37950.1.1.5.12.3.1.6.3.30
		priConnSvlanCos OBJECT-TYPE
			SYNTAX INTEGER (0..7)
			MAX-ACCESS read-write
			STATUS current
			DESCRIPTION
				"Description."
			::= { priWanConnCfg 30 }

		
--          1.3.6.1.4.1.37950.1.1.5.12.3.1.6.3.31
-- 1.3.6.1.4.1.37950.1.1.5.12.3.1.6.3.31
-- 1.3.6.1.4.1.37950.1.1.5.12.3.1.6.3.31
-- 1.3.6.1.4.1.37950.1.1.5.12.3.1.6.3.31
-- 1.3.6.1.4.1.37950.1.1.5.12.3.1.6.3.31
-- 1.3.6.1.4.1.37950.1.1.5.12.3.1.6.3.31
-- 1.3.6.1.4.1.37950.1.1.5.12.3.1.6.3.31
-- 1.3.6.1.4.1.37950.1.1.5.12.3.1.6.3.31
-- 1.3.6.1.4.1.37950.1.1.5.12.3.1.6.3.31
		-- 1.3.6.1.4.1.37950.1.1.5.12.3.1.6.3.31
		priConnCfgAction OBJECT-TYPE
			SYNTAX INTEGER { add(1) }
			MAX-ACCESS read-write
			STATUS current
			DESCRIPTION
				"Description."
			::= { priWanConnCfg 31 }

		
--         1.3.6.1.4.1.37950.1.1.5.12.3.1.6.3.32
-- 1.3.6.1.4.1.37950.1.1.5.12.3.1.6.3.32
-- 1.3.6.1.4.1.37950.1.1.5.12.3.1.6.3.32
-- 1.3.6.1.4.1.37950.1.1.5.12.3.1.6.3.32
-- 1.3.6.1.4.1.37950.1.1.5.12.3.1.6.3.32
-- 1.3.6.1.4.1.37950.1.1.5.12.3.1.6.3.32
-- 1.3.6.1.4.1.37950.1.1.5.12.3.1.6.3.32
-- 1.3.6.1.4.1.37950.1.1.5.12.3.1.6.3.32
		-- 1.3.6.1.4.1.37950.1.1.5.12.3.1.6.3.32
		priConnRouteMtu OBJECT-TYPE
			SYNTAX Integer32 (0 | 576..1500)
			MAX-ACCESS read-write
			STATUS current
			DESCRIPTION
				"Description."
			::= { priWanConnCfg 32 }

		
--          1.3.6.1.4.1.37950.1.1.5.12.3.1.6.4
-- 1.3.6.1.4.1.37950.1.1.5.12.3.1.6.4
-- 1.3.6.1.4.1.37950.1.1.5.12.3.1.6.4
-- 1.3.6.1.4.1.37950.1.1.5.12.3.1.6.4
-- 1.3.6.1.4.1.37950.1.1.5.12.3.1.6.4
-- 1.3.6.1.4.1.37950.1.1.5.12.3.1.6.4
-- 1.3.6.1.4.1.37950.1.1.5.12.3.1.6.4
-- 1.3.6.1.4.1.37950.1.1.5.12.3.1.6.4
-- 1.3.6.1.4.1.37950.1.1.5.12.3.1.6.4
		-- 1.3.6.1.4.1.37950.1.1.5.12.3.1.6.4
		priWanConnCommit OBJECT IDENTIFIER ::= { onuPriWanConn 4 }

		
--          1.3.6.1.4.1.37950.1.1.5.12.3.1.6.4.1
-- 1.3.6.1.4.1.37950.1.1.5.12.3.1.6.4.1
-- 1.3.6.1.4.1.37950.1.1.5.12.3.1.6.4.1
-- 1.3.6.1.4.1.37950.1.1.5.12.3.1.6.4.1
-- 1.3.6.1.4.1.37950.1.1.5.12.3.1.6.4.1
-- 1.3.6.1.4.1.37950.1.1.5.12.3.1.6.4.1
-- 1.3.6.1.4.1.37950.1.1.5.12.3.1.6.4.1
-- 1.3.6.1.4.1.37950.1.1.5.12.3.1.6.4.1
-- 1.3.6.1.4.1.37950.1.1.5.12.3.1.6.4.1
		-- 1.3.6.1.4.1.37950.1.1.5.12.3.1.6.4.1
		priConnCommitPon OBJECT-TYPE
			SYNTAX INTEGER (1..16)
			MAX-ACCESS read-write
			STATUS current
			DESCRIPTION
				"Description."
			::= { priWanConnCommit 1 }

		
--          1.3.6.1.4.1.37950.1.1.5.12.3.1.6.4.2
-- 1.3.6.1.4.1.37950.1.1.5.12.3.1.6.4.2
-- 1.3.6.1.4.1.37950.1.1.5.12.3.1.6.4.2
-- 1.3.6.1.4.1.37950.1.1.5.12.3.1.6.4.2
-- 1.3.6.1.4.1.37950.1.1.5.12.3.1.6.4.2
-- 1.3.6.1.4.1.37950.1.1.5.12.3.1.6.4.2
-- 1.3.6.1.4.1.37950.1.1.5.12.3.1.6.4.2
-- 1.3.6.1.4.1.37950.1.1.5.12.3.1.6.4.2
-- 1.3.6.1.4.1.37950.1.1.5.12.3.1.6.4.2
		-- 1.3.6.1.4.1.37950.1.1.5.12.3.1.6.4.2
		priConnCommitOnu OBJECT-TYPE
			SYNTAX INTEGER (1..65535)
			MAX-ACCESS read-write
			STATUS current
			DESCRIPTION
				"Description."
			::= { priWanConnCommit 2 }

		
--          1.3.6.1.4.1.37950.1.1.5.12.3.1.6.4.3
-- 1.3.6.1.4.1.37950.1.1.5.12.3.1.6.4.3
-- 1.3.6.1.4.1.37950.1.1.5.12.3.1.6.4.3
-- 1.3.6.1.4.1.37950.1.1.5.12.3.1.6.4.3
-- 1.3.6.1.4.1.37950.1.1.5.12.3.1.6.4.3
-- 1.3.6.1.4.1.37950.1.1.5.12.3.1.6.4.3
-- 1.3.6.1.4.1.37950.1.1.5.12.3.1.6.4.3
-- 1.3.6.1.4.1.37950.1.1.5.12.3.1.6.4.3
-- 1.3.6.1.4.1.37950.1.1.5.12.3.1.6.4.3
		-- 1.3.6.1.4.1.37950.1.1.5.12.3.1.6.4.3
		priConnCommitAction OBJECT-TYPE
			SYNTAX INTEGER
				{
				commit(1),
				remove(2)
				}
			MAX-ACCESS read-write
			STATUS current
			DESCRIPTION
				"Description."
			::= { priWanConnCommit 3 }

		
--          1.3.6.1.4.1.37950.1.1.5.12.3.1.7
-- 1.3.6.1.4.1.37950.1.1.5.12.3.1.7
-- 1.3.6.1.4.1.37950.1.1.5.12.3.1.7
-- 1.3.6.1.4.1.37950.1.1.5.12.3.1.7
-- 1.3.6.1.4.1.37950.1.1.5.12.3.1.7
-- 1.3.6.1.4.1.37950.1.1.5.12.3.1.7
-- 1.3.6.1.4.1.37950.1.1.5.12.3.1.7
-- 1.3.6.1.4.1.37950.1.1.5.12.3.1.7
-- 1.3.6.1.4.1.37950.1.1.5.12.3.1.7
		-- 1.3.6.1.4.1.37950.1.1.5.12.3.1.7
		onuPriPortIsolate OBJECT IDENTIFIER ::= { onuPriGlobalCfg 7 }

		
--          1.3.6.1.4.1.37950.1.1.5.12.3.1.7.1
-- 1.3.6.1.4.1.37950.1.1.5.12.3.1.7.1
-- 1.3.6.1.4.1.37950.1.1.5.12.3.1.7.1
-- 1.3.6.1.4.1.37950.1.1.5.12.3.1.7.1
-- 1.3.6.1.4.1.37950.1.1.5.12.3.1.7.1
-- 1.3.6.1.4.1.37950.1.1.5.12.3.1.7.1
-- 1.3.6.1.4.1.37950.1.1.5.12.3.1.7.1
-- 1.3.6.1.4.1.37950.1.1.5.12.3.1.7.1
-- 1.3.6.1.4.1.37950.1.1.5.12.3.1.7.1
		-- 1.3.6.1.4.1.37950.1.1.5.12.3.1.7.1
		priPortIsolatePon OBJECT-TYPE
			SYNTAX INTEGER (1..16)
			MAX-ACCESS read-write
			STATUS current
			DESCRIPTION
				"Description."
			::= { onuPriPortIsolate 1 }

		
--          1.3.6.1.4.1.37950.1.1.5.12.3.1.7.2
-- 1.3.6.1.4.1.37950.1.1.5.12.3.1.7.2
-- 1.3.6.1.4.1.37950.1.1.5.12.3.1.7.2
-- 1.3.6.1.4.1.37950.1.1.5.12.3.1.7.2
-- 1.3.6.1.4.1.37950.1.1.5.12.3.1.7.2
-- 1.3.6.1.4.1.37950.1.1.5.12.3.1.7.2
-- 1.3.6.1.4.1.37950.1.1.5.12.3.1.7.2
-- 1.3.6.1.4.1.37950.1.1.5.12.3.1.7.2
-- 1.3.6.1.4.1.37950.1.1.5.12.3.1.7.2
		-- 1.3.6.1.4.1.37950.1.1.5.12.3.1.7.2
		priPortIsolateOnu OBJECT-TYPE
			SYNTAX INTEGER (1..65535)
			MAX-ACCESS read-write
			STATUS current
			DESCRIPTION
				"Description."
			::= { onuPriPortIsolate 2 }

		
--          1.3.6.1.4.1.37950.1.1.5.12.3.1.7.3
-- 1.3.6.1.4.1.37950.1.1.5.12.3.1.7.3
-- 1.3.6.1.4.1.37950.1.1.5.12.3.1.7.3
-- 1.3.6.1.4.1.37950.1.1.5.12.3.1.7.3
-- 1.3.6.1.4.1.37950.1.1.5.12.3.1.7.3
-- 1.3.6.1.4.1.37950.1.1.5.12.3.1.7.3
-- 1.3.6.1.4.1.37950.1.1.5.12.3.1.7.3
-- 1.3.6.1.4.1.37950.1.1.5.12.3.1.7.3
-- 1.3.6.1.4.1.37950.1.1.5.12.3.1.7.3
		-- 1.3.6.1.4.1.37950.1.1.5.12.3.1.7.3
		priPortIsolate OBJECT-TYPE
			SYNTAX INTEGER
				{
				disable(0),
				enable(1)
				}
			MAX-ACCESS read-write
			STATUS current
			DESCRIPTION
				"Description."
			::= { onuPriPortIsolate 3 }

		
--          1.3.6.1.4.1.37950.1.1.5.12.3.1.7.4
-- 1.3.6.1.4.1.37950.1.1.5.12.3.1.7.4
-- 1.3.6.1.4.1.37950.1.1.5.12.3.1.7.4
-- 1.3.6.1.4.1.37950.1.1.5.12.3.1.7.4
-- 1.3.6.1.4.1.37950.1.1.5.12.3.1.7.4
-- 1.3.6.1.4.1.37950.1.1.5.12.3.1.7.4
-- 1.3.6.1.4.1.37950.1.1.5.12.3.1.7.4
-- 1.3.6.1.4.1.37950.1.1.5.12.3.1.7.4
-- 1.3.6.1.4.1.37950.1.1.5.12.3.1.7.4
		-- 1.3.6.1.4.1.37950.1.1.5.12.3.1.7.4
		priPortIsolateAction OBJECT-TYPE
			SYNTAX INTEGER
				{
				commit(1),
				remove(2)
				}
			MAX-ACCESS read-write
			STATUS current
			DESCRIPTION
				"Description."
			::= { onuPriPortIsolate 4 }

		
--          1.3.6.1.4.1.37950.1.1.5.12.3.1.8
-- 1.3.6.1.4.1.37950.1.1.5.12.3.1.8
-- 1.3.6.1.4.1.37950.1.1.5.12.3.1.8
-- 1.3.6.1.4.1.37950.1.1.5.12.3.1.8
-- 1.3.6.1.4.1.37950.1.1.5.12.3.1.8
-- 1.3.6.1.4.1.37950.1.1.5.12.3.1.8
-- 1.3.6.1.4.1.37950.1.1.5.12.3.1.8
-- 1.3.6.1.4.1.37950.1.1.5.12.3.1.8
-- 1.3.6.1.4.1.37950.1.1.5.12.3.1.8
		-- 1.3.6.1.4.1.37950.1.1.5.12.3.1.8
		onuPriFactoryReset OBJECT IDENTIFIER ::= { onuPriGlobalCfg 8 }

		
--          1.3.6.1.4.1.37950.1.1.5.12.3.1.8.1
-- 1.3.6.1.4.1.37950.1.1.5.12.3.1.8.1
-- 1.3.6.1.4.1.37950.1.1.5.12.3.1.8.1
-- 1.3.6.1.4.1.37950.1.1.5.12.3.1.8.1
-- 1.3.6.1.4.1.37950.1.1.5.12.3.1.8.1
-- 1.3.6.1.4.1.37950.1.1.5.12.3.1.8.1
-- 1.3.6.1.4.1.37950.1.1.5.12.3.1.8.1
-- 1.3.6.1.4.1.37950.1.1.5.12.3.1.8.1
-- 1.3.6.1.4.1.37950.1.1.5.12.3.1.8.1
		-- 1.3.6.1.4.1.37950.1.1.5.12.3.1.8.1
		priFactoryResetPon OBJECT-TYPE
			SYNTAX INTEGER (1..16)
			MAX-ACCESS read-write
			STATUS current
			DESCRIPTION
				"Description."
			::= { onuPriFactoryReset 1 }

		
--          1.3.6.1.4.1.37950.1.1.5.12.3.1.8.2
-- 1.3.6.1.4.1.37950.1.1.5.12.3.1.8.2
-- 1.3.6.1.4.1.37950.1.1.5.12.3.1.8.2
-- 1.3.6.1.4.1.37950.1.1.5.12.3.1.8.2
-- 1.3.6.1.4.1.37950.1.1.5.12.3.1.8.2
-- 1.3.6.1.4.1.37950.1.1.5.12.3.1.8.2
-- 1.3.6.1.4.1.37950.1.1.5.12.3.1.8.2
-- 1.3.6.1.4.1.37950.1.1.5.12.3.1.8.2
-- 1.3.6.1.4.1.37950.1.1.5.12.3.1.8.2
		-- 1.3.6.1.4.1.37950.1.1.5.12.3.1.8.2
		priFactoryResetOnu OBJECT-TYPE
			SYNTAX INTEGER (1..65535)
			MAX-ACCESS read-write
			STATUS current
			DESCRIPTION
				"Description."
			::= { onuPriFactoryReset 2 }

		
--          1.3.6.1.4.1.37950.1.1.5.12.3.1.8.3
-- 1.3.6.1.4.1.37950.1.1.5.12.3.1.8.3
-- 1.3.6.1.4.1.37950.1.1.5.12.3.1.8.3
-- 1.3.6.1.4.1.37950.1.1.5.12.3.1.8.3
-- 1.3.6.1.4.1.37950.1.1.5.12.3.1.8.3
-- 1.3.6.1.4.1.37950.1.1.5.12.3.1.8.3
-- 1.3.6.1.4.1.37950.1.1.5.12.3.1.8.3
-- 1.3.6.1.4.1.37950.1.1.5.12.3.1.8.3
-- 1.3.6.1.4.1.37950.1.1.5.12.3.1.8.3
		-- 1.3.6.1.4.1.37950.1.1.5.12.3.1.8.3
		priFactoryReset OBJECT-TYPE
			SYNTAX INTEGER { commit(1) }
			MAX-ACCESS read-write
			STATUS current
			DESCRIPTION
				"Description."
			::= { onuPriFactoryReset 3 }

		
--          1.3.6.1.4.1.37950.1.1.5.12.3.1.9
-- 1.3.6.1.4.1.37950.1.1.5.12.3.1.9
-- 1.3.6.1.4.1.37950.1.1.5.12.3.1.9
-- 1.3.6.1.4.1.37950.1.1.5.12.3.1.9
-- 1.3.6.1.4.1.37950.1.1.5.12.3.1.9
-- 1.3.6.1.4.1.37950.1.1.5.12.3.1.9
-- 1.3.6.1.4.1.37950.1.1.5.12.3.1.9
-- 1.3.6.1.4.1.37950.1.1.5.12.3.1.9
-- 1.3.6.1.4.1.37950.1.1.5.12.3.1.9
		-- 1.3.6.1.4.1.37950.1.1.5.12.3.1.9
		onuPriMacClean OBJECT IDENTIFIER ::= { onuPriGlobalCfg 9 }

		
--          1.3.6.1.4.1.37950.1.1.5.12.3.1.9.1
-- 1.3.6.1.4.1.37950.1.1.5.12.3.1.9.1
-- 1.3.6.1.4.1.37950.1.1.5.12.3.1.9.1
-- 1.3.6.1.4.1.37950.1.1.5.12.3.1.9.1
-- 1.3.6.1.4.1.37950.1.1.5.12.3.1.9.1
-- 1.3.6.1.4.1.37950.1.1.5.12.3.1.9.1
-- 1.3.6.1.4.1.37950.1.1.5.12.3.1.9.1
-- 1.3.6.1.4.1.37950.1.1.5.12.3.1.9.1
-- 1.3.6.1.4.1.37950.1.1.5.12.3.1.9.1
		-- 1.3.6.1.4.1.37950.1.1.5.12.3.1.9.1
		priMacCleanPon OBJECT-TYPE
			SYNTAX INTEGER (1..816)
			MAX-ACCESS read-write
			STATUS current
			DESCRIPTION
				"Description."
			::= { onuPriMacClean 1 }

		
--          1.3.6.1.4.1.37950.1.1.5.12.3.1.9.2
-- 1.3.6.1.4.1.37950.1.1.5.12.3.1.9.2
-- 1.3.6.1.4.1.37950.1.1.5.12.3.1.9.2
-- 1.3.6.1.4.1.37950.1.1.5.12.3.1.9.2
-- 1.3.6.1.4.1.37950.1.1.5.12.3.1.9.2
-- 1.3.6.1.4.1.37950.1.1.5.12.3.1.9.2
-- 1.3.6.1.4.1.37950.1.1.5.12.3.1.9.2
-- 1.3.6.1.4.1.37950.1.1.5.12.3.1.9.2
-- 1.3.6.1.4.1.37950.1.1.5.12.3.1.9.2
		-- 1.3.6.1.4.1.37950.1.1.5.12.3.1.9.2
		priMacCleanOnu OBJECT-TYPE
			SYNTAX INTEGER (1..65535)
			MAX-ACCESS read-write
			STATUS current
			DESCRIPTION
				"Description."
			::= { onuPriMacClean 2 }

		
--          1.3.6.1.4.1.37950.1.1.5.12.3.1.9.3
-- 1.3.6.1.4.1.37950.1.1.5.12.3.1.9.3
-- 1.3.6.1.4.1.37950.1.1.5.12.3.1.9.3
-- 1.3.6.1.4.1.37950.1.1.5.12.3.1.9.3
-- 1.3.6.1.4.1.37950.1.1.5.12.3.1.9.3
-- 1.3.6.1.4.1.37950.1.1.5.12.3.1.9.3
-- 1.3.6.1.4.1.37950.1.1.5.12.3.1.9.3
-- 1.3.6.1.4.1.37950.1.1.5.12.3.1.9.3
-- 1.3.6.1.4.1.37950.1.1.5.12.3.1.9.3
		-- 1.3.6.1.4.1.37950.1.1.5.12.3.1.9.3
		priMacClean OBJECT-TYPE
			SYNTAX INTEGER { commit(1) }
			MAX-ACCESS read-write
			STATUS current
			DESCRIPTION
				"Description."
			::= { onuPriMacClean 3 }

		
--          1.3.6.1.4.1.37950.1.1.5.12.3.1.10
-- 1.3.6.1.4.1.37950.1.1.5.12.3.1.10
-- 1.3.6.1.4.1.37950.1.1.5.12.3.1.10
-- 1.3.6.1.4.1.37950.1.1.5.12.3.1.10
-- 1.3.6.1.4.1.37950.1.1.5.12.3.1.10
-- 1.3.6.1.4.1.37950.1.1.5.12.3.1.10
-- 1.3.6.1.4.1.37950.1.1.5.12.3.1.10
-- 1.3.6.1.4.1.37950.1.1.5.12.3.1.10
-- 1.3.6.1.4.1.37950.1.1.5.12.3.1.10
		-- 1.3.6.1.4.1.37950.1.1.5.12.3.1.10
		onuPriSaveConfig OBJECT IDENTIFIER ::= { onuPriGlobalCfg 10 }

		
--          1.3.6.1.4.1.37950.1.1.5.12.3.1.10.1
-- 1.3.6.1.4.1.37950.1.1.5.12.3.1.10.1
-- 1.3.6.1.4.1.37950.1.1.5.12.3.1.10.1
-- 1.3.6.1.4.1.37950.1.1.5.12.3.1.10.1
-- 1.3.6.1.4.1.37950.1.1.5.12.3.1.10.1
-- 1.3.6.1.4.1.37950.1.1.5.12.3.1.10.1
-- 1.3.6.1.4.1.37950.1.1.5.12.3.1.10.1
-- 1.3.6.1.4.1.37950.1.1.5.12.3.1.10.1
-- 1.3.6.1.4.1.37950.1.1.5.12.3.1.10.1
		-- 1.3.6.1.4.1.37950.1.1.5.12.3.1.10.1
		priSaveConfigPon OBJECT-TYPE
			SYNTAX INTEGER (1..16)
			MAX-ACCESS read-write
			STATUS current
			DESCRIPTION
				"Description."
			::= { onuPriSaveConfig 1 }

		
--          1.3.6.1.4.1.37950.1.1.5.12.3.1.10.2
-- 1.3.6.1.4.1.37950.1.1.5.12.3.1.10.2
-- 1.3.6.1.4.1.37950.1.1.5.12.3.1.10.2
-- 1.3.6.1.4.1.37950.1.1.5.12.3.1.10.2
-- 1.3.6.1.4.1.37950.1.1.5.12.3.1.10.2
-- 1.3.6.1.4.1.37950.1.1.5.12.3.1.10.2
-- 1.3.6.1.4.1.37950.1.1.5.12.3.1.10.2
-- 1.3.6.1.4.1.37950.1.1.5.12.3.1.10.2
-- 1.3.6.1.4.1.37950.1.1.5.12.3.1.10.2
		-- 1.3.6.1.4.1.37950.1.1.5.12.3.1.10.2
		priSaveConfigOnu OBJECT-TYPE
			SYNTAX INTEGER (1..65535)
			MAX-ACCESS read-write
			STATUS current
			DESCRIPTION
				"Description."
			::= { onuPriSaveConfig 2 }

		
--          1.3.6.1.4.1.37950.1.1.5.12.3.1.10.3
-- 1.3.6.1.4.1.37950.1.1.5.12.3.1.10.3
-- 1.3.6.1.4.1.37950.1.1.5.12.3.1.10.3
-- 1.3.6.1.4.1.37950.1.1.5.12.3.1.10.3
-- 1.3.6.1.4.1.37950.1.1.5.12.3.1.10.3
-- 1.3.6.1.4.1.37950.1.1.5.12.3.1.10.3
-- 1.3.6.1.4.1.37950.1.1.5.12.3.1.10.3
-- 1.3.6.1.4.1.37950.1.1.5.12.3.1.10.3
-- 1.3.6.1.4.1.37950.1.1.5.12.3.1.10.3
		-- 1.3.6.1.4.1.37950.1.1.5.12.3.1.10.3
		priSaveConfig OBJECT-TYPE
			SYNTAX INTEGER { commit(1) }
			MAX-ACCESS read-write
			STATUS current
			DESCRIPTION
				"Description."
			::= { onuPriSaveConfig 3 }

		
--          1.3.6.1.4.1.37950.1.1.5.12.3.1.11
-- 1.3.6.1.4.1.37950.1.1.5.12.3.1.11
-- 1.3.6.1.4.1.37950.1.1.5.12.3.1.11
-- 1.3.6.1.4.1.37950.1.1.5.12.3.1.11
-- 1.3.6.1.4.1.37950.1.1.5.12.3.1.11
-- 1.3.6.1.4.1.37950.1.1.5.12.3.1.11
-- 1.3.6.1.4.1.37950.1.1.5.12.3.1.11
-- 1.3.6.1.4.1.37950.1.1.5.12.3.1.11
-- 1.3.6.1.4.1.37950.1.1.5.12.3.1.11
		-- 1.3.6.1.4.1.37950.1.1.5.12.3.1.11
		onuPriVoipTimer OBJECT IDENTIFIER ::= { onuPriGlobalCfg 11 }

		
--          1.3.6.1.4.1.37950.1.1.5.12.3.1.11.1
-- 1.3.6.1.4.1.37950.1.1.5.12.3.1.11.1
-- 1.3.6.1.4.1.37950.1.1.5.12.3.1.11.1
-- 1.3.6.1.4.1.37950.1.1.5.12.3.1.11.1
-- 1.3.6.1.4.1.37950.1.1.5.12.3.1.11.1
-- 1.3.6.1.4.1.37950.1.1.5.12.3.1.11.1
-- 1.3.6.1.4.1.37950.1.1.5.12.3.1.11.1
-- 1.3.6.1.4.1.37950.1.1.5.12.3.1.11.1
-- 1.3.6.1.4.1.37950.1.1.5.12.3.1.11.1
		-- 1.3.6.1.4.1.37950.1.1.5.12.3.1.11.1
		onuPriVoipPon OBJECT-TYPE
			SYNTAX Integer32 (1..16)
			MAX-ACCESS read-write
			STATUS current
			DESCRIPTION
				"Description."
			::= { onuPriVoipTimer 1 }

		
--          1.3.6.1.4.1.37950.1.1.5.12.3.1.11.2
-- 1.3.6.1.4.1.37950.1.1.5.12.3.1.11.2
-- 1.3.6.1.4.1.37950.1.1.5.12.3.1.11.2
-- 1.3.6.1.4.1.37950.1.1.5.12.3.1.11.2
-- 1.3.6.1.4.1.37950.1.1.5.12.3.1.11.2
-- 1.3.6.1.4.1.37950.1.1.5.12.3.1.11.2
-- 1.3.6.1.4.1.37950.1.1.5.12.3.1.11.2
-- 1.3.6.1.4.1.37950.1.1.5.12.3.1.11.2
-- 1.3.6.1.4.1.37950.1.1.5.12.3.1.11.2
		-- 1.3.6.1.4.1.37950.1.1.5.12.3.1.11.2
		onuPriVoipOnu OBJECT-TYPE
			SYNTAX Integer32 (1..65535)
			MAX-ACCESS read-write
			STATUS current
			DESCRIPTION
				"Description."
			::= { onuPriVoipTimer 2 }

		
--          1.3.6.1.4.1.37950.1.1.5.12.3.1.11.3
-- 1.3.6.1.4.1.37950.1.1.5.12.3.1.11.3
-- 1.3.6.1.4.1.37950.1.1.5.12.3.1.11.3
-- 1.3.6.1.4.1.37950.1.1.5.12.3.1.11.3
-- 1.3.6.1.4.1.37950.1.1.5.12.3.1.11.3
-- 1.3.6.1.4.1.37950.1.1.5.12.3.1.11.3
-- 1.3.6.1.4.1.37950.1.1.5.12.3.1.11.3
-- 1.3.6.1.4.1.37950.1.1.5.12.3.1.11.3
-- 1.3.6.1.4.1.37950.1.1.5.12.3.1.11.3
		-- 1.3.6.1.4.1.37950.1.1.5.12.3.1.11.3
		onuPriVoipWaitTime OBJECT-TYPE
			SYNTAX Integer32 (0..254)
			MAX-ACCESS read-write
			STATUS current
			DESCRIPTION
				"Description."
			::= { onuPriVoipTimer 3 }

		
--          1.3.6.1.4.1.37950.1.1.5.12.3.1.11.4
-- 1.3.6.1.4.1.37950.1.1.5.12.3.1.11.4
-- 1.3.6.1.4.1.37950.1.1.5.12.3.1.11.4
-- 1.3.6.1.4.1.37950.1.1.5.12.3.1.11.4
-- 1.3.6.1.4.1.37950.1.1.5.12.3.1.11.4
-- 1.3.6.1.4.1.37950.1.1.5.12.3.1.11.4
-- 1.3.6.1.4.1.37950.1.1.5.12.3.1.11.4
-- 1.3.6.1.4.1.37950.1.1.5.12.3.1.11.4
-- 1.3.6.1.4.1.37950.1.1.5.12.3.1.11.4
		-- 1.3.6.1.4.1.37950.1.1.5.12.3.1.11.4
		onuPriVoipStartTimer OBJECT-TYPE
			SYNTAX Integer32 (1..65535)
			MAX-ACCESS read-write
			STATUS current
			DESCRIPTION
				"Description."
			::= { onuPriVoipTimer 4 }

		
--          1.3.6.1.4.1.37950.1.1.5.12.3.1.11.5
-- 1.3.6.1.4.1.37950.1.1.5.12.3.1.11.5
-- 1.3.6.1.4.1.37950.1.1.5.12.3.1.11.5
-- 1.3.6.1.4.1.37950.1.1.5.12.3.1.11.5
-- 1.3.6.1.4.1.37950.1.1.5.12.3.1.11.5
-- 1.3.6.1.4.1.37950.1.1.5.12.3.1.11.5
-- 1.3.6.1.4.1.37950.1.1.5.12.3.1.11.5
-- 1.3.6.1.4.1.37950.1.1.5.12.3.1.11.5
-- 1.3.6.1.4.1.37950.1.1.5.12.3.1.11.5
		-- 1.3.6.1.4.1.37950.1.1.5.12.3.1.11.5
		onuPriVoipLongTimer OBJECT-TYPE
			SYNTAX Integer32 (1..65535)
			MAX-ACCESS read-write
			STATUS current
			DESCRIPTION
				"Description."
			::= { onuPriVoipTimer 5 }

		
--          1.3.6.1.4.1.37950.1.1.5.12.3.1.11.6
-- 1.3.6.1.4.1.37950.1.1.5.12.3.1.11.6
-- 1.3.6.1.4.1.37950.1.1.5.12.3.1.11.6
-- 1.3.6.1.4.1.37950.1.1.5.12.3.1.11.6
-- 1.3.6.1.4.1.37950.1.1.5.12.3.1.11.6
-- 1.3.6.1.4.1.37950.1.1.5.12.3.1.11.6
-- 1.3.6.1.4.1.37950.1.1.5.12.3.1.11.6
-- 1.3.6.1.4.1.37950.1.1.5.12.3.1.11.6
-- 1.3.6.1.4.1.37950.1.1.5.12.3.1.11.6
		-- 1.3.6.1.4.1.37950.1.1.5.12.3.1.11.6
		onuPriVoipShortTimer OBJECT-TYPE
			SYNTAX Integer32 (1..65535)
			MAX-ACCESS read-write
			STATUS current
			DESCRIPTION
				"Description."
			::= { onuPriVoipTimer 6 }

		
--          1.3.6.1.4.1.37950.1.1.5.12.3.1.11.7
-- 1.3.6.1.4.1.37950.1.1.5.12.3.1.11.7
-- 1.3.6.1.4.1.37950.1.1.5.12.3.1.11.7
-- 1.3.6.1.4.1.37950.1.1.5.12.3.1.11.7
-- 1.3.6.1.4.1.37950.1.1.5.12.3.1.11.7
-- 1.3.6.1.4.1.37950.1.1.5.12.3.1.11.7
-- 1.3.6.1.4.1.37950.1.1.5.12.3.1.11.7
-- 1.3.6.1.4.1.37950.1.1.5.12.3.1.11.7
-- 1.3.6.1.4.1.37950.1.1.5.12.3.1.11.7
		-- 1.3.6.1.4.1.37950.1.1.5.12.3.1.11.7
		onuPriVoipDigitmapNotify OBJECT-TYPE
			SYNTAX INTEGER
				{
				disable(0),
				enable(1)
				}
			MAX-ACCESS read-write
			STATUS current
			DESCRIPTION
				"Description."
			::= { onuPriVoipTimer 7 }

		
--          1.3.6.1.4.1.37950.1.1.5.12.3.1.11.8
-- 1.3.6.1.4.1.37950.1.1.5.12.3.1.11.8
-- 1.3.6.1.4.1.37950.1.1.5.12.3.1.11.8
-- 1.3.6.1.4.1.37950.1.1.5.12.3.1.11.8
-- 1.3.6.1.4.1.37950.1.1.5.12.3.1.11.8
-- 1.3.6.1.4.1.37950.1.1.5.12.3.1.11.8
-- 1.3.6.1.4.1.37950.1.1.5.12.3.1.11.8
-- 1.3.6.1.4.1.37950.1.1.5.12.3.1.11.8
-- 1.3.6.1.4.1.37950.1.1.5.12.3.1.11.8
		-- 1.3.6.1.4.1.37950.1.1.5.12.3.1.11.8
		onuPriVoipAction OBJECT-TYPE
			SYNTAX INTEGER
				{
				commit(1),
				remove(2)
				}
			MAX-ACCESS read-write
			STATUS current
			DESCRIPTION
				"Description."
			::= { onuPriVoipTimer 8 }

		
--          1.3.6.1.4.1.37950.1.1.5.12.3.1.12
-- 1.3.6.1.4.1.37950.1.1.5.12.3.1.12
-- 1.3.6.1.4.1.37950.1.1.5.12.3.1.12
-- 1.3.6.1.4.1.37950.1.1.5.12.3.1.12
-- 1.3.6.1.4.1.37950.1.1.5.12.3.1.12
-- 1.3.6.1.4.1.37950.1.1.5.12.3.1.12
-- 1.3.6.1.4.1.37950.1.1.5.12.3.1.12
-- 1.3.6.1.4.1.37950.1.1.5.12.3.1.12
-- 1.3.6.1.4.1.37950.1.1.5.12.3.1.12
		-- 1.3.6.1.4.1.37950.1.1.5.12.3.1.12
		onuPriDhcpServer OBJECT IDENTIFIER ::= { onuPriGlobalCfg 12 }

		
--          1.3.6.1.4.1.37950.1.1.5.12.3.1.12.1
-- 1.3.6.1.4.1.37950.1.1.5.12.3.1.12.1
-- 1.3.6.1.4.1.37950.1.1.5.12.3.1.12.1
-- 1.3.6.1.4.1.37950.1.1.5.12.3.1.12.1
-- 1.3.6.1.4.1.37950.1.1.5.12.3.1.12.1
-- 1.3.6.1.4.1.37950.1.1.5.12.3.1.12.1
-- 1.3.6.1.4.1.37950.1.1.5.12.3.1.12.1
-- 1.3.6.1.4.1.37950.1.1.5.12.3.1.12.1
-- 1.3.6.1.4.1.37950.1.1.5.12.3.1.12.1
		-- 1.3.6.1.4.1.37950.1.1.5.12.3.1.12.1
		onuPriDhcpServerPon OBJECT-TYPE
			SYNTAX Integer32 (1..16)
			MAX-ACCESS read-write
			STATUS current
			DESCRIPTION
				"Description."
			::= { onuPriDhcpServer 1 }

		
--          1.3.6.1.4.1.37950.1.1.5.12.3.1.12.2
-- 1.3.6.1.4.1.37950.1.1.5.12.3.1.12.2
-- 1.3.6.1.4.1.37950.1.1.5.12.3.1.12.2
-- 1.3.6.1.4.1.37950.1.1.5.12.3.1.12.2
-- 1.3.6.1.4.1.37950.1.1.5.12.3.1.12.2
-- 1.3.6.1.4.1.37950.1.1.5.12.3.1.12.2
-- 1.3.6.1.4.1.37950.1.1.5.12.3.1.12.2
-- 1.3.6.1.4.1.37950.1.1.5.12.3.1.12.2
-- 1.3.6.1.4.1.37950.1.1.5.12.3.1.12.2
		-- 1.3.6.1.4.1.37950.1.1.5.12.3.1.12.2
		onuPriDhcpServerOnu OBJECT-TYPE
			SYNTAX Integer32 (1..65535)
			MAX-ACCESS read-write
			STATUS current
			DESCRIPTION
				"Description."
			::= { onuPriDhcpServer 2 }

		
--          1.3.6.1.4.1.37950.1.1.5.12.3.1.12.3
-- 1.3.6.1.4.1.37950.1.1.5.12.3.1.12.3
-- 1.3.6.1.4.1.37950.1.1.5.12.3.1.12.3
-- 1.3.6.1.4.1.37950.1.1.5.12.3.1.12.3
-- 1.3.6.1.4.1.37950.1.1.5.12.3.1.12.3
-- 1.3.6.1.4.1.37950.1.1.5.12.3.1.12.3
-- 1.3.6.1.4.1.37950.1.1.5.12.3.1.12.3
-- 1.3.6.1.4.1.37950.1.1.5.12.3.1.12.3
-- 1.3.6.1.4.1.37950.1.1.5.12.3.1.12.3
		-- 1.3.6.1.4.1.37950.1.1.5.12.3.1.12.3
		onuPriDhcpLanIp OBJECT-TYPE
			SYNTAX IpAddress
			MAX-ACCESS read-write
			STATUS current
			DESCRIPTION
				"Description."
			::= { onuPriDhcpServer 3 }

		
--          1.3.6.1.4.1.37950.1.1.5.12.3.1.12.4
-- 1.3.6.1.4.1.37950.1.1.5.12.3.1.12.4
-- 1.3.6.1.4.1.37950.1.1.5.12.3.1.12.4
-- 1.3.6.1.4.1.37950.1.1.5.12.3.1.12.4
-- 1.3.6.1.4.1.37950.1.1.5.12.3.1.12.4
-- 1.3.6.1.4.1.37950.1.1.5.12.3.1.12.4
-- 1.3.6.1.4.1.37950.1.1.5.12.3.1.12.4
-- 1.3.6.1.4.1.37950.1.1.5.12.3.1.12.4
-- 1.3.6.1.4.1.37950.1.1.5.12.3.1.12.4
		-- 1.3.6.1.4.1.37950.1.1.5.12.3.1.12.4
		onuPriDhcpLanMask OBJECT-TYPE
			SYNTAX IpAddress
			MAX-ACCESS read-write
			STATUS current
			DESCRIPTION
				"Description."
			::= { onuPriDhcpServer 4 }

		
--          1.3.6.1.4.1.37950.1.1.5.12.3.1.12.5
-- 1.3.6.1.4.1.37950.1.1.5.12.3.1.12.5
-- 1.3.6.1.4.1.37950.1.1.5.12.3.1.12.5
-- 1.3.6.1.4.1.37950.1.1.5.12.3.1.12.5
-- 1.3.6.1.4.1.37950.1.1.5.12.3.1.12.5
-- 1.3.6.1.4.1.37950.1.1.5.12.3.1.12.5
-- 1.3.6.1.4.1.37950.1.1.5.12.3.1.12.5
-- 1.3.6.1.4.1.37950.1.1.5.12.3.1.12.5
-- 1.3.6.1.4.1.37950.1.1.5.12.3.1.12.5
		-- 1.3.6.1.4.1.37950.1.1.5.12.3.1.12.5
		onuPriDhcpEnable OBJECT-TYPE
			SYNTAX INTEGER
				{
				disable(0),
				enable(1),
				relay(2)
				}
			MAX-ACCESS read-write
			STATUS current
			DESCRIPTION
				"Description."
			::= { onuPriDhcpServer 5 }

		
--          1.3.6.1.4.1.37950.1.1.5.12.3.1.12.6
-- 1.3.6.1.4.1.37950.1.1.5.12.3.1.12.6
-- 1.3.6.1.4.1.37950.1.1.5.12.3.1.12.6
-- 1.3.6.1.4.1.37950.1.1.5.12.3.1.12.6
-- 1.3.6.1.4.1.37950.1.1.5.12.3.1.12.6
-- 1.3.6.1.4.1.37950.1.1.5.12.3.1.12.6
-- 1.3.6.1.4.1.37950.1.1.5.12.3.1.12.6
-- 1.3.6.1.4.1.37950.1.1.5.12.3.1.12.6
-- 1.3.6.1.4.1.37950.1.1.5.12.3.1.12.6
		-- 1.3.6.1.4.1.37950.1.1.5.12.3.1.12.6
		onuPriDhcpLease OBJECT-TYPE
			SYNTAX Unsigned32 (0..4294967295)
			MAX-ACCESS read-write
			STATUS current
			DESCRIPTION
				"Description."
			::= { onuPriDhcpServer 6 }

		
--          1.3.6.1.4.1.37950.1.1.5.12.3.1.12.7
-- 1.3.6.1.4.1.37950.1.1.5.12.3.1.12.7
-- 1.3.6.1.4.1.37950.1.1.5.12.3.1.12.7
-- 1.3.6.1.4.1.37950.1.1.5.12.3.1.12.7
-- 1.3.6.1.4.1.37950.1.1.5.12.3.1.12.7
-- 1.3.6.1.4.1.37950.1.1.5.12.3.1.12.7
-- 1.3.6.1.4.1.37950.1.1.5.12.3.1.12.7
-- 1.3.6.1.4.1.37950.1.1.5.12.3.1.12.7
-- 1.3.6.1.4.1.37950.1.1.5.12.3.1.12.7
		-- 1.3.6.1.4.1.37950.1.1.5.12.3.1.12.7
		onuPriDhcpBeginIp OBJECT-TYPE
			SYNTAX IpAddress
			MAX-ACCESS read-write
			STATUS current
			DESCRIPTION
				"Description."
			::= { onuPriDhcpServer 7 }

		
--          1.3.6.1.4.1.37950.1.1.5.12.3.1.12.8
-- 1.3.6.1.4.1.37950.1.1.5.12.3.1.12.8
-- 1.3.6.1.4.1.37950.1.1.5.12.3.1.12.8
-- 1.3.6.1.4.1.37950.1.1.5.12.3.1.12.8
-- 1.3.6.1.4.1.37950.1.1.5.12.3.1.12.8
-- 1.3.6.1.4.1.37950.1.1.5.12.3.1.12.8
-- 1.3.6.1.4.1.37950.1.1.5.12.3.1.12.8
-- 1.3.6.1.4.1.37950.1.1.5.12.3.1.12.8
-- 1.3.6.1.4.1.37950.1.1.5.12.3.1.12.8
		-- 1.3.6.1.4.1.37950.1.1.5.12.3.1.12.8
		onuPriDhcpEndIp OBJECT-TYPE
			SYNTAX IpAddress
			MAX-ACCESS read-write
			STATUS current
			DESCRIPTION
				"Description."
			::= { onuPriDhcpServer 8 }

		
--          1.3.6.1.4.1.37950.1.1.5.12.3.1.12.9
-- 1.3.6.1.4.1.37950.1.1.5.12.3.1.12.9
-- 1.3.6.1.4.1.37950.1.1.5.12.3.1.12.9
-- 1.3.6.1.4.1.37950.1.1.5.12.3.1.12.9
-- 1.3.6.1.4.1.37950.1.1.5.12.3.1.12.9
-- 1.3.6.1.4.1.37950.1.1.5.12.3.1.12.9
-- 1.3.6.1.4.1.37950.1.1.5.12.3.1.12.9
-- 1.3.6.1.4.1.37950.1.1.5.12.3.1.12.9
-- 1.3.6.1.4.1.37950.1.1.5.12.3.1.12.9
		-- 1.3.6.1.4.1.37950.1.1.5.12.3.1.12.9
		onuPriDhcpPoolType OBJECT-TYPE
			SYNTAX INTEGER
				{
				pc(0),
				camera(1),
				stb(2),
				ip-phone(3)
				}
			MAX-ACCESS read-write
			STATUS current
			DESCRIPTION
				"Description."
			::= { onuPriDhcpServer 9 }

		
--          1.3.6.1.4.1.37950.1.1.5.12.3.1.12.10
-- 1.3.6.1.4.1.37950.1.1.5.12.3.1.12.10
-- 1.3.6.1.4.1.37950.1.1.5.12.3.1.12.10
-- 1.3.6.1.4.1.37950.1.1.5.12.3.1.12.10
-- 1.3.6.1.4.1.37950.1.1.5.12.3.1.12.10
-- 1.3.6.1.4.1.37950.1.1.5.12.3.1.12.10
-- 1.3.6.1.4.1.37950.1.1.5.12.3.1.12.10
-- 1.3.6.1.4.1.37950.1.1.5.12.3.1.12.10
-- 1.3.6.1.4.1.37950.1.1.5.12.3.1.12.10
		-- 1.3.6.1.4.1.37950.1.1.5.12.3.1.12.10
		onuPriDhcpMasterDns OBJECT-TYPE
			SYNTAX IpAddress
			MAX-ACCESS read-write
			STATUS current
			DESCRIPTION
				"Description."
			::= { onuPriDhcpServer 10 }

		
--          1.3.6.1.4.1.37950.1.1.5.12.3.1.12.11
-- 1.3.6.1.4.1.37950.1.1.5.12.3.1.12.11
-- 1.3.6.1.4.1.37950.1.1.5.12.3.1.12.11
-- 1.3.6.1.4.1.37950.1.1.5.12.3.1.12.11
-- 1.3.6.1.4.1.37950.1.1.5.12.3.1.12.11
-- 1.3.6.1.4.1.37950.1.1.5.12.3.1.12.11
-- 1.3.6.1.4.1.37950.1.1.5.12.3.1.12.11
-- 1.3.6.1.4.1.37950.1.1.5.12.3.1.12.11
-- 1.3.6.1.4.1.37950.1.1.5.12.3.1.12.11
		-- 1.3.6.1.4.1.37950.1.1.5.12.3.1.12.11
		onuPriDhcpSlaveDns OBJECT-TYPE
			SYNTAX IpAddress
			MAX-ACCESS read-write
			STATUS current
			DESCRIPTION
				"Description."
			::= { onuPriDhcpServer 11 }

		
--          1.3.6.1.4.1.37950.1.1.5.12.3.1.12.12
-- 1.3.6.1.4.1.37950.1.1.5.12.3.1.12.12
-- 1.3.6.1.4.1.37950.1.1.5.12.3.1.12.12
-- 1.3.6.1.4.1.37950.1.1.5.12.3.1.12.12
-- 1.3.6.1.4.1.37950.1.1.5.12.3.1.12.12
-- 1.3.6.1.4.1.37950.1.1.5.12.3.1.12.12
-- 1.3.6.1.4.1.37950.1.1.5.12.3.1.12.12
-- 1.3.6.1.4.1.37950.1.1.5.12.3.1.12.12
-- 1.3.6.1.4.1.37950.1.1.5.12.3.1.12.12
		-- 1.3.6.1.4.1.37950.1.1.5.12.3.1.12.12
		onuPriDhcpGateway OBJECT-TYPE
			SYNTAX IpAddress
			MAX-ACCESS read-write
			STATUS current
			DESCRIPTION
				"Description."
			::= { onuPriDhcpServer 12 }

		
--          1.3.6.1.4.1.37950.1.1.5.12.3.1.12.13
-- 1.3.6.1.4.1.37950.1.1.5.12.3.1.12.13
-- 1.3.6.1.4.1.37950.1.1.5.12.3.1.12.13
-- 1.3.6.1.4.1.37950.1.1.5.12.3.1.12.13
-- 1.3.6.1.4.1.37950.1.1.5.12.3.1.12.13
-- 1.3.6.1.4.1.37950.1.1.5.12.3.1.12.13
-- 1.3.6.1.4.1.37950.1.1.5.12.3.1.12.13
-- 1.3.6.1.4.1.37950.1.1.5.12.3.1.12.13
-- 1.3.6.1.4.1.37950.1.1.5.12.3.1.12.13
		-- 1.3.6.1.4.1.37950.1.1.5.12.3.1.12.13
		onuPriDhcpRelayIp OBJECT-TYPE
			SYNTAX IpAddress
			MAX-ACCESS read-write
			STATUS current
			DESCRIPTION
				"Description."
			::= { onuPriDhcpServer 13 }

		
--          1.3.6.1.4.1.37950.1.1.5.12.3.1.12.14
-- 1.3.6.1.4.1.37950.1.1.5.12.3.1.12.14
-- 1.3.6.1.4.1.37950.1.1.5.12.3.1.12.14
-- 1.3.6.1.4.1.37950.1.1.5.12.3.1.12.14
-- 1.3.6.1.4.1.37950.1.1.5.12.3.1.12.14
-- 1.3.6.1.4.1.37950.1.1.5.12.3.1.12.14
-- 1.3.6.1.4.1.37950.1.1.5.12.3.1.12.14
-- 1.3.6.1.4.1.37950.1.1.5.12.3.1.12.14
-- 1.3.6.1.4.1.37950.1.1.5.12.3.1.12.14
		-- 1.3.6.1.4.1.37950.1.1.5.12.3.1.12.14
		onuPriDhcpAction OBJECT-TYPE
			SYNTAX INTEGER
				{
				commit(1),
				remove(2)
				}
			MAX-ACCESS read-write
			STATUS current
			DESCRIPTION
				"Description."
			::= { onuPriDhcpServer 14 }

		
--          1.3.6.1.4.1.37950.1.1.5.12.3.1.13
-- 1.3.6.1.4.1.37950.1.1.5.12.3.1.13
-- 1.3.6.1.4.1.37950.1.1.5.12.3.1.13
-- 1.3.6.1.4.1.37950.1.1.5.12.3.1.13
-- 1.3.6.1.4.1.37950.1.1.5.12.3.1.13
-- 1.3.6.1.4.1.37950.1.1.5.12.3.1.13
-- 1.3.6.1.4.1.37950.1.1.5.12.3.1.13
-- 1.3.6.1.4.1.37950.1.1.5.12.3.1.13
-- 1.3.6.1.4.1.37950.1.1.5.12.3.1.13
		-- 1.3.6.1.4.1.37950.1.1.5.12.3.1.13
		onuPriDhcpOption82 OBJECT IDENTIFIER ::= { onuPriGlobalCfg 13 }

		
--          1.3.6.1.4.1.37950.1.1.5.12.3.1.13.1
-- 1.3.6.1.4.1.37950.1.1.5.12.3.1.13.1
-- 1.3.6.1.4.1.37950.1.1.5.12.3.1.13.1
-- 1.3.6.1.4.1.37950.1.1.5.12.3.1.13.1
-- 1.3.6.1.4.1.37950.1.1.5.12.3.1.13.1
-- 1.3.6.1.4.1.37950.1.1.5.12.3.1.13.1
-- 1.3.6.1.4.1.37950.1.1.5.12.3.1.13.1
-- 1.3.6.1.4.1.37950.1.1.5.12.3.1.13.1
-- 1.3.6.1.4.1.37950.1.1.5.12.3.1.13.1
		-- 1.3.6.1.4.1.37950.1.1.5.12.3.1.13.1
		onuPriDhcpOption82Pon OBJECT-TYPE
			SYNTAX Integer32 (1..8)
			MAX-ACCESS read-write
			STATUS current
			DESCRIPTION
				"Description."
			::= { onuPriDhcpOption82 1 }

		
--          1.3.6.1.4.1.37950.1.1.5.12.3.1.13.2
-- 1.3.6.1.4.1.37950.1.1.5.12.3.1.13.2
-- 1.3.6.1.4.1.37950.1.1.5.12.3.1.13.2
-- 1.3.6.1.4.1.37950.1.1.5.12.3.1.13.2
-- 1.3.6.1.4.1.37950.1.1.5.12.3.1.13.2
-- 1.3.6.1.4.1.37950.1.1.5.12.3.1.13.2
-- 1.3.6.1.4.1.37950.1.1.5.12.3.1.13.2
-- 1.3.6.1.4.1.37950.1.1.5.12.3.1.13.2
-- 1.3.6.1.4.1.37950.1.1.5.12.3.1.13.2
		-- 1.3.6.1.4.1.37950.1.1.5.12.3.1.13.2
		onuPriDhcpOption82Onu OBJECT-TYPE
			SYNTAX Integer32 (1..65535)
			MAX-ACCESS read-write
			STATUS current
			DESCRIPTION
				"Description."
			::= { onuPriDhcpOption82 2 }

		
--          1.3.6.1.4.1.37950.1.1.5.12.3.1.13.3
-- 1.3.6.1.4.1.37950.1.1.5.12.3.1.13.3
-- 1.3.6.1.4.1.37950.1.1.5.12.3.1.13.3
-- 1.3.6.1.4.1.37950.1.1.5.12.3.1.13.3
-- 1.3.6.1.4.1.37950.1.1.5.12.3.1.13.3
-- 1.3.6.1.4.1.37950.1.1.5.12.3.1.13.3
-- 1.3.6.1.4.1.37950.1.1.5.12.3.1.13.3
-- 1.3.6.1.4.1.37950.1.1.5.12.3.1.13.3
-- 1.3.6.1.4.1.37950.1.1.5.12.3.1.13.3
		-- 1.3.6.1.4.1.37950.1.1.5.12.3.1.13.3
		onuPriDhcpOption82Enable OBJECT-TYPE
			SYNTAX INTEGER
				{
				disable(0),
				enable(1)
				}
			MAX-ACCESS read-write
			STATUS current
			DESCRIPTION
				"Description."
			::= { onuPriDhcpOption82 3 }

		
--          1.3.6.1.4.1.37950.1.1.5.12.3.1.13.4
-- 1.3.6.1.4.1.37950.1.1.5.12.3.1.13.4
-- 1.3.6.1.4.1.37950.1.1.5.12.3.1.13.4
-- 1.3.6.1.4.1.37950.1.1.5.12.3.1.13.4
-- 1.3.6.1.4.1.37950.1.1.5.12.3.1.13.4
-- 1.3.6.1.4.1.37950.1.1.5.12.3.1.13.4
-- 1.3.6.1.4.1.37950.1.1.5.12.3.1.13.4
-- 1.3.6.1.4.1.37950.1.1.5.12.3.1.13.4
-- 1.3.6.1.4.1.37950.1.1.5.12.3.1.13.4
		-- 1.3.6.1.4.1.37950.1.1.5.12.3.1.13.4
		onuPriDhcpOption82Action OBJECT-TYPE
			SYNTAX INTEGER
				{
				commit(1),
				remove(2)
				}
			MAX-ACCESS read-write
			STATUS current
			DESCRIPTION
				"Description."
			::= { onuPriDhcpOption82 4 }

		
--          1.3.6.1.4.1.37950.1.1.5.12.3.1.14
-- 1.3.6.1.4.1.37950.1.1.5.12.3.1.14
-- 1.3.6.1.4.1.37950.1.1.5.12.3.1.14
-- 1.3.6.1.4.1.37950.1.1.5.12.3.1.14
-- 1.3.6.1.4.1.37950.1.1.5.12.3.1.14
-- 1.3.6.1.4.1.37950.1.1.5.12.3.1.14
-- 1.3.6.1.4.1.37950.1.1.5.12.3.1.14
-- 1.3.6.1.4.1.37950.1.1.5.12.3.1.14
-- 1.3.6.1.4.1.37950.1.1.5.12.3.1.14
		-- 1.3.6.1.4.1.37950.1.1.5.12.3.1.14
		onuPriPPPoE OBJECT IDENTIFIER ::= { onuPriGlobalCfg 14 }

		
--          1.3.6.1.4.1.37950.1.1.5.12.3.1.14.1
-- 1.3.6.1.4.1.37950.1.1.5.12.3.1.14.1
-- 1.3.6.1.4.1.37950.1.1.5.12.3.1.14.1
-- 1.3.6.1.4.1.37950.1.1.5.12.3.1.14.1
-- 1.3.6.1.4.1.37950.1.1.5.12.3.1.14.1
-- 1.3.6.1.4.1.37950.1.1.5.12.3.1.14.1
-- 1.3.6.1.4.1.37950.1.1.5.12.3.1.14.1
-- 1.3.6.1.4.1.37950.1.1.5.12.3.1.14.1
-- 1.3.6.1.4.1.37950.1.1.5.12.3.1.14.1
		-- 1.3.6.1.4.1.37950.1.1.5.12.3.1.14.1
		onuPriPPPoEPon OBJECT-TYPE
			SYNTAX Integer32 (1..8)
			MAX-ACCESS read-write
			STATUS current
			DESCRIPTION
				"Description."
			::= { onuPriPPPoE 1 }

		
--          1.3.6.1.4.1.37950.1.1.5.12.3.1.14.2
-- 1.3.6.1.4.1.37950.1.1.5.12.3.1.14.2
-- 1.3.6.1.4.1.37950.1.1.5.12.3.1.14.2
-- 1.3.6.1.4.1.37950.1.1.5.12.3.1.14.2
-- 1.3.6.1.4.1.37950.1.1.5.12.3.1.14.2
-- 1.3.6.1.4.1.37950.1.1.5.12.3.1.14.2
-- 1.3.6.1.4.1.37950.1.1.5.12.3.1.14.2
-- 1.3.6.1.4.1.37950.1.1.5.12.3.1.14.2
-- 1.3.6.1.4.1.37950.1.1.5.12.3.1.14.2
		-- 1.3.6.1.4.1.37950.1.1.5.12.3.1.14.2
		onuPriPPPoEOnu OBJECT-TYPE
			SYNTAX Integer32 (1..65535)
			MAX-ACCESS read-write
			STATUS current
			DESCRIPTION
				"Description."
			::= { onuPriPPPoE 2 }

		
--          1.3.6.1.4.1.37950.1.1.5.12.3.1.14.3
-- 1.3.6.1.4.1.37950.1.1.5.12.3.1.14.3
-- 1.3.6.1.4.1.37950.1.1.5.12.3.1.14.3
-- 1.3.6.1.4.1.37950.1.1.5.12.3.1.14.3
-- 1.3.6.1.4.1.37950.1.1.5.12.3.1.14.3
-- 1.3.6.1.4.1.37950.1.1.5.12.3.1.14.3
-- 1.3.6.1.4.1.37950.1.1.5.12.3.1.14.3
-- 1.3.6.1.4.1.37950.1.1.5.12.3.1.14.3
-- 1.3.6.1.4.1.37950.1.1.5.12.3.1.14.3
		-- 1.3.6.1.4.1.37950.1.1.5.12.3.1.14.3
		onuPriPPPoEEnable OBJECT-TYPE
			SYNTAX INTEGER
				{
				disable(0),
				enable(1)
				}
			MAX-ACCESS read-write
			STATUS current
			DESCRIPTION
				"Description."
			::= { onuPriPPPoE 3 }

		
--          1.3.6.1.4.1.37950.1.1.5.12.3.1.14.4
-- 1.3.6.1.4.1.37950.1.1.5.12.3.1.14.4
-- 1.3.6.1.4.1.37950.1.1.5.12.3.1.14.4
-- 1.3.6.1.4.1.37950.1.1.5.12.3.1.14.4
-- 1.3.6.1.4.1.37950.1.1.5.12.3.1.14.4
-- 1.3.6.1.4.1.37950.1.1.5.12.3.1.14.4
-- 1.3.6.1.4.1.37950.1.1.5.12.3.1.14.4
-- 1.3.6.1.4.1.37950.1.1.5.12.3.1.14.4
-- 1.3.6.1.4.1.37950.1.1.5.12.3.1.14.4
		-- 1.3.6.1.4.1.37950.1.1.5.12.3.1.14.4
		onuPriPPPoEAction OBJECT-TYPE
			SYNTAX INTEGER
				{
				commit(1),
				remove(2)
				}
			MAX-ACCESS read-write
			STATUS current
			DESCRIPTION
				"Description."
			::= { onuPriPPPoE 4 }

		
--          1.3.6.1.4.1.37950.1.1.5.12.3.1.15
-- 1.3.6.1.4.1.37950.1.1.5.12.3.1.15
-- 1.3.6.1.4.1.37950.1.1.5.12.3.1.15
-- 1.3.6.1.4.1.37950.1.1.5.12.3.1.15
-- 1.3.6.1.4.1.37950.1.1.5.12.3.1.15
-- 1.3.6.1.4.1.37950.1.1.5.12.3.1.15
-- 1.3.6.1.4.1.37950.1.1.5.12.3.1.15
-- 1.3.6.1.4.1.37950.1.1.5.12.3.1.15
-- 1.3.6.1.4.1.37950.1.1.5.12.3.1.15
		-- 1.3.6.1.4.1.37950.1.1.5.12.3.1.15
		onuPriDhcpV6 OBJECT IDENTIFIER ::= { onuPriGlobalCfg 15 }

		
--          1.3.6.1.4.1.37950.1.1.5.12.3.1.15.1
-- 1.3.6.1.4.1.37950.1.1.5.12.3.1.15.1
-- 1.3.6.1.4.1.37950.1.1.5.12.3.1.15.1
-- 1.3.6.1.4.1.37950.1.1.5.12.3.1.15.1
-- 1.3.6.1.4.1.37950.1.1.5.12.3.1.15.1
-- 1.3.6.1.4.1.37950.1.1.5.12.3.1.15.1
-- 1.3.6.1.4.1.37950.1.1.5.12.3.1.15.1
-- 1.3.6.1.4.1.37950.1.1.5.12.3.1.15.1
-- 1.3.6.1.4.1.37950.1.1.5.12.3.1.15.1
		-- 1.3.6.1.4.1.37950.1.1.5.12.3.1.15.1
		onuPriDhcpV6Pon OBJECT-TYPE
			SYNTAX Integer32 (1..8)
			MAX-ACCESS read-write
			STATUS current
			DESCRIPTION
				"Description."
			::= { onuPriDhcpV6 1 }

		
--          1.3.6.1.4.1.37950.1.1.5.12.3.1.15.2
-- 1.3.6.1.4.1.37950.1.1.5.12.3.1.15.2
-- 1.3.6.1.4.1.37950.1.1.5.12.3.1.15.2
-- 1.3.6.1.4.1.37950.1.1.5.12.3.1.15.2
-- 1.3.6.1.4.1.37950.1.1.5.12.3.1.15.2
-- 1.3.6.1.4.1.37950.1.1.5.12.3.1.15.2
-- 1.3.6.1.4.1.37950.1.1.5.12.3.1.15.2
-- 1.3.6.1.4.1.37950.1.1.5.12.3.1.15.2
-- 1.3.6.1.4.1.37950.1.1.5.12.3.1.15.2
		-- 1.3.6.1.4.1.37950.1.1.5.12.3.1.15.2
		onuPriDhcpV6Onu OBJECT-TYPE
			SYNTAX Integer32 (1..65535)
			MAX-ACCESS read-write
			STATUS current
			DESCRIPTION
				"Description."
			::= { onuPriDhcpV6 2 }

		
--          1.3.6.1.4.1.37950.1.1.5.12.3.1.15.3
-- 1.3.6.1.4.1.37950.1.1.5.12.3.1.15.3
-- 1.3.6.1.4.1.37950.1.1.5.12.3.1.15.3
-- 1.3.6.1.4.1.37950.1.1.5.12.3.1.15.3
-- 1.3.6.1.4.1.37950.1.1.5.12.3.1.15.3
-- 1.3.6.1.4.1.37950.1.1.5.12.3.1.15.3
-- 1.3.6.1.4.1.37950.1.1.5.12.3.1.15.3
-- 1.3.6.1.4.1.37950.1.1.5.12.3.1.15.3
-- 1.3.6.1.4.1.37950.1.1.5.12.3.1.15.3
		-- 1.3.6.1.4.1.37950.1.1.5.12.3.1.15.3
		onuPriDhcpV6Option18Enable OBJECT-TYPE
			SYNTAX INTEGER
				{
				disable(0),
				enable(1)
				}
			MAX-ACCESS read-write
			STATUS current
			DESCRIPTION
				"Description."
			::= { onuPriDhcpV6 3 }

		
--          1.3.6.1.4.1.37950.1.1.5.12.3.1.15.4
-- 1.3.6.1.4.1.37950.1.1.5.12.3.1.15.4
-- 1.3.6.1.4.1.37950.1.1.5.12.3.1.15.4
-- 1.3.6.1.4.1.37950.1.1.5.12.3.1.15.4
-- 1.3.6.1.4.1.37950.1.1.5.12.3.1.15.4
-- 1.3.6.1.4.1.37950.1.1.5.12.3.1.15.4
-- 1.3.6.1.4.1.37950.1.1.5.12.3.1.15.4
-- 1.3.6.1.4.1.37950.1.1.5.12.3.1.15.4
-- 1.3.6.1.4.1.37950.1.1.5.12.3.1.15.4
		-- 1.3.6.1.4.1.37950.1.1.5.12.3.1.15.4
		onuPriDhcpV6Option37Enable OBJECT-TYPE
			SYNTAX INTEGER
				{
				disable(0),
				enable(1)
				}
			MAX-ACCESS read-write
			STATUS current
			DESCRIPTION
				"Description."
			::= { onuPriDhcpV6 4 }

		
--          1.3.6.1.4.1.37950.1.1.5.12.3.1.15.5
-- 1.3.6.1.4.1.37950.1.1.5.12.3.1.15.5
-- 1.3.6.1.4.1.37950.1.1.5.12.3.1.15.5
-- 1.3.6.1.4.1.37950.1.1.5.12.3.1.15.5
-- 1.3.6.1.4.1.37950.1.1.5.12.3.1.15.5
-- 1.3.6.1.4.1.37950.1.1.5.12.3.1.15.5
-- 1.3.6.1.4.1.37950.1.1.5.12.3.1.15.5
-- 1.3.6.1.4.1.37950.1.1.5.12.3.1.15.5
-- 1.3.6.1.4.1.37950.1.1.5.12.3.1.15.5
		-- 1.3.6.1.4.1.37950.1.1.5.12.3.1.15.5
		onuPriDhcpV6Action OBJECT-TYPE
			SYNTAX INTEGER
				{
				commit(1),
				remove(2)
				}
			MAX-ACCESS read-write
			STATUS current
			DESCRIPTION
				"Description."
			::= { onuPriDhcpV6 5 }

		
--          1.3.6.1.4.1.37950.1.1.5.12.3.1.16
-- 1.3.6.1.4.1.37950.1.1.5.12.3.1.16
-- 1.3.6.1.4.1.37950.1.1.5.12.3.1.16
-- 1.3.6.1.4.1.37950.1.1.5.12.3.1.16
-- 1.3.6.1.4.1.37950.1.1.5.12.3.1.16
-- 1.3.6.1.4.1.37950.1.1.5.12.3.1.16
-- 1.3.6.1.4.1.37950.1.1.5.12.3.1.16
-- 1.3.6.1.4.1.37950.1.1.5.12.3.1.16
-- 1.3.6.1.4.1.37950.1.1.5.12.3.1.16
		-- 1.3.6.1.4.1.37950.1.1.5.12.3.1.16
		onuPriVoipParam OBJECT IDENTIFIER ::= { onuPriGlobalCfg 16 }

		
--          1.3.6.1.4.1.37950.1.1.5.12.3.1.16.1
-- 1.3.6.1.4.1.37950.1.1.5.12.3.1.16.1
-- 1.3.6.1.4.1.37950.1.1.5.12.3.1.16.1
-- 1.3.6.1.4.1.37950.1.1.5.12.3.1.16.1
-- 1.3.6.1.4.1.37950.1.1.5.12.3.1.16.1
-- 1.3.6.1.4.1.37950.1.1.5.12.3.1.16.1
-- 1.3.6.1.4.1.37950.1.1.5.12.3.1.16.1
-- 1.3.6.1.4.1.37950.1.1.5.12.3.1.16.1
-- 1.3.6.1.4.1.37950.1.1.5.12.3.1.16.1
		-- 1.3.6.1.4.1.37950.1.1.5.12.3.1.16.1
		priVoipParamPon OBJECT-TYPE
			SYNTAX Integer32 (1..8)
			MAX-ACCESS read-write
			STATUS current
			DESCRIPTION
				"Description."
			::= { onuPriVoipParam 1 }

		
--          1.3.6.1.4.1.37950.1.1.5.12.3.1.16.2
-- 1.3.6.1.4.1.37950.1.1.5.12.3.1.16.2
-- 1.3.6.1.4.1.37950.1.1.5.12.3.1.16.2
-- 1.3.6.1.4.1.37950.1.1.5.12.3.1.16.2
-- 1.3.6.1.4.1.37950.1.1.5.12.3.1.16.2
-- 1.3.6.1.4.1.37950.1.1.5.12.3.1.16.2
-- 1.3.6.1.4.1.37950.1.1.5.12.3.1.16.2
-- 1.3.6.1.4.1.37950.1.1.5.12.3.1.16.2
-- 1.3.6.1.4.1.37950.1.1.5.12.3.1.16.2
		-- 1.3.6.1.4.1.37950.1.1.5.12.3.1.16.2
		priVoipParamOnu OBJECT-TYPE
			SYNTAX Integer32 (1..65535)
			MAX-ACCESS read-write
			STATUS current
			DESCRIPTION
				"Description."
			::= { onuPriVoipParam 2 }

		
--          1.3.6.1.4.1.37950.1.1.5.12.3.1.16.3
-- 1.3.6.1.4.1.37950.1.1.5.12.3.1.16.3
-- 1.3.6.1.4.1.37950.1.1.5.12.3.1.16.3
-- 1.3.6.1.4.1.37950.1.1.5.12.3.1.16.3
-- 1.3.6.1.4.1.37950.1.1.5.12.3.1.16.3
-- 1.3.6.1.4.1.37950.1.1.5.12.3.1.16.3
-- 1.3.6.1.4.1.37950.1.1.5.12.3.1.16.3
-- 1.3.6.1.4.1.37950.1.1.5.12.3.1.16.3
-- 1.3.6.1.4.1.37950.1.1.5.12.3.1.16.3
		-- 1.3.6.1.4.1.37950.1.1.5.12.3.1.16.3
		priIpMode OBJECT-TYPE
			SYNTAX INTEGER
				{
				static(1),
				dhcp(2),
				pppoe(3)
				}
			MAX-ACCESS read-write
			STATUS current
			DESCRIPTION
				"Description."
			::= { onuPriVoipParam 3 }

		
--          1.3.6.1.4.1.37950.1.1.5.12.3.1.16.4
-- 1.3.6.1.4.1.37950.1.1.5.12.3.1.16.4
-- 1.3.6.1.4.1.37950.1.1.5.12.3.1.16.4
-- 1.3.6.1.4.1.37950.1.1.5.12.3.1.16.4
-- 1.3.6.1.4.1.37950.1.1.5.12.3.1.16.4
-- 1.3.6.1.4.1.37950.1.1.5.12.3.1.16.4
-- 1.3.6.1.4.1.37950.1.1.5.12.3.1.16.4
-- 1.3.6.1.4.1.37950.1.1.5.12.3.1.16.4
-- 1.3.6.1.4.1.37950.1.1.5.12.3.1.16.4
		-- 1.3.6.1.4.1.37950.1.1.5.12.3.1.16.4
		priIp OBJECT-TYPE
			SYNTAX IpAddress
			MAX-ACCESS read-write
			STATUS current
			DESCRIPTION
				"Description."
			::= { onuPriVoipParam 4 }

		
--          1.3.6.1.4.1.37950.1.1.5.12.3.1.16.5
-- 1.3.6.1.4.1.37950.1.1.5.12.3.1.16.5
-- 1.3.6.1.4.1.37950.1.1.5.12.3.1.16.5
-- 1.3.6.1.4.1.37950.1.1.5.12.3.1.16.5
-- 1.3.6.1.4.1.37950.1.1.5.12.3.1.16.5
-- 1.3.6.1.4.1.37950.1.1.5.12.3.1.16.5
-- 1.3.6.1.4.1.37950.1.1.5.12.3.1.16.5
-- 1.3.6.1.4.1.37950.1.1.5.12.3.1.16.5
-- 1.3.6.1.4.1.37950.1.1.5.12.3.1.16.5
		-- 1.3.6.1.4.1.37950.1.1.5.12.3.1.16.5
		priMask OBJECT-TYPE
			SYNTAX IpAddress
			MAX-ACCESS read-write
			STATUS current
			DESCRIPTION
				"Description."
			::= { onuPriVoipParam 5 }

		
--          1.3.6.1.4.1.37950.1.1.5.12.3.1.16.6
-- 1.3.6.1.4.1.37950.1.1.5.12.3.1.16.6
-- 1.3.6.1.4.1.37950.1.1.5.12.3.1.16.6
-- 1.3.6.1.4.1.37950.1.1.5.12.3.1.16.6
-- 1.3.6.1.4.1.37950.1.1.5.12.3.1.16.6
-- 1.3.6.1.4.1.37950.1.1.5.12.3.1.16.6
-- 1.3.6.1.4.1.37950.1.1.5.12.3.1.16.6
-- 1.3.6.1.4.1.37950.1.1.5.12.3.1.16.6
-- 1.3.6.1.4.1.37950.1.1.5.12.3.1.16.6
		-- 1.3.6.1.4.1.37950.1.1.5.12.3.1.16.6
		priGw OBJECT-TYPE
			SYNTAX IpAddress
			MAX-ACCESS read-write
			STATUS current
			DESCRIPTION
				"Description."
			::= { onuPriVoipParam 6 }

		
--          1.3.6.1.4.1.37950.1.1.5.12.3.1.16.7
-- 1.3.6.1.4.1.37950.1.1.5.12.3.1.16.7
-- 1.3.6.1.4.1.37950.1.1.5.12.3.1.16.7
-- 1.3.6.1.4.1.37950.1.1.5.12.3.1.16.7
-- 1.3.6.1.4.1.37950.1.1.5.12.3.1.16.7
-- 1.3.6.1.4.1.37950.1.1.5.12.3.1.16.7
-- 1.3.6.1.4.1.37950.1.1.5.12.3.1.16.7
-- 1.3.6.1.4.1.37950.1.1.5.12.3.1.16.7
-- 1.3.6.1.4.1.37950.1.1.5.12.3.1.16.7
		-- 1.3.6.1.4.1.37950.1.1.5.12.3.1.16.7
		priRtpIp OBJECT-TYPE
			SYNTAX IpAddress
			MAX-ACCESS read-write
			STATUS current
			DESCRIPTION
				"Description."
			::= { onuPriVoipParam 7 }

		
--          1.3.6.1.4.1.37950.1.1.5.12.3.1.16.8
-- 1.3.6.1.4.1.37950.1.1.5.12.3.1.16.8
-- 1.3.6.1.4.1.37950.1.1.5.12.3.1.16.8
-- 1.3.6.1.4.1.37950.1.1.5.12.3.1.16.8
-- 1.3.6.1.4.1.37950.1.1.5.12.3.1.16.8
-- 1.3.6.1.4.1.37950.1.1.5.12.3.1.16.8
-- 1.3.6.1.4.1.37950.1.1.5.12.3.1.16.8
-- 1.3.6.1.4.1.37950.1.1.5.12.3.1.16.8
-- 1.3.6.1.4.1.37950.1.1.5.12.3.1.16.8
		-- 1.3.6.1.4.1.37950.1.1.5.12.3.1.16.8
		priRtpMask OBJECT-TYPE
			SYNTAX IpAddress
			MAX-ACCESS read-write
			STATUS current
			DESCRIPTION
				"Description."
			::= { onuPriVoipParam 8 }

		
--          1.3.6.1.4.1.37950.1.1.5.12.3.1.16.9
-- 1.3.6.1.4.1.37950.1.1.5.12.3.1.16.9
-- 1.3.6.1.4.1.37950.1.1.5.12.3.1.16.9
-- 1.3.6.1.4.1.37950.1.1.5.12.3.1.16.9
-- 1.3.6.1.4.1.37950.1.1.5.12.3.1.16.9
-- 1.3.6.1.4.1.37950.1.1.5.12.3.1.16.9
-- 1.3.6.1.4.1.37950.1.1.5.12.3.1.16.9
-- 1.3.6.1.4.1.37950.1.1.5.12.3.1.16.9
-- 1.3.6.1.4.1.37950.1.1.5.12.3.1.16.9
		-- 1.3.6.1.4.1.37950.1.1.5.12.3.1.16.9
		priRtpGw OBJECT-TYPE
			SYNTAX IpAddress
			MAX-ACCESS read-write
			STATUS current
			DESCRIPTION
				"Description."
			::= { onuPriVoipParam 9 }

		
--          1.3.6.1.4.1.37950.1.1.5.12.3.1.16.10
-- 1.3.6.1.4.1.37950.1.1.5.12.3.1.16.10
-- 1.3.6.1.4.1.37950.1.1.5.12.3.1.16.10
-- 1.3.6.1.4.1.37950.1.1.5.12.3.1.16.10
-- 1.3.6.1.4.1.37950.1.1.5.12.3.1.16.10
-- 1.3.6.1.4.1.37950.1.1.5.12.3.1.16.10
-- 1.3.6.1.4.1.37950.1.1.5.12.3.1.16.10
-- 1.3.6.1.4.1.37950.1.1.5.12.3.1.16.10
-- 1.3.6.1.4.1.37950.1.1.5.12.3.1.16.10
		-- 1.3.6.1.4.1.37950.1.1.5.12.3.1.16.10
		priDnsMaster OBJECT-TYPE
			SYNTAX IpAddress
			MAX-ACCESS read-write
			STATUS current
			DESCRIPTION
				"Description."
			::= { onuPriVoipParam 10 }

		
--          1.3.6.1.4.1.37950.1.1.5.12.3.1.16.11
-- 1.3.6.1.4.1.37950.1.1.5.12.3.1.16.11
-- 1.3.6.1.4.1.37950.1.1.5.12.3.1.16.11
-- 1.3.6.1.4.1.37950.1.1.5.12.3.1.16.11
-- 1.3.6.1.4.1.37950.1.1.5.12.3.1.16.11
-- 1.3.6.1.4.1.37950.1.1.5.12.3.1.16.11
-- 1.3.6.1.4.1.37950.1.1.5.12.3.1.16.11
-- 1.3.6.1.4.1.37950.1.1.5.12.3.1.16.11
-- 1.3.6.1.4.1.37950.1.1.5.12.3.1.16.11
		-- 1.3.6.1.4.1.37950.1.1.5.12.3.1.16.11
		priDnsSlave OBJECT-TYPE
			SYNTAX IpAddress
			MAX-ACCESS read-write
			STATUS current
			DESCRIPTION
				"Description."
			::= { onuPriVoipParam 11 }

		
--          1.3.6.1.4.1.37950.1.1.5.12.3.1.16.12
-- 1.3.6.1.4.1.37950.1.1.5.12.3.1.16.12
-- 1.3.6.1.4.1.37950.1.1.5.12.3.1.16.12
-- 1.3.6.1.4.1.37950.1.1.5.12.3.1.16.12
-- 1.3.6.1.4.1.37950.1.1.5.12.3.1.16.12
-- 1.3.6.1.4.1.37950.1.1.5.12.3.1.16.12
-- 1.3.6.1.4.1.37950.1.1.5.12.3.1.16.12
-- 1.3.6.1.4.1.37950.1.1.5.12.3.1.16.12
-- 1.3.6.1.4.1.37950.1.1.5.12.3.1.16.12
		-- 1.3.6.1.4.1.37950.1.1.5.12.3.1.16.12
		priDhcpOption60Enable OBJECT-TYPE
			SYNTAX INTEGER
				{
				disable(0),
				enable(1)
				}
			MAX-ACCESS read-write
			STATUS current
			DESCRIPTION
				"Description."
			::= { onuPriVoipParam 12 }

		
--          1.3.6.1.4.1.37950.1.1.5.12.3.1.16.13
-- 1.3.6.1.4.1.37950.1.1.5.12.3.1.16.13
-- 1.3.6.1.4.1.37950.1.1.5.12.3.1.16.13
-- 1.3.6.1.4.1.37950.1.1.5.12.3.1.16.13
-- 1.3.6.1.4.1.37950.1.1.5.12.3.1.16.13
-- 1.3.6.1.4.1.37950.1.1.5.12.3.1.16.13
-- 1.3.6.1.4.1.37950.1.1.5.12.3.1.16.13
-- 1.3.6.1.4.1.37950.1.1.5.12.3.1.16.13
-- 1.3.6.1.4.1.37950.1.1.5.12.3.1.16.13
		-- 1.3.6.1.4.1.37950.1.1.5.12.3.1.16.13
		priDhcpOption60Base OBJECT-TYPE
			SYNTAX OCTET STRING
			MAX-ACCESS read-write
			STATUS current
			DESCRIPTION
				"Description."
			::= { onuPriVoipParam 13 }

		
--          1.3.6.1.4.1.37950.1.1.5.12.3.1.16.14
-- 1.3.6.1.4.1.37950.1.1.5.12.3.1.16.14
-- 1.3.6.1.4.1.37950.1.1.5.12.3.1.16.14
-- 1.3.6.1.4.1.37950.1.1.5.12.3.1.16.14
-- 1.3.6.1.4.1.37950.1.1.5.12.3.1.16.14
-- 1.3.6.1.4.1.37950.1.1.5.12.3.1.16.14
-- 1.3.6.1.4.1.37950.1.1.5.12.3.1.16.14
-- 1.3.6.1.4.1.37950.1.1.5.12.3.1.16.14
-- 1.3.6.1.4.1.37950.1.1.5.12.3.1.16.14
		-- 1.3.6.1.4.1.37950.1.1.5.12.3.1.16.14
		priDhcpOption60Value OBJECT-TYPE
			SYNTAX OCTET STRING
			MAX-ACCESS read-write
			STATUS current
			DESCRIPTION
				"Description."
			::= { onuPriVoipParam 14 }

		
--          1.3.6.1.4.1.37950.1.1.5.12.3.1.16.15
-- 1.3.6.1.4.1.37950.1.1.5.12.3.1.16.15
-- 1.3.6.1.4.1.37950.1.1.5.12.3.1.16.15
-- 1.3.6.1.4.1.37950.1.1.5.12.3.1.16.15
-- 1.3.6.1.4.1.37950.1.1.5.12.3.1.16.15
-- 1.3.6.1.4.1.37950.1.1.5.12.3.1.16.15
-- 1.3.6.1.4.1.37950.1.1.5.12.3.1.16.15
-- 1.3.6.1.4.1.37950.1.1.5.12.3.1.16.15
-- 1.3.6.1.4.1.37950.1.1.5.12.3.1.16.15
		-- 1.3.6.1.4.1.37950.1.1.5.12.3.1.16.15
		priPPPoEMode OBJECT-TYPE
			SYNTAX INTEGER
				{
				auto(0),
				chap(1),
				pap(2)
				}
			MAX-ACCESS read-write
			STATUS current
			DESCRIPTION
				"Description."
			::= { onuPriVoipParam 15 }

		
--          1.3.6.1.4.1.37950.1.1.5.12.3.1.16.16
-- 1.3.6.1.4.1.37950.1.1.5.12.3.1.16.16
-- 1.3.6.1.4.1.37950.1.1.5.12.3.1.16.16
-- 1.3.6.1.4.1.37950.1.1.5.12.3.1.16.16
-- 1.3.6.1.4.1.37950.1.1.5.12.3.1.16.16
-- 1.3.6.1.4.1.37950.1.1.5.12.3.1.16.16
-- 1.3.6.1.4.1.37950.1.1.5.12.3.1.16.16
-- 1.3.6.1.4.1.37950.1.1.5.12.3.1.16.16
-- 1.3.6.1.4.1.37950.1.1.5.12.3.1.16.16
		-- 1.3.6.1.4.1.37950.1.1.5.12.3.1.16.16
		priPPPoEUsername OBJECT-TYPE
			SYNTAX OCTET STRING
			MAX-ACCESS read-write
			STATUS current
			DESCRIPTION
				"Description."
			::= { onuPriVoipParam 16 }

		
--          1.3.6.1.4.1.37950.1.1.5.12.3.1.16.17
-- 1.3.6.1.4.1.37950.1.1.5.12.3.1.16.17
-- 1.3.6.1.4.1.37950.1.1.5.12.3.1.16.17
-- 1.3.6.1.4.1.37950.1.1.5.12.3.1.16.17
-- 1.3.6.1.4.1.37950.1.1.5.12.3.1.16.17
-- 1.3.6.1.4.1.37950.1.1.5.12.3.1.16.17
-- 1.3.6.1.4.1.37950.1.1.5.12.3.1.16.17
-- 1.3.6.1.4.1.37950.1.1.5.12.3.1.16.17
-- 1.3.6.1.4.1.37950.1.1.5.12.3.1.16.17
		-- 1.3.6.1.4.1.37950.1.1.5.12.3.1.16.17
		priPPPoEPassword OBJECT-TYPE
			SYNTAX OCTET STRING
			MAX-ACCESS read-write
			STATUS current
			DESCRIPTION
				"Description."
			::= { onuPriVoipParam 17 }

		
--          1.3.6.1.4.1.37950.1.1.5.12.3.1.16.18
-- 1.3.6.1.4.1.37950.1.1.5.12.3.1.16.18
-- 1.3.6.1.4.1.37950.1.1.5.12.3.1.16.18
-- 1.3.6.1.4.1.37950.1.1.5.12.3.1.16.18
-- 1.3.6.1.4.1.37950.1.1.5.12.3.1.16.18
-- 1.3.6.1.4.1.37950.1.1.5.12.3.1.16.18
-- 1.3.6.1.4.1.37950.1.1.5.12.3.1.16.18
-- 1.3.6.1.4.1.37950.1.1.5.12.3.1.16.18
-- 1.3.6.1.4.1.37950.1.1.5.12.3.1.16.18
		-- 1.3.6.1.4.1.37950.1.1.5.12.3.1.16.18
		priSVlanTpid OBJECT-TYPE
			SYNTAX Integer32
			MAX-ACCESS read-write
			STATUS current
			DESCRIPTION
				"Description."
			::= { onuPriVoipParam 18 }

		
--          1.3.6.1.4.1.37950.1.1.5.12.3.1.16.19
-- 1.3.6.1.4.1.37950.1.1.5.12.3.1.16.19
-- 1.3.6.1.4.1.37950.1.1.5.12.3.1.16.19
-- 1.3.6.1.4.1.37950.1.1.5.12.3.1.16.19
-- 1.3.6.1.4.1.37950.1.1.5.12.3.1.16.19
-- 1.3.6.1.4.1.37950.1.1.5.12.3.1.16.19
-- 1.3.6.1.4.1.37950.1.1.5.12.3.1.16.19
-- 1.3.6.1.4.1.37950.1.1.5.12.3.1.16.19
-- 1.3.6.1.4.1.37950.1.1.5.12.3.1.16.19
		-- 1.3.6.1.4.1.37950.1.1.5.12.3.1.16.19
		priSVlanId OBJECT-TYPE
			SYNTAX Integer32 (0..4095)
			MAX-ACCESS read-write
			STATUS current
			DESCRIPTION
				"Description."
			::= { onuPriVoipParam 19 }

		
--          1.3.6.1.4.1.37950.1.1.5.12.3.1.16.20
-- 1.3.6.1.4.1.37950.1.1.5.12.3.1.16.20
-- 1.3.6.1.4.1.37950.1.1.5.12.3.1.16.20
-- 1.3.6.1.4.1.37950.1.1.5.12.3.1.16.20
-- 1.3.6.1.4.1.37950.1.1.5.12.3.1.16.20
-- 1.3.6.1.4.1.37950.1.1.5.12.3.1.16.20
-- 1.3.6.1.4.1.37950.1.1.5.12.3.1.16.20
-- 1.3.6.1.4.1.37950.1.1.5.12.3.1.16.20
-- 1.3.6.1.4.1.37950.1.1.5.12.3.1.16.20
		-- 1.3.6.1.4.1.37950.1.1.5.12.3.1.16.20
		priSVlanCos OBJECT-TYPE
			SYNTAX Integer32 (0..7)
			MAX-ACCESS read-write
			STATUS current
			DESCRIPTION
				"Description."
			::= { onuPriVoipParam 20 }

		
--          1.3.6.1.4.1.37950.1.1.5.12.3.1.16.21
-- 1.3.6.1.4.1.37950.1.1.5.12.3.1.16.21
-- 1.3.6.1.4.1.37950.1.1.5.12.3.1.16.21
-- 1.3.6.1.4.1.37950.1.1.5.12.3.1.16.21
-- 1.3.6.1.4.1.37950.1.1.5.12.3.1.16.21
-- 1.3.6.1.4.1.37950.1.1.5.12.3.1.16.21
-- 1.3.6.1.4.1.37950.1.1.5.12.3.1.16.21
-- 1.3.6.1.4.1.37950.1.1.5.12.3.1.16.21
-- 1.3.6.1.4.1.37950.1.1.5.12.3.1.16.21
		-- 1.3.6.1.4.1.37950.1.1.5.12.3.1.16.21
		priCVlanTpid OBJECT-TYPE
			SYNTAX Integer32
			MAX-ACCESS read-write
			STATUS current
			DESCRIPTION
				"Description."
			::= { onuPriVoipParam 21 }

		
--          1.3.6.1.4.1.37950.1.1.5.12.3.1.16.22
-- 1.3.6.1.4.1.37950.1.1.5.12.3.1.16.22
-- 1.3.6.1.4.1.37950.1.1.5.12.3.1.16.22
-- 1.3.6.1.4.1.37950.1.1.5.12.3.1.16.22
-- 1.3.6.1.4.1.37950.1.1.5.12.3.1.16.22
-- 1.3.6.1.4.1.37950.1.1.5.12.3.1.16.22
-- 1.3.6.1.4.1.37950.1.1.5.12.3.1.16.22
-- 1.3.6.1.4.1.37950.1.1.5.12.3.1.16.22
-- 1.3.6.1.4.1.37950.1.1.5.12.3.1.16.22
		-- 1.3.6.1.4.1.37950.1.1.5.12.3.1.16.22
		priCVlanId OBJECT-TYPE
			SYNTAX Integer32 (0..4095)
			MAX-ACCESS read-write
			STATUS current
			DESCRIPTION
				"Description."
			::= { onuPriVoipParam 22 }

		
--          1.3.6.1.4.1.37950.1.1.5.12.3.1.16.23
-- 1.3.6.1.4.1.37950.1.1.5.12.3.1.16.23
-- 1.3.6.1.4.1.37950.1.1.5.12.3.1.16.23
-- 1.3.6.1.4.1.37950.1.1.5.12.3.1.16.23
-- 1.3.6.1.4.1.37950.1.1.5.12.3.1.16.23
-- 1.3.6.1.4.1.37950.1.1.5.12.3.1.16.23
-- 1.3.6.1.4.1.37950.1.1.5.12.3.1.16.23
-- 1.3.6.1.4.1.37950.1.1.5.12.3.1.16.23
-- 1.3.6.1.4.1.37950.1.1.5.12.3.1.16.23
		-- 1.3.6.1.4.1.37950.1.1.5.12.3.1.16.23
		priCVlanCos OBJECT-TYPE
			SYNTAX Integer32 (0..7)
			MAX-ACCESS read-write
			STATUS current
			DESCRIPTION
				"Description."
			::= { onuPriVoipParam 23 }

		
--          1.3.6.1.4.1.37950.1.1.5.12.3.1.16.24
-- 1.3.6.1.4.1.37950.1.1.5.12.3.1.16.24
-- 1.3.6.1.4.1.37950.1.1.5.12.3.1.16.24
-- 1.3.6.1.4.1.37950.1.1.5.12.3.1.16.24
-- 1.3.6.1.4.1.37950.1.1.5.12.3.1.16.24
-- 1.3.6.1.4.1.37950.1.1.5.12.3.1.16.24
-- 1.3.6.1.4.1.37950.1.1.5.12.3.1.16.24
-- 1.3.6.1.4.1.37950.1.1.5.12.3.1.16.24
-- 1.3.6.1.4.1.37950.1.1.5.12.3.1.16.24
		-- 1.3.6.1.4.1.37950.1.1.5.12.3.1.16.24
		priRtpSVlanTpid OBJECT-TYPE
			SYNTAX Integer32
			MAX-ACCESS read-write
			STATUS current
			DESCRIPTION
				"Description."
			::= { onuPriVoipParam 24 }

		
--          1.3.6.1.4.1.37950.1.1.5.12.3.1.16.25
-- 1.3.6.1.4.1.37950.1.1.5.12.3.1.16.25
-- 1.3.6.1.4.1.37950.1.1.5.12.3.1.16.25
-- 1.3.6.1.4.1.37950.1.1.5.12.3.1.16.25
-- 1.3.6.1.4.1.37950.1.1.5.12.3.1.16.25
-- 1.3.6.1.4.1.37950.1.1.5.12.3.1.16.25
-- 1.3.6.1.4.1.37950.1.1.5.12.3.1.16.25
-- 1.3.6.1.4.1.37950.1.1.5.12.3.1.16.25
-- 1.3.6.1.4.1.37950.1.1.5.12.3.1.16.25
		-- 1.3.6.1.4.1.37950.1.1.5.12.3.1.16.25
		priRtpSVlanId OBJECT-TYPE
			SYNTAX Integer32 (0..4095)
			MAX-ACCESS read-write
			STATUS current
			DESCRIPTION
				"Description."
			::= { onuPriVoipParam 25 }

		
--          1.3.6.1.4.1.37950.1.1.5.12.3.1.16.26
-- 1.3.6.1.4.1.37950.1.1.5.12.3.1.16.26
-- 1.3.6.1.4.1.37950.1.1.5.12.3.1.16.26
-- 1.3.6.1.4.1.37950.1.1.5.12.3.1.16.26
-- 1.3.6.1.4.1.37950.1.1.5.12.3.1.16.26
-- 1.3.6.1.4.1.37950.1.1.5.12.3.1.16.26
-- 1.3.6.1.4.1.37950.1.1.5.12.3.1.16.26
-- 1.3.6.1.4.1.37950.1.1.5.12.3.1.16.26
-- 1.3.6.1.4.1.37950.1.1.5.12.3.1.16.26
		-- 1.3.6.1.4.1.37950.1.1.5.12.3.1.16.26
		priRtpSVlanCos OBJECT-TYPE
			SYNTAX Integer32 (0..7)
			MAX-ACCESS read-write
			STATUS current
			DESCRIPTION
				"Description."
			::= { onuPriVoipParam 26 }

		
--          1.3.6.1.4.1.37950.1.1.5.12.3.1.16.27
-- 1.3.6.1.4.1.37950.1.1.5.12.3.1.16.27
-- 1.3.6.1.4.1.37950.1.1.5.12.3.1.16.27
-- 1.3.6.1.4.1.37950.1.1.5.12.3.1.16.27
-- 1.3.6.1.4.1.37950.1.1.5.12.3.1.16.27
-- 1.3.6.1.4.1.37950.1.1.5.12.3.1.16.27
-- 1.3.6.1.4.1.37950.1.1.5.12.3.1.16.27
-- 1.3.6.1.4.1.37950.1.1.5.12.3.1.16.27
-- 1.3.6.1.4.1.37950.1.1.5.12.3.1.16.27
		-- 1.3.6.1.4.1.37950.1.1.5.12.3.1.16.27
		priRtpCVlanTpid OBJECT-TYPE
			SYNTAX Integer32
			MAX-ACCESS read-write
			STATUS current
			DESCRIPTION
				"Description."
			::= { onuPriVoipParam 27 }

		
--          1.3.6.1.4.1.37950.1.1.5.12.3.1.16.28
-- 1.3.6.1.4.1.37950.1.1.5.12.3.1.16.28
-- 1.3.6.1.4.1.37950.1.1.5.12.3.1.16.28
-- 1.3.6.1.4.1.37950.1.1.5.12.3.1.16.28
-- 1.3.6.1.4.1.37950.1.1.5.12.3.1.16.28
-- 1.3.6.1.4.1.37950.1.1.5.12.3.1.16.28
-- 1.3.6.1.4.1.37950.1.1.5.12.3.1.16.28
-- 1.3.6.1.4.1.37950.1.1.5.12.3.1.16.28
-- 1.3.6.1.4.1.37950.1.1.5.12.3.1.16.28
		-- 1.3.6.1.4.1.37950.1.1.5.12.3.1.16.28
		priRtpCVlanId OBJECT-TYPE
			SYNTAX Integer32 (0..4095)
			MAX-ACCESS read-write
			STATUS current
			DESCRIPTION
				"Description."
			::= { onuPriVoipParam 28 }

		
--          1.3.6.1.4.1.37950.1.1.5.12.3.1.16.29
-- 1.3.6.1.4.1.37950.1.1.5.12.3.1.16.29
-- 1.3.6.1.4.1.37950.1.1.5.12.3.1.16.29
-- 1.3.6.1.4.1.37950.1.1.5.12.3.1.16.29
-- 1.3.6.1.4.1.37950.1.1.5.12.3.1.16.29
-- 1.3.6.1.4.1.37950.1.1.5.12.3.1.16.29
-- 1.3.6.1.4.1.37950.1.1.5.12.3.1.16.29
-- 1.3.6.1.4.1.37950.1.1.5.12.3.1.16.29
-- 1.3.6.1.4.1.37950.1.1.5.12.3.1.16.29
		-- 1.3.6.1.4.1.37950.1.1.5.12.3.1.16.29
		priRtpCVlanCos OBJECT-TYPE
			SYNTAX Integer32 (0..7)
			MAX-ACCESS read-write
			STATUS current
			DESCRIPTION
				"Description."
			::= { onuPriVoipParam 29 }

		
--          1.3.6.1.4.1.37950.1.1.5.12.3.1.16.30
-- 1.3.6.1.4.1.37950.1.1.5.12.3.1.16.30
-- 1.3.6.1.4.1.37950.1.1.5.12.3.1.16.30
-- 1.3.6.1.4.1.37950.1.1.5.12.3.1.16.30
-- 1.3.6.1.4.1.37950.1.1.5.12.3.1.16.30
-- 1.3.6.1.4.1.37950.1.1.5.12.3.1.16.30
-- 1.3.6.1.4.1.37950.1.1.5.12.3.1.16.30
-- 1.3.6.1.4.1.37950.1.1.5.12.3.1.16.30
-- 1.3.6.1.4.1.37950.1.1.5.12.3.1.16.30
		-- 1.3.6.1.4.1.37950.1.1.5.12.3.1.16.30
		priVoipParamAction OBJECT-TYPE
			SYNTAX INTEGER
				{
				commit(1),
				remove(2)
				}
			MAX-ACCESS read-write
			STATUS current
			DESCRIPTION
				"Description."
			::= { onuPriVoipParam 30 }

		
--          1.3.6.1.4.1.37950.1.1.5.12.3.1.17
-- 1.3.6.1.4.1.37950.1.1.5.12.3.1.17
-- 1.3.6.1.4.1.37950.1.1.5.12.3.1.17
-- 1.3.6.1.4.1.37950.1.1.5.12.3.1.17
-- 1.3.6.1.4.1.37950.1.1.5.12.3.1.17
-- 1.3.6.1.4.1.37950.1.1.5.12.3.1.17
-- 1.3.6.1.4.1.37950.1.1.5.12.3.1.17
-- 1.3.6.1.4.1.37950.1.1.5.12.3.1.17
-- 1.3.6.1.4.1.37950.1.1.5.12.3.1.17
		-- 1.3.6.1.4.1.37950.1.1.5.12.3.1.17
		onuPriSipParam OBJECT IDENTIFIER ::= { onuPriGlobalCfg 17 }

		
--          1.3.6.1.4.1.37950.1.1.5.12.3.1.17.1
-- 1.3.6.1.4.1.37950.1.1.5.12.3.1.17.1
-- 1.3.6.1.4.1.37950.1.1.5.12.3.1.17.1
-- 1.3.6.1.4.1.37950.1.1.5.12.3.1.17.1
-- 1.3.6.1.4.1.37950.1.1.5.12.3.1.17.1
-- 1.3.6.1.4.1.37950.1.1.5.12.3.1.17.1
-- 1.3.6.1.4.1.37950.1.1.5.12.3.1.17.1
-- 1.3.6.1.4.1.37950.1.1.5.12.3.1.17.1
-- 1.3.6.1.4.1.37950.1.1.5.12.3.1.17.1
		-- 1.3.6.1.4.1.37950.1.1.5.12.3.1.17.1
		priSipParamPon OBJECT-TYPE
			SYNTAX Integer32 (1..8)
			MAX-ACCESS read-write
			STATUS current
			DESCRIPTION
				"Description."
			::= { onuPriSipParam 1 }

		
--          1.3.6.1.4.1.37950.1.1.5.12.3.1.17.2
-- 1.3.6.1.4.1.37950.1.1.5.12.3.1.17.2
-- 1.3.6.1.4.1.37950.1.1.5.12.3.1.17.2
-- 1.3.6.1.4.1.37950.1.1.5.12.3.1.17.2
-- 1.3.6.1.4.1.37950.1.1.5.12.3.1.17.2
-- 1.3.6.1.4.1.37950.1.1.5.12.3.1.17.2
-- 1.3.6.1.4.1.37950.1.1.5.12.3.1.17.2
-- 1.3.6.1.4.1.37950.1.1.5.12.3.1.17.2
-- 1.3.6.1.4.1.37950.1.1.5.12.3.1.17.2
		-- 1.3.6.1.4.1.37950.1.1.5.12.3.1.17.2
		priSipParamOnu OBJECT-TYPE
			SYNTAX Integer32 (1..65535)
			MAX-ACCESS read-write
			STATUS current
			DESCRIPTION
				"Description."
			::= { onuPriSipParam 2 }

		
--          1.3.6.1.4.1.37950.1.1.5.12.3.1.17.3
-- 1.3.6.1.4.1.37950.1.1.5.12.3.1.17.3
-- 1.3.6.1.4.1.37950.1.1.5.12.3.1.17.3
-- 1.3.6.1.4.1.37950.1.1.5.12.3.1.17.3
-- 1.3.6.1.4.1.37950.1.1.5.12.3.1.17.3
-- 1.3.6.1.4.1.37950.1.1.5.12.3.1.17.3
-- 1.3.6.1.4.1.37950.1.1.5.12.3.1.17.3
-- 1.3.6.1.4.1.37950.1.1.5.12.3.1.17.3
-- 1.3.6.1.4.1.37950.1.1.5.12.3.1.17.3
		-- 1.3.6.1.4.1.37950.1.1.5.12.3.1.17.3
		priProxyServName OBJECT-TYPE
			SYNTAX OCTET STRING
			MAX-ACCESS read-write
			STATUS current
			DESCRIPTION
				"Description."
			::= { onuPriSipParam 3 }

		
--          1.3.6.1.4.1.37950.1.1.5.12.3.1.17.4
-- 1.3.6.1.4.1.37950.1.1.5.12.3.1.17.4
-- 1.3.6.1.4.1.37950.1.1.5.12.3.1.17.4
-- 1.3.6.1.4.1.37950.1.1.5.12.3.1.17.4
-- 1.3.6.1.4.1.37950.1.1.5.12.3.1.17.4
-- 1.3.6.1.4.1.37950.1.1.5.12.3.1.17.4
-- 1.3.6.1.4.1.37950.1.1.5.12.3.1.17.4
-- 1.3.6.1.4.1.37950.1.1.5.12.3.1.17.4
-- 1.3.6.1.4.1.37950.1.1.5.12.3.1.17.4
		-- 1.3.6.1.4.1.37950.1.1.5.12.3.1.17.4
		priProxyServPort OBJECT-TYPE
			SYNTAX Integer32 (0..65535)
			MAX-ACCESS read-write
			STATUS current
			DESCRIPTION
				"Description."
			::= { onuPriSipParam 4 }

		
--          1.3.6.1.4.1.37950.1.1.5.12.3.1.17.5
-- 1.3.6.1.4.1.37950.1.1.5.12.3.1.17.5
-- 1.3.6.1.4.1.37950.1.1.5.12.3.1.17.5
-- 1.3.6.1.4.1.37950.1.1.5.12.3.1.17.5
-- 1.3.6.1.4.1.37950.1.1.5.12.3.1.17.5
-- 1.3.6.1.4.1.37950.1.1.5.12.3.1.17.5
-- 1.3.6.1.4.1.37950.1.1.5.12.3.1.17.5
-- 1.3.6.1.4.1.37950.1.1.5.12.3.1.17.5
-- 1.3.6.1.4.1.37950.1.1.5.12.3.1.17.5
		-- 1.3.6.1.4.1.37950.1.1.5.12.3.1.17.5
		priBakProxyServName OBJECT-TYPE
			SYNTAX OCTET STRING
			MAX-ACCESS read-write
			STATUS current
			DESCRIPTION
				"Description."
			::= { onuPriSipParam 5 }

		
--          1.3.6.1.4.1.37950.1.1.5.12.3.1.17.6
-- 1.3.6.1.4.1.37950.1.1.5.12.3.1.17.6
-- 1.3.6.1.4.1.37950.1.1.5.12.3.1.17.6
-- 1.3.6.1.4.1.37950.1.1.5.12.3.1.17.6
-- 1.3.6.1.4.1.37950.1.1.5.12.3.1.17.6
-- 1.3.6.1.4.1.37950.1.1.5.12.3.1.17.6
-- 1.3.6.1.4.1.37950.1.1.5.12.3.1.17.6
-- 1.3.6.1.4.1.37950.1.1.5.12.3.1.17.6
-- 1.3.6.1.4.1.37950.1.1.5.12.3.1.17.6
		-- 1.3.6.1.4.1.37950.1.1.5.12.3.1.17.6
		priBakProxyServPort OBJECT-TYPE
			SYNTAX Integer32 (0..65535)
			MAX-ACCESS read-write
			STATUS current
			DESCRIPTION
				"Description."
			::= { onuPriSipParam 6 }

		
--          1.3.6.1.4.1.37950.1.1.5.12.3.1.17.7
-- 1.3.6.1.4.1.37950.1.1.5.12.3.1.17.7
-- 1.3.6.1.4.1.37950.1.1.5.12.3.1.17.7
-- 1.3.6.1.4.1.37950.1.1.5.12.3.1.17.7
-- 1.3.6.1.4.1.37950.1.1.5.12.3.1.17.7
-- 1.3.6.1.4.1.37950.1.1.5.12.3.1.17.7
-- 1.3.6.1.4.1.37950.1.1.5.12.3.1.17.7
-- 1.3.6.1.4.1.37950.1.1.5.12.3.1.17.7
-- 1.3.6.1.4.1.37950.1.1.5.12.3.1.17.7
		-- 1.3.6.1.4.1.37950.1.1.5.12.3.1.17.7
		priRegServName OBJECT-TYPE
			SYNTAX OCTET STRING
			MAX-ACCESS read-write
			STATUS current
			DESCRIPTION
				"Description."
			::= { onuPriSipParam 7 }

		
--          1.3.6.1.4.1.37950.1.1.5.12.3.1.17.8
-- 1.3.6.1.4.1.37950.1.1.5.12.3.1.17.8
-- 1.3.6.1.4.1.37950.1.1.5.12.3.1.17.8
-- 1.3.6.1.4.1.37950.1.1.5.12.3.1.17.8
-- 1.3.6.1.4.1.37950.1.1.5.12.3.1.17.8
-- 1.3.6.1.4.1.37950.1.1.5.12.3.1.17.8
-- 1.3.6.1.4.1.37950.1.1.5.12.3.1.17.8
-- 1.3.6.1.4.1.37950.1.1.5.12.3.1.17.8
-- 1.3.6.1.4.1.37950.1.1.5.12.3.1.17.8
		-- 1.3.6.1.4.1.37950.1.1.5.12.3.1.17.8
		priRegServPort OBJECT-TYPE
			SYNTAX Integer32 (0..65535)
			MAX-ACCESS read-write
			STATUS current
			DESCRIPTION
				"Description."
			::= { onuPriSipParam 8 }

		
--          1.3.6.1.4.1.37950.1.1.5.12.3.1.17.9
-- 1.3.6.1.4.1.37950.1.1.5.12.3.1.17.9
-- 1.3.6.1.4.1.37950.1.1.5.12.3.1.17.9
-- 1.3.6.1.4.1.37950.1.1.5.12.3.1.17.9
-- 1.3.6.1.4.1.37950.1.1.5.12.3.1.17.9
-- 1.3.6.1.4.1.37950.1.1.5.12.3.1.17.9
-- 1.3.6.1.4.1.37950.1.1.5.12.3.1.17.9
-- 1.3.6.1.4.1.37950.1.1.5.12.3.1.17.9
-- 1.3.6.1.4.1.37950.1.1.5.12.3.1.17.9
		-- 1.3.6.1.4.1.37950.1.1.5.12.3.1.17.9
		priBakRegServName OBJECT-TYPE
			SYNTAX OCTET STRING
			MAX-ACCESS read-write
			STATUS current
			DESCRIPTION
				"Description."
			::= { onuPriSipParam 9 }

		
--          1.3.6.1.4.1.37950.1.1.5.12.3.1.17.10
-- 1.3.6.1.4.1.37950.1.1.5.12.3.1.17.10
-- 1.3.6.1.4.1.37950.1.1.5.12.3.1.17.10
-- 1.3.6.1.4.1.37950.1.1.5.12.3.1.17.10
-- 1.3.6.1.4.1.37950.1.1.5.12.3.1.17.10
-- 1.3.6.1.4.1.37950.1.1.5.12.3.1.17.10
-- 1.3.6.1.4.1.37950.1.1.5.12.3.1.17.10
-- 1.3.6.1.4.1.37950.1.1.5.12.3.1.17.10
-- 1.3.6.1.4.1.37950.1.1.5.12.3.1.17.10
		-- 1.3.6.1.4.1.37950.1.1.5.12.3.1.17.10
		priBakRegServPort OBJECT-TYPE
			SYNTAX Integer32 (0..65535)
			MAX-ACCESS read-write
			STATUS current
			DESCRIPTION
				"Description."
			::= { onuPriSipParam 10 }

		
--          1.3.6.1.4.1.37950.1.1.5.12.3.1.17.11
-- 1.3.6.1.4.1.37950.1.1.5.12.3.1.17.11
-- 1.3.6.1.4.1.37950.1.1.5.12.3.1.17.11
-- 1.3.6.1.4.1.37950.1.1.5.12.3.1.17.11
-- 1.3.6.1.4.1.37950.1.1.5.12.3.1.17.11
-- 1.3.6.1.4.1.37950.1.1.5.12.3.1.17.11
-- 1.3.6.1.4.1.37950.1.1.5.12.3.1.17.11
-- 1.3.6.1.4.1.37950.1.1.5.12.3.1.17.11
-- 1.3.6.1.4.1.37950.1.1.5.12.3.1.17.11
		-- 1.3.6.1.4.1.37950.1.1.5.12.3.1.17.11
		priOutBndServName OBJECT-TYPE
			SYNTAX OCTET STRING
			MAX-ACCESS read-write
			STATUS current
			DESCRIPTION
				"Description."
			::= { onuPriSipParam 11 }

		
--          1.3.6.1.4.1.37950.1.1.5.12.3.1.17.12
-- 1.3.6.1.4.1.37950.1.1.5.12.3.1.17.12
-- 1.3.6.1.4.1.37950.1.1.5.12.3.1.17.12
-- 1.3.6.1.4.1.37950.1.1.5.12.3.1.17.12
-- 1.3.6.1.4.1.37950.1.1.5.12.3.1.17.12
-- 1.3.6.1.4.1.37950.1.1.5.12.3.1.17.12
-- 1.3.6.1.4.1.37950.1.1.5.12.3.1.17.12
-- 1.3.6.1.4.1.37950.1.1.5.12.3.1.17.12
-- 1.3.6.1.4.1.37950.1.1.5.12.3.1.17.12
		-- 1.3.6.1.4.1.37950.1.1.5.12.3.1.17.12
		priOutBndServPort OBJECT-TYPE
			SYNTAX Integer32 (0..65535)
			MAX-ACCESS read-write
			STATUS current
			DESCRIPTION
				"Description."
			::= { onuPriSipParam 12 }

		
--          1.3.6.1.4.1.37950.1.1.5.12.3.1.17.13
-- 1.3.6.1.4.1.37950.1.1.5.12.3.1.17.13
-- 1.3.6.1.4.1.37950.1.1.5.12.3.1.17.13
-- 1.3.6.1.4.1.37950.1.1.5.12.3.1.17.13
-- 1.3.6.1.4.1.37950.1.1.5.12.3.1.17.13
-- 1.3.6.1.4.1.37950.1.1.5.12.3.1.17.13
-- 1.3.6.1.4.1.37950.1.1.5.12.3.1.17.13
-- 1.3.6.1.4.1.37950.1.1.5.12.3.1.17.13
-- 1.3.6.1.4.1.37950.1.1.5.12.3.1.17.13
		-- 1.3.6.1.4.1.37950.1.1.5.12.3.1.17.13
		priSipParamMgPort OBJECT-TYPE
			SYNTAX Integer32 (0..65535)
			MAX-ACCESS read-write
			STATUS current
			DESCRIPTION
				"Description."
			::= { onuPriSipParam 13 }

		
--          1.3.6.1.4.1.37950.1.1.5.12.3.1.17.14
-- 1.3.6.1.4.1.37950.1.1.5.12.3.1.17.14
-- 1.3.6.1.4.1.37950.1.1.5.12.3.1.17.14
-- 1.3.6.1.4.1.37950.1.1.5.12.3.1.17.14
-- 1.3.6.1.4.1.37950.1.1.5.12.3.1.17.14
-- 1.3.6.1.4.1.37950.1.1.5.12.3.1.17.14
-- 1.3.6.1.4.1.37950.1.1.5.12.3.1.17.14
-- 1.3.6.1.4.1.37950.1.1.5.12.3.1.17.14
-- 1.3.6.1.4.1.37950.1.1.5.12.3.1.17.14
		-- 1.3.6.1.4.1.37950.1.1.5.12.3.1.17.14
		priRegInterval OBJECT-TYPE
			SYNTAX Integer32 (0..10000000)
			MAX-ACCESS read-write
			STATUS current
			DESCRIPTION
				"Description."
			::= { onuPriSipParam 14 }

		
--          1.3.6.1.4.1.37950.1.1.5.12.3.1.17.15
-- 1.3.6.1.4.1.37950.1.1.5.12.3.1.17.15
-- 1.3.6.1.4.1.37950.1.1.5.12.3.1.17.15
-- 1.3.6.1.4.1.37950.1.1.5.12.3.1.17.15
-- 1.3.6.1.4.1.37950.1.1.5.12.3.1.17.15
-- 1.3.6.1.4.1.37950.1.1.5.12.3.1.17.15
-- 1.3.6.1.4.1.37950.1.1.5.12.3.1.17.15
-- 1.3.6.1.4.1.37950.1.1.5.12.3.1.17.15
-- 1.3.6.1.4.1.37950.1.1.5.12.3.1.17.15
		-- 1.3.6.1.4.1.37950.1.1.5.12.3.1.17.15
		priHBeatCfg OBJECT-TYPE
			SYNTAX INTEGER
				{
				disable(0),
				active(1),
				passive(2)
				}
			MAX-ACCESS read-write
			STATUS current
			DESCRIPTION
				"Description."
			::= { onuPriSipParam 15 }

		
--          1.3.6.1.4.1.37950.1.1.5.12.3.1.17.16
-- 1.3.6.1.4.1.37950.1.1.5.12.3.1.17.16
-- 1.3.6.1.4.1.37950.1.1.5.12.3.1.17.16
-- 1.3.6.1.4.1.37950.1.1.5.12.3.1.17.16
-- 1.3.6.1.4.1.37950.1.1.5.12.3.1.17.16
-- 1.3.6.1.4.1.37950.1.1.5.12.3.1.17.16
-- 1.3.6.1.4.1.37950.1.1.5.12.3.1.17.16
-- 1.3.6.1.4.1.37950.1.1.5.12.3.1.17.16
-- 1.3.6.1.4.1.37950.1.1.5.12.3.1.17.16
		-- 1.3.6.1.4.1.37950.1.1.5.12.3.1.17.16
		priHBeatCycle OBJECT-TYPE
			SYNTAX Integer32 (1..65525)
			MAX-ACCESS read-write
			STATUS current
			DESCRIPTION
				"Description."
			::= { onuPriSipParam 16 }

		
--          1.3.6.1.4.1.37950.1.1.5.12.3.1.17.17
-- 1.3.6.1.4.1.37950.1.1.5.12.3.1.17.17
-- 1.3.6.1.4.1.37950.1.1.5.12.3.1.17.17
-- 1.3.6.1.4.1.37950.1.1.5.12.3.1.17.17
-- 1.3.6.1.4.1.37950.1.1.5.12.3.1.17.17
-- 1.3.6.1.4.1.37950.1.1.5.12.3.1.17.17
-- 1.3.6.1.4.1.37950.1.1.5.12.3.1.17.17
-- 1.3.6.1.4.1.37950.1.1.5.12.3.1.17.17
-- 1.3.6.1.4.1.37950.1.1.5.12.3.1.17.17
		-- 1.3.6.1.4.1.37950.1.1.5.12.3.1.17.17
		priHBeatCount OBJECT-TYPE
			SYNTAX Integer32 (1..65535)
			MAX-ACCESS read-write
			STATUS current
			DESCRIPTION
				"Description."
			::= { onuPriSipParam 17 }

		
--          1.3.6.1.4.1.37950.1.1.5.12.3.1.17.18
-- 1.3.6.1.4.1.37950.1.1.5.12.3.1.17.18
-- 1.3.6.1.4.1.37950.1.1.5.12.3.1.17.18
-- 1.3.6.1.4.1.37950.1.1.5.12.3.1.17.18
-- 1.3.6.1.4.1.37950.1.1.5.12.3.1.17.18
-- 1.3.6.1.4.1.37950.1.1.5.12.3.1.17.18
-- 1.3.6.1.4.1.37950.1.1.5.12.3.1.17.18
-- 1.3.6.1.4.1.37950.1.1.5.12.3.1.17.18
-- 1.3.6.1.4.1.37950.1.1.5.12.3.1.17.18
		-- 1.3.6.1.4.1.37950.1.1.5.12.3.1.17.18
		priSipGloParamAction OBJECT-TYPE
			SYNTAX INTEGER
				{
				commit(1),
				remove(2)
				}
			MAX-ACCESS read-write
			STATUS current
			DESCRIPTION
				"Description."
			::= { onuPriSipParam 18 }

		
--         1.3.6.1.4.1.37950.1.1.5.12.3.1.18
-- 1.3.6.1.4.1.37950.1.1.5.12.3.1.18
-- 1.3.6.1.4.1.37950.1.1.5.12.3.1.18
-- 1.3.6.1.4.1.37950.1.1.5.12.3.1.18
-- 1.3.6.1.4.1.37950.1.1.5.12.3.1.18
-- 1.3.6.1.4.1.37950.1.1.5.12.3.1.18
-- 1.3.6.1.4.1.37950.1.1.5.12.3.1.18
-- 1.3.6.1.4.1.37950.1.1.5.12.3.1.18
		-- 1.3.6.1.4.1.37950.1.1.5.12.3.1.18
		onuPriSecurity OBJECT IDENTIFIER ::= { onuPriGlobalCfg 18 }

		
--         1.3.6.1.4.1.37950.1.1.5.12.3.1.18.1
-- 1.3.6.1.4.1.37950.1.1.5.12.3.1.18.1
-- 1.3.6.1.4.1.37950.1.1.5.12.3.1.18.1
-- 1.3.6.1.4.1.37950.1.1.5.12.3.1.18.1
-- 1.3.6.1.4.1.37950.1.1.5.12.3.1.18.1
-- 1.3.6.1.4.1.37950.1.1.5.12.3.1.18.1
-- 1.3.6.1.4.1.37950.1.1.5.12.3.1.18.1
-- 1.3.6.1.4.1.37950.1.1.5.12.3.1.18.1
		-- 1.3.6.1.4.1.37950.1.1.5.12.3.1.18.1
		priPonID OBJECT-TYPE
			SYNTAX Unsigned32
			MAX-ACCESS read-write
			STATUS current
			DESCRIPTION
				"Description."
			::= { onuPriSecurity 1 }

		
--         1.3.6.1.4.1.37950.1.1.5.12.3.1.18.2
-- 1.3.6.1.4.1.37950.1.1.5.12.3.1.18.2
-- 1.3.6.1.4.1.37950.1.1.5.12.3.1.18.2
-- 1.3.6.1.4.1.37950.1.1.5.12.3.1.18.2
-- 1.3.6.1.4.1.37950.1.1.5.12.3.1.18.2
-- 1.3.6.1.4.1.37950.1.1.5.12.3.1.18.2
-- 1.3.6.1.4.1.37950.1.1.5.12.3.1.18.2
-- 1.3.6.1.4.1.37950.1.1.5.12.3.1.18.2
		-- 1.3.6.1.4.1.37950.1.1.5.12.3.1.18.2
		priOnuID OBJECT-TYPE
			SYNTAX Unsigned32
			MAX-ACCESS read-write
			STATUS current
			DESCRIPTION
				"Description."
			::= { onuPriSecurity 2 }

		
--         1.3.6.1.4.1.37950.1.1.5.12.3.1.18.3
-- 1.3.6.1.4.1.37950.1.1.5.12.3.1.18.3
-- 1.3.6.1.4.1.37950.1.1.5.12.3.1.18.3
-- 1.3.6.1.4.1.37950.1.1.5.12.3.1.18.3
-- 1.3.6.1.4.1.37950.1.1.5.12.3.1.18.3
-- 1.3.6.1.4.1.37950.1.1.5.12.3.1.18.3
-- 1.3.6.1.4.1.37950.1.1.5.12.3.1.18.3
-- 1.3.6.1.4.1.37950.1.1.5.12.3.1.18.3
		-- 1.3.6.1.4.1.37950.1.1.5.12.3.1.18.3
		onuPriUsername OBJECT IDENTIFIER ::= { onuPriSecurity 3 }

		
--         1.3.6.1.4.1.37950.1.1.5.12.3.1.18.3.1
-- 1.3.6.1.4.1.37950.1.1.5.12.3.1.18.3.1
-- 1.3.6.1.4.1.37950.1.1.5.12.3.1.18.3.1
-- 1.3.6.1.4.1.37950.1.1.5.12.3.1.18.3.1
-- 1.3.6.1.4.1.37950.1.1.5.12.3.1.18.3.1
-- 1.3.6.1.4.1.37950.1.1.5.12.3.1.18.3.1
-- 1.3.6.1.4.1.37950.1.1.5.12.3.1.18.3.1
-- 1.3.6.1.4.1.37950.1.1.5.12.3.1.18.3.1
		-- 1.3.6.1.4.1.37950.1.1.5.12.3.1.18.3.1
		priAdminCtl OBJECT-TYPE
			SYNTAX INTEGER
				{
				disable(0),
				enable(1)
				}
			MAX-ACCESS read-write
			STATUS current
			DESCRIPTION
				"Description."
			::= { onuPriUsername 1 }

		
--         1.3.6.1.4.1.37950.1.1.5.12.3.1.18.3.2
-- 1.3.6.1.4.1.37950.1.1.5.12.3.1.18.3.2
-- 1.3.6.1.4.1.37950.1.1.5.12.3.1.18.3.2
-- 1.3.6.1.4.1.37950.1.1.5.12.3.1.18.3.2
-- 1.3.6.1.4.1.37950.1.1.5.12.3.1.18.3.2
-- 1.3.6.1.4.1.37950.1.1.5.12.3.1.18.3.2
-- 1.3.6.1.4.1.37950.1.1.5.12.3.1.18.3.2
-- 1.3.6.1.4.1.37950.1.1.5.12.3.1.18.3.2
		-- 1.3.6.1.4.1.37950.1.1.5.12.3.1.18.3.2
		priAdminName OBJECT-TYPE
			SYNTAX OCTET STRING
			MAX-ACCESS read-write
			STATUS current
			DESCRIPTION
				"Description."
			::= { onuPriUsername 2 }

		
--         1.3.6.1.4.1.37950.1.1.5.12.3.1.18.3.3
-- 1.3.6.1.4.1.37950.1.1.5.12.3.1.18.3.3
-- 1.3.6.1.4.1.37950.1.1.5.12.3.1.18.3.3
-- 1.3.6.1.4.1.37950.1.1.5.12.3.1.18.3.3
-- 1.3.6.1.4.1.37950.1.1.5.12.3.1.18.3.3
-- 1.3.6.1.4.1.37950.1.1.5.12.3.1.18.3.3
-- 1.3.6.1.4.1.37950.1.1.5.12.3.1.18.3.3
-- 1.3.6.1.4.1.37950.1.1.5.12.3.1.18.3.3
		-- 1.3.6.1.4.1.37950.1.1.5.12.3.1.18.3.3
		priAdminPwd OBJECT-TYPE
			SYNTAX OCTET STRING
			MAX-ACCESS read-write
			STATUS current
			DESCRIPTION
				"Description."
			::= { onuPriUsername 3 }

		
--         1.3.6.1.4.1.37950.1.1.5.12.3.1.18.3.4
-- 1.3.6.1.4.1.37950.1.1.5.12.3.1.18.3.4
-- 1.3.6.1.4.1.37950.1.1.5.12.3.1.18.3.4
-- 1.3.6.1.4.1.37950.1.1.5.12.3.1.18.3.4
-- 1.3.6.1.4.1.37950.1.1.5.12.3.1.18.3.4
-- 1.3.6.1.4.1.37950.1.1.5.12.3.1.18.3.4
-- 1.3.6.1.4.1.37950.1.1.5.12.3.1.18.3.4
-- 1.3.6.1.4.1.37950.1.1.5.12.3.1.18.3.4
		-- 1.3.6.1.4.1.37950.1.1.5.12.3.1.18.3.4
		priUserCtl OBJECT-TYPE
			SYNTAX INTEGER
				{
				disable(0),
				enable(1)
				}
			MAX-ACCESS read-write
			STATUS current
			DESCRIPTION
				"Description."
			::= { onuPriUsername 4 }

		
--         1.3.6.1.4.1.37950.1.1.5.12.3.1.18.3.5
-- 1.3.6.1.4.1.37950.1.1.5.12.3.1.18.3.5
-- 1.3.6.1.4.1.37950.1.1.5.12.3.1.18.3.5
-- 1.3.6.1.4.1.37950.1.1.5.12.3.1.18.3.5
-- 1.3.6.1.4.1.37950.1.1.5.12.3.1.18.3.5
-- 1.3.6.1.4.1.37950.1.1.5.12.3.1.18.3.5
-- 1.3.6.1.4.1.37950.1.1.5.12.3.1.18.3.5
-- 1.3.6.1.4.1.37950.1.1.5.12.3.1.18.3.5
		-- 1.3.6.1.4.1.37950.1.1.5.12.3.1.18.3.5
		priUserName OBJECT-TYPE
			SYNTAX OCTET STRING
			MAX-ACCESS read-write
			STATUS current
			DESCRIPTION
				"Description."
			::= { onuPriUsername 5 }

		
--         1.3.6.1.4.1.37950.1.1.5.12.3.1.18.3.6
-- 1.3.6.1.4.1.37950.1.1.5.12.3.1.18.3.6
-- 1.3.6.1.4.1.37950.1.1.5.12.3.1.18.3.6
-- 1.3.6.1.4.1.37950.1.1.5.12.3.1.18.3.6
-- 1.3.6.1.4.1.37950.1.1.5.12.3.1.18.3.6
-- 1.3.6.1.4.1.37950.1.1.5.12.3.1.18.3.6
-- 1.3.6.1.4.1.37950.1.1.5.12.3.1.18.3.6
-- 1.3.6.1.4.1.37950.1.1.5.12.3.1.18.3.6
		-- 1.3.6.1.4.1.37950.1.1.5.12.3.1.18.3.6
		priUserPwd OBJECT-TYPE
			SYNTAX OCTET STRING
			MAX-ACCESS read-write
			STATUS current
			DESCRIPTION
				"Description."
			::= { onuPriUsername 6 }

		
--         1.3.6.1.4.1.37950.1.1.5.12.3.1.18.3.7
-- 1.3.6.1.4.1.37950.1.1.5.12.3.1.18.3.7
-- 1.3.6.1.4.1.37950.1.1.5.12.3.1.18.3.7
-- 1.3.6.1.4.1.37950.1.1.5.12.3.1.18.3.7
-- 1.3.6.1.4.1.37950.1.1.5.12.3.1.18.3.7
-- 1.3.6.1.4.1.37950.1.1.5.12.3.1.18.3.7
-- 1.3.6.1.4.1.37950.1.1.5.12.3.1.18.3.7
-- 1.3.6.1.4.1.37950.1.1.5.12.3.1.18.3.7
		-- 1.3.6.1.4.1.37950.1.1.5.12.3.1.18.3.7
		priUsernameAction OBJECT-TYPE
			SYNTAX INTEGER
				{
				del(0),
				add(1)
				}
			MAX-ACCESS read-write
			STATUS current
			DESCRIPTION
				"Description."
			::= { onuPriUsername 7 }

		
--         1.3.6.1.4.1.37950.1.1.5.12.3.1.18.4
-- 1.3.6.1.4.1.37950.1.1.5.12.3.1.18.4
-- 1.3.6.1.4.1.37950.1.1.5.12.3.1.18.4
-- 1.3.6.1.4.1.37950.1.1.5.12.3.1.18.4
-- 1.3.6.1.4.1.37950.1.1.5.12.3.1.18.4
-- 1.3.6.1.4.1.37950.1.1.5.12.3.1.18.4
-- 1.3.6.1.4.1.37950.1.1.5.12.3.1.18.4
-- 1.3.6.1.4.1.37950.1.1.5.12.3.1.18.4
		-- 1.3.6.1.4.1.37950.1.1.5.12.3.1.18.4
		onuPriFirewall OBJECT IDENTIFIER ::= { onuPriSecurity 4 }

		
--         1.3.6.1.4.1.37950.1.1.5.12.3.1.18.4.1
-- 1.3.6.1.4.1.37950.1.1.5.12.3.1.18.4.1
-- 1.3.6.1.4.1.37950.1.1.5.12.3.1.18.4.1
-- 1.3.6.1.4.1.37950.1.1.5.12.3.1.18.4.1
-- 1.3.6.1.4.1.37950.1.1.5.12.3.1.18.4.1
-- 1.3.6.1.4.1.37950.1.1.5.12.3.1.18.4.1
-- 1.3.6.1.4.1.37950.1.1.5.12.3.1.18.4.1
-- 1.3.6.1.4.1.37950.1.1.5.12.3.1.18.4.1
		-- 1.3.6.1.4.1.37950.1.1.5.12.3.1.18.4.1
		priFirewall OBJECT-TYPE
			SYNTAX INTEGER
				{
				disable(0),
				low(1),
				middle(2),
				high(3)
				}
			MAX-ACCESS read-write
			STATUS current
			DESCRIPTION
				"Description."
			::= { onuPriFirewall 1 }

		
--         1.3.6.1.4.1.37950.1.1.5.12.3.1.18.5
-- 1.3.6.1.4.1.37950.1.1.5.12.3.1.18.5
-- 1.3.6.1.4.1.37950.1.1.5.12.3.1.18.5
-- 1.3.6.1.4.1.37950.1.1.5.12.3.1.18.5
-- 1.3.6.1.4.1.37950.1.1.5.12.3.1.18.5
-- 1.3.6.1.4.1.37950.1.1.5.12.3.1.18.5
-- 1.3.6.1.4.1.37950.1.1.5.12.3.1.18.5
-- 1.3.6.1.4.1.37950.1.1.5.12.3.1.18.5
		-- 1.3.6.1.4.1.37950.1.1.5.12.3.1.18.5
		onuPriAcl OBJECT IDENTIFIER ::= { onuPriSecurity 5 }

		
--         1.3.6.1.4.1.37950.1.1.5.12.3.1.18.5.1
-- 1.3.6.1.4.1.37950.1.1.5.12.3.1.18.5.1
-- 1.3.6.1.4.1.37950.1.1.5.12.3.1.18.5.1
-- 1.3.6.1.4.1.37950.1.1.5.12.3.1.18.5.1
-- 1.3.6.1.4.1.37950.1.1.5.12.3.1.18.5.1
-- 1.3.6.1.4.1.37950.1.1.5.12.3.1.18.5.1
-- 1.3.6.1.4.1.37950.1.1.5.12.3.1.18.5.1
-- 1.3.6.1.4.1.37950.1.1.5.12.3.1.18.5.1
		-- 1.3.6.1.4.1.37950.1.1.5.12.3.1.18.5.1
		priAclProtocol OBJECT-TYPE
			SYNTAX INTEGER
				{
				telnet(0),
				ftp(1),
				http(2),
				https(3),
				tftp(4),
				ping(5)
				}
			MAX-ACCESS read-write
			STATUS current
			DESCRIPTION
				"Description."
			::= { onuPriAcl 1 }

		
--         1.3.6.1.4.1.37950.1.1.5.12.3.1.18.5.2
-- 1.3.6.1.4.1.37950.1.1.5.12.3.1.18.5.2
-- 1.3.6.1.4.1.37950.1.1.5.12.3.1.18.5.2
-- 1.3.6.1.4.1.37950.1.1.5.12.3.1.18.5.2
-- 1.3.6.1.4.1.37950.1.1.5.12.3.1.18.5.2
-- 1.3.6.1.4.1.37950.1.1.5.12.3.1.18.5.2
-- 1.3.6.1.4.1.37950.1.1.5.12.3.1.18.5.2
-- 1.3.6.1.4.1.37950.1.1.5.12.3.1.18.5.2
		-- 1.3.6.1.4.1.37950.1.1.5.12.3.1.18.5.2
		priAclCtl OBJECT-TYPE
			SYNTAX INTEGER
				{
				disable(0),
				enable(1)
				}
			MAX-ACCESS read-write
			STATUS current
			DESCRIPTION
				"Description."
			::= { onuPriAcl 2 }

		
--         1.3.6.1.4.1.37950.1.1.5.12.3.1.18.5.3
-- 1.3.6.1.4.1.37950.1.1.5.12.3.1.18.5.3
-- 1.3.6.1.4.1.37950.1.1.5.12.3.1.18.5.3
-- 1.3.6.1.4.1.37950.1.1.5.12.3.1.18.5.3
-- 1.3.6.1.4.1.37950.1.1.5.12.3.1.18.5.3
-- 1.3.6.1.4.1.37950.1.1.5.12.3.1.18.5.3
-- 1.3.6.1.4.1.37950.1.1.5.12.3.1.18.5.3
-- 1.3.6.1.4.1.37950.1.1.5.12.3.1.18.5.3
		-- 1.3.6.1.4.1.37950.1.1.5.12.3.1.18.5.3
		priAclLanCtl OBJECT-TYPE
			SYNTAX INTEGER
				{
				disable(0),
				enable(1)
				}
			MAX-ACCESS read-write
			STATUS current
			DESCRIPTION
				"Description."
			::= { onuPriAcl 3 }

		
--         1.3.6.1.4.1.37950.1.1.5.12.3.1.18.5.4
-- 1.3.6.1.4.1.37950.1.1.5.12.3.1.18.5.4
-- 1.3.6.1.4.1.37950.1.1.5.12.3.1.18.5.4
-- 1.3.6.1.4.1.37950.1.1.5.12.3.1.18.5.4
-- 1.3.6.1.4.1.37950.1.1.5.12.3.1.18.5.4
-- 1.3.6.1.4.1.37950.1.1.5.12.3.1.18.5.4
-- 1.3.6.1.4.1.37950.1.1.5.12.3.1.18.5.4
-- 1.3.6.1.4.1.37950.1.1.5.12.3.1.18.5.4
		-- 1.3.6.1.4.1.37950.1.1.5.12.3.1.18.5.4
		priAclWanCtl OBJECT-TYPE
			SYNTAX INTEGER
				{
				disable(0),
				enable(1)
				}
			MAX-ACCESS read-write
			STATUS current
			DESCRIPTION
				"Description."
			::= { onuPriAcl 4 }

		
--         1.3.6.1.4.1.37950.1.1.5.12.3.1.18.5.5
-- 1.3.6.1.4.1.37950.1.1.5.12.3.1.18.5.5
-- 1.3.6.1.4.1.37950.1.1.5.12.3.1.18.5.5
-- 1.3.6.1.4.1.37950.1.1.5.12.3.1.18.5.5
-- 1.3.6.1.4.1.37950.1.1.5.12.3.1.18.5.5
-- 1.3.6.1.4.1.37950.1.1.5.12.3.1.18.5.5
-- 1.3.6.1.4.1.37950.1.1.5.12.3.1.18.5.5
-- 1.3.6.1.4.1.37950.1.1.5.12.3.1.18.5.5
		-- 1.3.6.1.4.1.37950.1.1.5.12.3.1.18.5.5
		priAclIPv4Ctl OBJECT-TYPE
			SYNTAX INTEGER
				{
				disable(0),
				enable(1)
				}
			MAX-ACCESS read-write
			STATUS current
			DESCRIPTION
				"Description."
			::= { onuPriAcl 5 }

		
--         1.3.6.1.4.1.37950.1.1.5.12.3.1.18.5.6
-- 1.3.6.1.4.1.37950.1.1.5.12.3.1.18.5.6
-- 1.3.6.1.4.1.37950.1.1.5.12.3.1.18.5.6
-- 1.3.6.1.4.1.37950.1.1.5.12.3.1.18.5.6
-- 1.3.6.1.4.1.37950.1.1.5.12.3.1.18.5.6
-- 1.3.6.1.4.1.37950.1.1.5.12.3.1.18.5.6
-- 1.3.6.1.4.1.37950.1.1.5.12.3.1.18.5.6
-- 1.3.6.1.4.1.37950.1.1.5.12.3.1.18.5.6
		-- 1.3.6.1.4.1.37950.1.1.5.12.3.1.18.5.6
		priAclIPv4Addr OBJECT-TYPE
			SYNTAX IpAddress
			MAX-ACCESS read-write
			STATUS current
			DESCRIPTION
				"Description."
			::= { onuPriAcl 6 }

		
--         1.3.6.1.4.1.37950.1.1.5.12.3.1.18.5.7
-- 1.3.6.1.4.1.37950.1.1.5.12.3.1.18.5.7
-- 1.3.6.1.4.1.37950.1.1.5.12.3.1.18.5.7
-- 1.3.6.1.4.1.37950.1.1.5.12.3.1.18.5.7
-- 1.3.6.1.4.1.37950.1.1.5.12.3.1.18.5.7
-- 1.3.6.1.4.1.37950.1.1.5.12.3.1.18.5.7
-- 1.3.6.1.4.1.37950.1.1.5.12.3.1.18.5.7
-- 1.3.6.1.4.1.37950.1.1.5.12.3.1.18.5.7
		-- 1.3.6.1.4.1.37950.1.1.5.12.3.1.18.5.7
		priAclIPv4Mask OBJECT-TYPE
			SYNTAX OCTET STRING
			MAX-ACCESS read-write
			STATUS current
			DESCRIPTION
				"Description."
			::= { onuPriAcl 7 }

		
--         1.3.6.1.4.1.37950.1.1.5.12.3.1.18.5.8
-- 1.3.6.1.4.1.37950.1.1.5.12.3.1.18.5.8
-- 1.3.6.1.4.1.37950.1.1.5.12.3.1.18.5.8
-- 1.3.6.1.4.1.37950.1.1.5.12.3.1.18.5.8
-- 1.3.6.1.4.1.37950.1.1.5.12.3.1.18.5.8
-- 1.3.6.1.4.1.37950.1.1.5.12.3.1.18.5.8
-- 1.3.6.1.4.1.37950.1.1.5.12.3.1.18.5.8
-- 1.3.6.1.4.1.37950.1.1.5.12.3.1.18.5.8
		-- 1.3.6.1.4.1.37950.1.1.5.12.3.1.18.5.8
		priAclIPv6Ctl OBJECT-TYPE
			SYNTAX INTEGER
				{
				disable(0),
				enable(1)
				}
			MAX-ACCESS read-write
			STATUS current
			DESCRIPTION
				"Description."
			::= { onuPriAcl 8 }

		
--         1.3.6.1.4.1.37950.1.1.5.12.3.1.18.5.9
-- 1.3.6.1.4.1.37950.1.1.5.12.3.1.18.5.9
-- 1.3.6.1.4.1.37950.1.1.5.12.3.1.18.5.9
-- 1.3.6.1.4.1.37950.1.1.5.12.3.1.18.5.9
-- 1.3.6.1.4.1.37950.1.1.5.12.3.1.18.5.9
-- 1.3.6.1.4.1.37950.1.1.5.12.3.1.18.5.9
-- 1.3.6.1.4.1.37950.1.1.5.12.3.1.18.5.9
-- 1.3.6.1.4.1.37950.1.1.5.12.3.1.18.5.9
		-- 1.3.6.1.4.1.37950.1.1.5.12.3.1.18.5.9
		priAclIPv6Addr OBJECT-TYPE
			SYNTAX OCTET STRING
			MAX-ACCESS read-write
			STATUS current
			DESCRIPTION
				"Description."
			::= { onuPriAcl 9 }

		
--         1.3.6.1.4.1.37950.1.1.5.12.3.1.18.5.10
-- 1.3.6.1.4.1.37950.1.1.5.12.3.1.18.5.10
-- 1.3.6.1.4.1.37950.1.1.5.12.3.1.18.5.10
-- 1.3.6.1.4.1.37950.1.1.5.12.3.1.18.5.10
-- 1.3.6.1.4.1.37950.1.1.5.12.3.1.18.5.10
-- 1.3.6.1.4.1.37950.1.1.5.12.3.1.18.5.10
-- 1.3.6.1.4.1.37950.1.1.5.12.3.1.18.5.10
-- 1.3.6.1.4.1.37950.1.1.5.12.3.1.18.5.10
		-- 1.3.6.1.4.1.37950.1.1.5.12.3.1.18.5.10
		priAclIPv6Pfx OBJECT-TYPE
			SYNTAX Unsigned32
			MAX-ACCESS read-write
			STATUS current
			DESCRIPTION
				"Description."
			::= { onuPriAcl 10 }

		
--         1.3.6.1.4.1.37950.1.1.5.12.3.1.18.5.11
-- 1.3.6.1.4.1.37950.1.1.5.12.3.1.18.5.11
-- 1.3.6.1.4.1.37950.1.1.5.12.3.1.18.5.11
-- 1.3.6.1.4.1.37950.1.1.5.12.3.1.18.5.11
-- 1.3.6.1.4.1.37950.1.1.5.12.3.1.18.5.11
-- 1.3.6.1.4.1.37950.1.1.5.12.3.1.18.5.11
-- 1.3.6.1.4.1.37950.1.1.5.12.3.1.18.5.11
-- 1.3.6.1.4.1.37950.1.1.5.12.3.1.18.5.11
		-- 1.3.6.1.4.1.37950.1.1.5.12.3.1.18.5.11
		priAclPortID OBJECT-TYPE
			SYNTAX Unsigned32 (1..65535)
			MAX-ACCESS read-write
			STATUS current
			DESCRIPTION
				"Description."
			::= { onuPriAcl 11 }

		
--         1.3.6.1.4.1.37950.1.1.5.12.3.1.18.5.12
-- 1.3.6.1.4.1.37950.1.1.5.12.3.1.18.5.12
-- 1.3.6.1.4.1.37950.1.1.5.12.3.1.18.5.12
-- 1.3.6.1.4.1.37950.1.1.5.12.3.1.18.5.12
-- 1.3.6.1.4.1.37950.1.1.5.12.3.1.18.5.12
-- 1.3.6.1.4.1.37950.1.1.5.12.3.1.18.5.12
-- 1.3.6.1.4.1.37950.1.1.5.12.3.1.18.5.12
-- 1.3.6.1.4.1.37950.1.1.5.12.3.1.18.5.12
		-- 1.3.6.1.4.1.37950.1.1.5.12.3.1.18.5.12
		priAclAction OBJECT-TYPE
			SYNTAX INTEGER
				{
				del(0),
				add(1)
				}
			MAX-ACCESS read-write
			STATUS current
			DESCRIPTION
				"Description."
			::= { onuPriAcl 12 }

		
--         1.3.6.1.4.1.37950.1.1.5.12.3.1.18.6
-- 1.3.6.1.4.1.37950.1.1.5.12.3.1.18.6
-- 1.3.6.1.4.1.37950.1.1.5.12.3.1.18.6
-- 1.3.6.1.4.1.37950.1.1.5.12.3.1.18.6
-- 1.3.6.1.4.1.37950.1.1.5.12.3.1.18.6
-- 1.3.6.1.4.1.37950.1.1.5.12.3.1.18.6
-- 1.3.6.1.4.1.37950.1.1.5.12.3.1.18.6
-- 1.3.6.1.4.1.37950.1.1.5.12.3.1.18.6
		-- 1.3.6.1.4.1.37950.1.1.5.12.3.1.18.6
		onuPriAclCommit OBJECT IDENTIFIER ::= { onuPriSecurity 6 }

		
--         1.3.6.1.4.1.37950.1.1.5.12.3.1.18.6.1
-- 1.3.6.1.4.1.37950.1.1.5.12.3.1.18.6.1
-- 1.3.6.1.4.1.37950.1.1.5.12.3.1.18.6.1
-- 1.3.6.1.4.1.37950.1.1.5.12.3.1.18.6.1
-- 1.3.6.1.4.1.37950.1.1.5.12.3.1.18.6.1
-- 1.3.6.1.4.1.37950.1.1.5.12.3.1.18.6.1
-- 1.3.6.1.4.1.37950.1.1.5.12.3.1.18.6.1
-- 1.3.6.1.4.1.37950.1.1.5.12.3.1.18.6.1
		-- 1.3.6.1.4.1.37950.1.1.5.12.3.1.18.6.1
		priAclCommit OBJECT-TYPE
			SYNTAX INTEGER { enable(1) }
			MAX-ACCESS read-write
			STATUS current
			DESCRIPTION
				"Description."
			::= { onuPriAclCommit 1 }

		
--         1.3.6.1.4.1.37950.1.1.5.12.3.1.19
-- 1.3.6.1.4.1.37950.1.1.5.12.3.1.19
-- 1.3.6.1.4.1.37950.1.1.5.12.3.1.19
-- 1.3.6.1.4.1.37950.1.1.5.12.3.1.19
-- 1.3.6.1.4.1.37950.1.1.5.12.3.1.19
-- 1.3.6.1.4.1.37950.1.1.5.12.3.1.19
-- 1.3.6.1.4.1.37950.1.1.5.12.3.1.19
-- 1.3.6.1.4.1.37950.1.1.5.12.3.1.19
		-- 1.3.6.1.4.1.37950.1.1.5.12.3.1.19
		onuPriDhcpv6Server OBJECT IDENTIFIER ::= { onuPriGlobalCfg 19 }

		
--         1.3.6.1.4.1.37950.1.1.5.12.3.1.19.1
-- 1.3.6.1.4.1.37950.1.1.5.12.3.1.19.1
-- 1.3.6.1.4.1.37950.1.1.5.12.3.1.19.1
-- 1.3.6.1.4.1.37950.1.1.5.12.3.1.19.1
-- 1.3.6.1.4.1.37950.1.1.5.12.3.1.19.1
-- 1.3.6.1.4.1.37950.1.1.5.12.3.1.19.1
-- 1.3.6.1.4.1.37950.1.1.5.12.3.1.19.1
-- 1.3.6.1.4.1.37950.1.1.5.12.3.1.19.1
		-- 1.3.6.1.4.1.37950.1.1.5.12.3.1.19.1
		onuPriDhcpv6ServerPon OBJECT-TYPE
			SYNTAX Integer32 (1..16)
			MAX-ACCESS read-write
			STATUS current
			DESCRIPTION
				"Description."
			::= { onuPriDhcpv6Server 1 }

		
--         1.3.6.1.4.1.37950.1.1.5.12.3.1.19.2
-- 1.3.6.1.4.1.37950.1.1.5.12.3.1.19.2
-- 1.3.6.1.4.1.37950.1.1.5.12.3.1.19.2
-- 1.3.6.1.4.1.37950.1.1.5.12.3.1.19.2
-- 1.3.6.1.4.1.37950.1.1.5.12.3.1.19.2
-- 1.3.6.1.4.1.37950.1.1.5.12.3.1.19.2
-- 1.3.6.1.4.1.37950.1.1.5.12.3.1.19.2
-- 1.3.6.1.4.1.37950.1.1.5.12.3.1.19.2
		-- 1.3.6.1.4.1.37950.1.1.5.12.3.1.19.2
		onuPriDhcpv6ServerOnu OBJECT-TYPE
			SYNTAX Integer32 (1..65535)
			MAX-ACCESS read-write
			STATUS current
			DESCRIPTION
				"Description."
			::= { onuPriDhcpv6Server 2 }

		
--         1.3.6.1.4.1.37950.1.1.5.12.3.1.19.3
-- 1.3.6.1.4.1.37950.1.1.5.12.3.1.19.3
-- 1.3.6.1.4.1.37950.1.1.5.12.3.1.19.3
-- 1.3.6.1.4.1.37950.1.1.5.12.3.1.19.3
-- 1.3.6.1.4.1.37950.1.1.5.12.3.1.19.3
-- 1.3.6.1.4.1.37950.1.1.5.12.3.1.19.3
-- 1.3.6.1.4.1.37950.1.1.5.12.3.1.19.3
-- 1.3.6.1.4.1.37950.1.1.5.12.3.1.19.3
		-- 1.3.6.1.4.1.37950.1.1.5.12.3.1.19.3
		onuPriDhcpv6LanIp OBJECT-TYPE
			SYNTAX OCTET STRING
			MAX-ACCESS read-write
			STATUS current
			DESCRIPTION
				"Description."
			::= { onuPriDhcpv6Server 3 }

		
--         1.3.6.1.4.1.37950.1.1.5.12.3.1.19.4
-- 1.3.6.1.4.1.37950.1.1.5.12.3.1.19.4
-- 1.3.6.1.4.1.37950.1.1.5.12.3.1.19.4
-- 1.3.6.1.4.1.37950.1.1.5.12.3.1.19.4
-- 1.3.6.1.4.1.37950.1.1.5.12.3.1.19.4
-- 1.3.6.1.4.1.37950.1.1.5.12.3.1.19.4
-- 1.3.6.1.4.1.37950.1.1.5.12.3.1.19.4
-- 1.3.6.1.4.1.37950.1.1.5.12.3.1.19.4
		-- 1.3.6.1.4.1.37950.1.1.5.12.3.1.19.4
		onuPriDhcpv6LanPrefixlen OBJECT-TYPE
			SYNTAX INTEGER (0..128)
			MAX-ACCESS read-write
			STATUS current
			DESCRIPTION
				"Description."
			::= { onuPriDhcpv6Server 4 }

		
--         1.3.6.1.4.1.37950.1.1.5.12.3.1.19.5
-- 1.3.6.1.4.1.37950.1.1.5.12.3.1.19.5
-- 1.3.6.1.4.1.37950.1.1.5.12.3.1.19.5
-- 1.3.6.1.4.1.37950.1.1.5.12.3.1.19.5
-- 1.3.6.1.4.1.37950.1.1.5.12.3.1.19.5
-- 1.3.6.1.4.1.37950.1.1.5.12.3.1.19.5
-- 1.3.6.1.4.1.37950.1.1.5.12.3.1.19.5
-- 1.3.6.1.4.1.37950.1.1.5.12.3.1.19.5
		-- 1.3.6.1.4.1.37950.1.1.5.12.3.1.19.5
		onuPriDhcpv6PrefixMode OBJECT-TYPE
			SYNTAX INTEGER
				{
				disable(0),
				static(1)
				}
			MAX-ACCESS read-write
			STATUS current
			DESCRIPTION
				"Description."
			::= { onuPriDhcpv6Server 5 }

		
--         1.3.6.1.4.1.37950.1.1.5.12.3.1.19.6
-- 1.3.6.1.4.1.37950.1.1.5.12.3.1.19.6
-- 1.3.6.1.4.1.37950.1.1.5.12.3.1.19.6
-- 1.3.6.1.4.1.37950.1.1.5.12.3.1.19.6
-- 1.3.6.1.4.1.37950.1.1.5.12.3.1.19.6
-- 1.3.6.1.4.1.37950.1.1.5.12.3.1.19.6
-- 1.3.6.1.4.1.37950.1.1.5.12.3.1.19.6
-- 1.3.6.1.4.1.37950.1.1.5.12.3.1.19.6
		-- 1.3.6.1.4.1.37950.1.1.5.12.3.1.19.6
		onuPriDhcpv6PrefixModeIp OBJECT-TYPE
			SYNTAX OCTET STRING
			MAX-ACCESS read-write
			STATUS current
			DESCRIPTION
				"Description."
			::= { onuPriDhcpv6Server 6 }

		
--         1.3.6.1.4.1.37950.1.1.5.12.3.1.19.7
-- 1.3.6.1.4.1.37950.1.1.5.12.3.1.19.7
-- 1.3.6.1.4.1.37950.1.1.5.12.3.1.19.7
-- 1.3.6.1.4.1.37950.1.1.5.12.3.1.19.7
-- 1.3.6.1.4.1.37950.1.1.5.12.3.1.19.7
-- 1.3.6.1.4.1.37950.1.1.5.12.3.1.19.7
-- 1.3.6.1.4.1.37950.1.1.5.12.3.1.19.7
-- 1.3.6.1.4.1.37950.1.1.5.12.3.1.19.7
		-- 1.3.6.1.4.1.37950.1.1.5.12.3.1.19.7
		onuPriDhcpv6Enable OBJECT-TYPE
			SYNTAX INTEGER
				{
				disable(0),
				enable(1),
				relay(2)
				}
			MAX-ACCESS read-write
			STATUS current
			DESCRIPTION
				"Description."
			::= { onuPriDhcpv6Server 7 }

		
--         1.3.6.1.4.1.37950.1.1.5.12.3.1.19.8
-- 1.3.6.1.4.1.37950.1.1.5.12.3.1.19.8
-- 1.3.6.1.4.1.37950.1.1.5.12.3.1.19.8
-- 1.3.6.1.4.1.37950.1.1.5.12.3.1.19.8
-- 1.3.6.1.4.1.37950.1.1.5.12.3.1.19.8
-- 1.3.6.1.4.1.37950.1.1.5.12.3.1.19.8
-- 1.3.6.1.4.1.37950.1.1.5.12.3.1.19.8
-- 1.3.6.1.4.1.37950.1.1.5.12.3.1.19.8
		-- 1.3.6.1.4.1.37950.1.1.5.12.3.1.19.8
		onuPriDhcpv6Preference OBJECT-TYPE
			SYNTAX Unsigned32 (0..4294967295)
			MAX-ACCESS read-write
			STATUS current
			DESCRIPTION
				"Description."
			::= { onuPriDhcpv6Server 8 }

		
--         1.3.6.1.4.1.37950.1.1.5.12.3.1.19.9
-- 1.3.6.1.4.1.37950.1.1.5.12.3.1.19.9
-- 1.3.6.1.4.1.37950.1.1.5.12.3.1.19.9
-- 1.3.6.1.4.1.37950.1.1.5.12.3.1.19.9
-- 1.3.6.1.4.1.37950.1.1.5.12.3.1.19.9
-- 1.3.6.1.4.1.37950.1.1.5.12.3.1.19.9
-- 1.3.6.1.4.1.37950.1.1.5.12.3.1.19.9
-- 1.3.6.1.4.1.37950.1.1.5.12.3.1.19.9
		-- 1.3.6.1.4.1.37950.1.1.5.12.3.1.19.9
		onuPriDhcpv6BeginIp OBJECT-TYPE
			SYNTAX OCTET STRING
			MAX-ACCESS read-write
			STATUS current
			DESCRIPTION
				"Description."
			::= { onuPriDhcpv6Server 9 }

		
--         1.3.6.1.4.1.37950.1.1.5.12.3.1.19.10
-- 1.3.6.1.4.1.37950.1.1.5.12.3.1.19.10
-- 1.3.6.1.4.1.37950.1.1.5.12.3.1.19.10
-- 1.3.6.1.4.1.37950.1.1.5.12.3.1.19.10
-- 1.3.6.1.4.1.37950.1.1.5.12.3.1.19.10
-- 1.3.6.1.4.1.37950.1.1.5.12.3.1.19.10
-- 1.3.6.1.4.1.37950.1.1.5.12.3.1.19.10
-- 1.3.6.1.4.1.37950.1.1.5.12.3.1.19.10
		-- 1.3.6.1.4.1.37950.1.1.5.12.3.1.19.10
		onuPriDhcpv6EndIp OBJECT-TYPE
			SYNTAX OCTET STRING
			MAX-ACCESS read-write
			STATUS current
			DESCRIPTION
				"Description."
			::= { onuPriDhcpv6Server 10 }

		
--         1.3.6.1.4.1.37950.1.1.5.12.3.1.19.11
-- 1.3.6.1.4.1.37950.1.1.5.12.3.1.19.11
-- 1.3.6.1.4.1.37950.1.1.5.12.3.1.19.11
-- 1.3.6.1.4.1.37950.1.1.5.12.3.1.19.11
-- 1.3.6.1.4.1.37950.1.1.5.12.3.1.19.11
-- 1.3.6.1.4.1.37950.1.1.5.12.3.1.19.11
-- 1.3.6.1.4.1.37950.1.1.5.12.3.1.19.11
-- 1.3.6.1.4.1.37950.1.1.5.12.3.1.19.11
		-- 1.3.6.1.4.1.37950.1.1.5.12.3.1.19.11
		onuPriDhcpv6PoolType OBJECT-TYPE
			SYNTAX INTEGER
				{
				pc(0),
				camera(1),
				stb(2),
				ip-phone(3)
				}
			MAX-ACCESS read-write
			STATUS current
			DESCRIPTION
				"Description."
			::= { onuPriDhcpv6Server 11 }

		
--         1.3.6.1.4.1.37950.1.1.5.12.3.1.19.12
-- 1.3.6.1.4.1.37950.1.1.5.12.3.1.19.12
-- 1.3.6.1.4.1.37950.1.1.5.12.3.1.19.12
-- 1.3.6.1.4.1.37950.1.1.5.12.3.1.19.12
-- 1.3.6.1.4.1.37950.1.1.5.12.3.1.19.12
-- 1.3.6.1.4.1.37950.1.1.5.12.3.1.19.12
-- 1.3.6.1.4.1.37950.1.1.5.12.3.1.19.12
-- 1.3.6.1.4.1.37950.1.1.5.12.3.1.19.12
		-- 1.3.6.1.4.1.37950.1.1.5.12.3.1.19.12
		onuPriDhcpv6MasterDns OBJECT-TYPE
			SYNTAX OCTET STRING
			MAX-ACCESS read-write
			STATUS current
			DESCRIPTION
				"Description."
			::= { onuPriDhcpv6Server 12 }

		
--         1.3.6.1.4.1.37950.1.1.5.12.3.1.19.13
-- 1.3.6.1.4.1.37950.1.1.5.12.3.1.19.13
-- 1.3.6.1.4.1.37950.1.1.5.12.3.1.19.13
-- 1.3.6.1.4.1.37950.1.1.5.12.3.1.19.13
-- 1.3.6.1.4.1.37950.1.1.5.12.3.1.19.13
-- 1.3.6.1.4.1.37950.1.1.5.12.3.1.19.13
-- 1.3.6.1.4.1.37950.1.1.5.12.3.1.19.13
-- 1.3.6.1.4.1.37950.1.1.5.12.3.1.19.13
		-- 1.3.6.1.4.1.37950.1.1.5.12.3.1.19.13
		onuPriDhcpv6SlaveDns OBJECT-TYPE
			SYNTAX OCTET STRING
			MAX-ACCESS read-write
			STATUS current
			DESCRIPTION
				"Description."
			::= { onuPriDhcpv6Server 13 }

		
--         1.3.6.1.4.1.37950.1.1.5.12.3.1.19.14
-- 1.3.6.1.4.1.37950.1.1.5.12.3.1.19.14
-- 1.3.6.1.4.1.37950.1.1.5.12.3.1.19.14
-- 1.3.6.1.4.1.37950.1.1.5.12.3.1.19.14
-- 1.3.6.1.4.1.37950.1.1.5.12.3.1.19.14
-- 1.3.6.1.4.1.37950.1.1.5.12.3.1.19.14
-- 1.3.6.1.4.1.37950.1.1.5.12.3.1.19.14
-- 1.3.6.1.4.1.37950.1.1.5.12.3.1.19.14
		-- 1.3.6.1.4.1.37950.1.1.5.12.3.1.19.14
		onuPriDhcpv6Gateway OBJECT-TYPE
			SYNTAX OCTET STRING
			MAX-ACCESS read-write
			STATUS current
			DESCRIPTION
				"Description."
			::= { onuPriDhcpv6Server 14 }

		
--         1.3.6.1.4.1.37950.1.1.5.12.3.1.19.15
-- 1.3.6.1.4.1.37950.1.1.5.12.3.1.19.15
-- 1.3.6.1.4.1.37950.1.1.5.12.3.1.19.15
-- 1.3.6.1.4.1.37950.1.1.5.12.3.1.19.15
-- 1.3.6.1.4.1.37950.1.1.5.12.3.1.19.15
-- 1.3.6.1.4.1.37950.1.1.5.12.3.1.19.15
-- 1.3.6.1.4.1.37950.1.1.5.12.3.1.19.15
-- 1.3.6.1.4.1.37950.1.1.5.12.3.1.19.15
		-- 1.3.6.1.4.1.37950.1.1.5.12.3.1.19.15
		onuPriDhcpv6RelayIp OBJECT-TYPE
			SYNTAX OCTET STRING
			MAX-ACCESS read-write
			STATUS current
			DESCRIPTION
				"Description."
			::= { onuPriDhcpv6Server 15 }

		
--         1.3.6.1.4.1.37950.1.1.5.12.3.1.19.16
-- 1.3.6.1.4.1.37950.1.1.5.12.3.1.19.16
-- 1.3.6.1.4.1.37950.1.1.5.12.3.1.19.16
-- 1.3.6.1.4.1.37950.1.1.5.12.3.1.19.16
-- 1.3.6.1.4.1.37950.1.1.5.12.3.1.19.16
-- 1.3.6.1.4.1.37950.1.1.5.12.3.1.19.16
-- 1.3.6.1.4.1.37950.1.1.5.12.3.1.19.16
-- 1.3.6.1.4.1.37950.1.1.5.12.3.1.19.16
		-- 1.3.6.1.4.1.37950.1.1.5.12.3.1.19.16
		onuPriDhcpv6RA OBJECT-TYPE
			SYNTAX INTEGER
				{
				disable(0),
				enable(1)
				}
			MAX-ACCESS read-write
			STATUS current
			DESCRIPTION
				"Description."
			::= { onuPriDhcpv6Server 16 }

		
--         1.3.6.1.4.1.37950.1.1.5.12.3.1.19.17
-- 1.3.6.1.4.1.37950.1.1.5.12.3.1.19.17
-- 1.3.6.1.4.1.37950.1.1.5.12.3.1.19.17
-- 1.3.6.1.4.1.37950.1.1.5.12.3.1.19.17
-- 1.3.6.1.4.1.37950.1.1.5.12.3.1.19.17
-- 1.3.6.1.4.1.37950.1.1.5.12.3.1.19.17
-- 1.3.6.1.4.1.37950.1.1.5.12.3.1.19.17
-- 1.3.6.1.4.1.37950.1.1.5.12.3.1.19.17
		-- 1.3.6.1.4.1.37950.1.1.5.12.3.1.19.17
		onuPriDhcpv6RAManage OBJECT-TYPE
			SYNTAX INTEGER
				{
				disable(0),
				enable(1)
				}
			MAX-ACCESS read-write
			STATUS current
			DESCRIPTION
				"Description."
			::= { onuPriDhcpv6Server 17 }

		
--         1.3.6.1.4.1.37950.1.1.5.12.3.1.19.18
-- 1.3.6.1.4.1.37950.1.1.5.12.3.1.19.18
-- 1.3.6.1.4.1.37950.1.1.5.12.3.1.19.18
-- 1.3.6.1.4.1.37950.1.1.5.12.3.1.19.18
-- 1.3.6.1.4.1.37950.1.1.5.12.3.1.19.18
-- 1.3.6.1.4.1.37950.1.1.5.12.3.1.19.18
-- 1.3.6.1.4.1.37950.1.1.5.12.3.1.19.18
-- 1.3.6.1.4.1.37950.1.1.5.12.3.1.19.18
		-- 1.3.6.1.4.1.37950.1.1.5.12.3.1.19.18
		onuPriDhcpv6RAOther OBJECT-TYPE
			SYNTAX INTEGER
				{
				disable(0),
				enable(1)
				}
			MAX-ACCESS read-write
			STATUS current
			DESCRIPTION
				"Description."
			::= { onuPriDhcpv6Server 18 }

		
--         1.3.6.1.4.1.37950.1.1.5.12.3.1.19.19
-- 1.3.6.1.4.1.37950.1.1.5.12.3.1.19.19
-- 1.3.6.1.4.1.37950.1.1.5.12.3.1.19.19
-- 1.3.6.1.4.1.37950.1.1.5.12.3.1.19.19
-- 1.3.6.1.4.1.37950.1.1.5.12.3.1.19.19
-- 1.3.6.1.4.1.37950.1.1.5.12.3.1.19.19
-- 1.3.6.1.4.1.37950.1.1.5.12.3.1.19.19
-- 1.3.6.1.4.1.37950.1.1.5.12.3.1.19.19
		-- 1.3.6.1.4.1.37950.1.1.5.12.3.1.19.19
		onuPriDhcpv6RAMaxInterval OBJECT-TYPE
			SYNTAX Integer32 (1..1800)
			MAX-ACCESS read-write
			STATUS current
			DESCRIPTION
				"Description."
			::= { onuPriDhcpv6Server 19 }

		
--         1.3.6.1.4.1.37950.1.1.5.12.3.1.19.20
-- 1.3.6.1.4.1.37950.1.1.5.12.3.1.19.20
-- 1.3.6.1.4.1.37950.1.1.5.12.3.1.19.20
-- 1.3.6.1.4.1.37950.1.1.5.12.3.1.19.20
-- 1.3.6.1.4.1.37950.1.1.5.12.3.1.19.20
-- 1.3.6.1.4.1.37950.1.1.5.12.3.1.19.20
-- 1.3.6.1.4.1.37950.1.1.5.12.3.1.19.20
-- 1.3.6.1.4.1.37950.1.1.5.12.3.1.19.20
		-- 1.3.6.1.4.1.37950.1.1.5.12.3.1.19.20
		onuPriDhcpv6RAMinInterval OBJECT-TYPE
			SYNTAX Integer32 (1..1800)
			MAX-ACCESS read-write
			STATUS current
			DESCRIPTION
				"Description."
			::= { onuPriDhcpv6Server 20 }

		
--         1.3.6.1.4.1.37950.1.1.5.12.3.1.19.21
-- 1.3.6.1.4.1.37950.1.1.5.12.3.1.19.21
-- 1.3.6.1.4.1.37950.1.1.5.12.3.1.19.21
-- 1.3.6.1.4.1.37950.1.1.5.12.3.1.19.21
-- 1.3.6.1.4.1.37950.1.1.5.12.3.1.19.21
-- 1.3.6.1.4.1.37950.1.1.5.12.3.1.19.21
-- 1.3.6.1.4.1.37950.1.1.5.12.3.1.19.21
-- 1.3.6.1.4.1.37950.1.1.5.12.3.1.19.21
		-- 1.3.6.1.4.1.37950.1.1.5.12.3.1.19.21
		onuPriDhcpv6Action OBJECT-TYPE
			SYNTAX INTEGER
				{
				commit(1),
				remove(2)
				}
			MAX-ACCESS read-write
			STATUS current
			DESCRIPTION
				"Description."
			::= { onuPriDhcpv6Server 21 }

		
--         1.3.6.1.4.1.37950.1.1.5.12.3.1.19.22
-- 1.3.6.1.4.1.37950.1.1.5.12.3.1.19.22
-- 1.3.6.1.4.1.37950.1.1.5.12.3.1.19.22
-- 1.3.6.1.4.1.37950.1.1.5.12.3.1.19.22
-- 1.3.6.1.4.1.37950.1.1.5.12.3.1.19.22
-- 1.3.6.1.4.1.37950.1.1.5.12.3.1.19.22
-- 1.3.6.1.4.1.37950.1.1.5.12.3.1.19.22
-- 1.3.6.1.4.1.37950.1.1.5.12.3.1.19.22
		-- 1.3.6.1.4.1.37950.1.1.5.12.3.1.19.22
		onuPriDhcpv6Valid OBJECT-TYPE
			SYNTAX Unsigned32 (0..4294967295)
			MAX-ACCESS read-write
			STATUS current
			DESCRIPTION
				"Description."
			::= { onuPriDhcpv6Server 22 }

		
--         1.3.6.1.4.1.37950.1.1.5.12.3.1.19.23
-- 1.3.6.1.4.1.37950.1.1.5.12.3.1.19.23
-- 1.3.6.1.4.1.37950.1.1.5.12.3.1.19.23
-- 1.3.6.1.4.1.37950.1.1.5.12.3.1.19.23
-- 1.3.6.1.4.1.37950.1.1.5.12.3.1.19.23
-- 1.3.6.1.4.1.37950.1.1.5.12.3.1.19.23
-- 1.3.6.1.4.1.37950.1.1.5.12.3.1.19.23
-- 1.3.6.1.4.1.37950.1.1.5.12.3.1.19.23
		-- 1.3.6.1.4.1.37950.1.1.5.12.3.1.19.23
		onuPriDhcpv6DnsMode OBJECT-TYPE
			SYNTAX INTEGER
				{
				wanconnection(0),
				static(1),
				hgwproxy(2)
				}
			MAX-ACCESS read-write
			STATUS current
			DESCRIPTION
				"Description."
			::= { onuPriDhcpv6Server 23 }

		
--         1.3.6.1.4.1.37950.1.1.5.12.3.1.20
-- 1.3.6.1.4.1.37950.1.1.5.12.3.1.20
-- 1.3.6.1.4.1.37950.1.1.5.12.3.1.20
-- 1.3.6.1.4.1.37950.1.1.5.12.3.1.20
-- 1.3.6.1.4.1.37950.1.1.5.12.3.1.20
-- 1.3.6.1.4.1.37950.1.1.5.12.3.1.20
-- 1.3.6.1.4.1.37950.1.1.5.12.3.1.20
-- 1.3.6.1.4.1.37950.1.1.5.12.3.1.20
		-- 1.3.6.1.4.1.37950.1.1.5.12.3.1.20
		onuPriWifiSwitch1 OBJECT IDENTIFIER ::= { onuPriGlobalCfg 20 }

		
--         1.3.6.1.4.1.37950.1.1.5.12.3.1.20.1
-- 1.3.6.1.4.1.37950.1.1.5.12.3.1.20.1
-- 1.3.6.1.4.1.37950.1.1.5.12.3.1.20.1
-- 1.3.6.1.4.1.37950.1.1.5.12.3.1.20.1
-- 1.3.6.1.4.1.37950.1.1.5.12.3.1.20.1
-- 1.3.6.1.4.1.37950.1.1.5.12.3.1.20.1
-- 1.3.6.1.4.1.37950.1.1.5.12.3.1.20.1
-- 1.3.6.1.4.1.37950.1.1.5.12.3.1.20.1
		-- 1.3.6.1.4.1.37950.1.1.5.12.3.1.20.1
		priWifiSwitchPon1 OBJECT-TYPE
			SYNTAX INTEGER (1..16)
			MAX-ACCESS read-write
			STATUS current
			DESCRIPTION
				"Description."
			::= { onuPriWifiSwitch1 1 }

		
--         1.3.6.1.4.1.37950.1.1.5.12.3.1.20.2
-- 1.3.6.1.4.1.37950.1.1.5.12.3.1.20.2
-- 1.3.6.1.4.1.37950.1.1.5.12.3.1.20.2
-- 1.3.6.1.4.1.37950.1.1.5.12.3.1.20.2
-- 1.3.6.1.4.1.37950.1.1.5.12.3.1.20.2
-- 1.3.6.1.4.1.37950.1.1.5.12.3.1.20.2
-- 1.3.6.1.4.1.37950.1.1.5.12.3.1.20.2
-- 1.3.6.1.4.1.37950.1.1.5.12.3.1.20.2
		-- 1.3.6.1.4.1.37950.1.1.5.12.3.1.20.2
		priWifiSwitchOnu1 OBJECT-TYPE
			SYNTAX INTEGER (1..65535)
			MAX-ACCESS read-write
			STATUS current
			DESCRIPTION
				"Description."
			::= { onuPriWifiSwitch1 2 }

		
--         1.3.6.1.4.1.37950.1.1.5.12.3.1.20.3
-- 1.3.6.1.4.1.37950.1.1.5.12.3.1.20.3
-- 1.3.6.1.4.1.37950.1.1.5.12.3.1.20.3
-- 1.3.6.1.4.1.37950.1.1.5.12.3.1.20.3
-- 1.3.6.1.4.1.37950.1.1.5.12.3.1.20.3
-- 1.3.6.1.4.1.37950.1.1.5.12.3.1.20.3
-- 1.3.6.1.4.1.37950.1.1.5.12.3.1.20.3
-- 1.3.6.1.4.1.37950.1.1.5.12.3.1.20.3
		-- 1.3.6.1.4.1.37950.1.1.5.12.3.1.20.3
		priWifiApModule1 OBJECT-TYPE
			SYNTAX INTEGER
				{
				disable(0),
				enable(1)
				}
			MAX-ACCESS read-write
			STATUS current
			DESCRIPTION
				"Description."
			::= { onuPriWifiSwitch1 3 }

		
--         1.3.6.1.4.1.37950.1.1.5.12.3.1.20.4
-- 1.3.6.1.4.1.37950.1.1.5.12.3.1.20.4
-- 1.3.6.1.4.1.37950.1.1.5.12.3.1.20.4
-- 1.3.6.1.4.1.37950.1.1.5.12.3.1.20.4
-- 1.3.6.1.4.1.37950.1.1.5.12.3.1.20.4
-- 1.3.6.1.4.1.37950.1.1.5.12.3.1.20.4
-- 1.3.6.1.4.1.37950.1.1.5.12.3.1.20.4
-- 1.3.6.1.4.1.37950.1.1.5.12.3.1.20.4
		-- 1.3.6.1.4.1.37950.1.1.5.12.3.1.20.4
		priWifiContry1 OBJECT-TYPE
			SYNTAX INTEGER
				{
				etsi(0),
				fcc(1),
				ic(2),
				spain(3),
				france(4),
				mkk(5),
				isreal(6),
				mkk2(7),
				mkk3(8),
				russian(9),
				cn(10),
				global(11),
				world-wide(12),
				mkk1(13),
				ncc(14)
				}
			MAX-ACCESS read-write
			STATUS current
			DESCRIPTION
				"Description."
			::= { onuPriWifiSwitch1 4 }

		
--         1.3.6.1.4.1.37950.1.1.5.12.3.1.20.5
-- 1.3.6.1.4.1.37950.1.1.5.12.3.1.20.5
-- 1.3.6.1.4.1.37950.1.1.5.12.3.1.20.5
-- 1.3.6.1.4.1.37950.1.1.5.12.3.1.20.5
-- 1.3.6.1.4.1.37950.1.1.5.12.3.1.20.5
-- 1.3.6.1.4.1.37950.1.1.5.12.3.1.20.5
-- 1.3.6.1.4.1.37950.1.1.5.12.3.1.20.5
-- 1.3.6.1.4.1.37950.1.1.5.12.3.1.20.5
		-- 1.3.6.1.4.1.37950.1.1.5.12.3.1.20.5
		priWifiChannel1 OBJECT-TYPE
			SYNTAX INTEGER (0..13)
			MAX-ACCESS read-write
			STATUS current
			DESCRIPTION
				"Description."
			::= { onuPriWifiSwitch1 5 }

		
--         1.3.6.1.4.1.37950.1.1.5.12.3.1.20.6
-- 1.3.6.1.4.1.37950.1.1.5.12.3.1.20.6
-- 1.3.6.1.4.1.37950.1.1.5.12.3.1.20.6
-- 1.3.6.1.4.1.37950.1.1.5.12.3.1.20.6
-- 1.3.6.1.4.1.37950.1.1.5.12.3.1.20.6
-- 1.3.6.1.4.1.37950.1.1.5.12.3.1.20.6
-- 1.3.6.1.4.1.37950.1.1.5.12.3.1.20.6
-- 1.3.6.1.4.1.37950.1.1.5.12.3.1.20.6
		-- 1.3.6.1.4.1.37950.1.1.5.12.3.1.20.6
		priWifiStandard1 OBJECT-TYPE
			SYNTAX INTEGER
				{
				s80211b(0),
				s80211g(1),
				s80211bg(2),
				s80211n(3),
				s80211bgn(4),
				s80211ac(5),
				s80211a(6),
				s80211an(7),
				s80211nac(8),
				s80211anac(9),
				s80211aan(10),
				s80211ax(11),
				s80211anacax(12)
				}
			MAX-ACCESS read-write
			STATUS current
			DESCRIPTION
				"Description."
			::= { onuPriWifiSwitch1 6 }

		
--         1.3.6.1.4.1.37950.1.1.5.12.3.1.20.7
-- 1.3.6.1.4.1.37950.1.1.5.12.3.1.20.7
-- 1.3.6.1.4.1.37950.1.1.5.12.3.1.20.7
-- 1.3.6.1.4.1.37950.1.1.5.12.3.1.20.7
-- 1.3.6.1.4.1.37950.1.1.5.12.3.1.20.7
-- 1.3.6.1.4.1.37950.1.1.5.12.3.1.20.7
-- 1.3.6.1.4.1.37950.1.1.5.12.3.1.20.7
-- 1.3.6.1.4.1.37950.1.1.5.12.3.1.20.7
		-- 1.3.6.1.4.1.37950.1.1.5.12.3.1.20.7
		priWifiPower1 OBJECT-TYPE
			SYNTAX INTEGER (0..20)
			MAX-ACCESS read-write
			STATUS current
			DESCRIPTION
				"Description."
			::= { onuPriWifiSwitch1 7 }

		
--         1.3.6.1.4.1.37950.1.1.5.12.3.1.20.8
-- 1.3.6.1.4.1.37950.1.1.5.12.3.1.20.8
-- 1.3.6.1.4.1.37950.1.1.5.12.3.1.20.8
-- 1.3.6.1.4.1.37950.1.1.5.12.3.1.20.8
-- 1.3.6.1.4.1.37950.1.1.5.12.3.1.20.8
-- 1.3.6.1.4.1.37950.1.1.5.12.3.1.20.8
-- 1.3.6.1.4.1.37950.1.1.5.12.3.1.20.8
-- 1.3.6.1.4.1.37950.1.1.5.12.3.1.20.8
		-- 1.3.6.1.4.1.37950.1.1.5.12.3.1.20.8
		priWifiSwitchAction1 OBJECT-TYPE
			SYNTAX INTEGER
				{
				commit(1),
				remove(2)
				}
			MAX-ACCESS read-write
			STATUS current
			DESCRIPTION
				"Description."
			::= { onuPriWifiSwitch1 8 }

		
--         1.3.6.1.4.1.37950.1.1.5.12.3.1.20.9
-- 1.3.6.1.4.1.37950.1.1.5.12.3.1.20.9
-- 1.3.6.1.4.1.37950.1.1.5.12.3.1.20.9
-- 1.3.6.1.4.1.37950.1.1.5.12.3.1.20.9
-- 1.3.6.1.4.1.37950.1.1.5.12.3.1.20.9
-- 1.3.6.1.4.1.37950.1.1.5.12.3.1.20.9
-- 1.3.6.1.4.1.37950.1.1.5.12.3.1.20.9
-- 1.3.6.1.4.1.37950.1.1.5.12.3.1.20.9
		-- 1.3.6.1.4.1.37950.1.1.5.12.3.1.20.9
		priWifiChannelWidth1 OBJECT-TYPE
			SYNTAX INTEGER
				{
				s20(0),
				s40(1),
				s80(2),
				s20-40(3)
				}
			MAX-ACCESS read-write
			STATUS current
			DESCRIPTION
				"Description."
			::= { onuPriWifiSwitch1 9 }

		
--         1.3.6.1.4.1.37950.1.1.5.12.3.1.20.10
-- 1.3.6.1.4.1.37950.1.1.5.12.3.1.20.10
-- 1.3.6.1.4.1.37950.1.1.5.12.3.1.20.10
-- 1.3.6.1.4.1.37950.1.1.5.12.3.1.20.10
-- 1.3.6.1.4.1.37950.1.1.5.12.3.1.20.10
-- 1.3.6.1.4.1.37950.1.1.5.12.3.1.20.10
-- 1.3.6.1.4.1.37950.1.1.5.12.3.1.20.10
-- 1.3.6.1.4.1.37950.1.1.5.12.3.1.20.10
		-- 1.3.6.1.4.1.37950.1.1.5.12.3.1.20.10
		priWifiEasyMeshStatus OBJECT-TYPE
			SYNTAX INTEGER
				{
				disable(0),
				enable(1)
				}
			MAX-ACCESS read-write
			STATUS current
			DESCRIPTION
				"Description."
			::= { onuPriWifiSwitch1 10 }

		
--           1.3.6.1.4.1.37950.1.1.5.12.3.1.6
-- 1.3.6.1.4.1.37950.1.1.5.12.3.1.21
-- 1.3.6.1.4.1.37950.1.1.5.12.3.1.21
-- 1.3.6.1.4.1.37950.1.1.5.12.3.1.21
-- 1.3.6.1.4.1.37950.1.1.5.12.3.1.21
-- 1.3.6.1.4.1.37950.1.1.5.12.3.1.21
-- 1.3.6.1.4.1.37950.1.1.5.12.3.1.21
-- 1.3.6.1.4.1.37950.1.1.5.12.3.1.21
-- 1.3.6.1.4.1.37950.1.1.5.12.3.1.21
		-- 1.3.6.1.4.1.37950.1.1.5.12.3.1.21
		onuPriWanConnV6 OBJECT IDENTIFIER ::= { onuPriGlobalCfg 21 }

		
--           1.3.6.1.4.1.37950.1.1.5.12.3.1.6.1
-- 1.3.6.1.4.1.37950.1.1.5.12.3.1.21.1
-- 1.3.6.1.4.1.37950.1.1.5.12.3.1.21.1
-- 1.3.6.1.4.1.37950.1.1.5.12.3.1.21.1
-- 1.3.6.1.4.1.37950.1.1.5.12.3.1.21.1
-- 1.3.6.1.4.1.37950.1.1.5.12.3.1.21.1
-- 1.3.6.1.4.1.37950.1.1.5.12.3.1.21.1
-- 1.3.6.1.4.1.37950.1.1.5.12.3.1.21.1
-- 1.3.6.1.4.1.37950.1.1.5.12.3.1.21.1
		-- 1.3.6.1.4.1.37950.1.1.5.12.3.1.21.1
		priV6WanConnAdd OBJECT IDENTIFIER ::= { onuPriWanConnV6 1 }

		
--           1.3.6.1.4.1.37950.1.1.5.12.3.1.6.1.1
-- 1.3.6.1.4.1.37950.1.1.5.12.3.1.21.1.1
-- 1.3.6.1.4.1.37950.1.1.5.12.3.1.21.1.1
-- 1.3.6.1.4.1.37950.1.1.5.12.3.1.21.1.1
-- 1.3.6.1.4.1.37950.1.1.5.12.3.1.21.1.1
-- 1.3.6.1.4.1.37950.1.1.5.12.3.1.21.1.1
-- 1.3.6.1.4.1.37950.1.1.5.12.3.1.21.1.1
-- 1.3.6.1.4.1.37950.1.1.5.12.3.1.21.1.1
-- 1.3.6.1.4.1.37950.1.1.5.12.3.1.21.1.1
		-- 1.3.6.1.4.1.37950.1.1.5.12.3.1.21.1.1
		priV6WanAddPon OBJECT-TYPE
			SYNTAX INTEGER (1..16)
			MAX-ACCESS read-write
			STATUS current
			DESCRIPTION
				"Description."
			::= { priV6WanConnAdd 1 }

		
--           1.3.6.1.4.1.37950.1.1.5.12.3.1.6.1.2
-- 1.3.6.1.4.1.37950.1.1.5.12.3.1.21.1.2
-- 1.3.6.1.4.1.37950.1.1.5.12.3.1.21.1.2
-- 1.3.6.1.4.1.37950.1.1.5.12.3.1.21.1.2
-- 1.3.6.1.4.1.37950.1.1.5.12.3.1.21.1.2
-- 1.3.6.1.4.1.37950.1.1.5.12.3.1.21.1.2
-- 1.3.6.1.4.1.37950.1.1.5.12.3.1.21.1.2
-- 1.3.6.1.4.1.37950.1.1.5.12.3.1.21.1.2
-- 1.3.6.1.4.1.37950.1.1.5.12.3.1.21.1.2
		-- 1.3.6.1.4.1.37950.1.1.5.12.3.1.21.1.2
		priV6WanAddOnu OBJECT-TYPE
			SYNTAX INTEGER (1..65535)
			MAX-ACCESS read-write
			STATUS current
			DESCRIPTION
				"Description."
			::= { priV6WanConnAdd 2 }

		
--           1.3.6.1.4.1.37950.1.1.5.12.3.1.6.1.3
-- 1.3.6.1.4.1.37950.1.1.5.12.3.1.21.1.3
-- 1.3.6.1.4.1.37950.1.1.5.12.3.1.21.1.3
-- 1.3.6.1.4.1.37950.1.1.5.12.3.1.21.1.3
-- 1.3.6.1.4.1.37950.1.1.5.12.3.1.21.1.3
-- 1.3.6.1.4.1.37950.1.1.5.12.3.1.21.1.3
-- 1.3.6.1.4.1.37950.1.1.5.12.3.1.21.1.3
-- 1.3.6.1.4.1.37950.1.1.5.12.3.1.21.1.3
-- 1.3.6.1.4.1.37950.1.1.5.12.3.1.21.1.3
		-- 1.3.6.1.4.1.37950.1.1.5.12.3.1.21.1.3
		priV6ConnType OBJECT-TYPE
			SYNTAX INTEGER
				{
				bridge(0),
				route(1)
				}
			MAX-ACCESS read-write
			STATUS current
			DESCRIPTION
				"Description."
			::= { priV6WanConnAdd 3 }

		
--           1.3.6.1.4.1.37950.1.1.5.12.3.1.6.1.4
-- 1.3.6.1.4.1.37950.1.1.5.12.3.1.21.1.4
-- 1.3.6.1.4.1.37950.1.1.5.12.3.1.21.1.4
-- 1.3.6.1.4.1.37950.1.1.5.12.3.1.21.1.4
-- 1.3.6.1.4.1.37950.1.1.5.12.3.1.21.1.4
-- 1.3.6.1.4.1.37950.1.1.5.12.3.1.21.1.4
-- 1.3.6.1.4.1.37950.1.1.5.12.3.1.21.1.4
-- 1.3.6.1.4.1.37950.1.1.5.12.3.1.21.1.4
-- 1.3.6.1.4.1.37950.1.1.5.12.3.1.21.1.4
		-- 1.3.6.1.4.1.37950.1.1.5.12.3.1.21.1.4
		priV6ConnAddAction OBJECT-TYPE
			SYNTAX INTEGER { add(1) }
			MAX-ACCESS read-write
			STATUS current
			DESCRIPTION
				"Description."
			::= { priV6WanConnAdd 4 }

		
--           1.3.6.1.4.1.37950.1.1.5.12.3.1.6.2
-- 1.3.6.1.4.1.37950.1.1.5.12.3.1.21.2
-- 1.3.6.1.4.1.37950.1.1.5.12.3.1.21.2
-- 1.3.6.1.4.1.37950.1.1.5.12.3.1.21.2
-- 1.3.6.1.4.1.37950.1.1.5.12.3.1.21.2
-- 1.3.6.1.4.1.37950.1.1.5.12.3.1.21.2
-- 1.3.6.1.4.1.37950.1.1.5.12.3.1.21.2
-- 1.3.6.1.4.1.37950.1.1.5.12.3.1.21.2
-- 1.3.6.1.4.1.37950.1.1.5.12.3.1.21.2
		-- 1.3.6.1.4.1.37950.1.1.5.12.3.1.21.2
		priV6WanConnDelete OBJECT IDENTIFIER ::= { onuPriWanConnV6 2 }

		
--           1.3.6.1.4.1.37950.1.1.5.12.3.1.6.2.1
-- 1.3.6.1.4.1.37950.1.1.5.12.3.1.21.2.1
-- 1.3.6.1.4.1.37950.1.1.5.12.3.1.21.2.1
-- 1.3.6.1.4.1.37950.1.1.5.12.3.1.21.2.1
-- 1.3.6.1.4.1.37950.1.1.5.12.3.1.21.2.1
-- 1.3.6.1.4.1.37950.1.1.5.12.3.1.21.2.1
-- 1.3.6.1.4.1.37950.1.1.5.12.3.1.21.2.1
-- 1.3.6.1.4.1.37950.1.1.5.12.3.1.21.2.1
-- 1.3.6.1.4.1.37950.1.1.5.12.3.1.21.2.1
		-- 1.3.6.1.4.1.37950.1.1.5.12.3.1.21.2.1
		priV6WanDeletePon OBJECT-TYPE
			SYNTAX INTEGER (1..16)
			MAX-ACCESS read-write
			STATUS current
			DESCRIPTION
				"Description."
			::= { priV6WanConnDelete 1 }

		
--           1.3.6.1.4.1.37950.1.1.5.12.3.1.6.2.2
-- 1.3.6.1.4.1.37950.1.1.5.12.3.1.21.2.2
-- 1.3.6.1.4.1.37950.1.1.5.12.3.1.21.2.2
-- 1.3.6.1.4.1.37950.1.1.5.12.3.1.21.2.2
-- 1.3.6.1.4.1.37950.1.1.5.12.3.1.21.2.2
-- 1.3.6.1.4.1.37950.1.1.5.12.3.1.21.2.2
-- 1.3.6.1.4.1.37950.1.1.5.12.3.1.21.2.2
-- 1.3.6.1.4.1.37950.1.1.5.12.3.1.21.2.2
-- 1.3.6.1.4.1.37950.1.1.5.12.3.1.21.2.2
		-- 1.3.6.1.4.1.37950.1.1.5.12.3.1.21.2.2
		priV6WanDeleteOnu OBJECT-TYPE
			SYNTAX INTEGER (1..65535)
			MAX-ACCESS read-write
			STATUS current
			DESCRIPTION
				"Description."
			::= { priV6WanConnDelete 2 }

		
--           1.3.6.1.4.1.37950.1.1.5.12.3.1.6.2.3
-- 1.3.6.1.4.1.37950.1.1.5.12.3.1.21.2.3
-- 1.3.6.1.4.1.37950.1.1.5.12.3.1.21.2.3
-- 1.3.6.1.4.1.37950.1.1.5.12.3.1.21.2.3
-- 1.3.6.1.4.1.37950.1.1.5.12.3.1.21.2.3
-- 1.3.6.1.4.1.37950.1.1.5.12.3.1.21.2.3
-- 1.3.6.1.4.1.37950.1.1.5.12.3.1.21.2.3
-- 1.3.6.1.4.1.37950.1.1.5.12.3.1.21.2.3
-- 1.3.6.1.4.1.37950.1.1.5.12.3.1.21.2.3
		-- 1.3.6.1.4.1.37950.1.1.5.12.3.1.21.2.3
		priV6ConnIndexD OBJECT-TYPE
			SYNTAX Integer32 (1..8)
			MAX-ACCESS read-write
			STATUS current
			DESCRIPTION
				"Description."
			::= { priV6WanConnDelete 3 }

		
--           1.3.6.1.4.1.37950.1.1.5.12.3.1.6.2.4
-- 1.3.6.1.4.1.37950.1.1.5.12.3.1.21.2.4
-- 1.3.6.1.4.1.37950.1.1.5.12.3.1.21.2.4
-- 1.3.6.1.4.1.37950.1.1.5.12.3.1.21.2.4
-- 1.3.6.1.4.1.37950.1.1.5.12.3.1.21.2.4
-- 1.3.6.1.4.1.37950.1.1.5.12.3.1.21.2.4
-- 1.3.6.1.4.1.37950.1.1.5.12.3.1.21.2.4
-- 1.3.6.1.4.1.37950.1.1.5.12.3.1.21.2.4
-- 1.3.6.1.4.1.37950.1.1.5.12.3.1.21.2.4
		-- 1.3.6.1.4.1.37950.1.1.5.12.3.1.21.2.4
		priV6ConnDeleteAction OBJECT-TYPE
			SYNTAX INTEGER { delete(1) }
			MAX-ACCESS read-write
			STATUS current
			DESCRIPTION
				"Description."
			::= { priV6WanConnDelete 4 }

		
--           1.3.6.1.4.1.37950.1.1.5.12.3.1.6.3
-- 1.3.6.1.4.1.37950.1.1.5.12.3.1.21.3
-- 1.3.6.1.4.1.37950.1.1.5.12.3.1.21.3
-- 1.3.6.1.4.1.37950.1.1.5.12.3.1.21.3
-- 1.3.6.1.4.1.37950.1.1.5.12.3.1.21.3
-- 1.3.6.1.4.1.37950.1.1.5.12.3.1.21.3
-- 1.3.6.1.4.1.37950.1.1.5.12.3.1.21.3
-- 1.3.6.1.4.1.37950.1.1.5.12.3.1.21.3
-- 1.3.6.1.4.1.37950.1.1.5.12.3.1.21.3
		-- 1.3.6.1.4.1.37950.1.1.5.12.3.1.21.3
		priV6WanConnCfg OBJECT IDENTIFIER ::= { onuPriWanConnV6 3 }

		
--           1.3.6.1.4.1.37950.1.1.5.12.3.1.6.3.1
-- 1.3.6.1.4.1.37950.1.1.5.12.3.1.21.3.1
-- 1.3.6.1.4.1.37950.1.1.5.12.3.1.21.3.1
-- 1.3.6.1.4.1.37950.1.1.5.12.3.1.21.3.1
-- 1.3.6.1.4.1.37950.1.1.5.12.3.1.21.3.1
-- 1.3.6.1.4.1.37950.1.1.5.12.3.1.21.3.1
-- 1.3.6.1.4.1.37950.1.1.5.12.3.1.21.3.1
-- 1.3.6.1.4.1.37950.1.1.5.12.3.1.21.3.1
-- 1.3.6.1.4.1.37950.1.1.5.12.3.1.21.3.1
		-- 1.3.6.1.4.1.37950.1.1.5.12.3.1.21.3.1
		priV6ConnPon OBJECT-TYPE
			SYNTAX INTEGER (1..16)
			MAX-ACCESS read-write
			STATUS current
			DESCRIPTION
				"Description."
			::= { priV6WanConnCfg 1 }

		
--           1.3.6.1.4.1.37950.1.1.5.12.3.1.6.3.2
-- 1.3.6.1.4.1.37950.1.1.5.12.3.1.21.3.2
-- 1.3.6.1.4.1.37950.1.1.5.12.3.1.21.3.2
-- 1.3.6.1.4.1.37950.1.1.5.12.3.1.21.3.2
-- 1.3.6.1.4.1.37950.1.1.5.12.3.1.21.3.2
-- 1.3.6.1.4.1.37950.1.1.5.12.3.1.21.3.2
-- 1.3.6.1.4.1.37950.1.1.5.12.3.1.21.3.2
-- 1.3.6.1.4.1.37950.1.1.5.12.3.1.21.3.2
-- 1.3.6.1.4.1.37950.1.1.5.12.3.1.21.3.2
		-- 1.3.6.1.4.1.37950.1.1.5.12.3.1.21.3.2
		priV6ConnOnu OBJECT-TYPE
			SYNTAX INTEGER (1..65535)
			MAX-ACCESS read-write
			STATUS current
			DESCRIPTION
				"Description."
			::= { priV6WanConnCfg 2 }

		
--           1.3.6.1.4.1.37950.1.1.5.12.3.1.6.3.3
-- 1.3.6.1.4.1.37950.1.1.5.12.3.1.21.3.3
-- 1.3.6.1.4.1.37950.1.1.5.12.3.1.21.3.3
-- 1.3.6.1.4.1.37950.1.1.5.12.3.1.21.3.3
-- 1.3.6.1.4.1.37950.1.1.5.12.3.1.21.3.3
-- 1.3.6.1.4.1.37950.1.1.5.12.3.1.21.3.3
-- 1.3.6.1.4.1.37950.1.1.5.12.3.1.21.3.3
-- 1.3.6.1.4.1.37950.1.1.5.12.3.1.21.3.3
-- 1.3.6.1.4.1.37950.1.1.5.12.3.1.21.3.3
		-- 1.3.6.1.4.1.37950.1.1.5.12.3.1.21.3.3
		priV6ConnIndex OBJECT-TYPE
			SYNTAX INTEGER (1..8)
			MAX-ACCESS read-write
			STATUS current
			DESCRIPTION
				"Description."
			::= { priV6WanConnCfg 3 }

		
--           1.3.6.1.4.1.37950.1.1.5.12.3.1.6.3.4
-- 1.3.6.1.4.1.37950.1.1.5.12.3.1.21.3.4
-- 1.3.6.1.4.1.37950.1.1.5.12.3.1.21.3.4
-- 1.3.6.1.4.1.37950.1.1.5.12.3.1.21.3.4
-- 1.3.6.1.4.1.37950.1.1.5.12.3.1.21.3.4
-- 1.3.6.1.4.1.37950.1.1.5.12.3.1.21.3.4
-- 1.3.6.1.4.1.37950.1.1.5.12.3.1.21.3.4
-- 1.3.6.1.4.1.37950.1.1.5.12.3.1.21.3.4
-- 1.3.6.1.4.1.37950.1.1.5.12.3.1.21.3.4
		-- 1.3.6.1.4.1.37950.1.1.5.12.3.1.21.3.4
		priV6ConnBindLan OBJECT-TYPE
			SYNTAX INTEGER (0..15)
			MAX-ACCESS read-write
			STATUS current
			DESCRIPTION
				"Description."
			::= { priV6WanConnCfg 4 }

		
--           1.3.6.1.4.1.37950.1.1.5.12.3.1.6.3.5
-- 1.3.6.1.4.1.37950.1.1.5.12.3.1.21.3.5
-- 1.3.6.1.4.1.37950.1.1.5.12.3.1.21.3.5
-- 1.3.6.1.4.1.37950.1.1.5.12.3.1.21.3.5
-- 1.3.6.1.4.1.37950.1.1.5.12.3.1.21.3.5
-- 1.3.6.1.4.1.37950.1.1.5.12.3.1.21.3.5
-- 1.3.6.1.4.1.37950.1.1.5.12.3.1.21.3.5
-- 1.3.6.1.4.1.37950.1.1.5.12.3.1.21.3.5
-- 1.3.6.1.4.1.37950.1.1.5.12.3.1.21.3.5
		-- 1.3.6.1.4.1.37950.1.1.5.12.3.1.21.3.5
		priV6ConnBindSsid OBJECT-TYPE
			SYNTAX INTEGER (0..65535)
			MAX-ACCESS read-write
			STATUS current
			DESCRIPTION
				"Description."
			::= { priV6WanConnCfg 5 }

		
--           1.3.6.1.4.1.37950.1.1.5.12.3.1.6.3.6
-- 1.3.6.1.4.1.37950.1.1.5.12.3.1.21.3.6
-- 1.3.6.1.4.1.37950.1.1.5.12.3.1.21.3.6
-- 1.3.6.1.4.1.37950.1.1.5.12.3.1.21.3.6
-- 1.3.6.1.4.1.37950.1.1.5.12.3.1.21.3.6
-- 1.3.6.1.4.1.37950.1.1.5.12.3.1.21.3.6
-- 1.3.6.1.4.1.37950.1.1.5.12.3.1.21.3.6
-- 1.3.6.1.4.1.37950.1.1.5.12.3.1.21.3.6
-- 1.3.6.1.4.1.37950.1.1.5.12.3.1.21.3.6
		-- 1.3.6.1.4.1.37950.1.1.5.12.3.1.21.3.6
		priV6WanMode OBJECT-TYPE
			SYNTAX INTEGER
				{
				internet(0),
				multicast(1),
				tr069(2),
				tr069-internet(3),
				tr069-voip(4),
				voip-internet(5),
				tr069-voip-internet(6),
				voip(7),
				other(100)
				}
			MAX-ACCESS read-write
			STATUS current
			DESCRIPTION
				"Description."
			::= { priV6WanConnCfg 6 }

		
--           1.3.6.1.4.1.37950.1.1.5.12.3.1.6.3.7
-- 1.3.6.1.4.1.37950.1.1.5.12.3.1.21.3.7
-- 1.3.6.1.4.1.37950.1.1.5.12.3.1.21.3.7
-- 1.3.6.1.4.1.37950.1.1.5.12.3.1.21.3.7
-- 1.3.6.1.4.1.37950.1.1.5.12.3.1.21.3.7
-- 1.3.6.1.4.1.37950.1.1.5.12.3.1.21.3.7
-- 1.3.6.1.4.1.37950.1.1.5.12.3.1.21.3.7
-- 1.3.6.1.4.1.37950.1.1.5.12.3.1.21.3.7
-- 1.3.6.1.4.1.37950.1.1.5.12.3.1.21.3.7
		-- 1.3.6.1.4.1.37950.1.1.5.12.3.1.21.3.7
		priV6ConnTypeCfg OBJECT-TYPE
			SYNTAX INTEGER
				{
				bridge(0),
				route(1)
				}
			MAX-ACCESS read-write
			STATUS current
			DESCRIPTION
				"Description."
			::= { priV6WanConnCfg 7 }

		
--           1.3.6.1.4.1.37950.1.1.5.12.3.1.6.3.8
-- 1.3.6.1.4.1.37950.1.1.5.12.3.1.21.3.8
-- 1.3.6.1.4.1.37950.1.1.5.12.3.1.21.3.8
-- 1.3.6.1.4.1.37950.1.1.5.12.3.1.21.3.8
-- 1.3.6.1.4.1.37950.1.1.5.12.3.1.21.3.8
-- 1.3.6.1.4.1.37950.1.1.5.12.3.1.21.3.8
-- 1.3.6.1.4.1.37950.1.1.5.12.3.1.21.3.8
-- 1.3.6.1.4.1.37950.1.1.5.12.3.1.21.3.8
-- 1.3.6.1.4.1.37950.1.1.5.12.3.1.21.3.8
		-- 1.3.6.1.4.1.37950.1.1.5.12.3.1.21.3.8
		priV6ConnVlanId OBJECT-TYPE
			SYNTAX Integer32 (0..4095)
			MAX-ACCESS read-write
			STATUS current
			DESCRIPTION
				"Description."
			::= { priV6WanConnCfg 8 }

		
--           1.3.6.1.4.1.37950.1.1.5.12.3.1.6.3.9
-- 1.3.6.1.4.1.37950.1.1.5.12.3.1.21.3.9
-- 1.3.6.1.4.1.37950.1.1.5.12.3.1.21.3.9
-- 1.3.6.1.4.1.37950.1.1.5.12.3.1.21.3.9
-- 1.3.6.1.4.1.37950.1.1.5.12.3.1.21.3.9
-- 1.3.6.1.4.1.37950.1.1.5.12.3.1.21.3.9
-- 1.3.6.1.4.1.37950.1.1.5.12.3.1.21.3.9
-- 1.3.6.1.4.1.37950.1.1.5.12.3.1.21.3.9
-- 1.3.6.1.4.1.37950.1.1.5.12.3.1.21.3.9
		-- 1.3.6.1.4.1.37950.1.1.5.12.3.1.21.3.9
		priV6ConnVlanCos OBJECT-TYPE
			SYNTAX INTEGER (0..7)
			MAX-ACCESS read-write
			STATUS current
			DESCRIPTION
				"Description."
			::= { priV6WanConnCfg 9 }

		
--           1.3.6.1.4.1.37950.1.1.5.12.3.1.6.3.31
-- 1.3.6.1.4.1.37950.1.1.5.12.3.1.21.3.10
-- 1.3.6.1.4.1.37950.1.1.5.12.3.1.21.3.10
-- 1.3.6.1.4.1.37950.1.1.5.12.3.1.21.3.10
-- 1.3.6.1.4.1.37950.1.1.5.12.3.1.21.3.10
-- 1.3.6.1.4.1.37950.1.1.5.12.3.1.21.3.10
-- 1.3.6.1.4.1.37950.1.1.5.12.3.1.21.3.10
-- 1.3.6.1.4.1.37950.1.1.5.12.3.1.21.3.10
-- 1.3.6.1.4.1.37950.1.1.5.12.3.1.21.3.10
		-- 1.3.6.1.4.1.37950.1.1.5.12.3.1.21.3.10
		priV6ConnIpProtocol OBJECT-TYPE
			SYNTAX INTEGER
				{
				ipv4(0),
				ipv6(1),
				ipv4-ipv6(2)
				}
			MAX-ACCESS read-write
			STATUS current
			DESCRIPTION
				"Description."
			::= { priV6WanConnCfg 10 }

		
--           1.3.6.1.4.1.37950.1.1.5.12.3.1.6.3.11
-- 1.3.6.1.4.1.37950.1.1.5.12.3.1.21.3.11
-- 1.3.6.1.4.1.37950.1.1.5.12.3.1.21.3.11
-- 1.3.6.1.4.1.37950.1.1.5.12.3.1.21.3.11
-- 1.3.6.1.4.1.37950.1.1.5.12.3.1.21.3.11
-- 1.3.6.1.4.1.37950.1.1.5.12.3.1.21.3.11
-- 1.3.6.1.4.1.37950.1.1.5.12.3.1.21.3.11
-- 1.3.6.1.4.1.37950.1.1.5.12.3.1.21.3.11
-- 1.3.6.1.4.1.37950.1.1.5.12.3.1.21.3.11
		-- 1.3.6.1.4.1.37950.1.1.5.12.3.1.21.3.11
		priV6ConnModeCfg OBJECT-TYPE
			SYNTAX INTEGER
				{
				dhcp(0),
				static(1),
				pppoe(2)
				}
			MAX-ACCESS read-write
			STATUS current
			DESCRIPTION
				"Description."
			::= { priV6WanConnCfg 11 }

		
--           1.3.6.1.4.1.37950.1.1.5.12.3.1.6.3.12
-- 1.3.6.1.4.1.37950.1.1.5.12.3.1.21.3.12
-- 1.3.6.1.4.1.37950.1.1.5.12.3.1.21.3.12
-- 1.3.6.1.4.1.37950.1.1.5.12.3.1.21.3.12
-- 1.3.6.1.4.1.37950.1.1.5.12.3.1.21.3.12
-- 1.3.6.1.4.1.37950.1.1.5.12.3.1.21.3.12
-- 1.3.6.1.4.1.37950.1.1.5.12.3.1.21.3.12
-- 1.3.6.1.4.1.37950.1.1.5.12.3.1.21.3.12
-- 1.3.6.1.4.1.37950.1.1.5.12.3.1.21.3.12
		-- 1.3.6.1.4.1.37950.1.1.5.12.3.1.21.3.12
		priV6ConnIpAddressIpv4 OBJECT-TYPE
			SYNTAX IpAddress
			MAX-ACCESS read-write
			STATUS current
			DESCRIPTION
				"Description."
			::= { priV6WanConnCfg 12 }

		
--           1.3.6.1.4.1.37950.1.1.5.12.3.1.6.3.13
-- 1.3.6.1.4.1.37950.1.1.5.12.3.1.21.3.13
-- 1.3.6.1.4.1.37950.1.1.5.12.3.1.21.3.13
-- 1.3.6.1.4.1.37950.1.1.5.12.3.1.21.3.13
-- 1.3.6.1.4.1.37950.1.1.5.12.3.1.21.3.13
-- 1.3.6.1.4.1.37950.1.1.5.12.3.1.21.3.13
-- 1.3.6.1.4.1.37950.1.1.5.12.3.1.21.3.13
-- 1.3.6.1.4.1.37950.1.1.5.12.3.1.21.3.13
-- 1.3.6.1.4.1.37950.1.1.5.12.3.1.21.3.13
		-- 1.3.6.1.4.1.37950.1.1.5.12.3.1.21.3.13
		priV6ConnIpNetMaskIpv4 OBJECT-TYPE
			SYNTAX IpAddress
			MAX-ACCESS read-write
			STATUS current
			DESCRIPTION
				"Description."
			::= { priV6WanConnCfg 13 }

		
--           1.3.6.1.4.1.37950.1.1.5.12.3.1.6.3.14
-- 1.3.6.1.4.1.37950.1.1.5.12.3.1.21.3.14
-- 1.3.6.1.4.1.37950.1.1.5.12.3.1.21.3.14
-- 1.3.6.1.4.1.37950.1.1.5.12.3.1.21.3.14
-- 1.3.6.1.4.1.37950.1.1.5.12.3.1.21.3.14
-- 1.3.6.1.4.1.37950.1.1.5.12.3.1.21.3.14
-- 1.3.6.1.4.1.37950.1.1.5.12.3.1.21.3.14
-- 1.3.6.1.4.1.37950.1.1.5.12.3.1.21.3.14
-- 1.3.6.1.4.1.37950.1.1.5.12.3.1.21.3.14
		-- 1.3.6.1.4.1.37950.1.1.5.12.3.1.21.3.14
		priV6ConnGatewayIpv4 OBJECT-TYPE
			SYNTAX IpAddress
			MAX-ACCESS read-write
			STATUS current
			DESCRIPTION
				"Description."
			::= { priV6WanConnCfg 14 }

		
--           1.3.6.1.4.1.37950.1.1.5.12.3.1.6.3.27
-- 1.3.6.1.4.1.37950.1.1.5.12.3.1.21.3.15
-- 1.3.6.1.4.1.37950.1.1.5.12.3.1.21.3.15
-- 1.3.6.1.4.1.37950.1.1.5.12.3.1.21.3.15
-- 1.3.6.1.4.1.37950.1.1.5.12.3.1.21.3.15
-- 1.3.6.1.4.1.37950.1.1.5.12.3.1.21.3.15
-- 1.3.6.1.4.1.37950.1.1.5.12.3.1.21.3.15
-- 1.3.6.1.4.1.37950.1.1.5.12.3.1.21.3.15
-- 1.3.6.1.4.1.37950.1.1.5.12.3.1.21.3.15
		-- 1.3.6.1.4.1.37950.1.1.5.12.3.1.21.3.15
		priV6ConnDnsEnableIpv4 OBJECT-TYPE
			SYNTAX INTEGER
				{
				disable(0),
				enable(1)
				}
			MAX-ACCESS read-write
			STATUS current
			DESCRIPTION
				"Description."
			::= { priV6WanConnCfg 15 }

		
--           1.3.6.1.4.1.37950.1.1.5.12.3.1.6.3.15
-- 1.3.6.1.4.1.37950.1.1.5.12.3.1.21.3.16
-- 1.3.6.1.4.1.37950.1.1.5.12.3.1.21.3.16
-- 1.3.6.1.4.1.37950.1.1.5.12.3.1.21.3.16
-- 1.3.6.1.4.1.37950.1.1.5.12.3.1.21.3.16
-- 1.3.6.1.4.1.37950.1.1.5.12.3.1.21.3.16
-- 1.3.6.1.4.1.37950.1.1.5.12.3.1.21.3.16
-- 1.3.6.1.4.1.37950.1.1.5.12.3.1.21.3.16
-- 1.3.6.1.4.1.37950.1.1.5.12.3.1.21.3.16
		-- 1.3.6.1.4.1.37950.1.1.5.12.3.1.21.3.16
		priV6ConnMasterDnsIpv4 OBJECT-TYPE
			SYNTAX IpAddress
			MAX-ACCESS read-write
			STATUS current
			DESCRIPTION
				"Description."
			::= { priV6WanConnCfg 16 }

		
--           1.3.6.1.4.1.37950.1.1.5.12.3.1.6.3.16
-- 1.3.6.1.4.1.37950.1.1.5.12.3.1.21.3.17
-- 1.3.6.1.4.1.37950.1.1.5.12.3.1.21.3.17
-- 1.3.6.1.4.1.37950.1.1.5.12.3.1.21.3.17
-- 1.3.6.1.4.1.37950.1.1.5.12.3.1.21.3.17
-- 1.3.6.1.4.1.37950.1.1.5.12.3.1.21.3.17
-- 1.3.6.1.4.1.37950.1.1.5.12.3.1.21.3.17
-- 1.3.6.1.4.1.37950.1.1.5.12.3.1.21.3.17
-- 1.3.6.1.4.1.37950.1.1.5.12.3.1.21.3.17
		-- 1.3.6.1.4.1.37950.1.1.5.12.3.1.21.3.17
		priV6ConnSlaveDnsIpv4 OBJECT-TYPE
			SYNTAX IpAddress
			MAX-ACCESS read-write
			STATUS current
			DESCRIPTION
				"Description."
			::= { priV6WanConnCfg 17 }

		
--           1.3.6.1.4.1.37950.1.1.5.12.3.1.6.3.10
-- 1.3.6.1.4.1.37950.1.1.5.12.3.1.21.3.18
-- 1.3.6.1.4.1.37950.1.1.5.12.3.1.21.3.18
-- 1.3.6.1.4.1.37950.1.1.5.12.3.1.21.3.18
-- 1.3.6.1.4.1.37950.1.1.5.12.3.1.21.3.18
-- 1.3.6.1.4.1.37950.1.1.5.12.3.1.21.3.18
-- 1.3.6.1.4.1.37950.1.1.5.12.3.1.21.3.18
-- 1.3.6.1.4.1.37950.1.1.5.12.3.1.21.3.18
-- 1.3.6.1.4.1.37950.1.1.5.12.3.1.21.3.18
		-- 1.3.6.1.4.1.37950.1.1.5.12.3.1.21.3.18
		priV6ConnNatEnable OBJECT-TYPE
			SYNTAX INTEGER
				{
				disable(0),
				enable(1)
				}
			MAX-ACCESS read-write
			STATUS current
			DESCRIPTION
				"Description."
			::= { priV6WanConnCfg 18 }

		
--           1.3.6.1.4.1.37950.1.1.5.12.3.1.6.3.31
-- 1.3.6.1.4.1.37950.1.1.5.12.3.1.21.3.19
-- 1.3.6.1.4.1.37950.1.1.5.12.3.1.21.3.19
-- 1.3.6.1.4.1.37950.1.1.5.12.3.1.21.3.19
-- 1.3.6.1.4.1.37950.1.1.5.12.3.1.21.3.19
-- 1.3.6.1.4.1.37950.1.1.5.12.3.1.21.3.19
-- 1.3.6.1.4.1.37950.1.1.5.12.3.1.21.3.19
-- 1.3.6.1.4.1.37950.1.1.5.12.3.1.21.3.19
-- 1.3.6.1.4.1.37950.1.1.5.12.3.1.21.3.19
		-- 1.3.6.1.4.1.37950.1.1.5.12.3.1.21.3.19
		priV6ConnAddressIpv6 OBJECT-TYPE
			SYNTAX OCTET STRING
			MAX-ACCESS read-write
			STATUS current
			DESCRIPTION
				"Description."
			::= { priV6WanConnCfg 19 }

		
--           1.3.6.1.4.1.37950.1.1.5.12.3.1.6.3.31
-- 1.3.6.1.4.1.37950.1.1.5.12.3.1.21.3.20
-- 1.3.6.1.4.1.37950.1.1.5.12.3.1.21.3.20
-- 1.3.6.1.4.1.37950.1.1.5.12.3.1.21.3.20
-- 1.3.6.1.4.1.37950.1.1.5.12.3.1.21.3.20
-- 1.3.6.1.4.1.37950.1.1.5.12.3.1.21.3.20
-- 1.3.6.1.4.1.37950.1.1.5.12.3.1.21.3.20
-- 1.3.6.1.4.1.37950.1.1.5.12.3.1.21.3.20
-- 1.3.6.1.4.1.37950.1.1.5.12.3.1.21.3.20
		-- 1.3.6.1.4.1.37950.1.1.5.12.3.1.21.3.20
		priV6ConnPrefixLenIpv6 OBJECT-TYPE
			SYNTAX INTEGER (0..128)
			MAX-ACCESS read-write
			STATUS current
			DESCRIPTION
				"Description."
			::= { priV6WanConnCfg 20 }

		
--           1.3.6.1.4.1.37950.1.1.5.12.3.1.6.3.31
-- 1.3.6.1.4.1.37950.1.1.5.12.3.1.21.3.21
-- 1.3.6.1.4.1.37950.1.1.5.12.3.1.21.3.21
-- 1.3.6.1.4.1.37950.1.1.5.12.3.1.21.3.21
-- 1.3.6.1.4.1.37950.1.1.5.12.3.1.21.3.21
-- 1.3.6.1.4.1.37950.1.1.5.12.3.1.21.3.21
-- 1.3.6.1.4.1.37950.1.1.5.12.3.1.21.3.21
-- 1.3.6.1.4.1.37950.1.1.5.12.3.1.21.3.21
-- 1.3.6.1.4.1.37950.1.1.5.12.3.1.21.3.21
		-- 1.3.6.1.4.1.37950.1.1.5.12.3.1.21.3.21
		priV6ConnGatewayIpv6 OBJECT-TYPE
			SYNTAX OCTET STRING
			MAX-ACCESS read-write
			STATUS current
			DESCRIPTION
				"Description."
			::= { priV6WanConnCfg 21 }

		
--           1.3.6.1.4.1.37950.1.1.5.12.3.1.6.3.27
-- 1.3.6.1.4.1.37950.1.1.5.12.3.1.21.3.22
-- 1.3.6.1.4.1.37950.1.1.5.12.3.1.21.3.22
-- 1.3.6.1.4.1.37950.1.1.5.12.3.1.21.3.22
-- 1.3.6.1.4.1.37950.1.1.5.12.3.1.21.3.22
-- 1.3.6.1.4.1.37950.1.1.5.12.3.1.21.3.22
-- 1.3.6.1.4.1.37950.1.1.5.12.3.1.21.3.22
-- 1.3.6.1.4.1.37950.1.1.5.12.3.1.21.3.22
-- 1.3.6.1.4.1.37950.1.1.5.12.3.1.21.3.22
		-- 1.3.6.1.4.1.37950.1.1.5.12.3.1.21.3.22
		priV6ConnDnsEnableIpv6 OBJECT-TYPE
			SYNTAX INTEGER
				{
				disable(0),
				enable(1)
				}
			MAX-ACCESS read-write
			STATUS current
			DESCRIPTION
				"Description."
			::= { priV6WanConnCfg 22 }

		
--           1.3.6.1.4.1.37950.1.1.5.12.3.1.6.3.31
-- 1.3.6.1.4.1.37950.1.1.5.12.3.1.21.3.23
-- 1.3.6.1.4.1.37950.1.1.5.12.3.1.21.3.23
-- 1.3.6.1.4.1.37950.1.1.5.12.3.1.21.3.23
-- 1.3.6.1.4.1.37950.1.1.5.12.3.1.21.3.23
-- 1.3.6.1.4.1.37950.1.1.5.12.3.1.21.3.23
-- 1.3.6.1.4.1.37950.1.1.5.12.3.1.21.3.23
-- 1.3.6.1.4.1.37950.1.1.5.12.3.1.21.3.23
-- 1.3.6.1.4.1.37950.1.1.5.12.3.1.21.3.23
		-- 1.3.6.1.4.1.37950.1.1.5.12.3.1.21.3.23
		priV6ConnMasterDnsIpv6 OBJECT-TYPE
			SYNTAX OCTET STRING
			MAX-ACCESS read-write
			STATUS current
			DESCRIPTION
				"Description."
			::= { priV6WanConnCfg 23 }

		
--           1.3.6.1.4.1.37950.1.1.5.12.3.1.6.3.31
-- 1.3.6.1.4.1.37950.1.1.5.12.3.1.21.3.24
-- 1.3.6.1.4.1.37950.1.1.5.12.3.1.21.3.24
-- 1.3.6.1.4.1.37950.1.1.5.12.3.1.21.3.24
-- 1.3.6.1.4.1.37950.1.1.5.12.3.1.21.3.24
-- 1.3.6.1.4.1.37950.1.1.5.12.3.1.21.3.24
-- 1.3.6.1.4.1.37950.1.1.5.12.3.1.21.3.24
-- 1.3.6.1.4.1.37950.1.1.5.12.3.1.21.3.24
-- 1.3.6.1.4.1.37950.1.1.5.12.3.1.21.3.24
		-- 1.3.6.1.4.1.37950.1.1.5.12.3.1.21.3.24
		priV6ConnSlaveDnsIpv6 OBJECT-TYPE
			SYNTAX OCTET STRING
			MAX-ACCESS read-write
			STATUS current
			DESCRIPTION
				"Description."
			::= { priV6WanConnCfg 24 }

		
--           1.3.6.1.4.1.37950.1.1.5.12.3.1.6.3.31
-- 1.3.6.1.4.1.37950.1.1.5.12.3.1.21.3.25
-- 1.3.6.1.4.1.37950.1.1.5.12.3.1.21.3.25
-- 1.3.6.1.4.1.37950.1.1.5.12.3.1.21.3.25
-- 1.3.6.1.4.1.37950.1.1.5.12.3.1.21.3.25
-- 1.3.6.1.4.1.37950.1.1.5.12.3.1.21.3.25
-- 1.3.6.1.4.1.37950.1.1.5.12.3.1.21.3.25
-- 1.3.6.1.4.1.37950.1.1.5.12.3.1.21.3.25
-- 1.3.6.1.4.1.37950.1.1.5.12.3.1.21.3.25
		-- 1.3.6.1.4.1.37950.1.1.5.12.3.1.21.3.25
		priV6ConnSlaac OBJECT-TYPE
			SYNTAX INTEGER
				{
				disable(0),
				enable(1)
				}
			MAX-ACCESS read-write
			STATUS current
			DESCRIPTION
				"Description."
			::= { priV6WanConnCfg 25 }

		
--           1.3.6.1.4.1.37950.1.1.5.12.3.1.6.3.17
-- 1.3.6.1.4.1.37950.1.1.5.12.3.1.21.3.26
-- 1.3.6.1.4.1.37950.1.1.5.12.3.1.21.3.26
-- 1.3.6.1.4.1.37950.1.1.5.12.3.1.21.3.26
-- 1.3.6.1.4.1.37950.1.1.5.12.3.1.21.3.26
-- 1.3.6.1.4.1.37950.1.1.5.12.3.1.21.3.26
-- 1.3.6.1.4.1.37950.1.1.5.12.3.1.21.3.26
-- 1.3.6.1.4.1.37950.1.1.5.12.3.1.21.3.26
-- 1.3.6.1.4.1.37950.1.1.5.12.3.1.21.3.26
		-- 1.3.6.1.4.1.37950.1.1.5.12.3.1.21.3.26
		priV6ConnPppoeProxy OBJECT-TYPE
			SYNTAX INTEGER
				{
				disable(0),
				enable(1)
				}
			MAX-ACCESS read-write
			STATUS current
			DESCRIPTION
				"Description."
			::= { priV6WanConnCfg 26 }

		
--           1.3.6.1.4.1.37950.1.1.5.12.3.1.6.3.18
-- 1.3.6.1.4.1.37950.1.1.5.12.3.1.21.3.27
-- 1.3.6.1.4.1.37950.1.1.5.12.3.1.21.3.27
-- 1.3.6.1.4.1.37950.1.1.5.12.3.1.21.3.27
-- 1.3.6.1.4.1.37950.1.1.5.12.3.1.21.3.27
-- 1.3.6.1.4.1.37950.1.1.5.12.3.1.21.3.27
-- 1.3.6.1.4.1.37950.1.1.5.12.3.1.21.3.27
-- 1.3.6.1.4.1.37950.1.1.5.12.3.1.21.3.27
-- 1.3.6.1.4.1.37950.1.1.5.12.3.1.21.3.27
		-- 1.3.6.1.4.1.37950.1.1.5.12.3.1.21.3.27
		priV6ConnPppoeUsername OBJECT-TYPE
			SYNTAX OCTET STRING
			MAX-ACCESS read-write
			STATUS current
			DESCRIPTION
				"Description."
			::= { priV6WanConnCfg 27 }

		
--           1.3.6.1.4.1.37950.1.1.5.12.3.1.6.3.19
-- 1.3.6.1.4.1.37950.1.1.5.12.3.1.21.3.28
-- 1.3.6.1.4.1.37950.1.1.5.12.3.1.21.3.28
-- 1.3.6.1.4.1.37950.1.1.5.12.3.1.21.3.28
-- 1.3.6.1.4.1.37950.1.1.5.12.3.1.21.3.28
-- 1.3.6.1.4.1.37950.1.1.5.12.3.1.21.3.28
-- 1.3.6.1.4.1.37950.1.1.5.12.3.1.21.3.28
-- 1.3.6.1.4.1.37950.1.1.5.12.3.1.21.3.28
-- 1.3.6.1.4.1.37950.1.1.5.12.3.1.21.3.28
		-- 1.3.6.1.4.1.37950.1.1.5.12.3.1.21.3.28
		priV6ConnPppoePassword OBJECT-TYPE
			SYNTAX OCTET STRING
			MAX-ACCESS read-write
			STATUS current
			DESCRIPTION
				"Description."
			::= { priV6WanConnCfg 28 }

		
--           1.3.6.1.4.1.37950.1.1.5.12.3.1.6.3.20
-- 1.3.6.1.4.1.37950.1.1.5.12.3.1.21.3.29
-- 1.3.6.1.4.1.37950.1.1.5.12.3.1.21.3.29
-- 1.3.6.1.4.1.37950.1.1.5.12.3.1.21.3.29
-- 1.3.6.1.4.1.37950.1.1.5.12.3.1.21.3.29
-- 1.3.6.1.4.1.37950.1.1.5.12.3.1.21.3.29
-- 1.3.6.1.4.1.37950.1.1.5.12.3.1.21.3.29
-- 1.3.6.1.4.1.37950.1.1.5.12.3.1.21.3.29
-- 1.3.6.1.4.1.37950.1.1.5.12.3.1.21.3.29
		-- 1.3.6.1.4.1.37950.1.1.5.12.3.1.21.3.29
		priV6ConnPppoeSerName OBJECT-TYPE
			SYNTAX OCTET STRING
			MAX-ACCESS read-write
			STATUS current
			DESCRIPTION
				"Description."
			::= { priV6WanConnCfg 29 }

		
--           1.3.6.1.4.1.37950.1.1.5.12.3.1.6.3.21
-- 1.3.6.1.4.1.37950.1.1.5.12.3.1.21.3.30
-- 1.3.6.1.4.1.37950.1.1.5.12.3.1.21.3.30
-- 1.3.6.1.4.1.37950.1.1.5.12.3.1.21.3.30
-- 1.3.6.1.4.1.37950.1.1.5.12.3.1.21.3.30
-- 1.3.6.1.4.1.37950.1.1.5.12.3.1.21.3.30
-- 1.3.6.1.4.1.37950.1.1.5.12.3.1.21.3.30
-- 1.3.6.1.4.1.37950.1.1.5.12.3.1.21.3.30
-- 1.3.6.1.4.1.37950.1.1.5.12.3.1.21.3.30
		-- 1.3.6.1.4.1.37950.1.1.5.12.3.1.21.3.30
		priV6ConnPppoeMode OBJECT-TYPE
			SYNTAX INTEGER
				{
				autoConnect(0),
				flowConnect(1)
				}
			MAX-ACCESS read-write
			STATUS current
			DESCRIPTION
				"Description."
			::= { priV6WanConnCfg 30 }

		
--           1.3.6.1.4.1.37950.1.1.5.12.3.1.6.3.31
-- 1.3.6.1.4.1.37950.1.1.5.12.3.1.21.3.31
-- 1.3.6.1.4.1.37950.1.1.5.12.3.1.21.3.31
-- 1.3.6.1.4.1.37950.1.1.5.12.3.1.21.3.31
-- 1.3.6.1.4.1.37950.1.1.5.12.3.1.21.3.31
-- 1.3.6.1.4.1.37950.1.1.5.12.3.1.21.3.31
-- 1.3.6.1.4.1.37950.1.1.5.12.3.1.21.3.31
-- 1.3.6.1.4.1.37950.1.1.5.12.3.1.21.3.31
-- 1.3.6.1.4.1.37950.1.1.5.12.3.1.21.3.31
		-- 1.3.6.1.4.1.37950.1.1.5.12.3.1.21.3.31
		priV6ConnDhcpv6ClientAddress OBJECT-TYPE
			SYNTAX INTEGER
				{
				disable(0),
				enable(1)
				}
			MAX-ACCESS read-write
			STATUS current
			DESCRIPTION
				"Description."
			::= { priV6WanConnCfg 31 }

		
--           1.3.6.1.4.1.37950.1.1.5.12.3.1.6.3.31
-- 1.3.6.1.4.1.37950.1.1.5.12.3.1.21.3.32
-- 1.3.6.1.4.1.37950.1.1.5.12.3.1.21.3.32
-- 1.3.6.1.4.1.37950.1.1.5.12.3.1.21.3.32
-- 1.3.6.1.4.1.37950.1.1.5.12.3.1.21.3.32
-- 1.3.6.1.4.1.37950.1.1.5.12.3.1.21.3.32
-- 1.3.6.1.4.1.37950.1.1.5.12.3.1.21.3.32
-- 1.3.6.1.4.1.37950.1.1.5.12.3.1.21.3.32
-- 1.3.6.1.4.1.37950.1.1.5.12.3.1.21.3.32
		-- 1.3.6.1.4.1.37950.1.1.5.12.3.1.21.3.32
		priV6ConnDhcpv6ClientPrefix OBJECT-TYPE
			SYNTAX INTEGER
				{
				disable(0),
				enable(1)
				}
			MAX-ACCESS read-write
			STATUS current
			DESCRIPTION
				"Description."
			::= { priV6WanConnCfg 32 }

		
--           1.3.6.1.4.1.37950.1.1.5.12.3.1.6.3.31
-- 1.3.6.1.4.1.37950.1.1.5.12.3.1.21.3.33
-- 1.3.6.1.4.1.37950.1.1.5.12.3.1.21.3.33
-- 1.3.6.1.4.1.37950.1.1.5.12.3.1.21.3.33
-- 1.3.6.1.4.1.37950.1.1.5.12.3.1.21.3.33
-- 1.3.6.1.4.1.37950.1.1.5.12.3.1.21.3.33
-- 1.3.6.1.4.1.37950.1.1.5.12.3.1.21.3.33
-- 1.3.6.1.4.1.37950.1.1.5.12.3.1.21.3.33
-- 1.3.6.1.4.1.37950.1.1.5.12.3.1.21.3.33
		-- 1.3.6.1.4.1.37950.1.1.5.12.3.1.21.3.33
		priV6ConnDsLiteEnable OBJECT-TYPE
			SYNTAX INTEGER
				{
				disable(0),
				enable(1)
				}
			MAX-ACCESS read-write
			STATUS current
			DESCRIPTION
				"Description."
			::= { priV6WanConnCfg 33 }

		
--           1.3.6.1.4.1.37950.1.1.5.12.3.1.6.3.31
-- 1.3.6.1.4.1.37950.1.1.5.12.3.1.21.3.34
-- 1.3.6.1.4.1.37950.1.1.5.12.3.1.21.3.34
-- 1.3.6.1.4.1.37950.1.1.5.12.3.1.21.3.34
-- 1.3.6.1.4.1.37950.1.1.5.12.3.1.21.3.34
-- 1.3.6.1.4.1.37950.1.1.5.12.3.1.21.3.34
-- 1.3.6.1.4.1.37950.1.1.5.12.3.1.21.3.34
-- 1.3.6.1.4.1.37950.1.1.5.12.3.1.21.3.34
-- 1.3.6.1.4.1.37950.1.1.5.12.3.1.21.3.34
		-- 1.3.6.1.4.1.37950.1.1.5.12.3.1.21.3.34
		priV6ConnDsLiteAftrMode OBJECT-TYPE
			SYNTAX INTEGER
				{
				dhcpv6(0),
				manual(1)
				}
			MAX-ACCESS read-write
			STATUS current
			DESCRIPTION
				"Description."
			::= { priV6WanConnCfg 34 }

		
--           1.3.6.1.4.1.37950.1.1.5.12.3.1.6.3.31
-- 1.3.6.1.4.1.37950.1.1.5.12.3.1.21.3.35
-- 1.3.6.1.4.1.37950.1.1.5.12.3.1.21.3.35
-- 1.3.6.1.4.1.37950.1.1.5.12.3.1.21.3.35
-- 1.3.6.1.4.1.37950.1.1.5.12.3.1.21.3.35
-- 1.3.6.1.4.1.37950.1.1.5.12.3.1.21.3.35
-- 1.3.6.1.4.1.37950.1.1.5.12.3.1.21.3.35
-- 1.3.6.1.4.1.37950.1.1.5.12.3.1.21.3.35
-- 1.3.6.1.4.1.37950.1.1.5.12.3.1.21.3.35
		-- 1.3.6.1.4.1.37950.1.1.5.12.3.1.21.3.35
		priV6ConnDsLiteAddressType OBJECT-TYPE
			SYNTAX INTEGER
				{
				ipv6(0),
				dns(1)
				}
			MAX-ACCESS read-write
			STATUS current
			DESCRIPTION
				"Description."
			::= { priV6WanConnCfg 35 }

		
--           1.3.6.1.4.1.37950.1.1.5.12.3.1.6.3.31
-- 1.3.6.1.4.1.37950.1.1.5.12.3.1.21.3.36
-- 1.3.6.1.4.1.37950.1.1.5.12.3.1.21.3.36
-- 1.3.6.1.4.1.37950.1.1.5.12.3.1.21.3.36
-- 1.3.6.1.4.1.37950.1.1.5.12.3.1.21.3.36
-- 1.3.6.1.4.1.37950.1.1.5.12.3.1.21.3.36
-- 1.3.6.1.4.1.37950.1.1.5.12.3.1.21.3.36
-- 1.3.6.1.4.1.37950.1.1.5.12.3.1.21.3.36
-- 1.3.6.1.4.1.37950.1.1.5.12.3.1.21.3.36
		-- 1.3.6.1.4.1.37950.1.1.5.12.3.1.21.3.36
		priV6ConnDsLiteAddress OBJECT-TYPE
			SYNTAX OCTET STRING
			MAX-ACCESS read-write
			STATUS current
			DESCRIPTION
				"Description."
			::= { priV6WanConnCfg 36 }

		
--           1.3.6.1.4.1.37950.1.1.5.12.3.1.6.3.22
-- 1.3.6.1.4.1.37950.1.1.5.12.3.1.21.3.37
-- 1.3.6.1.4.1.37950.1.1.5.12.3.1.21.3.37
-- 1.3.6.1.4.1.37950.1.1.5.12.3.1.21.3.37
-- 1.3.6.1.4.1.37950.1.1.5.12.3.1.21.3.37
-- 1.3.6.1.4.1.37950.1.1.5.12.3.1.21.3.37
-- 1.3.6.1.4.1.37950.1.1.5.12.3.1.21.3.37
-- 1.3.6.1.4.1.37950.1.1.5.12.3.1.21.3.37
-- 1.3.6.1.4.1.37950.1.1.5.12.3.1.21.3.37
		-- 1.3.6.1.4.1.37950.1.1.5.12.3.1.21.3.37
		priV6ConnQosEnable OBJECT-TYPE
			SYNTAX INTEGER
				{
				disable(0),
				enable(1)
				}
			MAX-ACCESS read-write
			STATUS current
			DESCRIPTION
				"Description."
			::= { priV6WanConnCfg 37 }

		
--           1.3.6.1.4.1.37950.1.1.5.12.3.1.6.3.23
-- 1.3.6.1.4.1.37950.1.1.5.12.3.1.21.3.38
-- 1.3.6.1.4.1.37950.1.1.5.12.3.1.21.3.38
-- 1.3.6.1.4.1.37950.1.1.5.12.3.1.21.3.38
-- 1.3.6.1.4.1.37950.1.1.5.12.3.1.21.3.38
-- 1.3.6.1.4.1.37950.1.1.5.12.3.1.21.3.38
-- 1.3.6.1.4.1.37950.1.1.5.12.3.1.21.3.38
-- 1.3.6.1.4.1.37950.1.1.5.12.3.1.21.3.38
-- 1.3.6.1.4.1.37950.1.1.5.12.3.1.21.3.38
		-- 1.3.6.1.4.1.37950.1.1.5.12.3.1.21.3.38
		priV6ConnVlanMode OBJECT-TYPE
			SYNTAX INTEGER
				{
				disable(0),
				tag(1),
				transparent(2)
				}
			MAX-ACCESS read-write
			STATUS current
			DESCRIPTION
				"Description."
			::= { priV6WanConnCfg 38 }

		
--           1.3.6.1.4.1.37950.1.1.5.12.3.1.6.3.24
-- 1.3.6.1.4.1.37950.1.1.5.12.3.1.21.3.39
-- 1.3.6.1.4.1.37950.1.1.5.12.3.1.21.3.39
-- 1.3.6.1.4.1.37950.1.1.5.12.3.1.21.3.39
-- 1.3.6.1.4.1.37950.1.1.5.12.3.1.21.3.39
-- 1.3.6.1.4.1.37950.1.1.5.12.3.1.21.3.39
-- 1.3.6.1.4.1.37950.1.1.5.12.3.1.21.3.39
-- 1.3.6.1.4.1.37950.1.1.5.12.3.1.21.3.39
-- 1.3.6.1.4.1.37950.1.1.5.12.3.1.21.3.39
		-- 1.3.6.1.4.1.37950.1.1.5.12.3.1.21.3.39
		priV6ConnTranslationEnable OBJECT-TYPE
			SYNTAX INTEGER
				{
				disable(0),
				enable(1)
				}
			MAX-ACCESS read-write
			STATUS current
			DESCRIPTION
				"Description."
			::= { priV6WanConnCfg 39 }

		
--           1.3.6.1.4.1.37950.1.1.5.12.3.1.6.3.25
-- 1.3.6.1.4.1.37950.1.1.5.12.3.1.21.3.40
-- 1.3.6.1.4.1.37950.1.1.5.12.3.1.21.3.40
-- 1.3.6.1.4.1.37950.1.1.5.12.3.1.21.3.40
-- 1.3.6.1.4.1.37950.1.1.5.12.3.1.21.3.40
-- 1.3.6.1.4.1.37950.1.1.5.12.3.1.21.3.40
-- 1.3.6.1.4.1.37950.1.1.5.12.3.1.21.3.40
-- 1.3.6.1.4.1.37950.1.1.5.12.3.1.21.3.40
-- 1.3.6.1.4.1.37950.1.1.5.12.3.1.21.3.40
		-- 1.3.6.1.4.1.37950.1.1.5.12.3.1.21.3.40
		priV6ConnTranslationVlan OBJECT-TYPE
			SYNTAX INTEGER (1..4095)
			MAX-ACCESS read-write
			STATUS current
			DESCRIPTION
				"Description."
			::= { priV6WanConnCfg 40 }

		
--           1.3.6.1.4.1.37950.1.1.5.12.3.1.6.3.26
-- 1.3.6.1.4.1.37950.1.1.5.12.3.1.21.3.41
-- 1.3.6.1.4.1.37950.1.1.5.12.3.1.21.3.41
-- 1.3.6.1.4.1.37950.1.1.5.12.3.1.21.3.41
-- 1.3.6.1.4.1.37950.1.1.5.12.3.1.21.3.41
-- 1.3.6.1.4.1.37950.1.1.5.12.3.1.21.3.41
-- 1.3.6.1.4.1.37950.1.1.5.12.3.1.21.3.41
-- 1.3.6.1.4.1.37950.1.1.5.12.3.1.21.3.41
-- 1.3.6.1.4.1.37950.1.1.5.12.3.1.21.3.41
		-- 1.3.6.1.4.1.37950.1.1.5.12.3.1.21.3.41
		priV6ConnTranslationCos OBJECT-TYPE
			SYNTAX INTEGER (0..7)
			MAX-ACCESS read-write
			STATUS current
			DESCRIPTION
				"Description."
			::= { priV6WanConnCfg 41 }

		
--           1.3.6.1.4.1.37950.1.1.5.12.3.1.6.3.27
-- 1.3.6.1.4.1.37950.1.1.5.12.3.1.21.3.42
-- 1.3.6.1.4.1.37950.1.1.5.12.3.1.21.3.42
-- 1.3.6.1.4.1.37950.1.1.5.12.3.1.21.3.42
-- 1.3.6.1.4.1.37950.1.1.5.12.3.1.21.3.42
-- 1.3.6.1.4.1.37950.1.1.5.12.3.1.21.3.42
-- 1.3.6.1.4.1.37950.1.1.5.12.3.1.21.3.42
-- 1.3.6.1.4.1.37950.1.1.5.12.3.1.21.3.42
-- 1.3.6.1.4.1.37950.1.1.5.12.3.1.21.3.42
		-- 1.3.6.1.4.1.37950.1.1.5.12.3.1.21.3.42
		priV6ConnQinqEnable OBJECT-TYPE
			SYNTAX INTEGER
				{
				disable(0),
				enable(1)
				}
			MAX-ACCESS read-write
			STATUS current
			DESCRIPTION
				"Description."
			::= { priV6WanConnCfg 42 }

		
--           1.3.6.1.4.1.37950.1.1.5.12.3.1.6.3.28
-- 1.3.6.1.4.1.37950.1.1.5.12.3.1.21.3.43
-- 1.3.6.1.4.1.37950.1.1.5.12.3.1.21.3.43
-- 1.3.6.1.4.1.37950.1.1.5.12.3.1.21.3.43
-- 1.3.6.1.4.1.37950.1.1.5.12.3.1.21.3.43
-- 1.3.6.1.4.1.37950.1.1.5.12.3.1.21.3.43
-- 1.3.6.1.4.1.37950.1.1.5.12.3.1.21.3.43
-- 1.3.6.1.4.1.37950.1.1.5.12.3.1.21.3.43
-- 1.3.6.1.4.1.37950.1.1.5.12.3.1.21.3.43
		-- 1.3.6.1.4.1.37950.1.1.5.12.3.1.21.3.43
		priV6ConnQinqTpid OBJECT-TYPE
			SYNTAX Integer32 (1..65534)
			MAX-ACCESS read-write
			STATUS current
			DESCRIPTION
				"Description."
			::= { priV6WanConnCfg 43 }

		
--           1.3.6.1.4.1.37950.1.1.5.12.3.1.6.3.29
-- 1.3.6.1.4.1.37950.1.1.5.12.3.1.21.3.44
-- 1.3.6.1.4.1.37950.1.1.5.12.3.1.21.3.44
-- 1.3.6.1.4.1.37950.1.1.5.12.3.1.21.3.44
-- 1.3.6.1.4.1.37950.1.1.5.12.3.1.21.3.44
-- 1.3.6.1.4.1.37950.1.1.5.12.3.1.21.3.44
-- 1.3.6.1.4.1.37950.1.1.5.12.3.1.21.3.44
-- 1.3.6.1.4.1.37950.1.1.5.12.3.1.21.3.44
-- 1.3.6.1.4.1.37950.1.1.5.12.3.1.21.3.44
		-- 1.3.6.1.4.1.37950.1.1.5.12.3.1.21.3.44
		priV6ConnSvlanId OBJECT-TYPE
			SYNTAX INTEGER (1..4095)
			MAX-ACCESS read-write
			STATUS current
			DESCRIPTION
				"Description."
			::= { priV6WanConnCfg 44 }

		
--           1.3.6.1.4.1.37950.1.1.5.12.3.1.6.3.30
-- 1.3.6.1.4.1.37950.1.1.5.12.3.1.21.3.45
-- 1.3.6.1.4.1.37950.1.1.5.12.3.1.21.3.45
-- 1.3.6.1.4.1.37950.1.1.5.12.3.1.21.3.45
-- 1.3.6.1.4.1.37950.1.1.5.12.3.1.21.3.45
-- 1.3.6.1.4.1.37950.1.1.5.12.3.1.21.3.45
-- 1.3.6.1.4.1.37950.1.1.5.12.3.1.21.3.45
-- 1.3.6.1.4.1.37950.1.1.5.12.3.1.21.3.45
-- 1.3.6.1.4.1.37950.1.1.5.12.3.1.21.3.45
		-- 1.3.6.1.4.1.37950.1.1.5.12.3.1.21.3.45
		priV6ConnSvlanCos OBJECT-TYPE
			SYNTAX INTEGER (0..7)
			MAX-ACCESS read-write
			STATUS current
			DESCRIPTION
				"Description."
			::= { priV6WanConnCfg 45 }

		
--           1.3.6.1.4.1.37950.1.1.5.12.3.1.6.3.31
-- 1.3.6.1.4.1.37950.1.1.5.12.3.1.21.3.46
-- 1.3.6.1.4.1.37950.1.1.5.12.3.1.21.3.46
-- 1.3.6.1.4.1.37950.1.1.5.12.3.1.21.3.46
-- 1.3.6.1.4.1.37950.1.1.5.12.3.1.21.3.46
-- 1.3.6.1.4.1.37950.1.1.5.12.3.1.21.3.46
-- 1.3.6.1.4.1.37950.1.1.5.12.3.1.21.3.46
-- 1.3.6.1.4.1.37950.1.1.5.12.3.1.21.3.46
-- 1.3.6.1.4.1.37950.1.1.5.12.3.1.21.3.46
		-- 1.3.6.1.4.1.37950.1.1.5.12.3.1.21.3.46
		priV6ConnRouteMtu OBJECT-TYPE
			SYNTAX Integer32 (576..1500)
			MAX-ACCESS read-write
			STATUS current
			DESCRIPTION
				"Description."
			::= { priV6WanConnCfg 46 }

		
--           1.3.6.1.4.1.37950.1.1.5.12.3.1.6.3.31
-- 1.3.6.1.4.1.37950.1.1.5.12.3.1.21.3.47
-- 1.3.6.1.4.1.37950.1.1.5.12.3.1.21.3.47
-- 1.3.6.1.4.1.37950.1.1.5.12.3.1.21.3.47
-- 1.3.6.1.4.1.37950.1.1.5.12.3.1.21.3.47
-- 1.3.6.1.4.1.37950.1.1.5.12.3.1.21.3.47
-- 1.3.6.1.4.1.37950.1.1.5.12.3.1.21.3.47
-- 1.3.6.1.4.1.37950.1.1.5.12.3.1.21.3.47
-- 1.3.6.1.4.1.37950.1.1.5.12.3.1.21.3.47
		-- 1.3.6.1.4.1.37950.1.1.5.12.3.1.21.3.47
		priV6ConnCfgAction OBJECT-TYPE
			SYNTAX INTEGER { add(1) }
			MAX-ACCESS read-write
			STATUS current
			DESCRIPTION
				"Description."
			::= { priV6WanConnCfg 47 }

		
--           1.3.6.1.4.1.37950.1.1.5.12.3.1.6.4
-- 1.3.6.1.4.1.37950.1.1.5.12.3.1.21.4
-- 1.3.6.1.4.1.37950.1.1.5.12.3.1.21.4
-- 1.3.6.1.4.1.37950.1.1.5.12.3.1.21.4
-- 1.3.6.1.4.1.37950.1.1.5.12.3.1.21.4
-- 1.3.6.1.4.1.37950.1.1.5.12.3.1.21.4
-- 1.3.6.1.4.1.37950.1.1.5.12.3.1.21.4
-- 1.3.6.1.4.1.37950.1.1.5.12.3.1.21.4
-- 1.3.6.1.4.1.37950.1.1.5.12.3.1.21.4
		-- 1.3.6.1.4.1.37950.1.1.5.12.3.1.21.4
		priV6WanConnCommit OBJECT IDENTIFIER ::= { onuPriWanConnV6 4 }

		
--           1.3.6.1.4.1.37950.1.1.5.12.3.1.6.4.1
-- 1.3.6.1.4.1.37950.1.1.5.12.3.1.21.4.1
-- 1.3.6.1.4.1.37950.1.1.5.12.3.1.21.4.1
-- 1.3.6.1.4.1.37950.1.1.5.12.3.1.21.4.1
-- 1.3.6.1.4.1.37950.1.1.5.12.3.1.21.4.1
-- 1.3.6.1.4.1.37950.1.1.5.12.3.1.21.4.1
-- 1.3.6.1.4.1.37950.1.1.5.12.3.1.21.4.1
-- 1.3.6.1.4.1.37950.1.1.5.12.3.1.21.4.1
-- 1.3.6.1.4.1.37950.1.1.5.12.3.1.21.4.1
		-- 1.3.6.1.4.1.37950.1.1.5.12.3.1.21.4.1
		priV6ConnCommitPon OBJECT-TYPE
			SYNTAX INTEGER (1..16)
			MAX-ACCESS read-write
			STATUS current
			DESCRIPTION
				"Description."
			::= { priV6WanConnCommit 1 }

		
--           1.3.6.1.4.1.37950.1.1.5.12.3.1.6.4.2
-- 1.3.6.1.4.1.37950.1.1.5.12.3.1.21.4.2
-- 1.3.6.1.4.1.37950.1.1.5.12.3.1.21.4.2
-- 1.3.6.1.4.1.37950.1.1.5.12.3.1.21.4.2
-- 1.3.6.1.4.1.37950.1.1.5.12.3.1.21.4.2
-- 1.3.6.1.4.1.37950.1.1.5.12.3.1.21.4.2
-- 1.3.6.1.4.1.37950.1.1.5.12.3.1.21.4.2
-- 1.3.6.1.4.1.37950.1.1.5.12.3.1.21.4.2
-- 1.3.6.1.4.1.37950.1.1.5.12.3.1.21.4.2
		-- 1.3.6.1.4.1.37950.1.1.5.12.3.1.21.4.2
		priV6ConnCommitOnu OBJECT-TYPE
			SYNTAX INTEGER (1..65535)
			MAX-ACCESS read-write
			STATUS current
			DESCRIPTION
				"Description."
			::= { priV6WanConnCommit 2 }

		
--           1.3.6.1.4.1.37950.1.1.5.12.3.1.6.4.3
-- 1.3.6.1.4.1.37950.1.1.5.12.3.1.21.4.3
-- 1.3.6.1.4.1.37950.1.1.5.12.3.1.21.4.3
-- 1.3.6.1.4.1.37950.1.1.5.12.3.1.21.4.3
-- 1.3.6.1.4.1.37950.1.1.5.12.3.1.21.4.3
-- 1.3.6.1.4.1.37950.1.1.5.12.3.1.21.4.3
-- 1.3.6.1.4.1.37950.1.1.5.12.3.1.21.4.3
-- 1.3.6.1.4.1.37950.1.1.5.12.3.1.21.4.3
-- 1.3.6.1.4.1.37950.1.1.5.12.3.1.21.4.3
		-- 1.3.6.1.4.1.37950.1.1.5.12.3.1.21.4.3
		priV6ConnCommitAction OBJECT-TYPE
			SYNTAX INTEGER
				{
				commit(1),
				remove(2)
				}
			MAX-ACCESS read-write
			STATUS current
			DESCRIPTION
				"Description."
			::= { priV6WanConnCommit 3 }

		
--         1.3.6.1.4.1.37950.1.1.5.12.3.1.22
-- 1.3.6.1.4.1.37950.1.1.5.12.3.1.22
-- 1.3.6.1.4.1.37950.1.1.5.12.3.1.22
-- 1.3.6.1.4.1.37950.1.1.5.12.3.1.22
-- 1.3.6.1.4.1.37950.1.1.5.12.3.1.22
-- 1.3.6.1.4.1.37950.1.1.5.12.3.1.22
-- 1.3.6.1.4.1.37950.1.1.5.12.3.1.22
-- 1.3.6.1.4.1.37950.1.1.5.12.3.1.22
		-- 1.3.6.1.4.1.37950.1.1.5.12.3.1.22
		onuPriTr069 OBJECT IDENTIFIER ::= { onuPriGlobalCfg 22 }

		
--         1.3.6.1.4.1.37950.1.1.5.12.3.1.22.1
-- 1.3.6.1.4.1.37950.1.1.5.12.3.1.22.1
-- 1.3.6.1.4.1.37950.1.1.5.12.3.1.22.1
-- 1.3.6.1.4.1.37950.1.1.5.12.3.1.22.1
-- 1.3.6.1.4.1.37950.1.1.5.12.3.1.22.1
-- 1.3.6.1.4.1.37950.1.1.5.12.3.1.22.1
-- 1.3.6.1.4.1.37950.1.1.5.12.3.1.22.1
-- 1.3.6.1.4.1.37950.1.1.5.12.3.1.22.1
		-- 1.3.6.1.4.1.37950.1.1.5.12.3.1.22.1
		onuPriTr069Manage OBJECT IDENTIFIER ::= { onuPriTr069 1 }

		
--         1.3.6.1.4.1.37950.1.1.5.12.3.1.22.1.1
-- 1.3.6.1.4.1.37950.1.1.5.12.3.1.22.1.1
-- 1.3.6.1.4.1.37950.1.1.5.12.3.1.22.1.1
-- 1.3.6.1.4.1.37950.1.1.5.12.3.1.22.1.1
-- 1.3.6.1.4.1.37950.1.1.5.12.3.1.22.1.1
-- 1.3.6.1.4.1.37950.1.1.5.12.3.1.22.1.1
-- 1.3.6.1.4.1.37950.1.1.5.12.3.1.22.1.1
-- 1.3.6.1.4.1.37950.1.1.5.12.3.1.22.1.1
		-- 1.3.6.1.4.1.37950.1.1.5.12.3.1.22.1.1
		priMngPonID OBJECT-TYPE
			SYNTAX Integer32 (1..16)
			MAX-ACCESS read-write
			STATUS current
			DESCRIPTION
				"Description."
			::= { onuPriTr069Manage 1 }

		
--         1.3.6.1.4.1.37950.1.1.5.12.3.1.22.1.2
-- 1.3.6.1.4.1.37950.1.1.5.12.3.1.22.1.2
-- 1.3.6.1.4.1.37950.1.1.5.12.3.1.22.1.2
-- 1.3.6.1.4.1.37950.1.1.5.12.3.1.22.1.2
-- 1.3.6.1.4.1.37950.1.1.5.12.3.1.22.1.2
-- 1.3.6.1.4.1.37950.1.1.5.12.3.1.22.1.2
-- 1.3.6.1.4.1.37950.1.1.5.12.3.1.22.1.2
-- 1.3.6.1.4.1.37950.1.1.5.12.3.1.22.1.2
		-- 1.3.6.1.4.1.37950.1.1.5.12.3.1.22.1.2
		priMngOnuID OBJECT-TYPE
			SYNTAX Integer32 (1..65535)
			MAX-ACCESS read-write
			STATUS current
			DESCRIPTION
				"Description."
			::= { onuPriTr069Manage 2 }

		
--         1.3.6.1.4.1.37950.1.1.5.12.3.1.22.1.3
-- 1.3.6.1.4.1.37950.1.1.5.12.3.1.22.1.3
-- 1.3.6.1.4.1.37950.1.1.5.12.3.1.22.1.3
-- 1.3.6.1.4.1.37950.1.1.5.12.3.1.22.1.3
-- 1.3.6.1.4.1.37950.1.1.5.12.3.1.22.1.3
-- 1.3.6.1.4.1.37950.1.1.5.12.3.1.22.1.3
-- 1.3.6.1.4.1.37950.1.1.5.12.3.1.22.1.3
-- 1.3.6.1.4.1.37950.1.1.5.12.3.1.22.1.3
		-- 1.3.6.1.4.1.37950.1.1.5.12.3.1.22.1.3
		priMngStatus OBJECT-TYPE
			SYNTAX INTEGER
				{
				disable(0),
				enable(1)
				}
			MAX-ACCESS read-write
			STATUS current
			DESCRIPTION
				"Description."
			::= { onuPriTr069Manage 3 }

		
--         1.3.6.1.4.1.37950.1.1.5.12.3.1.22.1.4
-- 1.3.6.1.4.1.37950.1.1.5.12.3.1.22.1.4
-- 1.3.6.1.4.1.37950.1.1.5.12.3.1.22.1.4
-- 1.3.6.1.4.1.37950.1.1.5.12.3.1.22.1.4
-- 1.3.6.1.4.1.37950.1.1.5.12.3.1.22.1.4
-- 1.3.6.1.4.1.37950.1.1.5.12.3.1.22.1.4
-- 1.3.6.1.4.1.37950.1.1.5.12.3.1.22.1.4
-- 1.3.6.1.4.1.37950.1.1.5.12.3.1.22.1.4
		-- 1.3.6.1.4.1.37950.1.1.5.12.3.1.22.1.4
		priMngAcsAddress OBJECT-TYPE
			SYNTAX OCTET STRING (SIZE (0..128))
			MAX-ACCESS read-write
			STATUS current
			DESCRIPTION
				"Description."
			::= { onuPriTr069Manage 4 }

		
--         1.3.6.1.4.1.37950.1.1.5.12.3.1.22.1.5
-- 1.3.6.1.4.1.37950.1.1.5.12.3.1.22.1.5
-- 1.3.6.1.4.1.37950.1.1.5.12.3.1.22.1.5
-- 1.3.6.1.4.1.37950.1.1.5.12.3.1.22.1.5
-- 1.3.6.1.4.1.37950.1.1.5.12.3.1.22.1.5
-- 1.3.6.1.4.1.37950.1.1.5.12.3.1.22.1.5
-- 1.3.6.1.4.1.37950.1.1.5.12.3.1.22.1.5
-- 1.3.6.1.4.1.37950.1.1.5.12.3.1.22.1.5
		-- 1.3.6.1.4.1.37950.1.1.5.12.3.1.22.1.5
		priMngAcsUsername OBJECT-TYPE
			SYNTAX OCTET STRING (SIZE (0..64))
			MAX-ACCESS read-write
			STATUS current
			DESCRIPTION
				"Description."
			::= { onuPriTr069Manage 5 }

		
--         1.3.6.1.4.1.37950.1.1.5.12.3.1.22.1.6
-- 1.3.6.1.4.1.37950.1.1.5.12.3.1.22.1.6
-- 1.3.6.1.4.1.37950.1.1.5.12.3.1.22.1.6
-- 1.3.6.1.4.1.37950.1.1.5.12.3.1.22.1.6
-- 1.3.6.1.4.1.37950.1.1.5.12.3.1.22.1.6
-- 1.3.6.1.4.1.37950.1.1.5.12.3.1.22.1.6
-- 1.3.6.1.4.1.37950.1.1.5.12.3.1.22.1.6
-- 1.3.6.1.4.1.37950.1.1.5.12.3.1.22.1.6
		-- 1.3.6.1.4.1.37950.1.1.5.12.3.1.22.1.6
		priMngAcsPassword OBJECT-TYPE
			SYNTAX OCTET STRING (SIZE (0..64))
			MAX-ACCESS read-write
			STATUS current
			DESCRIPTION
				"Description."
			::= { onuPriTr069Manage 6 }

		
--         1.3.6.1.4.1.37950.1.1.5.12.3.1.22.1.7
-- 1.3.6.1.4.1.37950.1.1.5.12.3.1.22.1.7
-- 1.3.6.1.4.1.37950.1.1.5.12.3.1.22.1.7
-- 1.3.6.1.4.1.37950.1.1.5.12.3.1.22.1.7
-- 1.3.6.1.4.1.37950.1.1.5.12.3.1.22.1.7
-- 1.3.6.1.4.1.37950.1.1.5.12.3.1.22.1.7
-- 1.3.6.1.4.1.37950.1.1.5.12.3.1.22.1.7
-- 1.3.6.1.4.1.37950.1.1.5.12.3.1.22.1.7
		-- 1.3.6.1.4.1.37950.1.1.5.12.3.1.22.1.7
		priMngCertificateEn OBJECT-TYPE
			SYNTAX INTEGER
				{
				disable(0),
				enable(1)
				}
			MAX-ACCESS read-write
			STATUS current
			DESCRIPTION
				"Description."
			::= { onuPriTr069Manage 7 }

		
--         1.3.6.1.4.1.37950.1.1.5.12.3.1.22.1.8
-- 1.3.6.1.4.1.37950.1.1.5.12.3.1.22.1.8
-- 1.3.6.1.4.1.37950.1.1.5.12.3.1.22.1.8
-- 1.3.6.1.4.1.37950.1.1.5.12.3.1.22.1.8
-- 1.3.6.1.4.1.37950.1.1.5.12.3.1.22.1.8
-- 1.3.6.1.4.1.37950.1.1.5.12.3.1.22.1.8
-- 1.3.6.1.4.1.37950.1.1.5.12.3.1.22.1.8
-- 1.3.6.1.4.1.37950.1.1.5.12.3.1.22.1.8
		-- 1.3.6.1.4.1.37950.1.1.5.12.3.1.22.1.8
		priMngInformEn OBJECT-TYPE
			SYNTAX INTEGER
				{
				disable(0),
				enable(1)
				}
			MAX-ACCESS read-write
			STATUS current
			DESCRIPTION
				"Description."
			::= { onuPriTr069Manage 8 }

		
--         1.3.6.1.4.1.37950.1.1.5.12.3.1.22.1.9
-- 1.3.6.1.4.1.37950.1.1.5.12.3.1.22.1.9
-- 1.3.6.1.4.1.37950.1.1.5.12.3.1.22.1.9
-- 1.3.6.1.4.1.37950.1.1.5.12.3.1.22.1.9
-- 1.3.6.1.4.1.37950.1.1.5.12.3.1.22.1.9
-- 1.3.6.1.4.1.37950.1.1.5.12.3.1.22.1.9
-- 1.3.6.1.4.1.37950.1.1.5.12.3.1.22.1.9
-- 1.3.6.1.4.1.37950.1.1.5.12.3.1.22.1.9
		-- 1.3.6.1.4.1.37950.1.1.5.12.3.1.22.1.9
		priMngInformIntervalTime OBJECT-TYPE
			SYNTAX Unsigned32 (0..4294967295)
			MAX-ACCESS read-write
			STATUS current
			DESCRIPTION
				"Description."
			::= { onuPriTr069Manage 9 }

		
--         1.3.6.1.4.1.37950.1.1.5.12.3.1.22.1.10
-- 1.3.6.1.4.1.37950.1.1.5.12.3.1.22.1.10
-- 1.3.6.1.4.1.37950.1.1.5.12.3.1.22.1.10
-- 1.3.6.1.4.1.37950.1.1.5.12.3.1.22.1.10
-- 1.3.6.1.4.1.37950.1.1.5.12.3.1.22.1.10
-- 1.3.6.1.4.1.37950.1.1.5.12.3.1.22.1.10
-- 1.3.6.1.4.1.37950.1.1.5.12.3.1.22.1.10
-- 1.3.6.1.4.1.37950.1.1.5.12.3.1.22.1.10
		-- 1.3.6.1.4.1.37950.1.1.5.12.3.1.22.1.10
		priMngRevConnUsername OBJECT-TYPE
			SYNTAX OCTET STRING (SIZE (0..64))
			MAX-ACCESS read-write
			STATUS current
			DESCRIPTION
				"Description."
			::= { onuPriTr069Manage 10 }

		
--         1.3.6.1.4.1.37950.1.1.5.12.3.1.22.1.11
-- 1.3.6.1.4.1.37950.1.1.5.12.3.1.22.1.11
-- 1.3.6.1.4.1.37950.1.1.5.12.3.1.22.1.11
-- 1.3.6.1.4.1.37950.1.1.5.12.3.1.22.1.11
-- 1.3.6.1.4.1.37950.1.1.5.12.3.1.22.1.11
-- 1.3.6.1.4.1.37950.1.1.5.12.3.1.22.1.11
-- 1.3.6.1.4.1.37950.1.1.5.12.3.1.22.1.11
-- 1.3.6.1.4.1.37950.1.1.5.12.3.1.22.1.11
		-- 1.3.6.1.4.1.37950.1.1.5.12.3.1.22.1.11
		priMngRevConnPassword OBJECT-TYPE
			SYNTAX OCTET STRING (SIZE (0..64))
			MAX-ACCESS read-write
			STATUS current
			DESCRIPTION
				"Description."
			::= { onuPriTr069Manage 11 }

		
--         1.3.6.1.4.1.37950.1.1.5.12.3.1.22.1.12
-- 1.3.6.1.4.1.37950.1.1.5.12.3.1.22.1.12
-- 1.3.6.1.4.1.37950.1.1.5.12.3.1.22.1.12
-- 1.3.6.1.4.1.37950.1.1.5.12.3.1.22.1.12
-- 1.3.6.1.4.1.37950.1.1.5.12.3.1.22.1.12
-- 1.3.6.1.4.1.37950.1.1.5.12.3.1.22.1.12
-- 1.3.6.1.4.1.37950.1.1.5.12.3.1.22.1.12
-- 1.3.6.1.4.1.37950.1.1.5.12.3.1.22.1.12
		-- 1.3.6.1.4.1.37950.1.1.5.12.3.1.22.1.12
		priMngAction OBJECT-TYPE
			SYNTAX INTEGER { submit(1) }
			MAX-ACCESS read-write
			STATUS current
			DESCRIPTION
				"Description."
			::= { onuPriTr069Manage 12 }

		
--         1.3.6.1.4.1.37950.1.1.5.12.3.1.22.2
-- 1.3.6.1.4.1.37950.1.1.5.12.3.1.22.2
-- 1.3.6.1.4.1.37950.1.1.5.12.3.1.22.2
-- 1.3.6.1.4.1.37950.1.1.5.12.3.1.22.2
-- 1.3.6.1.4.1.37950.1.1.5.12.3.1.22.2
-- 1.3.6.1.4.1.37950.1.1.5.12.3.1.22.2
-- 1.3.6.1.4.1.37950.1.1.5.12.3.1.22.2
-- 1.3.6.1.4.1.37950.1.1.5.12.3.1.22.2
		-- 1.3.6.1.4.1.37950.1.1.5.12.3.1.22.2
		onuPriTr069Stun OBJECT IDENTIFIER ::= { onuPriTr069 2 }

		
--         1.3.6.1.4.1.37950.1.1.5.12.3.1.22.2.1
-- 1.3.6.1.4.1.37950.1.1.5.12.3.1.22.2.1
-- 1.3.6.1.4.1.37950.1.1.5.12.3.1.22.2.1
-- 1.3.6.1.4.1.37950.1.1.5.12.3.1.22.2.1
-- 1.3.6.1.4.1.37950.1.1.5.12.3.1.22.2.1
-- 1.3.6.1.4.1.37950.1.1.5.12.3.1.22.2.1
-- 1.3.6.1.4.1.37950.1.1.5.12.3.1.22.2.1
-- 1.3.6.1.4.1.37950.1.1.5.12.3.1.22.2.1
		-- 1.3.6.1.4.1.37950.1.1.5.12.3.1.22.2.1
		priStunPonID OBJECT-TYPE
			SYNTAX Integer32 (1..16)
			MAX-ACCESS read-write
			STATUS current
			DESCRIPTION
				"Description."
			::= { onuPriTr069Stun 1 }

		
--         1.3.6.1.4.1.37950.1.1.5.12.3.1.22.2.2
-- 1.3.6.1.4.1.37950.1.1.5.12.3.1.22.2.2
-- 1.3.6.1.4.1.37950.1.1.5.12.3.1.22.2.2
-- 1.3.6.1.4.1.37950.1.1.5.12.3.1.22.2.2
-- 1.3.6.1.4.1.37950.1.1.5.12.3.1.22.2.2
-- 1.3.6.1.4.1.37950.1.1.5.12.3.1.22.2.2
-- 1.3.6.1.4.1.37950.1.1.5.12.3.1.22.2.2
-- 1.3.6.1.4.1.37950.1.1.5.12.3.1.22.2.2
		-- 1.3.6.1.4.1.37950.1.1.5.12.3.1.22.2.2
		priStunOnuID OBJECT-TYPE
			SYNTAX Integer32 (1..65535)
			MAX-ACCESS read-write
			STATUS current
			DESCRIPTION
				"Description."
			::= { onuPriTr069Stun 2 }

		
--         1.3.6.1.4.1.37950.1.1.5.12.3.1.22.2.3
-- 1.3.6.1.4.1.37950.1.1.5.12.3.1.22.2.3
-- 1.3.6.1.4.1.37950.1.1.5.12.3.1.22.2.3
-- 1.3.6.1.4.1.37950.1.1.5.12.3.1.22.2.3
-- 1.3.6.1.4.1.37950.1.1.5.12.3.1.22.2.3
-- 1.3.6.1.4.1.37950.1.1.5.12.3.1.22.2.3
-- 1.3.6.1.4.1.37950.1.1.5.12.3.1.22.2.3
-- 1.3.6.1.4.1.37950.1.1.5.12.3.1.22.2.3
		-- 1.3.6.1.4.1.37950.1.1.5.12.3.1.22.2.3
		priStunStatus OBJECT-TYPE
			SYNTAX INTEGER
				{
				disable(0),
				enable(1)
				}
			MAX-ACCESS read-write
			STATUS current
			DESCRIPTION
				"Description."
			::= { onuPriTr069Stun 3 }

		
--         1.3.6.1.4.1.37950.1.1.5.12.3.1.22.2.4
-- 1.3.6.1.4.1.37950.1.1.5.12.3.1.22.2.4
-- 1.3.6.1.4.1.37950.1.1.5.12.3.1.22.2.4
-- 1.3.6.1.4.1.37950.1.1.5.12.3.1.22.2.4
-- 1.3.6.1.4.1.37950.1.1.5.12.3.1.22.2.4
-- 1.3.6.1.4.1.37950.1.1.5.12.3.1.22.2.4
-- 1.3.6.1.4.1.37950.1.1.5.12.3.1.22.2.4
-- 1.3.6.1.4.1.37950.1.1.5.12.3.1.22.2.4
		-- 1.3.6.1.4.1.37950.1.1.5.12.3.1.22.2.4
		priStunAddress OBJECT-TYPE
			SYNTAX OCTET STRING (SIZE (0..128))
			MAX-ACCESS read-write
			STATUS current
			DESCRIPTION
				"Description."
			::= { onuPriTr069Stun 4 }

		
--         1.3.6.1.4.1.37950.1.1.5.12.3.1.22.2.5
-- 1.3.6.1.4.1.37950.1.1.5.12.3.1.22.2.5
-- 1.3.6.1.4.1.37950.1.1.5.12.3.1.22.2.5
-- 1.3.6.1.4.1.37950.1.1.5.12.3.1.22.2.5
-- 1.3.6.1.4.1.37950.1.1.5.12.3.1.22.2.5
-- 1.3.6.1.4.1.37950.1.1.5.12.3.1.22.2.5
-- 1.3.6.1.4.1.37950.1.1.5.12.3.1.22.2.5
-- 1.3.6.1.4.1.37950.1.1.5.12.3.1.22.2.5
		-- 1.3.6.1.4.1.37950.1.1.5.12.3.1.22.2.5
		priStunPort OBJECT-TYPE
			SYNTAX Integer32 (1..65535)
			MAX-ACCESS read-write
			STATUS current
			DESCRIPTION
				"Description."
			::= { onuPriTr069Stun 5 }

		
--         1.3.6.1.4.1.37950.1.1.5.12.3.1.22.2.6
-- 1.3.6.1.4.1.37950.1.1.5.12.3.1.22.2.6
-- 1.3.6.1.4.1.37950.1.1.5.12.3.1.22.2.6
-- 1.3.6.1.4.1.37950.1.1.5.12.3.1.22.2.6
-- 1.3.6.1.4.1.37950.1.1.5.12.3.1.22.2.6
-- 1.3.6.1.4.1.37950.1.1.5.12.3.1.22.2.6
-- 1.3.6.1.4.1.37950.1.1.5.12.3.1.22.2.6
-- 1.3.6.1.4.1.37950.1.1.5.12.3.1.22.2.6
		-- 1.3.6.1.4.1.37950.1.1.5.12.3.1.22.2.6
		priStunUsername OBJECT-TYPE
			SYNTAX OCTET STRING (SIZE (0..64))
			MAX-ACCESS read-write
			STATUS current
			DESCRIPTION
				"Description."
			::= { onuPriTr069Stun 6 }

		
--         1.3.6.1.4.1.37950.1.1.5.12.3.1.22.2.7
-- 1.3.6.1.4.1.37950.1.1.5.12.3.1.22.2.7
-- 1.3.6.1.4.1.37950.1.1.5.12.3.1.22.2.7
-- 1.3.6.1.4.1.37950.1.1.5.12.3.1.22.2.7
-- 1.3.6.1.4.1.37950.1.1.5.12.3.1.22.2.7
-- 1.3.6.1.4.1.37950.1.1.5.12.3.1.22.2.7
-- 1.3.6.1.4.1.37950.1.1.5.12.3.1.22.2.7
-- 1.3.6.1.4.1.37950.1.1.5.12.3.1.22.2.7
		-- 1.3.6.1.4.1.37950.1.1.5.12.3.1.22.2.7
		priStunPassword OBJECT-TYPE
			SYNTAX OCTET STRING (SIZE (0..64))
			MAX-ACCESS read-write
			STATUS current
			DESCRIPTION
				"Description."
			::= { onuPriTr069Stun 7 }

		
--         1.3.6.1.4.1.37950.1.1.5.12.3.1.22.2.8
-- 1.3.6.1.4.1.37950.1.1.5.12.3.1.22.2.8
-- 1.3.6.1.4.1.37950.1.1.5.12.3.1.22.2.8
-- 1.3.6.1.4.1.37950.1.1.5.12.3.1.22.2.8
-- 1.3.6.1.4.1.37950.1.1.5.12.3.1.22.2.8
-- 1.3.6.1.4.1.37950.1.1.5.12.3.1.22.2.8
-- 1.3.6.1.4.1.37950.1.1.5.12.3.1.22.2.8
-- 1.3.6.1.4.1.37950.1.1.5.12.3.1.22.2.8
		-- 1.3.6.1.4.1.37950.1.1.5.12.3.1.22.2.8
		priStunAction OBJECT-TYPE
			SYNTAX INTEGER { submit(1) }
			MAX-ACCESS read-write
			STATUS current
			DESCRIPTION
				"Description."
			::= { onuPriTr069Stun 8 }

		
--       1.3.6.1.4.1.37950.1.1.5.12.3.1.23
-- 1.3.6.1.4.1.37950.1.1.5.12.3.1.23
-- 1.3.6.1.4.1.37950.1.1.5.12.3.1.23
-- 1.3.6.1.4.1.37950.1.1.5.12.3.1.23
-- 1.3.6.1.4.1.37950.1.1.5.12.3.1.23
-- 1.3.6.1.4.1.37950.1.1.5.12.3.1.23
		-- 1.3.6.1.4.1.37950.1.1.5.12.3.1.23
		onuPriSelfDiagnosis OBJECT IDENTIFIER ::= { onuPriGlobalCfg 23 }

		
--       1.3.6.1.4.1.37950.1.1.5.12.3.1.23.1
-- 1.3.6.1.4.1.37950.1.1.5.12.3.1.23.1
-- 1.3.6.1.4.1.37950.1.1.5.12.3.1.23.1
-- 1.3.6.1.4.1.37950.1.1.5.12.3.1.23.1
-- 1.3.6.1.4.1.37950.1.1.5.12.3.1.23.1
-- 1.3.6.1.4.1.37950.1.1.5.12.3.1.23.1
		-- 1.3.6.1.4.1.37950.1.1.5.12.3.1.23.1
		onuPriSelfDiagCfg OBJECT IDENTIFIER ::= { onuPriSelfDiagnosis 1 }

		
--         1.3.6.1.4.1.37950.1.1.5.12.3.1.22.1.1
-- 1.3.6.1.4.1.37950.1.1.5.12.3.1.22.1.1
-- 1.3.6.1.4.1.37950.1.1.5.12.3.1.23.1.1
-- 1.3.6.1.4.1.37950.1.1.5.12.3.1.23.1.1
-- 1.3.6.1.4.1.37950.1.1.5.12.3.1.23.1.1
-- 1.3.6.1.4.1.37950.1.1.5.12.3.1.23.1.1
-- 1.3.6.1.4.1.37950.1.1.5.12.3.1.23.1.1
-- 1.3.6.1.4.1.37950.1.1.5.12.3.1.23.1.1
		-- 1.3.6.1.4.1.37950.1.1.5.12.3.1.23.1.1
		onuPriSelfDiagPonID OBJECT-TYPE
			SYNTAX Integer32 (1..16)
			MAX-ACCESS read-write
			STATUS current
			DESCRIPTION
				"Description."
			::= { onuPriSelfDiagCfg 1 }

		
--         1.3.6.1.4.1.37950.1.1.5.12.3.1.22.1.2
-- 1.3.6.1.4.1.37950.1.1.5.12.3.1.22.1.2
-- 1.3.6.1.4.1.37950.1.1.5.12.3.1.23.1.2
-- 1.3.6.1.4.1.37950.1.1.5.12.3.1.23.1.2
-- 1.3.6.1.4.1.37950.1.1.5.12.3.1.23.1.2
-- 1.3.6.1.4.1.37950.1.1.5.12.3.1.23.1.2
-- 1.3.6.1.4.1.37950.1.1.5.12.3.1.23.1.2
-- 1.3.6.1.4.1.37950.1.1.5.12.3.1.23.1.2
		-- 1.3.6.1.4.1.37950.1.1.5.12.3.1.23.1.2
		onuPriSelfDiagOnuID OBJECT-TYPE
			SYNTAX Integer32 (1..65535)
			MAX-ACCESS read-write
			STATUS current
			DESCRIPTION
				"Description."
			::= { onuPriSelfDiagCfg 2 }

		
--       1.3.6.1.4.1.37950.1.1.5.12.3.1.23.1.3
-- 1.3.6.1.4.1.37950.1.1.5.12.3.1.23.1.3
-- 1.3.6.1.4.1.37950.1.1.5.12.3.1.23.1.3
-- 1.3.6.1.4.1.37950.1.1.5.12.3.1.23.1.3
-- 1.3.6.1.4.1.37950.1.1.5.12.3.1.23.1.3
-- 1.3.6.1.4.1.37950.1.1.5.12.3.1.23.1.3
		-- 1.3.6.1.4.1.37950.1.1.5.12.3.1.23.1.3
		onuPriSelfDiagSessionID OBJECT-TYPE
			SYNTAX Integer32 (1..255)
			MAX-ACCESS read-write
			STATUS current
			DESCRIPTION
				"Description."
			::= { onuPriSelfDiagCfg 3 }

		
--       1.3.6.1.4.1.37950.1.1.5.12.3.1.23.1.4
-- 1.3.6.1.4.1.37950.1.1.5.12.3.1.23.1.4
-- 1.3.6.1.4.1.37950.1.1.5.12.3.1.23.1.4
-- 1.3.6.1.4.1.37950.1.1.5.12.3.1.23.1.4
-- 1.3.6.1.4.1.37950.1.1.5.12.3.1.23.1.4
-- 1.3.6.1.4.1.37950.1.1.5.12.3.1.23.1.4
		-- 1.3.6.1.4.1.37950.1.1.5.12.3.1.23.1.4
		onuPriSelfDiagTransportProtocol OBJECT-TYPE
			SYNTAX INTEGER
				{
				ftp(0),
				tftp(1)
				}
			MAX-ACCESS read-write
			STATUS current
			DESCRIPTION
				"Description."
			::= { onuPriSelfDiagCfg 4 }

		
--       1.3.6.1.4.1.37950.1.1.5.12.3.1.23.1.5
-- 1.3.6.1.4.1.37950.1.1.5.12.3.1.23.1.5
-- 1.3.6.1.4.1.37950.1.1.5.12.3.1.23.1.5
-- 1.3.6.1.4.1.37950.1.1.5.12.3.1.23.1.5
-- 1.3.6.1.4.1.37950.1.1.5.12.3.1.23.1.5
-- 1.3.6.1.4.1.37950.1.1.5.12.3.1.23.1.5
		-- 1.3.6.1.4.1.37950.1.1.5.12.3.1.23.1.5
		onuPriSelfDiagDiagnosisMethod OBJECT-TYPE
			SYNTAX INTEGER
				{
				all(0),
				port-status(1),
				pon-status(2),
				wan-status(3),
				sys-status(4),
				wan-params(5),
				dns-status(6),
				dhcp-config(7),
				pppoe-status(8),
				route-status(9)
				}
			MAX-ACCESS read-write
			STATUS current
			DESCRIPTION
				"Description."
			::= { onuPriSelfDiagCfg 5 }

		
--       1.3.6.1.4.1.37950.1.1.5.12.3.1.23.1.6
-- 1.3.6.1.4.1.37950.1.1.5.12.3.1.23.1.6
-- 1.3.6.1.4.1.37950.1.1.5.12.3.1.23.1.6
-- 1.3.6.1.4.1.37950.1.1.5.12.3.1.23.1.6
-- 1.3.6.1.4.1.37950.1.1.5.12.3.1.23.1.6
-- 1.3.6.1.4.1.37950.1.1.5.12.3.1.23.1.6
		-- 1.3.6.1.4.1.37950.1.1.5.12.3.1.23.1.6
		onuPriSelfDiagDiagnosisAction OBJECT-TYPE
			SYNTAX INTEGER
				{
				action-diag(0),
				action-fix(1)
				}
			MAX-ACCESS read-write
			STATUS current
			DESCRIPTION
				"Description."
			::= { onuPriSelfDiagCfg 6 }

		
--       1.3.6.1.4.1.37950.1.1.5.12.3.1.23.1.7
-- 1.3.6.1.4.1.37950.1.1.5.12.3.1.23.1.7
-- 1.3.6.1.4.1.37950.1.1.5.12.3.1.23.1.7
-- 1.3.6.1.4.1.37950.1.1.5.12.3.1.23.1.7
-- 1.3.6.1.4.1.37950.1.1.5.12.3.1.23.1.7
-- 1.3.6.1.4.1.37950.1.1.5.12.3.1.23.1.7
		-- 1.3.6.1.4.1.37950.1.1.5.12.3.1.23.1.7
		onuPriSelfDiagAction OBJECT-TYPE
			SYNTAX INTEGER
				{
				perform-diagnostic(0),
				upload-log(1)
				}
			MAX-ACCESS read-write
			STATUS current
			DESCRIPTION
				"Description."
			::= { onuPriSelfDiagCfg 7 }

		
--       1.3.6.1.4.1.37950.1.1.5.12.3.1.23.1.8
-- 1.3.6.1.4.1.37950.1.1.5.12.3.1.23.1.8
-- 1.3.6.1.4.1.37950.1.1.5.12.3.1.23.1.8
-- 1.3.6.1.4.1.37950.1.1.5.12.3.1.23.1.8
-- 1.3.6.1.4.1.37950.1.1.5.12.3.1.23.1.8
-- 1.3.6.1.4.1.37950.1.1.5.12.3.1.23.1.8
		-- 1.3.6.1.4.1.37950.1.1.5.12.3.1.23.1.8
		onuPriSelfDiagURL OBJECT-TYPE
			SYNTAX OCTET STRING
			MAX-ACCESS read-write
			STATUS current
			DESCRIPTION
				"Description."
			::= { onuPriSelfDiagCfg 8 }

		
--       1.3.6.1.4.1.37950.1.1.5.12.3.1.23.1.9
-- 1.3.6.1.4.1.37950.1.1.5.12.3.1.23.1.9
-- 1.3.6.1.4.1.37950.1.1.5.12.3.1.23.1.9
-- 1.3.6.1.4.1.37950.1.1.5.12.3.1.23.1.9
-- 1.3.6.1.4.1.37950.1.1.5.12.3.1.23.1.9
-- 1.3.6.1.4.1.37950.1.1.5.12.3.1.23.1.9
		-- 1.3.6.1.4.1.37950.1.1.5.12.3.1.23.1.9
		onuPriSelfDiagUseWanIndex OBJECT-TYPE
			SYNTAX Integer32 (1..8)
			MAX-ACCESS read-write
			STATUS current
			DESCRIPTION
				"Description."
			::= { onuPriSelfDiagCfg 9 }

		
--       1.3.6.1.4.1.37950.1.1.5.12.3.1.23.1.10
-- 1.3.6.1.4.1.37950.1.1.5.12.3.1.23.1.10
-- 1.3.6.1.4.1.37950.1.1.5.12.3.1.23.1.10
-- 1.3.6.1.4.1.37950.1.1.5.12.3.1.23.1.10
-- 1.3.6.1.4.1.37950.1.1.5.12.3.1.23.1.10
-- 1.3.6.1.4.1.37950.1.1.5.12.3.1.23.1.10
		-- 1.3.6.1.4.1.37950.1.1.5.12.3.1.23.1.10
		onuPriSelfDiagSubmit OBJECT-TYPE
			SYNTAX INTEGER
				{
				commit(1),
				remove(2)
				}
			MAX-ACCESS read-write
			STATUS current
			DESCRIPTION
				"Description."
			::= { onuPriSelfDiagCfg 10 }

		
--       1.3.6.1.4.1.37950.1.1.5.12.3.1.23.2
-- 1.3.6.1.4.1.37950.1.1.5.12.3.1.23.2
-- 1.3.6.1.4.1.37950.1.1.5.12.3.1.23.2
-- 1.3.6.1.4.1.37950.1.1.5.12.3.1.23.2
-- 1.3.6.1.4.1.37950.1.1.5.12.3.1.23.2
-- 1.3.6.1.4.1.37950.1.1.5.12.3.1.23.2
		-- 1.3.6.1.4.1.37950.1.1.5.12.3.1.23.2
		onuPriSelfDiagnosisCapturePackCfg OBJECT IDENTIFIER ::= { onuPriSelfDiagnosis 2 }

		
--         1.3.6.1.4.1.37950.1.1.5.12.3.1.22.1.1
-- 1.3.6.1.4.1.37950.1.1.5.12.3.1.22.1.1
-- 1.3.6.1.4.1.37950.1.1.5.12.3.1.23.2.1
-- 1.3.6.1.4.1.37950.1.1.5.12.3.1.23.2.1
-- 1.3.6.1.4.1.37950.1.1.5.12.3.1.23.2.1
-- 1.3.6.1.4.1.37950.1.1.5.12.3.1.23.2.1
-- 1.3.6.1.4.1.37950.1.1.5.12.3.1.23.2.1
-- 1.3.6.1.4.1.37950.1.1.5.12.3.1.23.2.1
		-- 1.3.6.1.4.1.37950.1.1.5.12.3.1.23.2.1
		onuPriSelfDiagCapturePackPonID OBJECT-TYPE
			SYNTAX Integer32 (1..16)
			MAX-ACCESS read-write
			STATUS current
			DESCRIPTION
				"Description."
			::= { onuPriSelfDiagnosisCapturePackCfg 1 }

		
--         1.3.6.1.4.1.37950.1.1.5.12.3.1.22.1.2
-- 1.3.6.1.4.1.37950.1.1.5.12.3.1.22.1.2
-- 1.3.6.1.4.1.37950.1.1.5.12.3.1.23.2.2
-- 1.3.6.1.4.1.37950.1.1.5.12.3.1.23.2.2
-- 1.3.6.1.4.1.37950.1.1.5.12.3.1.23.2.2
-- 1.3.6.1.4.1.37950.1.1.5.12.3.1.23.2.2
-- 1.3.6.1.4.1.37950.1.1.5.12.3.1.23.2.2
-- 1.3.6.1.4.1.37950.1.1.5.12.3.1.23.2.2
		-- 1.3.6.1.4.1.37950.1.1.5.12.3.1.23.2.2
		onuPriSelfDiagCapturePackOnuID OBJECT-TYPE
			SYNTAX Integer32 (1..65535)
			MAX-ACCESS read-write
			STATUS current
			DESCRIPTION
				"Description."
			::= { onuPriSelfDiagnosisCapturePackCfg 2 }

		
--       1.3.6.1.4.1.37950.1.1.5.12.3.1.23.2.3
-- 1.3.6.1.4.1.37950.1.1.5.12.3.1.23.2.3
-- 1.3.6.1.4.1.37950.1.1.5.12.3.1.23.2.3
-- 1.3.6.1.4.1.37950.1.1.5.12.3.1.23.2.3
-- 1.3.6.1.4.1.37950.1.1.5.12.3.1.23.2.3
-- 1.3.6.1.4.1.37950.1.1.5.12.3.1.23.2.3
		-- 1.3.6.1.4.1.37950.1.1.5.12.3.1.23.2.3
		onuPriSelfDiagCapturePackSessionID OBJECT-TYPE
			SYNTAX Integer32 (1..255)
			MAX-ACCESS read-write
			STATUS current
			DESCRIPTION
				"Description."
			::= { onuPriSelfDiagnosisCapturePackCfg 3 }

		
--       1.3.6.1.4.1.37950.1.1.5.12.3.1.23.2.4
-- 1.3.6.1.4.1.37950.1.1.5.12.3.1.23.2.4
-- 1.3.6.1.4.1.37950.1.1.5.12.3.1.23.2.4
-- 1.3.6.1.4.1.37950.1.1.5.12.3.1.23.2.4
-- 1.3.6.1.4.1.37950.1.1.5.12.3.1.23.2.4
-- 1.3.6.1.4.1.37950.1.1.5.12.3.1.23.2.4
		-- 1.3.6.1.4.1.37950.1.1.5.12.3.1.23.2.4
		onuPriSelfDiagCapturePackTransportProtocol OBJECT-TYPE
			SYNTAX INTEGER
				{
				ftp(0),
				tftp(1)
				}
			MAX-ACCESS read-write
			STATUS current
			DESCRIPTION
				"Description."
			::= { onuPriSelfDiagnosisCapturePackCfg 4 }

		
--       1.3.6.1.4.1.37950.1.1.5.12.3.1.23.2.5
-- 1.3.6.1.4.1.37950.1.1.5.12.3.1.23.2.5
-- 1.3.6.1.4.1.37950.1.1.5.12.3.1.23.2.5
-- 1.3.6.1.4.1.37950.1.1.5.12.3.1.23.2.5
-- 1.3.6.1.4.1.37950.1.1.5.12.3.1.23.2.5
-- 1.3.6.1.4.1.37950.1.1.5.12.3.1.23.2.5
		-- 1.3.6.1.4.1.37950.1.1.5.12.3.1.23.2.5
		onuPriSelfDiagCapturePackCaptureMode OBJECT-TYPE
			SYNTAX INTEGER
				{
				counting(0),
				circulation(1)
				}
			MAX-ACCESS read-write
			STATUS current
			DESCRIPTION
				"Description."
			::= { onuPriSelfDiagnosisCapturePackCfg 5 }

		
--       1.3.6.1.4.1.37950.1.1.5.12.3.1.23.2.6
-- 1.3.6.1.4.1.37950.1.1.5.12.3.1.23.2.6
-- 1.3.6.1.4.1.37950.1.1.5.12.3.1.23.2.6
-- 1.3.6.1.4.1.37950.1.1.5.12.3.1.23.2.6
-- 1.3.6.1.4.1.37950.1.1.5.12.3.1.23.2.6
-- 1.3.6.1.4.1.37950.1.1.5.12.3.1.23.2.6
		-- 1.3.6.1.4.1.37950.1.1.5.12.3.1.23.2.6
		onuPriSelfDiagCapturePackCaptureInterface OBJECT-TYPE
			SYNTAX INTEGER
				{
				any(0),
				wan-of-index-1(1),
				wan-of-index-2(2),
				wan-of-index-3(3),
				wan-of-index-4(4),
				wan-of-index-5(5),
				wan-of-index-6(6),
				wan-of-index-7(7),
				wan-of-index-8(8)
				}
			MAX-ACCESS read-write
			STATUS current
			DESCRIPTION
				"Description."
			::= { onuPriSelfDiagnosisCapturePackCfg 6 }

		
--       1.3.6.1.4.1.37950.1.1.5.12.3.1.23.2.7
-- 1.3.6.1.4.1.37950.1.1.5.12.3.1.23.2.7
-- 1.3.6.1.4.1.37950.1.1.5.12.3.1.23.2.7
-- 1.3.6.1.4.1.37950.1.1.5.12.3.1.23.2.7
-- 1.3.6.1.4.1.37950.1.1.5.12.3.1.23.2.7
-- 1.3.6.1.4.1.37950.1.1.5.12.3.1.23.2.7
		-- 1.3.6.1.4.1.37950.1.1.5.12.3.1.23.2.7
		onuPriSelfDiagCapturePackAction OBJECT-TYPE
			SYNTAX INTEGER
				{
				stop-capturing(0),
				start-capturing(1),
				upload-log(2)
				}
			MAX-ACCESS read-write
			STATUS current
			DESCRIPTION
				"Description."
			::= { onuPriSelfDiagnosisCapturePackCfg 7 }

		
--       1.3.6.1.4.1.37950.1.1.5.12.3.1.23.2.8
-- 1.3.6.1.4.1.37950.1.1.5.12.3.1.23.2.8
-- 1.3.6.1.4.1.37950.1.1.5.12.3.1.23.2.8
-- 1.3.6.1.4.1.37950.1.1.5.12.3.1.23.2.8
-- 1.3.6.1.4.1.37950.1.1.5.12.3.1.23.2.8
-- 1.3.6.1.4.1.37950.1.1.5.12.3.1.23.2.8
		-- 1.3.6.1.4.1.37950.1.1.5.12.3.1.23.2.8
		onuPriSelfDiagCapturePackURL OBJECT-TYPE
			SYNTAX OCTET STRING
			MAX-ACCESS read-write
			STATUS current
			DESCRIPTION
				"Description."
			::= { onuPriSelfDiagnosisCapturePackCfg 8 }

		
--       1.3.6.1.4.1.37950.1.1.5.12.3.1.23.2.9
-- 1.3.6.1.4.1.37950.1.1.5.12.3.1.23.2.9
-- 1.3.6.1.4.1.37950.1.1.5.12.3.1.23.2.9
-- 1.3.6.1.4.1.37950.1.1.5.12.3.1.23.2.9
-- 1.3.6.1.4.1.37950.1.1.5.12.3.1.23.2.9
-- 1.3.6.1.4.1.37950.1.1.5.12.3.1.23.2.9
		-- 1.3.6.1.4.1.37950.1.1.5.12.3.1.23.2.9
		onuPriSelfDiagCapturePackUseWanIndex OBJECT-TYPE
			SYNTAX Integer32 (1..8)
			MAX-ACCESS read-write
			STATUS current
			DESCRIPTION
				"Description."
			::= { onuPriSelfDiagnosisCapturePackCfg 9 }

		
--       1.3.6.1.4.1.37950.1.1.5.12.3.1.23.2.10
-- 1.3.6.1.4.1.37950.1.1.5.12.3.1.23.2.10
-- 1.3.6.1.4.1.37950.1.1.5.12.3.1.23.2.10
-- 1.3.6.1.4.1.37950.1.1.5.12.3.1.23.2.10
-- 1.3.6.1.4.1.37950.1.1.5.12.3.1.23.2.10
-- 1.3.6.1.4.1.37950.1.1.5.12.3.1.23.2.10
		-- 1.3.6.1.4.1.37950.1.1.5.12.3.1.23.2.10
		onuPriSelfDiagCapturePackSubmit OBJECT-TYPE
			SYNTAX INTEGER
				{
				commit(1),
				remove(2)
				}
			MAX-ACCESS read-write
			STATUS current
			DESCRIPTION
				"Description."
			::= { onuPriSelfDiagnosisCapturePackCfg 10 }

		
--       1.3.6.1.4.1.37950.1.1.5.12.3.1.24
-- 1.3.6.1.4.1.37950.1.1.5.12.3.1.24
-- 1.3.6.1.4.1.37950.1.1.5.12.3.1.24
-- 1.3.6.1.4.1.37950.1.1.5.12.3.1.24
-- 1.3.6.1.4.1.37950.1.1.5.12.3.1.24
-- 1.3.6.1.4.1.37950.1.1.5.12.3.1.24
		-- 1.3.6.1.4.1.37950.1.1.5.12.3.1.24
		onuPriNatType OBJECT IDENTIFIER ::= { onuPriGlobalCfg 24 }

		
--       1.3.6.1.4.1.37950.1.1.5.12.3.1.24.1
-- 1.3.6.1.4.1.37950.1.1.5.12.3.1.24.1
-- 1.3.6.1.4.1.37950.1.1.5.12.3.1.24.1
-- 1.3.6.1.4.1.37950.1.1.5.12.3.1.24.1
-- 1.3.6.1.4.1.37950.1.1.5.12.3.1.24.1
-- 1.3.6.1.4.1.37950.1.1.5.12.3.1.24.1
		-- 1.3.6.1.4.1.37950.1.1.5.12.3.1.24.1
		priNatTypePonID OBJECT-TYPE
			SYNTAX Integer32 (1..16)
			MAX-ACCESS read-write
			STATUS current
			DESCRIPTION
				"Description."
			::= { onuPriNatType 1 }

		
--       1.3.6.1.4.1.37950.1.1.5.12.3.1.24.2
-- 1.3.6.1.4.1.37950.1.1.5.12.3.1.24.2
-- 1.3.6.1.4.1.37950.1.1.5.12.3.1.24.2
-- 1.3.6.1.4.1.37950.1.1.5.12.3.1.24.2
-- 1.3.6.1.4.1.37950.1.1.5.12.3.1.24.2
-- 1.3.6.1.4.1.37950.1.1.5.12.3.1.24.2
		-- 1.3.6.1.4.1.37950.1.1.5.12.3.1.24.2
		priNatTypeOnuID OBJECT-TYPE
			SYNTAX Integer32 (1..65535)
			MAX-ACCESS read-write
			STATUS current
			DESCRIPTION
				"Description."
			::= { onuPriNatType 2 }

		
--       1.3.6.1.4.1.37950.1.1.5.12.3.1.24.3
-- 1.3.6.1.4.1.37950.1.1.5.12.3.1.24.3
-- 1.3.6.1.4.1.37950.1.1.5.12.3.1.24.3
-- 1.3.6.1.4.1.37950.1.1.5.12.3.1.24.3
-- 1.3.6.1.4.1.37950.1.1.5.12.3.1.24.3
-- 1.3.6.1.4.1.37950.1.1.5.12.3.1.24.3
		-- 1.3.6.1.4.1.37950.1.1.5.12.3.1.24.3
		priNatType OBJECT-TYPE
			SYNTAX INTEGER
				{
				nat1(1),
				nat2(2),
				nat3(3),
				nat4-napt(4)
				}
			MAX-ACCESS read-write
			STATUS current
			DESCRIPTION
				"Description."
			::= { onuPriNatType 3 }

		
--          1.3.6.1.4.1.37950.1.1.5.12.3.1.7.4
-- 1.3.6.1.4.1.37950.1.1.5.12.3.1.7.4
-- 1.3.6.1.4.1.37950.1.1.5.12.3.1.7.4
-- 1.3.6.1.4.1.37950.1.1.5.12.3.1.24.4
-- 1.3.6.1.4.1.37950.1.1.5.12.3.1.24.4
-- 1.3.6.1.4.1.37950.1.1.5.12.3.1.24.4
-- 1.3.6.1.4.1.37950.1.1.5.12.3.1.24.4
-- 1.3.6.1.4.1.37950.1.1.5.12.3.1.24.4
-- 1.3.6.1.4.1.37950.1.1.5.12.3.1.24.4
		-- 1.3.6.1.4.1.37950.1.1.5.12.3.1.24.4
		priNatTypeAction OBJECT-TYPE
			SYNTAX INTEGER
				{
				commit(1),
				remove(2)
				}
			MAX-ACCESS read-write
			STATUS current
			DESCRIPTION
				"Description."
			::= { onuPriNatType 4 }

		
--       1.3.6.1.4.1.37950.1.1.5.12.3.1.25
-- 1.3.6.1.4.1.37950.1.1.5.12.3.1.25
-- 1.3.6.1.4.1.37950.1.1.5.12.3.1.25
-- 1.3.6.1.4.1.37950.1.1.5.12.3.1.25
-- 1.3.6.1.4.1.37950.1.1.5.12.3.1.25
-- 1.3.6.1.4.1.37950.1.1.5.12.3.1.25
		-- 1.3.6.1.4.1.37950.1.1.5.12.3.1.25
		onuPriUPnP OBJECT IDENTIFIER ::= { onuPriGlobalCfg 25 }

		
--       1.3.6.1.4.1.37950.1.1.5.12.3.1.25.1
-- 1.3.6.1.4.1.37950.1.1.5.12.3.1.25.1
-- 1.3.6.1.4.1.37950.1.1.5.12.3.1.25.1
-- 1.3.6.1.4.1.37950.1.1.5.12.3.1.25.1
-- 1.3.6.1.4.1.37950.1.1.5.12.3.1.25.1
-- 1.3.6.1.4.1.37950.1.1.5.12.3.1.25.1
		-- 1.3.6.1.4.1.37950.1.1.5.12.3.1.25.1
		priUpnpPonID OBJECT-TYPE
			SYNTAX Integer32 (1..16)
			MAX-ACCESS read-write
			STATUS current
			DESCRIPTION
				"Description."
			::= { onuPriUPnP 1 }

		
--       1.3.6.1.4.1.37950.1.1.5.12.3.1.25.2
-- 1.3.6.1.4.1.37950.1.1.5.12.3.1.25.2
-- 1.3.6.1.4.1.37950.1.1.5.12.3.1.25.2
-- 1.3.6.1.4.1.37950.1.1.5.12.3.1.25.2
-- 1.3.6.1.4.1.37950.1.1.5.12.3.1.25.2
-- 1.3.6.1.4.1.37950.1.1.5.12.3.1.25.2
		-- 1.3.6.1.4.1.37950.1.1.5.12.3.1.25.2
		priUpnpOnuID OBJECT-TYPE
			SYNTAX Integer32 (1..65535)
			MAX-ACCESS read-write
			STATUS current
			DESCRIPTION
				"Description."
			::= { onuPriUPnP 2 }

		
--         1.3.6.1.4.1.37950.1.1.5.12.3.1.22.1.8
-- 1.3.6.1.4.1.37950.1.1.5.12.3.1.22.1.8
-- 1.3.6.1.4.1.37950.1.1.5.12.3.1.25.3
-- 1.3.6.1.4.1.37950.1.1.5.12.3.1.25.3
-- 1.3.6.1.4.1.37950.1.1.5.12.3.1.25.3
-- 1.3.6.1.4.1.37950.1.1.5.12.3.1.25.3
-- 1.3.6.1.4.1.37950.1.1.5.12.3.1.25.3
-- 1.3.6.1.4.1.37950.1.1.5.12.3.1.25.3
		-- 1.3.6.1.4.1.37950.1.1.5.12.3.1.25.3
		priUpnpStatus OBJECT-TYPE
			SYNTAX INTEGER
				{
				disable(0),
				enable(1)
				}
			MAX-ACCESS read-write
			STATUS current
			DESCRIPTION
				"Description."
			::= { onuPriUPnP 3 }

		
--       1.3.6.1.4.1.37950.1.1.5.12.3.1.25.4
-- 1.3.6.1.4.1.37950.1.1.5.12.3.1.25.4
-- 1.3.6.1.4.1.37950.1.1.5.12.3.1.25.4
-- 1.3.6.1.4.1.37950.1.1.5.12.3.1.25.4
-- 1.3.6.1.4.1.37950.1.1.5.12.3.1.25.4
-- 1.3.6.1.4.1.37950.1.1.5.12.3.1.25.4
		-- 1.3.6.1.4.1.37950.1.1.5.12.3.1.25.4
		priUpnpWanIndex OBJECT-TYPE
			SYNTAX Integer32 (1..8)
			MAX-ACCESS read-write
			STATUS current
			DESCRIPTION
				"Description."
			::= { onuPriUPnP 4 }

		
--          1.3.6.1.4.1.37950.1.1.5.12.3.1.7.4
-- 1.3.6.1.4.1.37950.1.1.5.12.3.1.7.4
-- 1.3.6.1.4.1.37950.1.1.5.12.3.1.7.4
-- 1.3.6.1.4.1.37950.1.1.5.12.3.1.25.5
-- 1.3.6.1.4.1.37950.1.1.5.12.3.1.25.5
-- 1.3.6.1.4.1.37950.1.1.5.12.3.1.25.5
-- 1.3.6.1.4.1.37950.1.1.5.12.3.1.25.5
-- 1.3.6.1.4.1.37950.1.1.5.12.3.1.25.5
-- 1.3.6.1.4.1.37950.1.1.5.12.3.1.25.5
		-- 1.3.6.1.4.1.37950.1.1.5.12.3.1.25.5
		priUpnpAction OBJECT-TYPE
			SYNTAX INTEGER
				{
				commit(1),
				remove(2)
				}
			MAX-ACCESS read-write
			STATUS current
			DESCRIPTION
				"Description."
			::= { onuPriUPnP 5 }

		
--           1.3.6.1.4.1.37950.1.1.5.12.3.2
-- 1.3.6.1.4.1.37950.1.1.5.12.3.2
-- 1.3.6.1.4.1.37950.1.1.5.12.3.2
-- 1.3.6.1.4.1.37950.1.1.5.12.3.2
-- 1.3.6.1.4.1.37950.1.1.5.12.3.2
-- 1.3.6.1.4.1.37950.1.1.5.12.3.2
-- 1.3.6.1.4.1.37950.1.1.5.12.3.2
-- 1.3.6.1.4.1.37950.1.1.5.12.3.2
-- 1.3.6.1.4.1.37950.1.1.5.12.3.2
		-- 1.3.6.1.4.1.37950.1.1.5.12.3.2
		onuPriGlobalInfo OBJECT IDENTIFIER ::= { onuPriGlobal 2 }

		
--          1.3.6.1.4.1.37950.1.1.5.12.3.2.1
-- 1.3.6.1.4.1.37950.1.1.5.12.3.2.1
-- 1.3.6.1.4.1.37950.1.1.5.12.3.2.1
-- 1.3.6.1.4.1.37950.1.1.5.12.3.2.1
-- 1.3.6.1.4.1.37950.1.1.5.12.3.2.1
-- 1.3.6.1.4.1.37950.1.1.5.12.3.2.1
-- 1.3.6.1.4.1.37950.1.1.5.12.3.2.1
-- 1.3.6.1.4.1.37950.1.1.5.12.3.2.1
-- 1.3.6.1.4.1.37950.1.1.5.12.3.2.1
		-- 1.3.6.1.4.1.37950.1.1.5.12.3.2.1
		priIgmpAdminTable OBJECT-TYPE
			SYNTAX SEQUENCE OF PriIgmpAdminEntry
			MAX-ACCESS not-accessible
			STATUS current
			DESCRIPTION
				"Description."
			::= { onuPriGlobalInfo 1 }

		
--          1.3.6.1.4.1.37950.1.1.5.12.3.2.1.1
-- 1.3.6.1.4.1.37950.1.1.5.12.3.2.1.1
-- 1.3.6.1.4.1.37950.1.1.5.12.3.2.1.1
-- 1.3.6.1.4.1.37950.1.1.5.12.3.2.1.1
-- 1.3.6.1.4.1.37950.1.1.5.12.3.2.1.1
-- 1.3.6.1.4.1.37950.1.1.5.12.3.2.1.1
-- 1.3.6.1.4.1.37950.1.1.5.12.3.2.1.1
-- 1.3.6.1.4.1.37950.1.1.5.12.3.2.1.1
-- 1.3.6.1.4.1.37950.1.1.5.12.3.2.1.1
		-- 1.3.6.1.4.1.37950.1.1.5.12.3.2.1.1
		priIgmpAdminEntry OBJECT-TYPE
			SYNTAX PriIgmpAdminEntry
			MAX-ACCESS not-accessible
			STATUS current
			DESCRIPTION
				"Description."
			INDEX { priIgmpAdminPonS, priIgmpAdminOnuS }
			::= { priIgmpAdminTable 1 }

		
		PriIgmpAdminEntry ::=
			SEQUENCE { 
				priIgmpAdminPonS
					INTEGER,
				priIgmpAdminOnuS
					INTEGER,
				priIgmpAdminEnableS
					INTEGER
			 }

--          1.3.6.1.4.1.37950.1.1.5.12.3.2.1.1.1
-- 1.3.6.1.4.1.37950.1.1.5.12.3.2.1.1.1
-- 1.3.6.1.4.1.37950.1.1.5.12.3.2.1.1.1
-- 1.3.6.1.4.1.37950.1.1.5.12.3.2.1.1.1
-- 1.3.6.1.4.1.37950.1.1.5.12.3.2.1.1.1
-- 1.3.6.1.4.1.37950.1.1.5.12.3.2.1.1.1
-- 1.3.6.1.4.1.37950.1.1.5.12.3.2.1.1.1
-- 1.3.6.1.4.1.37950.1.1.5.12.3.2.1.1.1
-- 1.3.6.1.4.1.37950.1.1.5.12.3.2.1.1.1
		-- 1.3.6.1.4.1.37950.1.1.5.12.3.2.1.1.1
		priIgmpAdminPonS OBJECT-TYPE
			SYNTAX INTEGER (1..16)
			MAX-ACCESS read-write
			STATUS current
			DESCRIPTION
				"Description."
			::= { priIgmpAdminEntry 1 }

		
--          1.3.6.1.4.1.37950.1.1.5.12.3.2.1.1.2
-- 1.3.6.1.4.1.37950.1.1.5.12.3.2.1.1.2
-- 1.3.6.1.4.1.37950.1.1.5.12.3.2.1.1.2
-- 1.3.6.1.4.1.37950.1.1.5.12.3.2.1.1.2
-- 1.3.6.1.4.1.37950.1.1.5.12.3.2.1.1.2
-- 1.3.6.1.4.1.37950.1.1.5.12.3.2.1.1.2
-- 1.3.6.1.4.1.37950.1.1.5.12.3.2.1.1.2
-- 1.3.6.1.4.1.37950.1.1.5.12.3.2.1.1.2
-- 1.3.6.1.4.1.37950.1.1.5.12.3.2.1.1.2
		-- 1.3.6.1.4.1.37950.1.1.5.12.3.2.1.1.2
		priIgmpAdminOnuS OBJECT-TYPE
			SYNTAX INTEGER (1..65535)
			MAX-ACCESS read-write
			STATUS current
			DESCRIPTION
				"Description."
			::= { priIgmpAdminEntry 2 }

		
--          1.3.6.1.4.1.37950.1.1.5.12.3.2.1.1.3
-- 1.3.6.1.4.1.37950.1.1.5.12.3.2.1.1.3
-- 1.3.6.1.4.1.37950.1.1.5.12.3.2.1.1.3
-- 1.3.6.1.4.1.37950.1.1.5.12.3.2.1.1.3
-- 1.3.6.1.4.1.37950.1.1.5.12.3.2.1.1.3
-- 1.3.6.1.4.1.37950.1.1.5.12.3.2.1.1.3
-- 1.3.6.1.4.1.37950.1.1.5.12.3.2.1.1.3
-- 1.3.6.1.4.1.37950.1.1.5.12.3.2.1.1.3
-- 1.3.6.1.4.1.37950.1.1.5.12.3.2.1.1.3
		-- 1.3.6.1.4.1.37950.1.1.5.12.3.2.1.1.3
		priIgmpAdminEnableS OBJECT-TYPE
			SYNTAX INTEGER
				{
				disable(0),
				enable(1)
				}
			MAX-ACCESS read-write
			STATUS current
			DESCRIPTION
				"Description."
			::= { priIgmpAdminEntry 3 }

		
--          1.3.6.1.4.1.37950.1.1.5.12.3.2.2
-- 1.3.6.1.4.1.37950.1.1.5.12.3.2.2
-- 1.3.6.1.4.1.37950.1.1.5.12.3.2.2
-- 1.3.6.1.4.1.37950.1.1.5.12.3.2.2
-- 1.3.6.1.4.1.37950.1.1.5.12.3.2.2
-- 1.3.6.1.4.1.37950.1.1.5.12.3.2.2
-- 1.3.6.1.4.1.37950.1.1.5.12.3.2.2
-- 1.3.6.1.4.1.37950.1.1.5.12.3.2.2
-- 1.3.6.1.4.1.37950.1.1.5.12.3.2.2
		-- 1.3.6.1.4.1.37950.1.1.5.12.3.2.2
		priCatvStatusTable OBJECT-TYPE
			SYNTAX SEQUENCE OF PriCatvStatusEntry
			MAX-ACCESS not-accessible
			STATUS current
			DESCRIPTION
				"Description."
			::= { onuPriGlobalInfo 2 }

		
--          1.3.6.1.4.1.37950.1.1.5.12.3.2.2.1
-- 1.3.6.1.4.1.37950.1.1.5.12.3.2.2.1
-- 1.3.6.1.4.1.37950.1.1.5.12.3.2.2.1
-- 1.3.6.1.4.1.37950.1.1.5.12.3.2.2.1
-- 1.3.6.1.4.1.37950.1.1.5.12.3.2.2.1
-- 1.3.6.1.4.1.37950.1.1.5.12.3.2.2.1
-- 1.3.6.1.4.1.37950.1.1.5.12.3.2.2.1
-- 1.3.6.1.4.1.37950.1.1.5.12.3.2.2.1
-- 1.3.6.1.4.1.37950.1.1.5.12.3.2.2.1
		-- 1.3.6.1.4.1.37950.1.1.5.12.3.2.2.1
		priCatvStatusEntry OBJECT-TYPE
			SYNTAX PriCatvStatusEntry
			MAX-ACCESS not-accessible
			STATUS current
			DESCRIPTION
				"Description."
			INDEX { priCatvStatusPonS, priCatvSatusOnuS }
			::= { priCatvStatusTable 1 }

		
		PriCatvStatusEntry ::=
			SEQUENCE { 
				priCatvStatusPonS
					INTEGER,
				priCatvSatusOnuS
					INTEGER,
				priCatvStatusS
					INTEGER
			 }

--          1.3.6.1.4.1.37950.1.1.5.12.3.2.2.1.1
-- 1.3.6.1.4.1.37950.1.1.5.12.3.2.2.1.1
-- 1.3.6.1.4.1.37950.1.1.5.12.3.2.2.1.1
-- 1.3.6.1.4.1.37950.1.1.5.12.3.2.2.1.1
-- 1.3.6.1.4.1.37950.1.1.5.12.3.2.2.1.1
-- 1.3.6.1.4.1.37950.1.1.5.12.3.2.2.1.1
-- 1.3.6.1.4.1.37950.1.1.5.12.3.2.2.1.1
-- 1.3.6.1.4.1.37950.1.1.5.12.3.2.2.1.1
-- 1.3.6.1.4.1.37950.1.1.5.12.3.2.2.1.1
		-- 1.3.6.1.4.1.37950.1.1.5.12.3.2.2.1.1
		priCatvStatusPonS OBJECT-TYPE
			SYNTAX INTEGER (1..16)
			MAX-ACCESS read-write
			STATUS current
			DESCRIPTION
				"Description."
			::= { priCatvStatusEntry 1 }

		
--          1.3.6.1.4.1.37950.1.1.5.12.3.2.2.1.2
-- 1.3.6.1.4.1.37950.1.1.5.12.3.2.2.1.2
-- 1.3.6.1.4.1.37950.1.1.5.12.3.2.2.1.2
-- 1.3.6.1.4.1.37950.1.1.5.12.3.2.2.1.2
-- 1.3.6.1.4.1.37950.1.1.5.12.3.2.2.1.2
-- 1.3.6.1.4.1.37950.1.1.5.12.3.2.2.1.2
-- 1.3.6.1.4.1.37950.1.1.5.12.3.2.2.1.2
-- 1.3.6.1.4.1.37950.1.1.5.12.3.2.2.1.2
-- 1.3.6.1.4.1.37950.1.1.5.12.3.2.2.1.2
		-- 1.3.6.1.4.1.37950.1.1.5.12.3.2.2.1.2
		priCatvSatusOnuS OBJECT-TYPE
			SYNTAX INTEGER (1..65535)
			MAX-ACCESS read-write
			STATUS current
			DESCRIPTION
				"Description."
			::= { priCatvStatusEntry 2 }

		
--          1.3.6.1.4.1.37950.1.1.5.12.3.2.2.1.3
-- 1.3.6.1.4.1.37950.1.1.5.12.3.2.2.1.3
-- 1.3.6.1.4.1.37950.1.1.5.12.3.2.2.1.3
-- 1.3.6.1.4.1.37950.1.1.5.12.3.2.2.1.3
-- 1.3.6.1.4.1.37950.1.1.5.12.3.2.2.1.3
-- 1.3.6.1.4.1.37950.1.1.5.12.3.2.2.1.3
-- 1.3.6.1.4.1.37950.1.1.5.12.3.2.2.1.3
-- 1.3.6.1.4.1.37950.1.1.5.12.3.2.2.1.3
-- 1.3.6.1.4.1.37950.1.1.5.12.3.2.2.1.3
		-- 1.3.6.1.4.1.37950.1.1.5.12.3.2.2.1.3
		priCatvStatusS OBJECT-TYPE
			SYNTAX INTEGER
				{
				disable(0),
				enable(1)
				}
			MAX-ACCESS read-write
			STATUS current
			DESCRIPTION
				"Description."
			::= { priCatvStatusEntry 3 }

		
--          1.3.6.1.4.1.37950.1.1.5.12.3.2.3
-- 1.3.6.1.4.1.37950.1.1.5.12.3.2.3
-- 1.3.6.1.4.1.37950.1.1.5.12.3.2.3
-- 1.3.6.1.4.1.37950.1.1.5.12.3.2.3
-- 1.3.6.1.4.1.37950.1.1.5.12.3.2.3
-- 1.3.6.1.4.1.37950.1.1.5.12.3.2.3
-- 1.3.6.1.4.1.37950.1.1.5.12.3.2.3
-- 1.3.6.1.4.1.37950.1.1.5.12.3.2.3
-- 1.3.6.1.4.1.37950.1.1.5.12.3.2.3
		-- 1.3.6.1.4.1.37950.1.1.5.12.3.2.3
		priCtcoamSkipTable OBJECT-TYPE
			SYNTAX SEQUENCE OF PriCtcoamSkipEntry
			MAX-ACCESS not-accessible
			STATUS current
			DESCRIPTION
				"Description."
			::= { onuPriGlobalInfo 3 }

		
--          1.3.6.1.4.1.37950.1.1.5.12.3.2.3.1
-- 1.3.6.1.4.1.37950.1.1.5.12.3.2.3.1
-- 1.3.6.1.4.1.37950.1.1.5.12.3.2.3.1
-- 1.3.6.1.4.1.37950.1.1.5.12.3.2.3.1
-- 1.3.6.1.4.1.37950.1.1.5.12.3.2.3.1
-- 1.3.6.1.4.1.37950.1.1.5.12.3.2.3.1
-- 1.3.6.1.4.1.37950.1.1.5.12.3.2.3.1
-- 1.3.6.1.4.1.37950.1.1.5.12.3.2.3.1
-- 1.3.6.1.4.1.37950.1.1.5.12.3.2.3.1
		-- 1.3.6.1.4.1.37950.1.1.5.12.3.2.3.1
		priCtcoamSkipEntry OBJECT-TYPE
			SYNTAX PriCtcoamSkipEntry
			MAX-ACCESS not-accessible
			STATUS current
			DESCRIPTION
				"Description."
			INDEX { priCtcoamSkipPonS, priCtcOamSkipOnuS }
			::= { priCtcoamSkipTable 1 }

		
		PriCtcoamSkipEntry ::=
			SEQUENCE { 
				priCtcoamSkipPonS
					INTEGER,
				priCtcOamSkipOnuS
					INTEGER,
				priCtcoamSkipS
					INTEGER
			 }

--          1.3.6.1.4.1.37950.1.1.5.12.3.2.3.1.1
-- 1.3.6.1.4.1.37950.1.1.5.12.3.2.3.1.1
-- 1.3.6.1.4.1.37950.1.1.5.12.3.2.3.1.1
-- 1.3.6.1.4.1.37950.1.1.5.12.3.2.3.1.1
-- 1.3.6.1.4.1.37950.1.1.5.12.3.2.3.1.1
-- 1.3.6.1.4.1.37950.1.1.5.12.3.2.3.1.1
-- 1.3.6.1.4.1.37950.1.1.5.12.3.2.3.1.1
-- 1.3.6.1.4.1.37950.1.1.5.12.3.2.3.1.1
-- 1.3.6.1.4.1.37950.1.1.5.12.3.2.3.1.1
		-- 1.3.6.1.4.1.37950.1.1.5.12.3.2.3.1.1
		priCtcoamSkipPonS OBJECT-TYPE
			SYNTAX INTEGER (1..16)
			MAX-ACCESS read-write
			STATUS current
			DESCRIPTION
				"Description."
			::= { priCtcoamSkipEntry 1 }

		
--          1.3.6.1.4.1.37950.1.1.5.12.3.2.3.1.2
-- 1.3.6.1.4.1.37950.1.1.5.12.3.2.3.1.2
-- 1.3.6.1.4.1.37950.1.1.5.12.3.2.3.1.2
-- 1.3.6.1.4.1.37950.1.1.5.12.3.2.3.1.2
-- 1.3.6.1.4.1.37950.1.1.5.12.3.2.3.1.2
-- 1.3.6.1.4.1.37950.1.1.5.12.3.2.3.1.2
-- 1.3.6.1.4.1.37950.1.1.5.12.3.2.3.1.2
-- 1.3.6.1.4.1.37950.1.1.5.12.3.2.3.1.2
-- 1.3.6.1.4.1.37950.1.1.5.12.3.2.3.1.2
		-- 1.3.6.1.4.1.37950.1.1.5.12.3.2.3.1.2
		priCtcOamSkipOnuS OBJECT-TYPE
			SYNTAX INTEGER (1..65535)
			MAX-ACCESS read-write
			STATUS current
			DESCRIPTION
				"Description."
			::= { priCtcoamSkipEntry 2 }

		
--          1.3.6.1.4.1.37950.1.1.5.12.3.2.3.1.3
-- 1.3.6.1.4.1.37950.1.1.5.12.3.2.3.1.3
-- 1.3.6.1.4.1.37950.1.1.5.12.3.2.3.1.3
-- 1.3.6.1.4.1.37950.1.1.5.12.3.2.3.1.3
-- 1.3.6.1.4.1.37950.1.1.5.12.3.2.3.1.3
-- 1.3.6.1.4.1.37950.1.1.5.12.3.2.3.1.3
-- 1.3.6.1.4.1.37950.1.1.5.12.3.2.3.1.3
-- 1.3.6.1.4.1.37950.1.1.5.12.3.2.3.1.3
-- 1.3.6.1.4.1.37950.1.1.5.12.3.2.3.1.3
		-- 1.3.6.1.4.1.37950.1.1.5.12.3.2.3.1.3
		priCtcoamSkipS OBJECT-TYPE
			SYNTAX INTEGER
				{
				disable(0),
				enable(1)
				}
			MAX-ACCESS read-write
			STATUS current
			DESCRIPTION
				"Description."
			::= { priCtcoamSkipEntry 3 }

		
--          1.3.6.1.4.1.37950.1.1.5.12.3.2.4
-- 1.3.6.1.4.1.37950.1.1.5.12.3.2.4
-- 1.3.6.1.4.1.37950.1.1.5.12.3.2.4
-- 1.3.6.1.4.1.37950.1.1.5.12.3.2.4
-- 1.3.6.1.4.1.37950.1.1.5.12.3.2.4
-- 1.3.6.1.4.1.37950.1.1.5.12.3.2.4
-- 1.3.6.1.4.1.37950.1.1.5.12.3.2.4
-- 1.3.6.1.4.1.37950.1.1.5.12.3.2.4
-- 1.3.6.1.4.1.37950.1.1.5.12.3.2.4
		-- 1.3.6.1.4.1.37950.1.1.5.12.3.2.4
		priWifiSwichTable OBJECT-TYPE
			SYNTAX SEQUENCE OF PriWifiSwichEntry
			MAX-ACCESS not-accessible
			STATUS current
			DESCRIPTION
				"Description."
			::= { onuPriGlobalInfo 4 }

		
--          1.3.6.1.4.1.37950.1.1.5.12.3.2.4.1
-- 1.3.6.1.4.1.37950.1.1.5.12.3.2.4.1
-- 1.3.6.1.4.1.37950.1.1.5.12.3.2.4.1
-- 1.3.6.1.4.1.37950.1.1.5.12.3.2.4.1
-- 1.3.6.1.4.1.37950.1.1.5.12.3.2.4.1
-- 1.3.6.1.4.1.37950.1.1.5.12.3.2.4.1
-- 1.3.6.1.4.1.37950.1.1.5.12.3.2.4.1
-- 1.3.6.1.4.1.37950.1.1.5.12.3.2.4.1
-- 1.3.6.1.4.1.37950.1.1.5.12.3.2.4.1
		-- 1.3.6.1.4.1.37950.1.1.5.12.3.2.4.1
		priWifiSwichEntry OBJECT-TYPE
			SYNTAX PriWifiSwichEntry
			MAX-ACCESS not-accessible
			STATUS current
			DESCRIPTION
				"Description."
			INDEX { priWifiSwichPonS, priWifiSwichOnuS }
			::= { priWifiSwichTable 1 }

		
		PriWifiSwichEntry ::=
			SEQUENCE { 
				priWifiSwichPonS
					INTEGER,
				priWifiSwichOnuS
					INTEGER,
				priWifiSwichAPModuleS
					INTEGER,
				priWifiSwichCountry
					INTEGER,
				priWifiSwichChannelS
					INTEGER,
				priWifiSwichStandardS
					INTEGER,
				priWifiSwitchPower
					INTEGER,
				priWifiSwichChannelWidth
					INTEGER
			 }

--          1.3.6.1.4.1.37950.1.1.5.12.3.2.4.1.1
-- 1.3.6.1.4.1.37950.1.1.5.12.3.2.4.1.1
-- 1.3.6.1.4.1.37950.1.1.5.12.3.2.4.1.1
-- 1.3.6.1.4.1.37950.1.1.5.12.3.2.4.1.1
-- 1.3.6.1.4.1.37950.1.1.5.12.3.2.4.1.1
-- 1.3.6.1.4.1.37950.1.1.5.12.3.2.4.1.1
-- 1.3.6.1.4.1.37950.1.1.5.12.3.2.4.1.1
-- 1.3.6.1.4.1.37950.1.1.5.12.3.2.4.1.1
-- 1.3.6.1.4.1.37950.1.1.5.12.3.2.4.1.1
		-- 1.3.6.1.4.1.37950.1.1.5.12.3.2.4.1.1
		priWifiSwichPonS OBJECT-TYPE
			SYNTAX INTEGER (1..16)
			MAX-ACCESS read-write
			STATUS current
			DESCRIPTION
				"Description."
			::= { priWifiSwichEntry 1 }

		
--          1.3.6.1.4.1.37950.1.1.5.12.3.2.4.1.2
-- 1.3.6.1.4.1.37950.1.1.5.12.3.2.4.1.2
-- 1.3.6.1.4.1.37950.1.1.5.12.3.2.4.1.2
-- 1.3.6.1.4.1.37950.1.1.5.12.3.2.4.1.2
-- 1.3.6.1.4.1.37950.1.1.5.12.3.2.4.1.2
-- 1.3.6.1.4.1.37950.1.1.5.12.3.2.4.1.2
-- 1.3.6.1.4.1.37950.1.1.5.12.3.2.4.1.2
-- 1.3.6.1.4.1.37950.1.1.5.12.3.2.4.1.2
-- 1.3.6.1.4.1.37950.1.1.5.12.3.2.4.1.2
		-- 1.3.6.1.4.1.37950.1.1.5.12.3.2.4.1.2
		priWifiSwichOnuS OBJECT-TYPE
			SYNTAX INTEGER (1..65535)
			MAX-ACCESS read-write
			STATUS current
			DESCRIPTION
				"Description."
			::= { priWifiSwichEntry 2 }

		
--          1.3.6.1.4.1.37950.1.1.5.12.3.2.4.1.3
-- 1.3.6.1.4.1.37950.1.1.5.12.3.2.4.1.3
-- 1.3.6.1.4.1.37950.1.1.5.12.3.2.4.1.3
-- 1.3.6.1.4.1.37950.1.1.5.12.3.2.4.1.3
-- 1.3.6.1.4.1.37950.1.1.5.12.3.2.4.1.3
-- 1.3.6.1.4.1.37950.1.1.5.12.3.2.4.1.3
-- 1.3.6.1.4.1.37950.1.1.5.12.3.2.4.1.3
-- 1.3.6.1.4.1.37950.1.1.5.12.3.2.4.1.3
-- 1.3.6.1.4.1.37950.1.1.5.12.3.2.4.1.3
		-- 1.3.6.1.4.1.37950.1.1.5.12.3.2.4.1.3
		priWifiSwichAPModuleS OBJECT-TYPE
			SYNTAX INTEGER
				{
				disable(0),
				enable(1)
				}
			MAX-ACCESS read-write
			STATUS current
			DESCRIPTION
				"Description."
			::= { priWifiSwichEntry 3 }

		
--          1.3.6.1.4.1.37950.1.1.5.12.3.2.4.1.4
-- 1.3.6.1.4.1.37950.1.1.5.12.3.2.4.1.4
-- 1.3.6.1.4.1.37950.1.1.5.12.3.2.4.1.4
-- 1.3.6.1.4.1.37950.1.1.5.12.3.2.4.1.4
-- 1.3.6.1.4.1.37950.1.1.5.12.3.2.4.1.4
-- 1.3.6.1.4.1.37950.1.1.5.12.3.2.4.1.4
-- 1.3.6.1.4.1.37950.1.1.5.12.3.2.4.1.4
-- 1.3.6.1.4.1.37950.1.1.5.12.3.2.4.1.4
-- 1.3.6.1.4.1.37950.1.1.5.12.3.2.4.1.4
		-- 1.3.6.1.4.1.37950.1.1.5.12.3.2.4.1.4
		priWifiSwichCountry OBJECT-TYPE
			SYNTAX INTEGER
				{
				etsi(0),
				fcc(1),
				ic(2),
				spain(3),
				france(4),
				mkk(5),
				isreal(6),
				mkk2(7),
				mkk3(8),
				russian(9),
				cn(10),
				global(11),
				world-wide(12),
				mkk1(13),
				ncc(14)
				}
			MAX-ACCESS read-write
			STATUS current
			DESCRIPTION
				"Description."
			::= { priWifiSwichEntry 4 }

		
--          1.3.6.1.4.1.37950.1.1.5.12.3.2.4.1.5
-- 1.3.6.1.4.1.37950.1.1.5.12.3.2.4.1.5
-- 1.3.6.1.4.1.37950.1.1.5.12.3.2.4.1.5
-- 1.3.6.1.4.1.37950.1.1.5.12.3.2.4.1.5
-- 1.3.6.1.4.1.37950.1.1.5.12.3.2.4.1.5
-- 1.3.6.1.4.1.37950.1.1.5.12.3.2.4.1.5
-- 1.3.6.1.4.1.37950.1.1.5.12.3.2.4.1.5
-- 1.3.6.1.4.1.37950.1.1.5.12.3.2.4.1.5
-- 1.3.6.1.4.1.37950.1.1.5.12.3.2.4.1.5
		-- 1.3.6.1.4.1.37950.1.1.5.12.3.2.4.1.5
		priWifiSwichChannelS OBJECT-TYPE
			SYNTAX INTEGER (0..13)
			MAX-ACCESS read-write
			STATUS current
			DESCRIPTION
				"Description."
			::= { priWifiSwichEntry 5 }

		
--          1.3.6.1.4.1.37950.1.1.5.12.3.2.4.1.6
-- 1.3.6.1.4.1.37950.1.1.5.12.3.2.4.1.6
-- 1.3.6.1.4.1.37950.1.1.5.12.3.2.4.1.6
-- 1.3.6.1.4.1.37950.1.1.5.12.3.2.4.1.6
-- 1.3.6.1.4.1.37950.1.1.5.12.3.2.4.1.6
-- 1.3.6.1.4.1.37950.1.1.5.12.3.2.4.1.6
-- 1.3.6.1.4.1.37950.1.1.5.12.3.2.4.1.6
-- 1.3.6.1.4.1.37950.1.1.5.12.3.2.4.1.6
-- 1.3.6.1.4.1.37950.1.1.5.12.3.2.4.1.6
		-- 1.3.6.1.4.1.37950.1.1.5.12.3.2.4.1.6
		priWifiSwichStandardS OBJECT-TYPE
			SYNTAX INTEGER
				{
				s80211b(0),
				s80211g(1),
				s80211bg(2),
				s80211n(3),
				s80211bgn(4),
				s80211ax(5),
				s80211bgnax(6)
				}
			MAX-ACCESS read-write
			STATUS current
			DESCRIPTION
				"Description."
			::= { priWifiSwichEntry 6 }

		
--          1.3.6.1.4.1.37950.1.1.5.12.3.2.4.1.7
-- 1.3.6.1.4.1.37950.1.1.5.12.3.2.4.1.7
-- 1.3.6.1.4.1.37950.1.1.5.12.3.2.4.1.7
-- 1.3.6.1.4.1.37950.1.1.5.12.3.2.4.1.7
-- 1.3.6.1.4.1.37950.1.1.5.12.3.2.4.1.7
-- 1.3.6.1.4.1.37950.1.1.5.12.3.2.4.1.7
-- 1.3.6.1.4.1.37950.1.1.5.12.3.2.4.1.7
-- 1.3.6.1.4.1.37950.1.1.5.12.3.2.4.1.7
-- 1.3.6.1.4.1.37950.1.1.5.12.3.2.4.1.7
		-- 1.3.6.1.4.1.37950.1.1.5.12.3.2.4.1.7
		priWifiSwitchPower OBJECT-TYPE
			SYNTAX INTEGER (0..20)
			MAX-ACCESS read-write
			STATUS current
			DESCRIPTION
				"Description."
			::= { priWifiSwichEntry 7 }

		
--         1.3.6.1.4.1.37950.1.1.5.12.3.2.4.1.8
-- 1.3.6.1.4.1.37950.1.1.5.12.3.2.4.1.8
-- 1.3.6.1.4.1.37950.1.1.5.12.3.2.4.1.8
-- 1.3.6.1.4.1.37950.1.1.5.12.3.2.4.1.8
-- 1.3.6.1.4.1.37950.1.1.5.12.3.2.4.1.8
-- 1.3.6.1.4.1.37950.1.1.5.12.3.2.4.1.8
-- 1.3.6.1.4.1.37950.1.1.5.12.3.2.4.1.8
-- 1.3.6.1.4.1.37950.1.1.5.12.3.2.4.1.8
		-- 1.3.6.1.4.1.37950.1.1.5.12.3.2.4.1.8
		priWifiSwichChannelWidth OBJECT-TYPE
			SYNTAX INTEGER
				{
				s20(0),
				s40(1),
				s20-40(3)
				}
			MAX-ACCESS read-write
			STATUS current
			DESCRIPTION
				"Description."
			::= { priWifiSwichEntry 8 }

		
--          1.3.6.1.4.1.37950.1.1.5.12.3.2.5
-- 1.3.6.1.4.1.37950.1.1.5.12.3.2.5
-- 1.3.6.1.4.1.37950.1.1.5.12.3.2.5
-- 1.3.6.1.4.1.37950.1.1.5.12.3.2.5
-- 1.3.6.1.4.1.37950.1.1.5.12.3.2.5
-- 1.3.6.1.4.1.37950.1.1.5.12.3.2.5
-- 1.3.6.1.4.1.37950.1.1.5.12.3.2.5
-- 1.3.6.1.4.1.37950.1.1.5.12.3.2.5
-- 1.3.6.1.4.1.37950.1.1.5.12.3.2.5
		-- 1.3.6.1.4.1.37950.1.1.5.12.3.2.5
		priWifiSsidTable OBJECT-TYPE
			SYNTAX SEQUENCE OF PriWifiSsidEntry
			MAX-ACCESS not-accessible
			STATUS current
			DESCRIPTION
				"Description."
			::= { onuPriGlobalInfo 5 }

		
--          1.3.6.1.4.1.37950.1.1.5.12.3.2.5.1
-- 1.3.6.1.4.1.37950.1.1.5.12.3.2.5.1
-- 1.3.6.1.4.1.37950.1.1.5.12.3.2.5.1
-- 1.3.6.1.4.1.37950.1.1.5.12.3.2.5.1
-- 1.3.6.1.4.1.37950.1.1.5.12.3.2.5.1
-- 1.3.6.1.4.1.37950.1.1.5.12.3.2.5.1
-- 1.3.6.1.4.1.37950.1.1.5.12.3.2.5.1
-- 1.3.6.1.4.1.37950.1.1.5.12.3.2.5.1
-- 1.3.6.1.4.1.37950.1.1.5.12.3.2.5.1
		-- 1.3.6.1.4.1.37950.1.1.5.12.3.2.5.1
		priWifiSsidEntry OBJECT-TYPE
			SYNTAX PriWifiSsidEntry
			MAX-ACCESS not-accessible
			STATUS current
			DESCRIPTION
				"Description."
			INDEX { priWifiSsidPonS, priWifiSsidOnuS, priWifiSsidIdS }
			::= { priWifiSsidTable 1 }

		
		PriWifiSsidEntry ::=
			SEQUENCE { 
				priWifiSsidPonS
					INTEGER,
				priWifiSsidOnuS
					INTEGER,
				priWifiSsidIdS
					Integer32,
				priWifiSsidNameS
					OCTET STRING,
				priWifiSsidEnableS
					INTEGER,
				priWifiSsidHideS
					INTEGER,
				priWifiSsidAuthMode
					INTEGER,
				priWifiSsidEncryTpeS
					INTEGER,
				priSsidPreshareKeyS
					OCTET STRING,
				priSsidWpaRekeyIntervalS
					INTEGER,
				priSsidRadiusServIpTypeS
					INTEGER,
				priSsidRadiusServIp
					OCTET STRING,
				priSsidRadiusServIpPrefixLenS
					INTEGER,
				priSsidRadiusPortS
					INTEGER,
				priSsidRadiusKeyS
					OCTET STRING,
				priSsidWepEncryptionLevelS
					INTEGER,
				priSsidWepKeyIndexS
					INTEGER,
				priSsidWepKey1S
					OCTET STRING,
				priSsidWepKey2S
					OCTET STRING,
				priSsidWepKey3S
					OCTET STRING,
				priSsidWepKey4S
					OCTET STRING
			 }

--          1.3.6.1.4.1.37950.1.1.5.12.3.2.5.1.1
-- 1.3.6.1.4.1.37950.1.1.5.12.3.2.5.1.1
-- 1.3.6.1.4.1.37950.1.1.5.12.3.2.5.1.1
-- 1.3.6.1.4.1.37950.1.1.5.12.3.2.5.1.1
-- 1.3.6.1.4.1.37950.1.1.5.12.3.2.5.1.1
-- 1.3.6.1.4.1.37950.1.1.5.12.3.2.5.1.1
-- 1.3.6.1.4.1.37950.1.1.5.12.3.2.5.1.1
-- 1.3.6.1.4.1.37950.1.1.5.12.3.2.5.1.1
-- 1.3.6.1.4.1.37950.1.1.5.12.3.2.5.1.1
		-- 1.3.6.1.4.1.37950.1.1.5.12.3.2.5.1.1
		priWifiSsidPonS OBJECT-TYPE
			SYNTAX INTEGER (1..16)
			MAX-ACCESS read-write
			STATUS current
			DESCRIPTION
				"Description."
			::= { priWifiSsidEntry 1 }

		
--          1.3.6.1.4.1.37950.1.1.5.12.3.2.5.1.2
-- 1.3.6.1.4.1.37950.1.1.5.12.3.2.5.1.2
-- 1.3.6.1.4.1.37950.1.1.5.12.3.2.5.1.2
-- 1.3.6.1.4.1.37950.1.1.5.12.3.2.5.1.2
-- 1.3.6.1.4.1.37950.1.1.5.12.3.2.5.1.2
-- 1.3.6.1.4.1.37950.1.1.5.12.3.2.5.1.2
-- 1.3.6.1.4.1.37950.1.1.5.12.3.2.5.1.2
-- 1.3.6.1.4.1.37950.1.1.5.12.3.2.5.1.2
-- 1.3.6.1.4.1.37950.1.1.5.12.3.2.5.1.2
		-- 1.3.6.1.4.1.37950.1.1.5.12.3.2.5.1.2
		priWifiSsidOnuS OBJECT-TYPE
			SYNTAX INTEGER (1..65535)
			MAX-ACCESS read-write
			STATUS current
			DESCRIPTION
				"Description."
			::= { priWifiSsidEntry 2 }

		
--          1.3.6.1.4.1.37950.1.1.5.12.3.2.5.1.3
-- 1.3.6.1.4.1.37950.1.1.5.12.3.2.5.1.3
-- 1.3.6.1.4.1.37950.1.1.5.12.3.2.5.1.3
-- 1.3.6.1.4.1.37950.1.1.5.12.3.2.5.1.3
-- 1.3.6.1.4.1.37950.1.1.5.12.3.2.5.1.3
-- 1.3.6.1.4.1.37950.1.1.5.12.3.2.5.1.3
-- 1.3.6.1.4.1.37950.1.1.5.12.3.2.5.1.3
-- 1.3.6.1.4.1.37950.1.1.5.12.3.2.5.1.3
-- 1.3.6.1.4.1.37950.1.1.5.12.3.2.5.1.3
		-- 1.3.6.1.4.1.37950.1.1.5.12.3.2.5.1.3
		priWifiSsidIdS OBJECT-TYPE
			SYNTAX Integer32 (1..4)
			MAX-ACCESS read-write
			STATUS current
			DESCRIPTION
				"Description."
			::= { priWifiSsidEntry 3 }

		
--          1.3.6.1.4.1.37950.1.1.5.12.3.2.5.1.4
-- 1.3.6.1.4.1.37950.1.1.5.12.3.2.5.1.4
-- 1.3.6.1.4.1.37950.1.1.5.12.3.2.5.1.4
-- 1.3.6.1.4.1.37950.1.1.5.12.3.2.5.1.4
-- 1.3.6.1.4.1.37950.1.1.5.12.3.2.5.1.4
-- 1.3.6.1.4.1.37950.1.1.5.12.3.2.5.1.4
-- 1.3.6.1.4.1.37950.1.1.5.12.3.2.5.1.4
-- 1.3.6.1.4.1.37950.1.1.5.12.3.2.5.1.4
-- 1.3.6.1.4.1.37950.1.1.5.12.3.2.5.1.4
		-- 1.3.6.1.4.1.37950.1.1.5.12.3.2.5.1.4
		priWifiSsidNameS OBJECT-TYPE
			SYNTAX OCTET STRING
			MAX-ACCESS read-write
			STATUS current
			DESCRIPTION
				"Description."
			::= { priWifiSsidEntry 4 }

		
--          1.3.6.1.4.1.37950.1.1.5.12.3.2.5.1.5
-- 1.3.6.1.4.1.37950.1.1.5.12.3.2.5.1.5
-- 1.3.6.1.4.1.37950.1.1.5.12.3.2.5.1.5
-- 1.3.6.1.4.1.37950.1.1.5.12.3.2.5.1.5
-- 1.3.6.1.4.1.37950.1.1.5.12.3.2.5.1.5
-- 1.3.6.1.4.1.37950.1.1.5.12.3.2.5.1.5
-- 1.3.6.1.4.1.37950.1.1.5.12.3.2.5.1.5
-- 1.3.6.1.4.1.37950.1.1.5.12.3.2.5.1.5
-- 1.3.6.1.4.1.37950.1.1.5.12.3.2.5.1.5
		-- 1.3.6.1.4.1.37950.1.1.5.12.3.2.5.1.5
		priWifiSsidEnableS OBJECT-TYPE
			SYNTAX INTEGER
				{
				disable(0),
				enable(1)
				}
			MAX-ACCESS read-write
			STATUS current
			DESCRIPTION
				"Description."
			::= { priWifiSsidEntry 5 }

		
--          1.3.6.1.4.1.37950.1.1.5.12.3.2.5.1.6
-- 1.3.6.1.4.1.37950.1.1.5.12.3.2.5.1.6
-- 1.3.6.1.4.1.37950.1.1.5.12.3.2.5.1.6
-- 1.3.6.1.4.1.37950.1.1.5.12.3.2.5.1.6
-- 1.3.6.1.4.1.37950.1.1.5.12.3.2.5.1.6
-- 1.3.6.1.4.1.37950.1.1.5.12.3.2.5.1.6
-- 1.3.6.1.4.1.37950.1.1.5.12.3.2.5.1.6
-- 1.3.6.1.4.1.37950.1.1.5.12.3.2.5.1.6
-- 1.3.6.1.4.1.37950.1.1.5.12.3.2.5.1.6
		-- 1.3.6.1.4.1.37950.1.1.5.12.3.2.5.1.6
		priWifiSsidHideS OBJECT-TYPE
			SYNTAX INTEGER
				{
				disable(0),
				enable(1)
				}
			MAX-ACCESS read-write
			STATUS current
			DESCRIPTION
				"Description."
			::= { priWifiSsidEntry 6 }

		
--          1.3.6.1.4.1.37950.1.1.5.12.3.2.5.1.7
-- 1.3.6.1.4.1.37950.1.1.5.12.3.2.5.1.7
-- 1.3.6.1.4.1.37950.1.1.5.12.3.2.5.1.7
-- 1.3.6.1.4.1.37950.1.1.5.12.3.2.5.1.7
-- 1.3.6.1.4.1.37950.1.1.5.12.3.2.5.1.7
-- 1.3.6.1.4.1.37950.1.1.5.12.3.2.5.1.7
-- 1.3.6.1.4.1.37950.1.1.5.12.3.2.5.1.7
-- 1.3.6.1.4.1.37950.1.1.5.12.3.2.5.1.7
-- 1.3.6.1.4.1.37950.1.1.5.12.3.2.5.1.7
		-- 1.3.6.1.4.1.37950.1.1.5.12.3.2.5.1.7
		priWifiSsidAuthMode OBJECT-TYPE
			SYNTAX INTEGER
				{
				open(1),
				shared(2),
				wepauto(3),
				wpapsk(4),
				wpa(5),
				wpa2psk(6),
				wpa2(7),
				wpa-wpa2(8),
				wpapsk-wpa2psk(9),
				wpa3psk(10),
				wpa2psk-wpa3psk(11)
				}
			MAX-ACCESS read-write
			STATUS current
			DESCRIPTION
				"Description."
			::= { priWifiSsidEntry 7 }

		
--          1.3.6.1.4.1.37950.1.1.5.12.3.2.5.1.8
-- 1.3.6.1.4.1.37950.1.1.5.12.3.2.5.1.8
-- 1.3.6.1.4.1.37950.1.1.5.12.3.2.5.1.8
-- 1.3.6.1.4.1.37950.1.1.5.12.3.2.5.1.8
-- 1.3.6.1.4.1.37950.1.1.5.12.3.2.5.1.8
-- 1.3.6.1.4.1.37950.1.1.5.12.3.2.5.1.8
-- 1.3.6.1.4.1.37950.1.1.5.12.3.2.5.1.8
-- 1.3.6.1.4.1.37950.1.1.5.12.3.2.5.1.8
-- 1.3.6.1.4.1.37950.1.1.5.12.3.2.5.1.8
		-- 1.3.6.1.4.1.37950.1.1.5.12.3.2.5.1.8
		priWifiSsidEncryTpeS OBJECT-TYPE
			SYNTAX INTEGER
				{
				none(1),
				wep(2),
				tkip(3),
				aes(4),
				tkipaes(5)
				}
			MAX-ACCESS read-write
			STATUS current
			DESCRIPTION
				"Description."
			::= { priWifiSsidEntry 8 }

		
--          1.3.6.1.4.1.37950.1.1.5.12.3.2.5.1.9
-- 1.3.6.1.4.1.37950.1.1.5.12.3.2.5.1.9
-- 1.3.6.1.4.1.37950.1.1.5.12.3.2.5.1.9
-- 1.3.6.1.4.1.37950.1.1.5.12.3.2.5.1.9
-- 1.3.6.1.4.1.37950.1.1.5.12.3.2.5.1.9
-- 1.3.6.1.4.1.37950.1.1.5.12.3.2.5.1.9
-- 1.3.6.1.4.1.37950.1.1.5.12.3.2.5.1.9
-- 1.3.6.1.4.1.37950.1.1.5.12.3.2.5.1.9
-- 1.3.6.1.4.1.37950.1.1.5.12.3.2.5.1.9
		-- 1.3.6.1.4.1.37950.1.1.5.12.3.2.5.1.9
		priSsidPreshareKeyS OBJECT-TYPE
			SYNTAX OCTET STRING
			MAX-ACCESS read-write
			STATUS current
			DESCRIPTION
				"Description."
			::= { priWifiSsidEntry 9 }

		
--          1.3.6.1.4.1.37950.1.1.5.12.3.2.5.1.10
-- 1.3.6.1.4.1.37950.1.1.5.12.3.2.5.1.10
-- 1.3.6.1.4.1.37950.1.1.5.12.3.2.5.1.10
-- 1.3.6.1.4.1.37950.1.1.5.12.3.2.5.1.10
-- 1.3.6.1.4.1.37950.1.1.5.12.3.2.5.1.10
-- 1.3.6.1.4.1.37950.1.1.5.12.3.2.5.1.10
-- 1.3.6.1.4.1.37950.1.1.5.12.3.2.5.1.10
-- 1.3.6.1.4.1.37950.1.1.5.12.3.2.5.1.10
-- 1.3.6.1.4.1.37950.1.1.5.12.3.2.5.1.10
		-- 1.3.6.1.4.1.37950.1.1.5.12.3.2.5.1.10
		priSsidWpaRekeyIntervalS OBJECT-TYPE
			SYNTAX INTEGER (0..4194303)
			MAX-ACCESS read-write
			STATUS current
			DESCRIPTION
				"Description."
			::= { priWifiSsidEntry 10 }

		
--          1.3.6.1.4.1.37950.1.1.5.12.3.2.5.1.11
-- 1.3.6.1.4.1.37950.1.1.5.12.3.2.5.1.11
-- 1.3.6.1.4.1.37950.1.1.5.12.3.2.5.1.11
-- 1.3.6.1.4.1.37950.1.1.5.12.3.2.5.1.11
-- 1.3.6.1.4.1.37950.1.1.5.12.3.2.5.1.11
-- 1.3.6.1.4.1.37950.1.1.5.12.3.2.5.1.11
-- 1.3.6.1.4.1.37950.1.1.5.12.3.2.5.1.11
-- 1.3.6.1.4.1.37950.1.1.5.12.3.2.5.1.11
-- 1.3.6.1.4.1.37950.1.1.5.12.3.2.5.1.11
		-- 1.3.6.1.4.1.37950.1.1.5.12.3.2.5.1.11
		priSsidRadiusServIpTypeS OBJECT-TYPE
			SYNTAX INTEGER
				{
				unknown(0),
				ipv4(1),
				ipv6(2),
				ipv4z(3),
				ipv6z(4),
				dns(16)
				}
			MAX-ACCESS read-write
			STATUS current
			DESCRIPTION
				"Description."
			::= { priWifiSsidEntry 11 }

		
--          1.3.6.1.4.1.37950.1.1.5.12.3.2.5.1.12
-- 1.3.6.1.4.1.37950.1.1.5.12.3.2.5.1.12
-- 1.3.6.1.4.1.37950.1.1.5.12.3.2.5.1.12
-- 1.3.6.1.4.1.37950.1.1.5.12.3.2.5.1.12
-- 1.3.6.1.4.1.37950.1.1.5.12.3.2.5.1.12
-- 1.3.6.1.4.1.37950.1.1.5.12.3.2.5.1.12
-- 1.3.6.1.4.1.37950.1.1.5.12.3.2.5.1.12
-- 1.3.6.1.4.1.37950.1.1.5.12.3.2.5.1.12
-- 1.3.6.1.4.1.37950.1.1.5.12.3.2.5.1.12
		-- 1.3.6.1.4.1.37950.1.1.5.12.3.2.5.1.12
		priSsidRadiusServIp OBJECT-TYPE
			SYNTAX OCTET STRING
			MAX-ACCESS read-write
			STATUS current
			DESCRIPTION
				"Description."
			::= { priWifiSsidEntry 12 }

		
--          1.3.6.1.4.1.37950.1.1.5.12.3.2.5.1.13
-- 1.3.6.1.4.1.37950.1.1.5.12.3.2.5.1.13
-- 1.3.6.1.4.1.37950.1.1.5.12.3.2.5.1.13
-- 1.3.6.1.4.1.37950.1.1.5.12.3.2.5.1.13
-- 1.3.6.1.4.1.37950.1.1.5.12.3.2.5.1.13
-- 1.3.6.1.4.1.37950.1.1.5.12.3.2.5.1.13
-- 1.3.6.1.4.1.37950.1.1.5.12.3.2.5.1.13
-- 1.3.6.1.4.1.37950.1.1.5.12.3.2.5.1.13
-- 1.3.6.1.4.1.37950.1.1.5.12.3.2.5.1.13
		-- 1.3.6.1.4.1.37950.1.1.5.12.3.2.5.1.13
		priSsidRadiusServIpPrefixLenS OBJECT-TYPE
			SYNTAX INTEGER (0..255)
			MAX-ACCESS read-write
			STATUS current
			DESCRIPTION
				"Description."
			::= { priWifiSsidEntry 13 }

		
--          1.3.6.1.4.1.37950.1.1.5.12.3.2.5.1.14
-- 1.3.6.1.4.1.37950.1.1.5.12.3.2.5.1.14
-- 1.3.6.1.4.1.37950.1.1.5.12.3.2.5.1.14
-- 1.3.6.1.4.1.37950.1.1.5.12.3.2.5.1.14
-- 1.3.6.1.4.1.37950.1.1.5.12.3.2.5.1.14
-- 1.3.6.1.4.1.37950.1.1.5.12.3.2.5.1.14
-- 1.3.6.1.4.1.37950.1.1.5.12.3.2.5.1.14
-- 1.3.6.1.4.1.37950.1.1.5.12.3.2.5.1.14
-- 1.3.6.1.4.1.37950.1.1.5.12.3.2.5.1.14
		-- 1.3.6.1.4.1.37950.1.1.5.12.3.2.5.1.14
		priSsidRadiusPortS OBJECT-TYPE
			SYNTAX INTEGER (0..65535)
			MAX-ACCESS read-write
			STATUS current
			DESCRIPTION
				"Description."
			::= { priWifiSsidEntry 14 }

		
--          1.3.6.1.4.1.37950.1.1.5.12.3.2.5.1.15
-- 1.3.6.1.4.1.37950.1.1.5.12.3.2.5.1.15
-- 1.3.6.1.4.1.37950.1.1.5.12.3.2.5.1.15
-- 1.3.6.1.4.1.37950.1.1.5.12.3.2.5.1.15
-- 1.3.6.1.4.1.37950.1.1.5.12.3.2.5.1.15
-- 1.3.6.1.4.1.37950.1.1.5.12.3.2.5.1.15
-- 1.3.6.1.4.1.37950.1.1.5.12.3.2.5.1.15
-- 1.3.6.1.4.1.37950.1.1.5.12.3.2.5.1.15
-- 1.3.6.1.4.1.37950.1.1.5.12.3.2.5.1.15
		-- 1.3.6.1.4.1.37950.1.1.5.12.3.2.5.1.15
		priSsidRadiusKeyS OBJECT-TYPE
			SYNTAX OCTET STRING (SIZE (0..32))
			MAX-ACCESS read-write
			STATUS current
			DESCRIPTION
				"Description."
			::= { priWifiSsidEntry 15 }

		
--          1.3.6.1.4.1.37950.1.1.5.12.3.2.5.1.16
-- 1.3.6.1.4.1.37950.1.1.5.12.3.2.5.1.16
-- 1.3.6.1.4.1.37950.1.1.5.12.3.2.5.1.16
-- 1.3.6.1.4.1.37950.1.1.5.12.3.2.5.1.16
-- 1.3.6.1.4.1.37950.1.1.5.12.3.2.5.1.16
-- 1.3.6.1.4.1.37950.1.1.5.12.3.2.5.1.16
-- 1.3.6.1.4.1.37950.1.1.5.12.3.2.5.1.16
-- 1.3.6.1.4.1.37950.1.1.5.12.3.2.5.1.16
-- 1.3.6.1.4.1.37950.1.1.5.12.3.2.5.1.16
		-- 1.3.6.1.4.1.37950.1.1.5.12.3.2.5.1.16
		priSsidWepEncryptionLevelS OBJECT-TYPE
			SYNTAX INTEGER
				{
				s64bit(1),
				s128bit(2)
				}
			MAX-ACCESS read-write
			STATUS current
			DESCRIPTION
				"Description."
			::= { priWifiSsidEntry 16 }

		
--          1.3.6.1.4.1.37950.1.1.5.12.3.2.5.1.17
-- 1.3.6.1.4.1.37950.1.1.5.12.3.2.5.1.17
-- 1.3.6.1.4.1.37950.1.1.5.12.3.2.5.1.17
-- 1.3.6.1.4.1.37950.1.1.5.12.3.2.5.1.17
-- 1.3.6.1.4.1.37950.1.1.5.12.3.2.5.1.17
-- 1.3.6.1.4.1.37950.1.1.5.12.3.2.5.1.17
-- 1.3.6.1.4.1.37950.1.1.5.12.3.2.5.1.17
-- 1.3.6.1.4.1.37950.1.1.5.12.3.2.5.1.17
-- 1.3.6.1.4.1.37950.1.1.5.12.3.2.5.1.17
		-- 1.3.6.1.4.1.37950.1.1.5.12.3.2.5.1.17
		priSsidWepKeyIndexS OBJECT-TYPE
			SYNTAX INTEGER (1..4)
			MAX-ACCESS read-write
			STATUS current
			DESCRIPTION
				"Description."
			::= { priWifiSsidEntry 17 }

		
--          1.3.6.1.4.1.37950.1.1.5.12.3.2.5.1.18
-- 1.3.6.1.4.1.37950.1.1.5.12.3.2.5.1.18
-- 1.3.6.1.4.1.37950.1.1.5.12.3.2.5.1.18
-- 1.3.6.1.4.1.37950.1.1.5.12.3.2.5.1.18
-- 1.3.6.1.4.1.37950.1.1.5.12.3.2.5.1.18
-- 1.3.6.1.4.1.37950.1.1.5.12.3.2.5.1.18
-- 1.3.6.1.4.1.37950.1.1.5.12.3.2.5.1.18
-- 1.3.6.1.4.1.37950.1.1.5.12.3.2.5.1.18
-- 1.3.6.1.4.1.37950.1.1.5.12.3.2.5.1.18
		-- 1.3.6.1.4.1.37950.1.1.5.12.3.2.5.1.18
		priSsidWepKey1S OBJECT-TYPE
			SYNTAX OCTET STRING
			MAX-ACCESS read-write
			STATUS current
			DESCRIPTION
				"Description."
			::= { priWifiSsidEntry 18 }

		
--          1.3.6.1.4.1.37950.1.1.5.12.3.2.5.1.19
-- 1.3.6.1.4.1.37950.1.1.5.12.3.2.5.1.19
-- 1.3.6.1.4.1.37950.1.1.5.12.3.2.5.1.19
-- 1.3.6.1.4.1.37950.1.1.5.12.3.2.5.1.19
-- 1.3.6.1.4.1.37950.1.1.5.12.3.2.5.1.19
-- 1.3.6.1.4.1.37950.1.1.5.12.3.2.5.1.19
-- 1.3.6.1.4.1.37950.1.1.5.12.3.2.5.1.19
-- 1.3.6.1.4.1.37950.1.1.5.12.3.2.5.1.19
-- 1.3.6.1.4.1.37950.1.1.5.12.3.2.5.1.19
		-- 1.3.6.1.4.1.37950.1.1.5.12.3.2.5.1.19
		priSsidWepKey2S OBJECT-TYPE
			SYNTAX OCTET STRING
			MAX-ACCESS read-write
			STATUS current
			DESCRIPTION
				"Description."
			::= { priWifiSsidEntry 19 }

		
--          1.3.6.1.4.1.37950.1.1.5.12.3.2.5.1.20
-- 1.3.6.1.4.1.37950.1.1.5.12.3.2.5.1.20
-- 1.3.6.1.4.1.37950.1.1.5.12.3.2.5.1.20
-- 1.3.6.1.4.1.37950.1.1.5.12.3.2.5.1.20
-- 1.3.6.1.4.1.37950.1.1.5.12.3.2.5.1.20
-- 1.3.6.1.4.1.37950.1.1.5.12.3.2.5.1.20
-- 1.3.6.1.4.1.37950.1.1.5.12.3.2.5.1.20
-- 1.3.6.1.4.1.37950.1.1.5.12.3.2.5.1.20
-- 1.3.6.1.4.1.37950.1.1.5.12.3.2.5.1.20
		-- 1.3.6.1.4.1.37950.1.1.5.12.3.2.5.1.20
		priSsidWepKey3S OBJECT-TYPE
			SYNTAX OCTET STRING
			MAX-ACCESS read-write
			STATUS current
			DESCRIPTION
				"Description."
			::= { priWifiSsidEntry 20 }

		
--          1.3.6.1.4.1.37950.1.1.5.12.3.2.5.1.21
-- 1.3.6.1.4.1.37950.1.1.5.12.3.2.5.1.21
-- 1.3.6.1.4.1.37950.1.1.5.12.3.2.5.1.21
-- 1.3.6.1.4.1.37950.1.1.5.12.3.2.5.1.21
-- 1.3.6.1.4.1.37950.1.1.5.12.3.2.5.1.21
-- 1.3.6.1.4.1.37950.1.1.5.12.3.2.5.1.21
-- 1.3.6.1.4.1.37950.1.1.5.12.3.2.5.1.21
-- 1.3.6.1.4.1.37950.1.1.5.12.3.2.5.1.21
-- 1.3.6.1.4.1.37950.1.1.5.12.3.2.5.1.21
		-- 1.3.6.1.4.1.37950.1.1.5.12.3.2.5.1.21
		priSsidWepKey4S OBJECT-TYPE
			SYNTAX OCTET STRING
			MAX-ACCESS read-write
			STATUS current
			DESCRIPTION
				"Description."
			::= { priWifiSsidEntry 21 }

		
--          1.3.6.1.4.1.37950.1.1.5.12.3.2.6
-- 1.3.6.1.4.1.37950.1.1.5.12.3.2.6
-- 1.3.6.1.4.1.37950.1.1.5.12.3.2.6
-- 1.3.6.1.4.1.37950.1.1.5.12.3.2.6
-- 1.3.6.1.4.1.37950.1.1.5.12.3.2.6
-- 1.3.6.1.4.1.37950.1.1.5.12.3.2.6
-- 1.3.6.1.4.1.37950.1.1.5.12.3.2.6
-- 1.3.6.1.4.1.37950.1.1.5.12.3.2.6
-- 1.3.6.1.4.1.37950.1.1.5.12.3.2.6
		-- 1.3.6.1.4.1.37950.1.1.5.12.3.2.6
		priWanConnTable OBJECT-TYPE
			SYNTAX SEQUENCE OF PriWanConnEntry
			MAX-ACCESS not-accessible
			STATUS current
			DESCRIPTION
				"Description."
			::= { onuPriGlobalInfo 6 }

		
--          1.3.6.1.4.1.37950.1.1.5.12.3.2.6.1
-- 1.3.6.1.4.1.37950.1.1.5.12.3.2.6.1
-- 1.3.6.1.4.1.37950.1.1.5.12.3.2.6.1
-- 1.3.6.1.4.1.37950.1.1.5.12.3.2.6.1
-- 1.3.6.1.4.1.37950.1.1.5.12.3.2.6.1
-- 1.3.6.1.4.1.37950.1.1.5.12.3.2.6.1
-- 1.3.6.1.4.1.37950.1.1.5.12.3.2.6.1
-- 1.3.6.1.4.1.37950.1.1.5.12.3.2.6.1
-- 1.3.6.1.4.1.37950.1.1.5.12.3.2.6.1
		-- 1.3.6.1.4.1.37950.1.1.5.12.3.2.6.1
		priWanConnEntry OBJECT-TYPE
			SYNTAX PriWanConnEntry
			MAX-ACCESS not-accessible
			STATUS current
			DESCRIPTION
				"Description."
			INDEX { priWanConnPonS, priWanConnOnuS, priWanConnIndexS }
			::= { priWanConnTable 1 }

		
		PriWanConnEntry ::=
			SEQUENCE { 
				priWanConnPonS
					INTEGER,
				priWanConnOnuS
					INTEGER,
				priWanConnIndexS
					Integer32,
				priWanConnBindLanS
					INTEGER,
				priWanConnBindSsidS
					INTEGER,
				priWanModeS
					INTEGER,
				priWanConnTypeS
					INTEGER,
				priWanConnVlanIdS
					INTEGER,
				priWanConnVlanCosS
					INTEGER,
				priWanConnNatEnableS
					INTEGER,
				priWanConnModeS
					INTEGER,
				priWanConnIpAddressS
					IpAddress,
				priWanConnIpMaskS
					IpAddress,
				priWanConnGatewayS
					IpAddress,
				priWanConnMasterDns
					IpAddress,
				priWanConnSlaveDns
					IpAddress,
				priWanConnPppoeProxyS
					INTEGER,
				priWanConnPppoeUsernameS
					OCTET STRING,
				priWanConnPppoePasswordS
					OCTET STRING,
				priWanConnPppoeSerName
					OCTET STRING,
				priWanConnPppoeModeS
					INTEGER,
				priWanConnQosEnableS
					INTEGER,
				priWanConnVlanModeS
					INTEGER,
				priWanConnTranslationEnableS
					INTEGER,
				priWanConnTranslationVlanS
					INTEGER,
				priWanConnTranslationCosS
					INTEGER,
				priWanConnQinqEnableS
					INTEGER,
				priWanConnQinqTpidS
					INTEGER,
				priWanConnSvlanIdS
					INTEGER,
				priWanConnSvlanCosS
					INTEGER,
				priWanConnName
					OCTET STRING,
				priWanConnStatus
					INTEGER,
				priWanConnMacAddr
					OCTET STRING,
				priWanConnRouteMtuS
					Integer32
			 }

--          1.3.6.1.4.1.37950.1.1.5.12.3.2.6.1.1
-- 1.3.6.1.4.1.37950.1.1.5.12.3.2.6.1.1
-- 1.3.6.1.4.1.37950.1.1.5.12.3.2.6.1.1
-- 1.3.6.1.4.1.37950.1.1.5.12.3.2.6.1.1
-- 1.3.6.1.4.1.37950.1.1.5.12.3.2.6.1.1
-- 1.3.6.1.4.1.37950.1.1.5.12.3.2.6.1.1
-- 1.3.6.1.4.1.37950.1.1.5.12.3.2.6.1.1
-- 1.3.6.1.4.1.37950.1.1.5.12.3.2.6.1.1
-- 1.3.6.1.4.1.37950.1.1.5.12.3.2.6.1.1
		-- 1.3.6.1.4.1.37950.1.1.5.12.3.2.6.1.1
		priWanConnPonS OBJECT-TYPE
			SYNTAX INTEGER (1..16)
			MAX-ACCESS read-write
			STATUS current
			DESCRIPTION
				"Description."
			::= { priWanConnEntry 1 }

		
--          1.3.6.1.4.1.37950.1.1.5.12.3.2.6.1.2
-- 1.3.6.1.4.1.37950.1.1.5.12.3.2.6.1.2
-- 1.3.6.1.4.1.37950.1.1.5.12.3.2.6.1.2
-- 1.3.6.1.4.1.37950.1.1.5.12.3.2.6.1.2
-- 1.3.6.1.4.1.37950.1.1.5.12.3.2.6.1.2
-- 1.3.6.1.4.1.37950.1.1.5.12.3.2.6.1.2
-- 1.3.6.1.4.1.37950.1.1.5.12.3.2.6.1.2
-- 1.3.6.1.4.1.37950.1.1.5.12.3.2.6.1.2
-- 1.3.6.1.4.1.37950.1.1.5.12.3.2.6.1.2
		-- 1.3.6.1.4.1.37950.1.1.5.12.3.2.6.1.2
		priWanConnOnuS OBJECT-TYPE
			SYNTAX INTEGER (1..65535)
			MAX-ACCESS read-write
			STATUS current
			DESCRIPTION
				"Description."
			::= { priWanConnEntry 2 }

		
--          1.3.6.1.4.1.37950.1.1.5.12.3.2.6.1.3
-- 1.3.6.1.4.1.37950.1.1.5.12.3.2.6.1.3
-- 1.3.6.1.4.1.37950.1.1.5.12.3.2.6.1.3
-- 1.3.6.1.4.1.37950.1.1.5.12.3.2.6.1.3
-- 1.3.6.1.4.1.37950.1.1.5.12.3.2.6.1.3
-- 1.3.6.1.4.1.37950.1.1.5.12.3.2.6.1.3
-- 1.3.6.1.4.1.37950.1.1.5.12.3.2.6.1.3
-- 1.3.6.1.4.1.37950.1.1.5.12.3.2.6.1.3
-- 1.3.6.1.4.1.37950.1.1.5.12.3.2.6.1.3
		-- 1.3.6.1.4.1.37950.1.1.5.12.3.2.6.1.3
		priWanConnIndexS OBJECT-TYPE
			SYNTAX Integer32 (1..8)
			MAX-ACCESS read-write
			STATUS current
			DESCRIPTION
				"Description."
			::= { priWanConnEntry 3 }

		
--          1.3.6.1.4.1.37950.1.1.5.12.3.2.6.1.4
-- 1.3.6.1.4.1.37950.1.1.5.12.3.2.6.1.4
-- 1.3.6.1.4.1.37950.1.1.5.12.3.2.6.1.4
-- 1.3.6.1.4.1.37950.1.1.5.12.3.2.6.1.4
-- 1.3.6.1.4.1.37950.1.1.5.12.3.2.6.1.4
-- 1.3.6.1.4.1.37950.1.1.5.12.3.2.6.1.4
-- 1.3.6.1.4.1.37950.1.1.5.12.3.2.6.1.4
-- 1.3.6.1.4.1.37950.1.1.5.12.3.2.6.1.4
-- 1.3.6.1.4.1.37950.1.1.5.12.3.2.6.1.4
		-- 1.3.6.1.4.1.37950.1.1.5.12.3.2.6.1.4
		priWanConnBindLanS OBJECT-TYPE
			SYNTAX INTEGER (0..15)
			MAX-ACCESS read-write
			STATUS current
			DESCRIPTION
				"Description."
			::= { priWanConnEntry 4 }

		
--          1.3.6.1.4.1.37950.1.1.5.12.3.2.6.1.5
-- 1.3.6.1.4.1.37950.1.1.5.12.3.2.6.1.5
-- 1.3.6.1.4.1.37950.1.1.5.12.3.2.6.1.5
-- 1.3.6.1.4.1.37950.1.1.5.12.3.2.6.1.5
-- 1.3.6.1.4.1.37950.1.1.5.12.3.2.6.1.5
-- 1.3.6.1.4.1.37950.1.1.5.12.3.2.6.1.5
-- 1.3.6.1.4.1.37950.1.1.5.12.3.2.6.1.5
-- 1.3.6.1.4.1.37950.1.1.5.12.3.2.6.1.5
-- 1.3.6.1.4.1.37950.1.1.5.12.3.2.6.1.5
		-- 1.3.6.1.4.1.37950.1.1.5.12.3.2.6.1.5
		priWanConnBindSsidS OBJECT-TYPE
			SYNTAX INTEGER (0..15)
			MAX-ACCESS read-write
			STATUS current
			DESCRIPTION
				"Description."
			::= { priWanConnEntry 5 }

		
--          1.3.6.1.4.1.37950.1.1.5.12.3.2.6.1.6
-- 1.3.6.1.4.1.37950.1.1.5.12.3.2.6.1.6
-- 1.3.6.1.4.1.37950.1.1.5.12.3.2.6.1.6
-- 1.3.6.1.4.1.37950.1.1.5.12.3.2.6.1.6
-- 1.3.6.1.4.1.37950.1.1.5.12.3.2.6.1.6
-- 1.3.6.1.4.1.37950.1.1.5.12.3.2.6.1.6
-- 1.3.6.1.4.1.37950.1.1.5.12.3.2.6.1.6
-- 1.3.6.1.4.1.37950.1.1.5.12.3.2.6.1.6
-- 1.3.6.1.4.1.37950.1.1.5.12.3.2.6.1.6
		-- 1.3.6.1.4.1.37950.1.1.5.12.3.2.6.1.6
		priWanModeS OBJECT-TYPE
			SYNTAX INTEGER
				{
				internet(0),
				multicast(1),
				tr069(2),
				tr069-internet(3),
				tr069-voip(4),
				voip-internet(5),
				tr069-voip-internet(6),
				other(100)
				}
			MAX-ACCESS read-write
			STATUS current
			DESCRIPTION
				"Description."
			::= { priWanConnEntry 6 }

		
--          1.3.6.1.4.1.37950.1.1.5.12.3.2.6.1.7
-- 1.3.6.1.4.1.37950.1.1.5.12.3.2.6.1.7
-- 1.3.6.1.4.1.37950.1.1.5.12.3.2.6.1.7
-- 1.3.6.1.4.1.37950.1.1.5.12.3.2.6.1.7
-- 1.3.6.1.4.1.37950.1.1.5.12.3.2.6.1.7
-- 1.3.6.1.4.1.37950.1.1.5.12.3.2.6.1.7
-- 1.3.6.1.4.1.37950.1.1.5.12.3.2.6.1.7
-- 1.3.6.1.4.1.37950.1.1.5.12.3.2.6.1.7
-- 1.3.6.1.4.1.37950.1.1.5.12.3.2.6.1.7
		-- 1.3.6.1.4.1.37950.1.1.5.12.3.2.6.1.7
		priWanConnTypeS OBJECT-TYPE
			SYNTAX INTEGER
				{
				bridge(0),
				route(1)
				}
			MAX-ACCESS read-write
			STATUS current
			DESCRIPTION
				"Description."
			::= { priWanConnEntry 7 }

		
--          1.3.6.1.4.1.37950.1.1.5.12.3.2.6.1.8
-- 1.3.6.1.4.1.37950.1.1.5.12.3.2.6.1.8
-- 1.3.6.1.4.1.37950.1.1.5.12.3.2.6.1.8
-- 1.3.6.1.4.1.37950.1.1.5.12.3.2.6.1.8
-- 1.3.6.1.4.1.37950.1.1.5.12.3.2.6.1.8
-- 1.3.6.1.4.1.37950.1.1.5.12.3.2.6.1.8
-- 1.3.6.1.4.1.37950.1.1.5.12.3.2.6.1.8
-- 1.3.6.1.4.1.37950.1.1.5.12.3.2.6.1.8
-- 1.3.6.1.4.1.37950.1.1.5.12.3.2.6.1.8
		-- 1.3.6.1.4.1.37950.1.1.5.12.3.2.6.1.8
		priWanConnVlanIdS OBJECT-TYPE
			SYNTAX INTEGER (0..4095)
			MAX-ACCESS read-write
			STATUS current
			DESCRIPTION
				"Description."
			::= { priWanConnEntry 8 }

		
--          1.3.6.1.4.1.37950.1.1.5.12.3.2.6.1.9
-- 1.3.6.1.4.1.37950.1.1.5.12.3.2.6.1.9
-- 1.3.6.1.4.1.37950.1.1.5.12.3.2.6.1.9
-- 1.3.6.1.4.1.37950.1.1.5.12.3.2.6.1.9
-- 1.3.6.1.4.1.37950.1.1.5.12.3.2.6.1.9
-- 1.3.6.1.4.1.37950.1.1.5.12.3.2.6.1.9
-- 1.3.6.1.4.1.37950.1.1.5.12.3.2.6.1.9
-- 1.3.6.1.4.1.37950.1.1.5.12.3.2.6.1.9
-- 1.3.6.1.4.1.37950.1.1.5.12.3.2.6.1.9
		-- 1.3.6.1.4.1.37950.1.1.5.12.3.2.6.1.9
		priWanConnVlanCosS OBJECT-TYPE
			SYNTAX INTEGER (0..7)
			MAX-ACCESS read-write
			STATUS current
			DESCRIPTION
				"Description."
			::= { priWanConnEntry 9 }

		
--          1.3.6.1.4.1.37950.1.1.5.12.3.2.6.1.10
-- 1.3.6.1.4.1.37950.1.1.5.12.3.2.6.1.10
-- 1.3.6.1.4.1.37950.1.1.5.12.3.2.6.1.10
-- 1.3.6.1.4.1.37950.1.1.5.12.3.2.6.1.10
-- 1.3.6.1.4.1.37950.1.1.5.12.3.2.6.1.10
-- 1.3.6.1.4.1.37950.1.1.5.12.3.2.6.1.10
-- 1.3.6.1.4.1.37950.1.1.5.12.3.2.6.1.10
-- 1.3.6.1.4.1.37950.1.1.5.12.3.2.6.1.10
-- 1.3.6.1.4.1.37950.1.1.5.12.3.2.6.1.10
		-- 1.3.6.1.4.1.37950.1.1.5.12.3.2.6.1.10
		priWanConnNatEnableS OBJECT-TYPE
			SYNTAX INTEGER
				{
				disable(0),
				enable(1)
				}
			MAX-ACCESS read-write
			STATUS current
			DESCRIPTION
				"Description."
			::= { priWanConnEntry 10 }

		
--          1.3.6.1.4.1.37950.1.1.5.12.3.2.6.1.11
-- 1.3.6.1.4.1.37950.1.1.5.12.3.2.6.1.11
-- 1.3.6.1.4.1.37950.1.1.5.12.3.2.6.1.11
-- 1.3.6.1.4.1.37950.1.1.5.12.3.2.6.1.11
-- 1.3.6.1.4.1.37950.1.1.5.12.3.2.6.1.11
-- 1.3.6.1.4.1.37950.1.1.5.12.3.2.6.1.11
-- 1.3.6.1.4.1.37950.1.1.5.12.3.2.6.1.11
-- 1.3.6.1.4.1.37950.1.1.5.12.3.2.6.1.11
-- 1.3.6.1.4.1.37950.1.1.5.12.3.2.6.1.11
		-- 1.3.6.1.4.1.37950.1.1.5.12.3.2.6.1.11
		priWanConnModeS OBJECT-TYPE
			SYNTAX INTEGER
				{
				dhcp(0),
				static(1),
				pppoe(2)
				}
			MAX-ACCESS read-write
			STATUS current
			DESCRIPTION
				"Description."
			::= { priWanConnEntry 11 }

		
--          1.3.6.1.4.1.37950.1.1.5.12.3.2.6.1.12
-- 1.3.6.1.4.1.37950.1.1.5.12.3.2.6.1.12
-- 1.3.6.1.4.1.37950.1.1.5.12.3.2.6.1.12
-- 1.3.6.1.4.1.37950.1.1.5.12.3.2.6.1.12
-- 1.3.6.1.4.1.37950.1.1.5.12.3.2.6.1.12
-- 1.3.6.1.4.1.37950.1.1.5.12.3.2.6.1.12
-- 1.3.6.1.4.1.37950.1.1.5.12.3.2.6.1.12
-- 1.3.6.1.4.1.37950.1.1.5.12.3.2.6.1.12
-- 1.3.6.1.4.1.37950.1.1.5.12.3.2.6.1.12
		-- 1.3.6.1.4.1.37950.1.1.5.12.3.2.6.1.12
		priWanConnIpAddressS OBJECT-TYPE
			SYNTAX IpAddress
			MAX-ACCESS read-write
			STATUS current
			DESCRIPTION
				"Description."
			::= { priWanConnEntry 12 }

		
--          1.3.6.1.4.1.37950.1.1.5.12.3.2.6.1.13
-- 1.3.6.1.4.1.37950.1.1.5.12.3.2.6.1.13
-- 1.3.6.1.4.1.37950.1.1.5.12.3.2.6.1.13
-- 1.3.6.1.4.1.37950.1.1.5.12.3.2.6.1.13
-- 1.3.6.1.4.1.37950.1.1.5.12.3.2.6.1.13
-- 1.3.6.1.4.1.37950.1.1.5.12.3.2.6.1.13
-- 1.3.6.1.4.1.37950.1.1.5.12.3.2.6.1.13
-- 1.3.6.1.4.1.37950.1.1.5.12.3.2.6.1.13
-- 1.3.6.1.4.1.37950.1.1.5.12.3.2.6.1.13
		-- 1.3.6.1.4.1.37950.1.1.5.12.3.2.6.1.13
		priWanConnIpMaskS OBJECT-TYPE
			SYNTAX IpAddress
			MAX-ACCESS read-write
			STATUS current
			DESCRIPTION
				"Description."
			::= { priWanConnEntry 13 }

		
--          1.3.6.1.4.1.37950.1.1.5.12.3.2.6.1.14
-- 1.3.6.1.4.1.37950.1.1.5.12.3.2.6.1.14
-- 1.3.6.1.4.1.37950.1.1.5.12.3.2.6.1.14
-- 1.3.6.1.4.1.37950.1.1.5.12.3.2.6.1.14
-- 1.3.6.1.4.1.37950.1.1.5.12.3.2.6.1.14
-- 1.3.6.1.4.1.37950.1.1.5.12.3.2.6.1.14
-- 1.3.6.1.4.1.37950.1.1.5.12.3.2.6.1.14
-- 1.3.6.1.4.1.37950.1.1.5.12.3.2.6.1.14
-- 1.3.6.1.4.1.37950.1.1.5.12.3.2.6.1.14
		-- 1.3.6.1.4.1.37950.1.1.5.12.3.2.6.1.14
		priWanConnGatewayS OBJECT-TYPE
			SYNTAX IpAddress
			MAX-ACCESS read-write
			STATUS current
			DESCRIPTION
				"Description."
			::= { priWanConnEntry 14 }

		
--          1.3.6.1.4.1.37950.1.1.5.12.3.2.6.1.15
-- 1.3.6.1.4.1.37950.1.1.5.12.3.2.6.1.15
-- 1.3.6.1.4.1.37950.1.1.5.12.3.2.6.1.15
-- 1.3.6.1.4.1.37950.1.1.5.12.3.2.6.1.15
-- 1.3.6.1.4.1.37950.1.1.5.12.3.2.6.1.15
-- 1.3.6.1.4.1.37950.1.1.5.12.3.2.6.1.15
-- 1.3.6.1.4.1.37950.1.1.5.12.3.2.6.1.15
-- 1.3.6.1.4.1.37950.1.1.5.12.3.2.6.1.15
-- 1.3.6.1.4.1.37950.1.1.5.12.3.2.6.1.15
		-- 1.3.6.1.4.1.37950.1.1.5.12.3.2.6.1.15
		priWanConnMasterDns OBJECT-TYPE
			SYNTAX IpAddress
			MAX-ACCESS read-write
			STATUS current
			DESCRIPTION
				"Description."
			::= { priWanConnEntry 15 }

		
--          1.3.6.1.4.1.37950.1.1.5.12.3.2.6.1.16
-- 1.3.6.1.4.1.37950.1.1.5.12.3.2.6.1.16
-- 1.3.6.1.4.1.37950.1.1.5.12.3.2.6.1.16
-- 1.3.6.1.4.1.37950.1.1.5.12.3.2.6.1.16
-- 1.3.6.1.4.1.37950.1.1.5.12.3.2.6.1.16
-- 1.3.6.1.4.1.37950.1.1.5.12.3.2.6.1.16
-- 1.3.6.1.4.1.37950.1.1.5.12.3.2.6.1.16
-- 1.3.6.1.4.1.37950.1.1.5.12.3.2.6.1.16
-- 1.3.6.1.4.1.37950.1.1.5.12.3.2.6.1.16
		-- 1.3.6.1.4.1.37950.1.1.5.12.3.2.6.1.16
		priWanConnSlaveDns OBJECT-TYPE
			SYNTAX IpAddress
			MAX-ACCESS read-write
			STATUS current
			DESCRIPTION
				"Description."
			::= { priWanConnEntry 16 }

		
--          1.3.6.1.4.1.37950.1.1.5.12.3.2.6.1.17
-- 1.3.6.1.4.1.37950.1.1.5.12.3.2.6.1.17
-- 1.3.6.1.4.1.37950.1.1.5.12.3.2.6.1.17
-- 1.3.6.1.4.1.37950.1.1.5.12.3.2.6.1.17
-- 1.3.6.1.4.1.37950.1.1.5.12.3.2.6.1.17
-- 1.3.6.1.4.1.37950.1.1.5.12.3.2.6.1.17
-- 1.3.6.1.4.1.37950.1.1.5.12.3.2.6.1.17
-- 1.3.6.1.4.1.37950.1.1.5.12.3.2.6.1.17
-- 1.3.6.1.4.1.37950.1.1.5.12.3.2.6.1.17
		-- 1.3.6.1.4.1.37950.1.1.5.12.3.2.6.1.17
		priWanConnPppoeProxyS OBJECT-TYPE
			SYNTAX INTEGER
				{
				disable(0),
				enable(1)
				}
			MAX-ACCESS read-write
			STATUS current
			DESCRIPTION
				"Description."
			::= { priWanConnEntry 17 }

		
--          1.3.6.1.4.1.37950.1.1.5.12.3.2.6.1.18
-- 1.3.6.1.4.1.37950.1.1.5.12.3.2.6.1.18
-- 1.3.6.1.4.1.37950.1.1.5.12.3.2.6.1.18
-- 1.3.6.1.4.1.37950.1.1.5.12.3.2.6.1.18
-- 1.3.6.1.4.1.37950.1.1.5.12.3.2.6.1.18
-- 1.3.6.1.4.1.37950.1.1.5.12.3.2.6.1.18
-- 1.3.6.1.4.1.37950.1.1.5.12.3.2.6.1.18
-- 1.3.6.1.4.1.37950.1.1.5.12.3.2.6.1.18
-- 1.3.6.1.4.1.37950.1.1.5.12.3.2.6.1.18
		-- 1.3.6.1.4.1.37950.1.1.5.12.3.2.6.1.18
		priWanConnPppoeUsernameS OBJECT-TYPE
			SYNTAX OCTET STRING
			MAX-ACCESS read-write
			STATUS current
			DESCRIPTION
				"Description."
			::= { priWanConnEntry 18 }

		
--          1.3.6.1.4.1.37950.1.1.5.12.3.2.6.1.19
-- 1.3.6.1.4.1.37950.1.1.5.12.3.2.6.1.19
-- 1.3.6.1.4.1.37950.1.1.5.12.3.2.6.1.19
-- 1.3.6.1.4.1.37950.1.1.5.12.3.2.6.1.19
-- 1.3.6.1.4.1.37950.1.1.5.12.3.2.6.1.19
-- 1.3.6.1.4.1.37950.1.1.5.12.3.2.6.1.19
-- 1.3.6.1.4.1.37950.1.1.5.12.3.2.6.1.19
-- 1.3.6.1.4.1.37950.1.1.5.12.3.2.6.1.19
-- 1.3.6.1.4.1.37950.1.1.5.12.3.2.6.1.19
		-- 1.3.6.1.4.1.37950.1.1.5.12.3.2.6.1.19
		priWanConnPppoePasswordS OBJECT-TYPE
			SYNTAX OCTET STRING
			MAX-ACCESS read-write
			STATUS current
			DESCRIPTION
				"Description."
			::= { priWanConnEntry 19 }

		
--          1.3.6.1.4.1.37950.1.1.5.12.3.2.6.1.20
-- 1.3.6.1.4.1.37950.1.1.5.12.3.2.6.1.20
-- 1.3.6.1.4.1.37950.1.1.5.12.3.2.6.1.20
-- 1.3.6.1.4.1.37950.1.1.5.12.3.2.6.1.20
-- 1.3.6.1.4.1.37950.1.1.5.12.3.2.6.1.20
-- 1.3.6.1.4.1.37950.1.1.5.12.3.2.6.1.20
-- 1.3.6.1.4.1.37950.1.1.5.12.3.2.6.1.20
-- 1.3.6.1.4.1.37950.1.1.5.12.3.2.6.1.20
-- 1.3.6.1.4.1.37950.1.1.5.12.3.2.6.1.20
		-- 1.3.6.1.4.1.37950.1.1.5.12.3.2.6.1.20
		priWanConnPppoeSerName OBJECT-TYPE
			SYNTAX OCTET STRING
			MAX-ACCESS read-write
			STATUS current
			DESCRIPTION
				"Description."
			::= { priWanConnEntry 20 }

		
--          1.3.6.1.4.1.37950.1.1.5.12.3.2.6.1.21
-- 1.3.6.1.4.1.37950.1.1.5.12.3.2.6.1.21
-- 1.3.6.1.4.1.37950.1.1.5.12.3.2.6.1.21
-- 1.3.6.1.4.1.37950.1.1.5.12.3.2.6.1.21
-- 1.3.6.1.4.1.37950.1.1.5.12.3.2.6.1.21
-- 1.3.6.1.4.1.37950.1.1.5.12.3.2.6.1.21
-- 1.3.6.1.4.1.37950.1.1.5.12.3.2.6.1.21
-- 1.3.6.1.4.1.37950.1.1.5.12.3.2.6.1.21
-- 1.3.6.1.4.1.37950.1.1.5.12.3.2.6.1.21
		-- 1.3.6.1.4.1.37950.1.1.5.12.3.2.6.1.21
		priWanConnPppoeModeS OBJECT-TYPE
			SYNTAX INTEGER
				{
				autoConnect(0),
				connectWhenPayload(1)
				}
			MAX-ACCESS read-write
			STATUS current
			DESCRIPTION
				"Description."
			::= { priWanConnEntry 21 }

		
--          1.3.6.1.4.1.37950.1.1.5.12.3.2.6.1.22
-- 1.3.6.1.4.1.37950.1.1.5.12.3.2.6.1.22
-- 1.3.6.1.4.1.37950.1.1.5.12.3.2.6.1.22
-- 1.3.6.1.4.1.37950.1.1.5.12.3.2.6.1.22
-- 1.3.6.1.4.1.37950.1.1.5.12.3.2.6.1.22
-- 1.3.6.1.4.1.37950.1.1.5.12.3.2.6.1.22
-- 1.3.6.1.4.1.37950.1.1.5.12.3.2.6.1.22
-- 1.3.6.1.4.1.37950.1.1.5.12.3.2.6.1.22
-- 1.3.6.1.4.1.37950.1.1.5.12.3.2.6.1.22
		-- 1.3.6.1.4.1.37950.1.1.5.12.3.2.6.1.22
		priWanConnQosEnableS OBJECT-TYPE
			SYNTAX INTEGER
				{
				disable(0),
				enable(1)
				}
			MAX-ACCESS read-write
			STATUS current
			DESCRIPTION
				"Description."
			::= { priWanConnEntry 22 }

		
--          1.3.6.1.4.1.37950.1.1.5.12.3.2.6.1.23
-- 1.3.6.1.4.1.37950.1.1.5.12.3.2.6.1.23
-- 1.3.6.1.4.1.37950.1.1.5.12.3.2.6.1.23
-- 1.3.6.1.4.1.37950.1.1.5.12.3.2.6.1.23
-- 1.3.6.1.4.1.37950.1.1.5.12.3.2.6.1.23
-- 1.3.6.1.4.1.37950.1.1.5.12.3.2.6.1.23
-- 1.3.6.1.4.1.37950.1.1.5.12.3.2.6.1.23
-- 1.3.6.1.4.1.37950.1.1.5.12.3.2.6.1.23
-- 1.3.6.1.4.1.37950.1.1.5.12.3.2.6.1.23
		-- 1.3.6.1.4.1.37950.1.1.5.12.3.2.6.1.23
		priWanConnVlanModeS OBJECT-TYPE
			SYNTAX INTEGER
				{
				disable(0),
				tag(1),
				transparent(2)
				}
			MAX-ACCESS read-write
			STATUS current
			DESCRIPTION
				"Description."
			::= { priWanConnEntry 23 }

		
--          1.3.6.1.4.1.37950.1.1.5.12.3.2.6.1.24
-- 1.3.6.1.4.1.37950.1.1.5.12.3.2.6.1.24
-- 1.3.6.1.4.1.37950.1.1.5.12.3.2.6.1.24
-- 1.3.6.1.4.1.37950.1.1.5.12.3.2.6.1.24
-- 1.3.6.1.4.1.37950.1.1.5.12.3.2.6.1.24
-- 1.3.6.1.4.1.37950.1.1.5.12.3.2.6.1.24
-- 1.3.6.1.4.1.37950.1.1.5.12.3.2.6.1.24
-- 1.3.6.1.4.1.37950.1.1.5.12.3.2.6.1.24
-- 1.3.6.1.4.1.37950.1.1.5.12.3.2.6.1.24
		-- 1.3.6.1.4.1.37950.1.1.5.12.3.2.6.1.24
		priWanConnTranslationEnableS OBJECT-TYPE
			SYNTAX INTEGER
				{
				disable(0),
				enable(1)
				}
			MAX-ACCESS read-write
			STATUS current
			DESCRIPTION
				"Description."
			::= { priWanConnEntry 24 }

		
--          1.3.6.1.4.1.37950.1.1.5.12.3.2.6.1.25
-- 1.3.6.1.4.1.37950.1.1.5.12.3.2.6.1.25
-- 1.3.6.1.4.1.37950.1.1.5.12.3.2.6.1.25
-- 1.3.6.1.4.1.37950.1.1.5.12.3.2.6.1.25
-- 1.3.6.1.4.1.37950.1.1.5.12.3.2.6.1.25
-- 1.3.6.1.4.1.37950.1.1.5.12.3.2.6.1.25
-- 1.3.6.1.4.1.37950.1.1.5.12.3.2.6.1.25
-- 1.3.6.1.4.1.37950.1.1.5.12.3.2.6.1.25
-- 1.3.6.1.4.1.37950.1.1.5.12.3.2.6.1.25
		-- 1.3.6.1.4.1.37950.1.1.5.12.3.2.6.1.25
		priWanConnTranslationVlanS OBJECT-TYPE
			SYNTAX INTEGER (0..4095)
			MAX-ACCESS read-write
			STATUS current
			DESCRIPTION
				"Description."
			::= { priWanConnEntry 25 }

		
--          1.3.6.1.4.1.37950.1.1.5.12.3.2.6.1.26
-- 1.3.6.1.4.1.37950.1.1.5.12.3.2.6.1.26
-- 1.3.6.1.4.1.37950.1.1.5.12.3.2.6.1.26
-- 1.3.6.1.4.1.37950.1.1.5.12.3.2.6.1.26
-- 1.3.6.1.4.1.37950.1.1.5.12.3.2.6.1.26
-- 1.3.6.1.4.1.37950.1.1.5.12.3.2.6.1.26
-- 1.3.6.1.4.1.37950.1.1.5.12.3.2.6.1.26
-- 1.3.6.1.4.1.37950.1.1.5.12.3.2.6.1.26
-- 1.3.6.1.4.1.37950.1.1.5.12.3.2.6.1.26
		-- 1.3.6.1.4.1.37950.1.1.5.12.3.2.6.1.26
		priWanConnTranslationCosS OBJECT-TYPE
			SYNTAX INTEGER (0..7)
			MAX-ACCESS read-write
			STATUS current
			DESCRIPTION
				"Description."
			::= { priWanConnEntry 26 }

		
--          1.3.6.1.4.1.37950.1.1.5.12.3.2.6.1.27
-- 1.3.6.1.4.1.37950.1.1.5.12.3.2.6.1.27
-- 1.3.6.1.4.1.37950.1.1.5.12.3.2.6.1.27
-- 1.3.6.1.4.1.37950.1.1.5.12.3.2.6.1.27
-- 1.3.6.1.4.1.37950.1.1.5.12.3.2.6.1.27
-- 1.3.6.1.4.1.37950.1.1.5.12.3.2.6.1.27
-- 1.3.6.1.4.1.37950.1.1.5.12.3.2.6.1.27
-- 1.3.6.1.4.1.37950.1.1.5.12.3.2.6.1.27
-- 1.3.6.1.4.1.37950.1.1.5.12.3.2.6.1.27
		-- 1.3.6.1.4.1.37950.1.1.5.12.3.2.6.1.27
		priWanConnQinqEnableS OBJECT-TYPE
			SYNTAX INTEGER
				{
				disable(0),
				enable(1)
				}
			MAX-ACCESS read-write
			STATUS current
			DESCRIPTION
				"Description."
			::= { priWanConnEntry 27 }

		
--          1.3.6.1.4.1.37950.1.1.5.12.3.2.6.1.28
-- 1.3.6.1.4.1.37950.1.1.5.12.3.2.6.1.28
-- 1.3.6.1.4.1.37950.1.1.5.12.3.2.6.1.28
-- 1.3.6.1.4.1.37950.1.1.5.12.3.2.6.1.28
-- 1.3.6.1.4.1.37950.1.1.5.12.3.2.6.1.28
-- 1.3.6.1.4.1.37950.1.1.5.12.3.2.6.1.28
-- 1.3.6.1.4.1.37950.1.1.5.12.3.2.6.1.28
-- 1.3.6.1.4.1.37950.1.1.5.12.3.2.6.1.28
-- 1.3.6.1.4.1.37950.1.1.5.12.3.2.6.1.28
		-- 1.3.6.1.4.1.37950.1.1.5.12.3.2.6.1.28
		priWanConnQinqTpidS OBJECT-TYPE
			SYNTAX INTEGER (0..65534)
			MAX-ACCESS read-write
			STATUS current
			DESCRIPTION
				"Description."
			::= { priWanConnEntry 28 }

		
--          1.3.6.1.4.1.37950.1.1.5.12.3.2.6.1.29
-- 1.3.6.1.4.1.37950.1.1.5.12.3.2.6.1.29
-- 1.3.6.1.4.1.37950.1.1.5.12.3.2.6.1.29
-- 1.3.6.1.4.1.37950.1.1.5.12.3.2.6.1.29
-- 1.3.6.1.4.1.37950.1.1.5.12.3.2.6.1.29
-- 1.3.6.1.4.1.37950.1.1.5.12.3.2.6.1.29
-- 1.3.6.1.4.1.37950.1.1.5.12.3.2.6.1.29
-- 1.3.6.1.4.1.37950.1.1.5.12.3.2.6.1.29
-- 1.3.6.1.4.1.37950.1.1.5.12.3.2.6.1.29
		-- 1.3.6.1.4.1.37950.1.1.5.12.3.2.6.1.29
		priWanConnSvlanIdS OBJECT-TYPE
			SYNTAX INTEGER (0..4095)
			MAX-ACCESS read-write
			STATUS current
			DESCRIPTION
				"Description."
			::= { priWanConnEntry 29 }

		
--          1.3.6.1.4.1.37950.1.1.5.12.3.2.6.1.30
-- 1.3.6.1.4.1.37950.1.1.5.12.3.2.6.1.30
-- 1.3.6.1.4.1.37950.1.1.5.12.3.2.6.1.30
-- 1.3.6.1.4.1.37950.1.1.5.12.3.2.6.1.30
-- 1.3.6.1.4.1.37950.1.1.5.12.3.2.6.1.30
-- 1.3.6.1.4.1.37950.1.1.5.12.3.2.6.1.30
-- 1.3.6.1.4.1.37950.1.1.5.12.3.2.6.1.30
-- 1.3.6.1.4.1.37950.1.1.5.12.3.2.6.1.30
-- 1.3.6.1.4.1.37950.1.1.5.12.3.2.6.1.30
		-- 1.3.6.1.4.1.37950.1.1.5.12.3.2.6.1.30
		priWanConnSvlanCosS OBJECT-TYPE
			SYNTAX INTEGER (0..7)
			MAX-ACCESS read-write
			STATUS current
			DESCRIPTION
				"Description."
			::= { priWanConnEntry 30 }

		
--          1.3.6.1.4.1.37950.1.1.5.12.3.2.6.1.31
-- 1.3.6.1.4.1.37950.1.1.5.12.3.2.6.1.31
-- 1.3.6.1.4.1.37950.1.1.5.12.3.2.6.1.31
-- 1.3.6.1.4.1.37950.1.1.5.12.3.2.6.1.31
-- 1.3.6.1.4.1.37950.1.1.5.12.3.2.6.1.31
-- 1.3.6.1.4.1.37950.1.1.5.12.3.2.6.1.31
-- 1.3.6.1.4.1.37950.1.1.5.12.3.2.6.1.31
-- 1.3.6.1.4.1.37950.1.1.5.12.3.2.6.1.31
-- 1.3.6.1.4.1.37950.1.1.5.12.3.2.6.1.31
		-- 1.3.6.1.4.1.37950.1.1.5.12.3.2.6.1.31
		priWanConnName OBJECT-TYPE
			SYNTAX OCTET STRING
			MAX-ACCESS read-write
			STATUS current
			DESCRIPTION
				"Description."
			::= { priWanConnEntry 31 }

		
--          1.3.6.1.4.1.37950.1.1.5.12.3.2.6.1.32
-- 1.3.6.1.4.1.37950.1.1.5.12.3.2.6.1.32
-- 1.3.6.1.4.1.37950.1.1.5.12.3.2.6.1.32
-- 1.3.6.1.4.1.37950.1.1.5.12.3.2.6.1.32
-- 1.3.6.1.4.1.37950.1.1.5.12.3.2.6.1.32
-- 1.3.6.1.4.1.37950.1.1.5.12.3.2.6.1.32
-- 1.3.6.1.4.1.37950.1.1.5.12.3.2.6.1.32
-- 1.3.6.1.4.1.37950.1.1.5.12.3.2.6.1.32
-- 1.3.6.1.4.1.37950.1.1.5.12.3.2.6.1.32
		-- 1.3.6.1.4.1.37950.1.1.5.12.3.2.6.1.32
		priWanConnStatus OBJECT-TYPE
			SYNTAX INTEGER
				{
				disconnected(0),
				connected(1)
				}
			MAX-ACCESS read-write
			STATUS current
			DESCRIPTION
				"Description."
			::= { priWanConnEntry 32 }

		
--         1.3.6.1.4.1.37950.1.1.5.12.3.2.6.1.33
-- 1.3.6.1.4.1.37950.1.1.5.12.3.2.6.1.33
-- 1.3.6.1.4.1.37950.1.1.5.12.3.2.6.1.33
-- 1.3.6.1.4.1.37950.1.1.5.12.3.2.6.1.33
-- 1.3.6.1.4.1.37950.1.1.5.12.3.2.6.1.33
-- 1.3.6.1.4.1.37950.1.1.5.12.3.2.6.1.33
-- 1.3.6.1.4.1.37950.1.1.5.12.3.2.6.1.33
-- 1.3.6.1.4.1.37950.1.1.5.12.3.2.6.1.33
		-- 1.3.6.1.4.1.37950.1.1.5.12.3.2.6.1.33
		priWanConnMacAddr OBJECT-TYPE
			SYNTAX OCTET STRING
			MAX-ACCESS read-write
			STATUS current
			DESCRIPTION
				"Description."
			::= { priWanConnEntry 33 }

		
--          1.3.6.1.4.1.37950.1.1.5.12.3.2.6.1.33
-- 1.3.6.1.4.1.37950.1.1.5.12.3.2.6.1.34
-- 1.3.6.1.4.1.37950.1.1.5.12.3.2.6.1.34
-- 1.3.6.1.4.1.37950.1.1.5.12.3.2.6.1.34
-- 1.3.6.1.4.1.37950.1.1.5.12.3.2.6.1.34
-- 1.3.6.1.4.1.37950.1.1.5.12.3.2.6.1.34
-- 1.3.6.1.4.1.37950.1.1.5.12.3.2.6.1.34
-- 1.3.6.1.4.1.37950.1.1.5.12.3.2.6.1.34
-- 1.3.6.1.4.1.37950.1.1.5.12.3.2.6.1.34
		-- 1.3.6.1.4.1.37950.1.1.5.12.3.2.6.1.34
		priWanConnRouteMtuS OBJECT-TYPE
			SYNTAX Integer32 (0 | 576..1500)
			MAX-ACCESS read-write
			STATUS current
			DESCRIPTION
				"Description."
			::= { priWanConnEntry 34 }

		
--         1.3.6.1.4.1.37950.1.1.5.12.3.2.7
-- 1.3.6.1.4.1.37950.1.1.5.12.3.2.7
-- 1.3.6.1.4.1.37950.1.1.5.12.3.2.7
-- 1.3.6.1.4.1.37950.1.1.5.12.3.2.7
-- 1.3.6.1.4.1.37950.1.1.5.12.3.2.7
-- 1.3.6.1.4.1.37950.1.1.5.12.3.2.7
-- 1.3.6.1.4.1.37950.1.1.5.12.3.2.7
-- 1.3.6.1.4.1.37950.1.1.5.12.3.2.7
		-- 1.3.6.1.4.1.37950.1.1.5.12.3.2.7
		priPortIsolateTable OBJECT-TYPE
			SYNTAX SEQUENCE OF PriPortIsolateEntry
			MAX-ACCESS not-accessible
			STATUS current
			DESCRIPTION
				"Description."
			::= { onuPriGlobalInfo 7 }

		
--          1.3.6.1.4.1.37950.1.1.5.12.3.2.7.1
-- 1.3.6.1.4.1.37950.1.1.5.12.3.2.7.1
-- 1.3.6.1.4.1.37950.1.1.5.12.3.2.7.1
-- 1.3.6.1.4.1.37950.1.1.5.12.3.2.7.1
-- 1.3.6.1.4.1.37950.1.1.5.12.3.2.7.1
-- 1.3.6.1.4.1.37950.1.1.5.12.3.2.7.1
-- 1.3.6.1.4.1.37950.1.1.5.12.3.2.7.1
-- 1.3.6.1.4.1.37950.1.1.5.12.3.2.7.1
-- 1.3.6.1.4.1.37950.1.1.5.12.3.2.7.1
		-- 1.3.6.1.4.1.37950.1.1.5.12.3.2.7.1
		priPortIsolateEntry OBJECT-TYPE
			SYNTAX PriPortIsolateEntry
			MAX-ACCESS not-accessible
			STATUS current
			DESCRIPTION
				"Description."
			INDEX { priPortIsolatePonS, priPortIsolateOnuS }
			::= { priPortIsolateTable 1 }

		
		PriPortIsolateEntry ::=
			SEQUENCE { 
				priPortIsolatePonS
					INTEGER,
				priPortIsolateOnuS
					INTEGER,
				priPortIsolateS
					INTEGER
			 }

--          1.3.6.1.4.1.37950.1.1.5.12.3.2.7.1.1
-- 1.3.6.1.4.1.37950.1.1.5.12.3.2.7.1.1
-- 1.3.6.1.4.1.37950.1.1.5.12.3.2.7.1.1
-- 1.3.6.1.4.1.37950.1.1.5.12.3.2.7.1.1
-- 1.3.6.1.4.1.37950.1.1.5.12.3.2.7.1.1
-- 1.3.6.1.4.1.37950.1.1.5.12.3.2.7.1.1
-- 1.3.6.1.4.1.37950.1.1.5.12.3.2.7.1.1
-- 1.3.6.1.4.1.37950.1.1.5.12.3.2.7.1.1
-- 1.3.6.1.4.1.37950.1.1.5.12.3.2.7.1.1
		-- 1.3.6.1.4.1.37950.1.1.5.12.3.2.7.1.1
		priPortIsolatePonS OBJECT-TYPE
			SYNTAX INTEGER (1..16)
			MAX-ACCESS read-write
			STATUS current
			DESCRIPTION
				"Description."
			::= { priPortIsolateEntry 1 }

		
--          1.3.6.1.4.1.37950.1.1.5.12.3.2.7.1.2
-- 1.3.6.1.4.1.37950.1.1.5.12.3.2.7.1.2
-- 1.3.6.1.4.1.37950.1.1.5.12.3.2.7.1.2
-- 1.3.6.1.4.1.37950.1.1.5.12.3.2.7.1.2
-- 1.3.6.1.4.1.37950.1.1.5.12.3.2.7.1.2
-- 1.3.6.1.4.1.37950.1.1.5.12.3.2.7.1.2
-- 1.3.6.1.4.1.37950.1.1.5.12.3.2.7.1.2
-- 1.3.6.1.4.1.37950.1.1.5.12.3.2.7.1.2
-- 1.3.6.1.4.1.37950.1.1.5.12.3.2.7.1.2
		-- 1.3.6.1.4.1.37950.1.1.5.12.3.2.7.1.2
		priPortIsolateOnuS OBJECT-TYPE
			SYNTAX INTEGER (1..65535)
			MAX-ACCESS read-write
			STATUS current
			DESCRIPTION
				"Description."
			::= { priPortIsolateEntry 2 }

		
--          1.3.6.1.4.1.37950.1.1.5.12.3.2.7.1.3
-- 1.3.6.1.4.1.37950.1.1.5.12.3.2.7.1.3
-- 1.3.6.1.4.1.37950.1.1.5.12.3.2.7.1.3
-- 1.3.6.1.4.1.37950.1.1.5.12.3.2.7.1.3
-- 1.3.6.1.4.1.37950.1.1.5.12.3.2.7.1.3
-- 1.3.6.1.4.1.37950.1.1.5.12.3.2.7.1.3
-- 1.3.6.1.4.1.37950.1.1.5.12.3.2.7.1.3
-- 1.3.6.1.4.1.37950.1.1.5.12.3.2.7.1.3
-- 1.3.6.1.4.1.37950.1.1.5.12.3.2.7.1.3
		-- 1.3.6.1.4.1.37950.1.1.5.12.3.2.7.1.3
		priPortIsolateS OBJECT-TYPE
			SYNTAX INTEGER
				{
				disable(0),
				enable(1)
				}
			MAX-ACCESS read-write
			STATUS current
			DESCRIPTION
				"Description."
			::= { priPortIsolateEntry 3 }

		
--          1.3.6.1.4.1.37950.1.1.5.12.3.2.8
-- 1.3.6.1.4.1.37950.1.1.5.12.3.2.8
-- 1.3.6.1.4.1.37950.1.1.5.12.3.2.8
-- 1.3.6.1.4.1.37950.1.1.5.12.3.2.8
-- 1.3.6.1.4.1.37950.1.1.5.12.3.2.8
-- 1.3.6.1.4.1.37950.1.1.5.12.3.2.8
-- 1.3.6.1.4.1.37950.1.1.5.12.3.2.8
-- 1.3.6.1.4.1.37950.1.1.5.12.3.2.8
-- 1.3.6.1.4.1.37950.1.1.5.12.3.2.8
		-- 1.3.6.1.4.1.37950.1.1.5.12.3.2.8
		priVoipTimerTable OBJECT-TYPE
			SYNTAX SEQUENCE OF PriVoipTimerEntry
			MAX-ACCESS not-accessible
			STATUS current
			DESCRIPTION
				"Description."
			::= { onuPriGlobalInfo 8 }

		
--          1.3.6.1.4.1.37950.1.1.5.12.3.2.8.1
-- 1.3.6.1.4.1.37950.1.1.5.12.3.2.8.1
-- 1.3.6.1.4.1.37950.1.1.5.12.3.2.8.1
-- 1.3.6.1.4.1.37950.1.1.5.12.3.2.8.1
-- 1.3.6.1.4.1.37950.1.1.5.12.3.2.8.1
-- 1.3.6.1.4.1.37950.1.1.5.12.3.2.8.1
-- 1.3.6.1.4.1.37950.1.1.5.12.3.2.8.1
-- 1.3.6.1.4.1.37950.1.1.5.12.3.2.8.1
-- 1.3.6.1.4.1.37950.1.1.5.12.3.2.8.1
		-- 1.3.6.1.4.1.37950.1.1.5.12.3.2.8.1
		priVoipTimerEntry OBJECT-TYPE
			SYNTAX PriVoipTimerEntry
			MAX-ACCESS not-accessible
			STATUS current
			DESCRIPTION
				"Description."
			INDEX { priVoipTimerPon, priVoipTimerOnu }
			::= { priVoipTimerTable 1 }

		
		PriVoipTimerEntry ::=
			SEQUENCE { 
				priVoipTimerPon
					Integer32,
				priVoipTimerOnu
					Integer32,
				priVoipTimerWaitTimer
					Integer32,
				priVoipTimerStartTimer
					Integer32,
				priVoipTimerLongTimer
					Integer32,
				priVoipTimerShortTimer
					Integer32,
				priVoipTimerDigitNotify
					INTEGER
			 }

--          1.3.6.1.4.1.37950.1.1.5.12.3.2.8.1.1
-- 1.3.6.1.4.1.37950.1.1.5.12.3.2.8.1.1
-- 1.3.6.1.4.1.37950.1.1.5.12.3.2.8.1.1
-- 1.3.6.1.4.1.37950.1.1.5.12.3.2.8.1.1
-- 1.3.6.1.4.1.37950.1.1.5.12.3.2.8.1.1
-- 1.3.6.1.4.1.37950.1.1.5.12.3.2.8.1.1
-- 1.3.6.1.4.1.37950.1.1.5.12.3.2.8.1.1
-- 1.3.6.1.4.1.37950.1.1.5.12.3.2.8.1.1
-- 1.3.6.1.4.1.37950.1.1.5.12.3.2.8.1.1
		-- 1.3.6.1.4.1.37950.1.1.5.12.3.2.8.1.1
		priVoipTimerPon OBJECT-TYPE
			SYNTAX Integer32 (1..16)
			MAX-ACCESS read-write
			STATUS current
			DESCRIPTION
				"Description."
			::= { priVoipTimerEntry 1 }

		
--          1.3.6.1.4.1.37950.1.1.5.12.3.2.8.1.2
-- 1.3.6.1.4.1.37950.1.1.5.12.3.2.8.1.2
-- 1.3.6.1.4.1.37950.1.1.5.12.3.2.8.1.2
-- 1.3.6.1.4.1.37950.1.1.5.12.3.2.8.1.2
-- 1.3.6.1.4.1.37950.1.1.5.12.3.2.8.1.2
-- 1.3.6.1.4.1.37950.1.1.5.12.3.2.8.1.2
-- 1.3.6.1.4.1.37950.1.1.5.12.3.2.8.1.2
-- 1.3.6.1.4.1.37950.1.1.5.12.3.2.8.1.2
-- 1.3.6.1.4.1.37950.1.1.5.12.3.2.8.1.2
		-- 1.3.6.1.4.1.37950.1.1.5.12.3.2.8.1.2
		priVoipTimerOnu OBJECT-TYPE
			SYNTAX Integer32 (1..65535)
			MAX-ACCESS read-write
			STATUS current
			DESCRIPTION
				"Description."
			::= { priVoipTimerEntry 2 }

		
--          1.3.6.1.4.1.37950.1.1.5.12.3.2.8.1.3
-- 1.3.6.1.4.1.37950.1.1.5.12.3.2.8.1.3
-- 1.3.6.1.4.1.37950.1.1.5.12.3.2.8.1.3
-- 1.3.6.1.4.1.37950.1.1.5.12.3.2.8.1.3
-- 1.3.6.1.4.1.37950.1.1.5.12.3.2.8.1.3
-- 1.3.6.1.4.1.37950.1.1.5.12.3.2.8.1.3
-- 1.3.6.1.4.1.37950.1.1.5.12.3.2.8.1.3
-- 1.3.6.1.4.1.37950.1.1.5.12.3.2.8.1.3
-- 1.3.6.1.4.1.37950.1.1.5.12.3.2.8.1.3
		-- 1.3.6.1.4.1.37950.1.1.5.12.3.2.8.1.3
		priVoipTimerWaitTimer OBJECT-TYPE
			SYNTAX Integer32 (0..254)
			MAX-ACCESS read-write
			STATUS current
			DESCRIPTION
				"Description."
			::= { priVoipTimerEntry 3 }

		
--          1.3.6.1.4.1.37950.1.1.5.12.3.2.8.1.4
-- 1.3.6.1.4.1.37950.1.1.5.12.3.2.8.1.4
-- 1.3.6.1.4.1.37950.1.1.5.12.3.2.8.1.4
-- 1.3.6.1.4.1.37950.1.1.5.12.3.2.8.1.4
-- 1.3.6.1.4.1.37950.1.1.5.12.3.2.8.1.4
-- 1.3.6.1.4.1.37950.1.1.5.12.3.2.8.1.4
-- 1.3.6.1.4.1.37950.1.1.5.12.3.2.8.1.4
-- 1.3.6.1.4.1.37950.1.1.5.12.3.2.8.1.4
-- 1.3.6.1.4.1.37950.1.1.5.12.3.2.8.1.4
		-- 1.3.6.1.4.1.37950.1.1.5.12.3.2.8.1.4
		priVoipTimerStartTimer OBJECT-TYPE
			SYNTAX Integer32 (1..65535)
			MAX-ACCESS read-write
			STATUS current
			DESCRIPTION
				"Description."
			::= { priVoipTimerEntry 4 }

		
--          1.3.6.1.4.1.37950.1.1.5.12.3.2.8.1.5
-- 1.3.6.1.4.1.37950.1.1.5.12.3.2.8.1.5
-- 1.3.6.1.4.1.37950.1.1.5.12.3.2.8.1.5
-- 1.3.6.1.4.1.37950.1.1.5.12.3.2.8.1.5
-- 1.3.6.1.4.1.37950.1.1.5.12.3.2.8.1.5
-- 1.3.6.1.4.1.37950.1.1.5.12.3.2.8.1.5
-- 1.3.6.1.4.1.37950.1.1.5.12.3.2.8.1.5
-- 1.3.6.1.4.1.37950.1.1.5.12.3.2.8.1.5
-- 1.3.6.1.4.1.37950.1.1.5.12.3.2.8.1.5
		-- 1.3.6.1.4.1.37950.1.1.5.12.3.2.8.1.5
		priVoipTimerLongTimer OBJECT-TYPE
			SYNTAX Integer32 (1..65535)
			MAX-ACCESS read-write
			STATUS current
			DESCRIPTION
				"Description."
			::= { priVoipTimerEntry 5 }

		
--          1.3.6.1.4.1.37950.1.1.5.12.3.2.8.1.6
-- 1.3.6.1.4.1.37950.1.1.5.12.3.2.8.1.6
-- 1.3.6.1.4.1.37950.1.1.5.12.3.2.8.1.6
-- 1.3.6.1.4.1.37950.1.1.5.12.3.2.8.1.6
-- 1.3.6.1.4.1.37950.1.1.5.12.3.2.8.1.6
-- 1.3.6.1.4.1.37950.1.1.5.12.3.2.8.1.6
-- 1.3.6.1.4.1.37950.1.1.5.12.3.2.8.1.6
-- 1.3.6.1.4.1.37950.1.1.5.12.3.2.8.1.6
-- 1.3.6.1.4.1.37950.1.1.5.12.3.2.8.1.6
		-- 1.3.6.1.4.1.37950.1.1.5.12.3.2.8.1.6
		priVoipTimerShortTimer OBJECT-TYPE
			SYNTAX Integer32 (1..65535)
			MAX-ACCESS read-write
			STATUS current
			DESCRIPTION
				"Description."
			::= { priVoipTimerEntry 6 }

		
--          1.3.6.1.4.1.37950.1.1.5.12.3.2.8.1.7
-- 1.3.6.1.4.1.37950.1.1.5.12.3.2.8.1.7
-- 1.3.6.1.4.1.37950.1.1.5.12.3.2.8.1.7
-- 1.3.6.1.4.1.37950.1.1.5.12.3.2.8.1.7
-- 1.3.6.1.4.1.37950.1.1.5.12.3.2.8.1.7
-- 1.3.6.1.4.1.37950.1.1.5.12.3.2.8.1.7
-- 1.3.6.1.4.1.37950.1.1.5.12.3.2.8.1.7
-- 1.3.6.1.4.1.37950.1.1.5.12.3.2.8.1.7
-- 1.3.6.1.4.1.37950.1.1.5.12.3.2.8.1.7
		-- 1.3.6.1.4.1.37950.1.1.5.12.3.2.8.1.7
		priVoipTimerDigitNotify OBJECT-TYPE
			SYNTAX INTEGER
				{
				disable(0),
				enable(1)
				}
			MAX-ACCESS read-write
			STATUS current
			DESCRIPTION
				"Description."
			::= { priVoipTimerEntry 7 }

		
--          1.3.6.1.4.1.37950.1.1.5.12.3.2.9
-- 1.3.6.1.4.1.37950.1.1.5.12.3.2.9
-- 1.3.6.1.4.1.37950.1.1.5.12.3.2.9
-- 1.3.6.1.4.1.37950.1.1.5.12.3.2.9
-- 1.3.6.1.4.1.37950.1.1.5.12.3.2.9
-- 1.3.6.1.4.1.37950.1.1.5.12.3.2.9
-- 1.3.6.1.4.1.37950.1.1.5.12.3.2.9
-- 1.3.6.1.4.1.37950.1.1.5.12.3.2.9
-- 1.3.6.1.4.1.37950.1.1.5.12.3.2.9
		-- 1.3.6.1.4.1.37950.1.1.5.12.3.2.9
		priDhcpServerTable OBJECT-TYPE
			SYNTAX SEQUENCE OF PriDhcpServerEntry
			MAX-ACCESS not-accessible
			STATUS current
			DESCRIPTION
				"Description."
			::= { onuPriGlobalInfo 9 }

		
--          1.3.6.1.4.1.37950.1.1.5.12.3.2.9.1
-- 1.3.6.1.4.1.37950.1.1.5.12.3.2.9.1
-- 1.3.6.1.4.1.37950.1.1.5.12.3.2.9.1
-- 1.3.6.1.4.1.37950.1.1.5.12.3.2.9.1
-- 1.3.6.1.4.1.37950.1.1.5.12.3.2.9.1
-- 1.3.6.1.4.1.37950.1.1.5.12.3.2.9.1
-- 1.3.6.1.4.1.37950.1.1.5.12.3.2.9.1
-- 1.3.6.1.4.1.37950.1.1.5.12.3.2.9.1
-- 1.3.6.1.4.1.37950.1.1.5.12.3.2.9.1
		-- 1.3.6.1.4.1.37950.1.1.5.12.3.2.9.1
		priDhcpServerEntry OBJECT-TYPE
			SYNTAX PriDhcpServerEntry
			MAX-ACCESS not-accessible
			STATUS current
			DESCRIPTION
				"Description."
			INDEX { priDhcpServerPon, priDhcpServerOnu }
			::= { priDhcpServerTable 1 }

		
		PriDhcpServerEntry ::=
			SEQUENCE { 
				priDhcpServerPon
					Integer32,
				priDhcpServerOnu
					Integer32,
				priDhcpLanIp
					IpAddress,
				priDhcpLanMask
					IpAddress,
				priDhcpEnable
					INTEGER,
				priDhcpLease
					Unsigned32,
				priDhcpBeginIp
					IpAddress,
				priDhcpEndIp
					IpAddress,
				priDhcpPoolType
					INTEGER,
				priDhcpMasterDns
					IpAddress,
				priDhcpSlaveDns
					IpAddress,
				priDhcpGateway
					IpAddress,
				priDhcpRelayIp
					IpAddress
			 }

--          1.3.6.1.4.1.37950.1.1.5.12.3.2.9.1.1
-- 1.3.6.1.4.1.37950.1.1.5.12.3.2.9.1.1
-- 1.3.6.1.4.1.37950.1.1.5.12.3.2.9.1.1
-- 1.3.6.1.4.1.37950.1.1.5.12.3.2.9.1.1
-- 1.3.6.1.4.1.37950.1.1.5.12.3.2.9.1.1
-- 1.3.6.1.4.1.37950.1.1.5.12.3.2.9.1.1
-- 1.3.6.1.4.1.37950.1.1.5.12.3.2.9.1.1
-- 1.3.6.1.4.1.37950.1.1.5.12.3.2.9.1.1
-- 1.3.6.1.4.1.37950.1.1.5.12.3.2.9.1.1
		-- 1.3.6.1.4.1.37950.1.1.5.12.3.2.9.1.1
		priDhcpServerPon OBJECT-TYPE
			SYNTAX Integer32
			MAX-ACCESS read-write
			STATUS current
			DESCRIPTION
				"Description."
			::= { priDhcpServerEntry 1 }

		
--          1.3.6.1.4.1.37950.1.1.5.12.3.2.9.1.2
-- 1.3.6.1.4.1.37950.1.1.5.12.3.2.9.1.2
-- 1.3.6.1.4.1.37950.1.1.5.12.3.2.9.1.2
-- 1.3.6.1.4.1.37950.1.1.5.12.3.2.9.1.2
-- 1.3.6.1.4.1.37950.1.1.5.12.3.2.9.1.2
-- 1.3.6.1.4.1.37950.1.1.5.12.3.2.9.1.2
-- 1.3.6.1.4.1.37950.1.1.5.12.3.2.9.1.2
-- 1.3.6.1.4.1.37950.1.1.5.12.3.2.9.1.2
-- 1.3.6.1.4.1.37950.1.1.5.12.3.2.9.1.2
		-- 1.3.6.1.4.1.37950.1.1.5.12.3.2.9.1.2
		priDhcpServerOnu OBJECT-TYPE
			SYNTAX Integer32
			MAX-ACCESS read-write
			STATUS current
			DESCRIPTION
				"Description."
			::= { priDhcpServerEntry 2 }

		
--          1.3.6.1.4.1.37950.1.1.5.12.3.2.9.1.3
-- 1.3.6.1.4.1.37950.1.1.5.12.3.2.9.1.3
-- 1.3.6.1.4.1.37950.1.1.5.12.3.2.9.1.3
-- 1.3.6.1.4.1.37950.1.1.5.12.3.2.9.1.3
-- 1.3.6.1.4.1.37950.1.1.5.12.3.2.9.1.3
-- 1.3.6.1.4.1.37950.1.1.5.12.3.2.9.1.3
-- 1.3.6.1.4.1.37950.1.1.5.12.3.2.9.1.3
-- 1.3.6.1.4.1.37950.1.1.5.12.3.2.9.1.3
-- 1.3.6.1.4.1.37950.1.1.5.12.3.2.9.1.3
		-- 1.3.6.1.4.1.37950.1.1.5.12.3.2.9.1.3
		priDhcpLanIp OBJECT-TYPE
			SYNTAX IpAddress
			MAX-ACCESS read-write
			STATUS current
			DESCRIPTION
				"Description."
			::= { priDhcpServerEntry 3 }

		
--          1.3.6.1.4.1.37950.1.1.5.12.3.2.9.1.4
-- 1.3.6.1.4.1.37950.1.1.5.12.3.2.9.1.4
-- 1.3.6.1.4.1.37950.1.1.5.12.3.2.9.1.4
-- 1.3.6.1.4.1.37950.1.1.5.12.3.2.9.1.4
-- 1.3.6.1.4.1.37950.1.1.5.12.3.2.9.1.4
-- 1.3.6.1.4.1.37950.1.1.5.12.3.2.9.1.4
-- 1.3.6.1.4.1.37950.1.1.5.12.3.2.9.1.4
-- 1.3.6.1.4.1.37950.1.1.5.12.3.2.9.1.4
-- 1.3.6.1.4.1.37950.1.1.5.12.3.2.9.1.4
		-- 1.3.6.1.4.1.37950.1.1.5.12.3.2.9.1.4
		priDhcpLanMask OBJECT-TYPE
			SYNTAX IpAddress
			MAX-ACCESS read-write
			STATUS current
			DESCRIPTION
				"Description."
			::= { priDhcpServerEntry 4 }

		
--          1.3.6.1.4.1.37950.1.1.5.12.3.2.9.1.5
-- 1.3.6.1.4.1.37950.1.1.5.12.3.2.9.1.5
-- 1.3.6.1.4.1.37950.1.1.5.12.3.2.9.1.5
-- 1.3.6.1.4.1.37950.1.1.5.12.3.2.9.1.5
-- 1.3.6.1.4.1.37950.1.1.5.12.3.2.9.1.5
-- 1.3.6.1.4.1.37950.1.1.5.12.3.2.9.1.5
-- 1.3.6.1.4.1.37950.1.1.5.12.3.2.9.1.5
-- 1.3.6.1.4.1.37950.1.1.5.12.3.2.9.1.5
-- 1.3.6.1.4.1.37950.1.1.5.12.3.2.9.1.5
		-- 1.3.6.1.4.1.37950.1.1.5.12.3.2.9.1.5
		priDhcpEnable OBJECT-TYPE
			SYNTAX INTEGER
				{
				disable(0),
				enable(1),
				relay(2)
				}
			MAX-ACCESS read-write
			STATUS current
			DESCRIPTION
				"Description."
			::= { priDhcpServerEntry 5 }

		
--          1.3.6.1.4.1.37950.1.1.5.12.3.2.9.1.6
-- 1.3.6.1.4.1.37950.1.1.5.12.3.2.9.1.6
-- 1.3.6.1.4.1.37950.1.1.5.12.3.2.9.1.6
-- 1.3.6.1.4.1.37950.1.1.5.12.3.2.9.1.6
-- 1.3.6.1.4.1.37950.1.1.5.12.3.2.9.1.6
-- 1.3.6.1.4.1.37950.1.1.5.12.3.2.9.1.6
-- 1.3.6.1.4.1.37950.1.1.5.12.3.2.9.1.6
-- 1.3.6.1.4.1.37950.1.1.5.12.3.2.9.1.6
-- 1.3.6.1.4.1.37950.1.1.5.12.3.2.9.1.6
		-- 1.3.6.1.4.1.37950.1.1.5.12.3.2.9.1.6
		priDhcpLease OBJECT-TYPE
			SYNTAX Unsigned32
			MAX-ACCESS read-write
			STATUS current
			DESCRIPTION
				"Description."
			::= { priDhcpServerEntry 6 }

		
--          1.3.6.1.4.1.37950.1.1.5.12.3.2.9.1.7
-- 1.3.6.1.4.1.37950.1.1.5.12.3.2.9.1.7
-- 1.3.6.1.4.1.37950.1.1.5.12.3.2.9.1.7
-- 1.3.6.1.4.1.37950.1.1.5.12.3.2.9.1.7
-- 1.3.6.1.4.1.37950.1.1.5.12.3.2.9.1.7
-- 1.3.6.1.4.1.37950.1.1.5.12.3.2.9.1.7
-- 1.3.6.1.4.1.37950.1.1.5.12.3.2.9.1.7
-- 1.3.6.1.4.1.37950.1.1.5.12.3.2.9.1.7
-- 1.3.6.1.4.1.37950.1.1.5.12.3.2.9.1.7
		-- 1.3.6.1.4.1.37950.1.1.5.12.3.2.9.1.7
		priDhcpBeginIp OBJECT-TYPE
			SYNTAX IpAddress
			MAX-ACCESS read-write
			STATUS current
			DESCRIPTION
				"Description."
			::= { priDhcpServerEntry 7 }

		
--          1.3.6.1.4.1.37950.1.1.5.12.3.2.9.1.8
-- 1.3.6.1.4.1.37950.1.1.5.12.3.2.9.1.8
-- 1.3.6.1.4.1.37950.1.1.5.12.3.2.9.1.8
-- 1.3.6.1.4.1.37950.1.1.5.12.3.2.9.1.8
-- 1.3.6.1.4.1.37950.1.1.5.12.3.2.9.1.8
-- 1.3.6.1.4.1.37950.1.1.5.12.3.2.9.1.8
-- 1.3.6.1.4.1.37950.1.1.5.12.3.2.9.1.8
-- 1.3.6.1.4.1.37950.1.1.5.12.3.2.9.1.8
-- 1.3.6.1.4.1.37950.1.1.5.12.3.2.9.1.8
		-- 1.3.6.1.4.1.37950.1.1.5.12.3.2.9.1.8
		priDhcpEndIp OBJECT-TYPE
			SYNTAX IpAddress
			MAX-ACCESS read-write
			STATUS current
			DESCRIPTION
				"Description."
			::= { priDhcpServerEntry 8 }

		
--          1.3.6.1.4.1.37950.1.1.5.12.3.2.9.1.9
-- 1.3.6.1.4.1.37950.1.1.5.12.3.2.9.1.9
-- 1.3.6.1.4.1.37950.1.1.5.12.3.2.9.1.9
-- 1.3.6.1.4.1.37950.1.1.5.12.3.2.9.1.9
-- 1.3.6.1.4.1.37950.1.1.5.12.3.2.9.1.9
-- 1.3.6.1.4.1.37950.1.1.5.12.3.2.9.1.9
-- 1.3.6.1.4.1.37950.1.1.5.12.3.2.9.1.9
-- 1.3.6.1.4.1.37950.1.1.5.12.3.2.9.1.9
-- 1.3.6.1.4.1.37950.1.1.5.12.3.2.9.1.9
		-- 1.3.6.1.4.1.37950.1.1.5.12.3.2.9.1.9
		priDhcpPoolType OBJECT-TYPE
			SYNTAX INTEGER
				{
				pc(0),
				camera(1),
				stb(2),
				ip-phone(3)
				}
			MAX-ACCESS read-write
			STATUS current
			DESCRIPTION
				"Description."
			::= { priDhcpServerEntry 9 }

		
--          1.3.6.1.4.1.37950.1.1.5.12.3.2.9.1.10
-- 1.3.6.1.4.1.37950.1.1.5.12.3.2.9.1.10
-- 1.3.6.1.4.1.37950.1.1.5.12.3.2.9.1.10
-- 1.3.6.1.4.1.37950.1.1.5.12.3.2.9.1.10
-- 1.3.6.1.4.1.37950.1.1.5.12.3.2.9.1.10
-- 1.3.6.1.4.1.37950.1.1.5.12.3.2.9.1.10
-- 1.3.6.1.4.1.37950.1.1.5.12.3.2.9.1.10
-- 1.3.6.1.4.1.37950.1.1.5.12.3.2.9.1.10
-- 1.3.6.1.4.1.37950.1.1.5.12.3.2.9.1.10
		-- 1.3.6.1.4.1.37950.1.1.5.12.3.2.9.1.10
		priDhcpMasterDns OBJECT-TYPE
			SYNTAX IpAddress
			MAX-ACCESS read-write
			STATUS current
			DESCRIPTION
				"Description."
			::= { priDhcpServerEntry 10 }

		
--          1.3.6.1.4.1.37950.1.1.5.12.3.2.9.1.11
-- 1.3.6.1.4.1.37950.1.1.5.12.3.2.9.1.11
-- 1.3.6.1.4.1.37950.1.1.5.12.3.2.9.1.11
-- 1.3.6.1.4.1.37950.1.1.5.12.3.2.9.1.11
-- 1.3.6.1.4.1.37950.1.1.5.12.3.2.9.1.11
-- 1.3.6.1.4.1.37950.1.1.5.12.3.2.9.1.11
-- 1.3.6.1.4.1.37950.1.1.5.12.3.2.9.1.11
-- 1.3.6.1.4.1.37950.1.1.5.12.3.2.9.1.11
-- 1.3.6.1.4.1.37950.1.1.5.12.3.2.9.1.11
		-- 1.3.6.1.4.1.37950.1.1.5.12.3.2.9.1.11
		priDhcpSlaveDns OBJECT-TYPE
			SYNTAX IpAddress
			MAX-ACCESS read-write
			STATUS current
			DESCRIPTION
				"Description."
			::= { priDhcpServerEntry 11 }

		
--          1.3.6.1.4.1.37950.1.1.5.12.3.2.9.1.12
-- 1.3.6.1.4.1.37950.1.1.5.12.3.2.9.1.12
-- 1.3.6.1.4.1.37950.1.1.5.12.3.2.9.1.12
-- 1.3.6.1.4.1.37950.1.1.5.12.3.2.9.1.12
-- 1.3.6.1.4.1.37950.1.1.5.12.3.2.9.1.12
-- 1.3.6.1.4.1.37950.1.1.5.12.3.2.9.1.12
-- 1.3.6.1.4.1.37950.1.1.5.12.3.2.9.1.12
-- 1.3.6.1.4.1.37950.1.1.5.12.3.2.9.1.12
-- 1.3.6.1.4.1.37950.1.1.5.12.3.2.9.1.12
		-- 1.3.6.1.4.1.37950.1.1.5.12.3.2.9.1.12
		priDhcpGateway OBJECT-TYPE
			SYNTAX IpAddress
			MAX-ACCESS read-write
			STATUS current
			DESCRIPTION
				"Description."
			::= { priDhcpServerEntry 12 }

		
--          1.3.6.1.4.1.37950.1.1.5.12.3.2.9.1.13
-- 1.3.6.1.4.1.37950.1.1.5.12.3.2.9.1.13
-- 1.3.6.1.4.1.37950.1.1.5.12.3.2.9.1.13
-- 1.3.6.1.4.1.37950.1.1.5.12.3.2.9.1.13
-- 1.3.6.1.4.1.37950.1.1.5.12.3.2.9.1.13
-- 1.3.6.1.4.1.37950.1.1.5.12.3.2.9.1.13
-- 1.3.6.1.4.1.37950.1.1.5.12.3.2.9.1.13
-- 1.3.6.1.4.1.37950.1.1.5.12.3.2.9.1.13
-- 1.3.6.1.4.1.37950.1.1.5.12.3.2.9.1.13
		-- 1.3.6.1.4.1.37950.1.1.5.12.3.2.9.1.13
		priDhcpRelayIp OBJECT-TYPE
			SYNTAX IpAddress
			MAX-ACCESS read-write
			STATUS current
			DESCRIPTION
				"Description."
			::= { priDhcpServerEntry 13 }

		
--          1.3.6.1.4.1.37950.1.1.5.12.3.2.10
-- 1.3.6.1.4.1.37950.1.1.5.12.3.2.10
-- 1.3.6.1.4.1.37950.1.1.5.12.3.2.10
-- 1.3.6.1.4.1.37950.1.1.5.12.3.2.10
-- 1.3.6.1.4.1.37950.1.1.5.12.3.2.10
-- 1.3.6.1.4.1.37950.1.1.5.12.3.2.10
-- 1.3.6.1.4.1.37950.1.1.5.12.3.2.10
-- 1.3.6.1.4.1.37950.1.1.5.12.3.2.10
-- 1.3.6.1.4.1.37950.1.1.5.12.3.2.10
		-- 1.3.6.1.4.1.37950.1.1.5.12.3.2.10
		priDhcpOption82Table OBJECT-TYPE
			SYNTAX SEQUENCE OF PriDhcpOption82Entry
			MAX-ACCESS not-accessible
			STATUS current
			DESCRIPTION
				"Description."
			::= { onuPriGlobalInfo 10 }

		
--          1.3.6.1.4.1.37950.1.1.5.12.3.2.10.1
-- 1.3.6.1.4.1.37950.1.1.5.12.3.2.10.1
-- 1.3.6.1.4.1.37950.1.1.5.12.3.2.10.1
-- 1.3.6.1.4.1.37950.1.1.5.12.3.2.10.1
-- 1.3.6.1.4.1.37950.1.1.5.12.3.2.10.1
-- 1.3.6.1.4.1.37950.1.1.5.12.3.2.10.1
-- 1.3.6.1.4.1.37950.1.1.5.12.3.2.10.1
-- 1.3.6.1.4.1.37950.1.1.5.12.3.2.10.1
-- 1.3.6.1.4.1.37950.1.1.5.12.3.2.10.1
		-- 1.3.6.1.4.1.37950.1.1.5.12.3.2.10.1
		priDhcpOption82Entry OBJECT-TYPE
			SYNTAX PriDhcpOption82Entry
			MAX-ACCESS not-accessible
			STATUS current
			DESCRIPTION
				"Description."
			INDEX { priDhcpOption82Pon, priDhcpOption82Onu }
			::= { priDhcpOption82Table 1 }

		
		PriDhcpOption82Entry ::=
			SEQUENCE { 
				priDhcpOption82Pon
					Integer32,
				priDhcpOption82Onu
					Integer32,
				priDhcpOption82Enable
					INTEGER
			 }

--          1.3.6.1.4.1.37950.1.1.5.12.3.2.10.1.1
-- 1.3.6.1.4.1.37950.1.1.5.12.3.2.10.1.1
-- 1.3.6.1.4.1.37950.1.1.5.12.3.2.10.1.1
-- 1.3.6.1.4.1.37950.1.1.5.12.3.2.10.1.1
-- 1.3.6.1.4.1.37950.1.1.5.12.3.2.10.1.1
-- 1.3.6.1.4.1.37950.1.1.5.12.3.2.10.1.1
-- 1.3.6.1.4.1.37950.1.1.5.12.3.2.10.1.1
-- 1.3.6.1.4.1.37950.1.1.5.12.3.2.10.1.1
-- 1.3.6.1.4.1.37950.1.1.5.12.3.2.10.1.1
		-- 1.3.6.1.4.1.37950.1.1.5.12.3.2.10.1.1
		priDhcpOption82Pon OBJECT-TYPE
			SYNTAX Integer32 (1..8)
			MAX-ACCESS read-write
			STATUS current
			DESCRIPTION
				"Description."
			::= { priDhcpOption82Entry 1 }

		
--          1.3.6.1.4.1.37950.1.1.5.12.3.2.10.1.2
-- 1.3.6.1.4.1.37950.1.1.5.12.3.2.10.1.2
-- 1.3.6.1.4.1.37950.1.1.5.12.3.2.10.1.2
-- 1.3.6.1.4.1.37950.1.1.5.12.3.2.10.1.2
-- 1.3.6.1.4.1.37950.1.1.5.12.3.2.10.1.2
-- 1.3.6.1.4.1.37950.1.1.5.12.3.2.10.1.2
-- 1.3.6.1.4.1.37950.1.1.5.12.3.2.10.1.2
-- 1.3.6.1.4.1.37950.1.1.5.12.3.2.10.1.2
-- 1.3.6.1.4.1.37950.1.1.5.12.3.2.10.1.2
		-- 1.3.6.1.4.1.37950.1.1.5.12.3.2.10.1.2
		priDhcpOption82Onu OBJECT-TYPE
			SYNTAX Integer32 (1..65535)
			MAX-ACCESS read-write
			STATUS current
			DESCRIPTION
				"Description."
			::= { priDhcpOption82Entry 2 }

		
--          1.3.6.1.4.1.37950.1.1.5.12.3.2.10.1.3
-- 1.3.6.1.4.1.37950.1.1.5.12.3.2.10.1.3
-- 1.3.6.1.4.1.37950.1.1.5.12.3.2.10.1.3
-- 1.3.6.1.4.1.37950.1.1.5.12.3.2.10.1.3
-- 1.3.6.1.4.1.37950.1.1.5.12.3.2.10.1.3
-- 1.3.6.1.4.1.37950.1.1.5.12.3.2.10.1.3
-- 1.3.6.1.4.1.37950.1.1.5.12.3.2.10.1.3
-- 1.3.6.1.4.1.37950.1.1.5.12.3.2.10.1.3
-- 1.3.6.1.4.1.37950.1.1.5.12.3.2.10.1.3
		-- 1.3.6.1.4.1.37950.1.1.5.12.3.2.10.1.3
		priDhcpOption82Enable OBJECT-TYPE
			SYNTAX INTEGER
				{
				disable(0),
				enable(1)
				}
			MAX-ACCESS read-write
			STATUS current
			DESCRIPTION
				"Description."
			::= { priDhcpOption82Entry 3 }

		
--          1.3.6.1.4.1.37950.1.1.5.12.3.2.11
-- 1.3.6.1.4.1.37950.1.1.5.12.3.2.11
-- 1.3.6.1.4.1.37950.1.1.5.12.3.2.11
-- 1.3.6.1.4.1.37950.1.1.5.12.3.2.11
-- 1.3.6.1.4.1.37950.1.1.5.12.3.2.11
-- 1.3.6.1.4.1.37950.1.1.5.12.3.2.11
-- 1.3.6.1.4.1.37950.1.1.5.12.3.2.11
-- 1.3.6.1.4.1.37950.1.1.5.12.3.2.11
-- 1.3.6.1.4.1.37950.1.1.5.12.3.2.11
		-- 1.3.6.1.4.1.37950.1.1.5.12.3.2.11
		priPPPoETable OBJECT-TYPE
			SYNTAX SEQUENCE OF PriPPPoEEntry
			MAX-ACCESS not-accessible
			STATUS current
			DESCRIPTION
				"Description."
			::= { onuPriGlobalInfo 11 }

		
--          1.3.6.1.4.1.37950.1.1.5.12.3.2.11.1
-- 1.3.6.1.4.1.37950.1.1.5.12.3.2.11.1
-- 1.3.6.1.4.1.37950.1.1.5.12.3.2.11.1
-- 1.3.6.1.4.1.37950.1.1.5.12.3.2.11.1
-- 1.3.6.1.4.1.37950.1.1.5.12.3.2.11.1
-- 1.3.6.1.4.1.37950.1.1.5.12.3.2.11.1
-- 1.3.6.1.4.1.37950.1.1.5.12.3.2.11.1
-- 1.3.6.1.4.1.37950.1.1.5.12.3.2.11.1
-- 1.3.6.1.4.1.37950.1.1.5.12.3.2.11.1
		-- 1.3.6.1.4.1.37950.1.1.5.12.3.2.11.1
		priPPPoEEntry OBJECT-TYPE
			SYNTAX PriPPPoEEntry
			MAX-ACCESS not-accessible
			STATUS current
			DESCRIPTION
				"Description."
			INDEX { priPPPoEPon, priPPPoEOnu }
			::= { priPPPoETable 1 }

		
		PriPPPoEEntry ::=
			SEQUENCE { 
				priPPPoEPon
					Integer32,
				priPPPoEOnu
					Integer32,
				priPPPoEEnable
					INTEGER
			 }

--          1.3.6.1.4.1.37950.1.1.5.12.3.2.11.1.1
-- 1.3.6.1.4.1.37950.1.1.5.12.3.2.11.1.1
-- 1.3.6.1.4.1.37950.1.1.5.12.3.2.11.1.1
-- 1.3.6.1.4.1.37950.1.1.5.12.3.2.11.1.1
-- 1.3.6.1.4.1.37950.1.1.5.12.3.2.11.1.1
-- 1.3.6.1.4.1.37950.1.1.5.12.3.2.11.1.1
-- 1.3.6.1.4.1.37950.1.1.5.12.3.2.11.1.1
-- 1.3.6.1.4.1.37950.1.1.5.12.3.2.11.1.1
-- 1.3.6.1.4.1.37950.1.1.5.12.3.2.11.1.1
		-- 1.3.6.1.4.1.37950.1.1.5.12.3.2.11.1.1
		priPPPoEPon OBJECT-TYPE
			SYNTAX Integer32 (1..8)
			MAX-ACCESS read-write
			STATUS current
			DESCRIPTION
				"Description."
			::= { priPPPoEEntry 1 }

		
--          1.3.6.1.4.1.37950.1.1.5.12.3.2.11.1.2
-- 1.3.6.1.4.1.37950.1.1.5.12.3.2.11.1.2
-- 1.3.6.1.4.1.37950.1.1.5.12.3.2.11.1.2
-- 1.3.6.1.4.1.37950.1.1.5.12.3.2.11.1.2
-- 1.3.6.1.4.1.37950.1.1.5.12.3.2.11.1.2
-- 1.3.6.1.4.1.37950.1.1.5.12.3.2.11.1.2
-- 1.3.6.1.4.1.37950.1.1.5.12.3.2.11.1.2
-- 1.3.6.1.4.1.37950.1.1.5.12.3.2.11.1.2
-- 1.3.6.1.4.1.37950.1.1.5.12.3.2.11.1.2
		-- 1.3.6.1.4.1.37950.1.1.5.12.3.2.11.1.2
		priPPPoEOnu OBJECT-TYPE
			SYNTAX Integer32 (1..65535)
			MAX-ACCESS read-write
			STATUS current
			DESCRIPTION
				"Description."
			::= { priPPPoEEntry 2 }

		
--          1.3.6.1.4.1.37950.1.1.5.12.3.2.11.1.3
-- 1.3.6.1.4.1.37950.1.1.5.12.3.2.11.1.3
-- 1.3.6.1.4.1.37950.1.1.5.12.3.2.11.1.3
-- 1.3.6.1.4.1.37950.1.1.5.12.3.2.11.1.3
-- 1.3.6.1.4.1.37950.1.1.5.12.3.2.11.1.3
-- 1.3.6.1.4.1.37950.1.1.5.12.3.2.11.1.3
-- 1.3.6.1.4.1.37950.1.1.5.12.3.2.11.1.3
-- 1.3.6.1.4.1.37950.1.1.5.12.3.2.11.1.3
-- 1.3.6.1.4.1.37950.1.1.5.12.3.2.11.1.3
		-- 1.3.6.1.4.1.37950.1.1.5.12.3.2.11.1.3
		priPPPoEEnable OBJECT-TYPE
			SYNTAX INTEGER
				{
				disable(0),
				enable(1)
				}
			MAX-ACCESS read-write
			STATUS current
			DESCRIPTION
				"Description."
			::= { priPPPoEEntry 3 }

		
--          1.3.6.1.4.1.37950.1.1.5.12.3.2.12
-- 1.3.6.1.4.1.37950.1.1.5.12.3.2.12
-- 1.3.6.1.4.1.37950.1.1.5.12.3.2.12
-- 1.3.6.1.4.1.37950.1.1.5.12.3.2.12
-- 1.3.6.1.4.1.37950.1.1.5.12.3.2.12
-- 1.3.6.1.4.1.37950.1.1.5.12.3.2.12
-- 1.3.6.1.4.1.37950.1.1.5.12.3.2.12
-- 1.3.6.1.4.1.37950.1.1.5.12.3.2.12
-- 1.3.6.1.4.1.37950.1.1.5.12.3.2.12
		-- 1.3.6.1.4.1.37950.1.1.5.12.3.2.12
		priDhcpV6Table OBJECT-TYPE
			SYNTAX SEQUENCE OF PriDhcpV6Entry
			MAX-ACCESS not-accessible
			STATUS current
			DESCRIPTION
				"Description."
			::= { onuPriGlobalInfo 12 }

		
--          1.3.6.1.4.1.37950.1.1.5.12.3.2.12.1
-- 1.3.6.1.4.1.37950.1.1.5.12.3.2.12.1
-- 1.3.6.1.4.1.37950.1.1.5.12.3.2.12.1
-- 1.3.6.1.4.1.37950.1.1.5.12.3.2.12.1
-- 1.3.6.1.4.1.37950.1.1.5.12.3.2.12.1
-- 1.3.6.1.4.1.37950.1.1.5.12.3.2.12.1
-- 1.3.6.1.4.1.37950.1.1.5.12.3.2.12.1
-- 1.3.6.1.4.1.37950.1.1.5.12.3.2.12.1
-- 1.3.6.1.4.1.37950.1.1.5.12.3.2.12.1
		-- 1.3.6.1.4.1.37950.1.1.5.12.3.2.12.1
		priDhcpV6Entry OBJECT-TYPE
			SYNTAX PriDhcpV6Entry
			MAX-ACCESS not-accessible
			STATUS current
			DESCRIPTION
				"Description."
			INDEX { priDhcpV6Pon, priDhcpV6Onu }
			::= { priDhcpV6Table 1 }

		
		PriDhcpV6Entry ::=
			SEQUENCE { 
				priDhcpV6Pon
					Integer32,
				priDhcpV6Onu
					Integer32,
				priDhcpV6Option18Enable
					INTEGER,
				priDhcpV6Option37Enable
					INTEGER
			 }

--          1.3.6.1.4.1.37950.1.1.5.12.3.2.12.1.1
-- 1.3.6.1.4.1.37950.1.1.5.12.3.2.12.1.1
-- 1.3.6.1.4.1.37950.1.1.5.12.3.2.12.1.1
-- 1.3.6.1.4.1.37950.1.1.5.12.3.2.12.1.1
-- 1.3.6.1.4.1.37950.1.1.5.12.3.2.12.1.1
-- 1.3.6.1.4.1.37950.1.1.5.12.3.2.12.1.1
-- 1.3.6.1.4.1.37950.1.1.5.12.3.2.12.1.1
-- 1.3.6.1.4.1.37950.1.1.5.12.3.2.12.1.1
-- 1.3.6.1.4.1.37950.1.1.5.12.3.2.12.1.1
		-- 1.3.6.1.4.1.37950.1.1.5.12.3.2.12.1.1
		priDhcpV6Pon OBJECT-TYPE
			SYNTAX Integer32 (1..8)
			MAX-ACCESS read-write
			STATUS current
			DESCRIPTION
				"Description."
			::= { priDhcpV6Entry 1 }

		
--          1.3.6.1.4.1.37950.1.1.5.12.3.2.12.1.2
-- 1.3.6.1.4.1.37950.1.1.5.12.3.2.12.1.2
-- 1.3.6.1.4.1.37950.1.1.5.12.3.2.12.1.2
-- 1.3.6.1.4.1.37950.1.1.5.12.3.2.12.1.2
-- 1.3.6.1.4.1.37950.1.1.5.12.3.2.12.1.2
-- 1.3.6.1.4.1.37950.1.1.5.12.3.2.12.1.2
-- 1.3.6.1.4.1.37950.1.1.5.12.3.2.12.1.2
-- 1.3.6.1.4.1.37950.1.1.5.12.3.2.12.1.2
-- 1.3.6.1.4.1.37950.1.1.5.12.3.2.12.1.2
		-- 1.3.6.1.4.1.37950.1.1.5.12.3.2.12.1.2
		priDhcpV6Onu OBJECT-TYPE
			SYNTAX Integer32 (1..65535)
			MAX-ACCESS read-write
			STATUS current
			DESCRIPTION
				"Description."
			::= { priDhcpV6Entry 2 }

		
--          1.3.6.1.4.1.37950.1.1.5.12.3.2.12.1.3
-- 1.3.6.1.4.1.37950.1.1.5.12.3.2.12.1.3
-- 1.3.6.1.4.1.37950.1.1.5.12.3.2.12.1.3
-- 1.3.6.1.4.1.37950.1.1.5.12.3.2.12.1.3
-- 1.3.6.1.4.1.37950.1.1.5.12.3.2.12.1.3
-- 1.3.6.1.4.1.37950.1.1.5.12.3.2.12.1.3
-- 1.3.6.1.4.1.37950.1.1.5.12.3.2.12.1.3
-- 1.3.6.1.4.1.37950.1.1.5.12.3.2.12.1.3
-- 1.3.6.1.4.1.37950.1.1.5.12.3.2.12.1.3
		-- 1.3.6.1.4.1.37950.1.1.5.12.3.2.12.1.3
		priDhcpV6Option18Enable OBJECT-TYPE
			SYNTAX INTEGER
				{
				disable(0),
				enable(1)
				}
			MAX-ACCESS read-write
			STATUS current
			DESCRIPTION
				"Description."
			::= { priDhcpV6Entry 3 }

		
--          1.3.6.1.4.1.37950.1.1.5.12.3.2.12.1.4
-- 1.3.6.1.4.1.37950.1.1.5.12.3.2.12.1.4
-- 1.3.6.1.4.1.37950.1.1.5.12.3.2.12.1.4
-- 1.3.6.1.4.1.37950.1.1.5.12.3.2.12.1.4
-- 1.3.6.1.4.1.37950.1.1.5.12.3.2.12.1.4
-- 1.3.6.1.4.1.37950.1.1.5.12.3.2.12.1.4
-- 1.3.6.1.4.1.37950.1.1.5.12.3.2.12.1.4
-- 1.3.6.1.4.1.37950.1.1.5.12.3.2.12.1.4
-- 1.3.6.1.4.1.37950.1.1.5.12.3.2.12.1.4
		-- 1.3.6.1.4.1.37950.1.1.5.12.3.2.12.1.4
		priDhcpV6Option37Enable OBJECT-TYPE
			SYNTAX INTEGER
				{
				disable(0),
				enable(1)
				}
			MAX-ACCESS read-write
			STATUS current
			DESCRIPTION
				"Description."
			::= { priDhcpV6Entry 4 }

		
--          1.3.6.1.4.1.37950.1.1.5.12.3.2.13
-- 1.3.6.1.4.1.37950.1.1.5.12.3.2.13
-- 1.3.6.1.4.1.37950.1.1.5.12.3.2.13
-- 1.3.6.1.4.1.37950.1.1.5.12.3.2.13
-- 1.3.6.1.4.1.37950.1.1.5.12.3.2.13
-- 1.3.6.1.4.1.37950.1.1.5.12.3.2.13
-- 1.3.6.1.4.1.37950.1.1.5.12.3.2.13
-- 1.3.6.1.4.1.37950.1.1.5.12.3.2.13
-- 1.3.6.1.4.1.37950.1.1.5.12.3.2.13
		-- 1.3.6.1.4.1.37950.1.1.5.12.3.2.13
		priVoipParamTable OBJECT-TYPE
			SYNTAX SEQUENCE OF PriVoipParamEntry
			MAX-ACCESS not-accessible
			STATUS current
			DESCRIPTION
				"Description."
			::= { onuPriGlobalInfo 13 }

		
--          1.3.6.1.4.1.37950.1.1.5.12.3.2.13.1
-- 1.3.6.1.4.1.37950.1.1.5.12.3.2.13.1
-- 1.3.6.1.4.1.37950.1.1.5.12.3.2.13.1
-- 1.3.6.1.4.1.37950.1.1.5.12.3.2.13.1
-- 1.3.6.1.4.1.37950.1.1.5.12.3.2.13.1
-- 1.3.6.1.4.1.37950.1.1.5.12.3.2.13.1
-- 1.3.6.1.4.1.37950.1.1.5.12.3.2.13.1
-- 1.3.6.1.4.1.37950.1.1.5.12.3.2.13.1
-- 1.3.6.1.4.1.37950.1.1.5.12.3.2.13.1
		-- 1.3.6.1.4.1.37950.1.1.5.12.3.2.13.1
		priVoipParamEntry OBJECT-TYPE
			SYNTAX PriVoipParamEntry
			MAX-ACCESS not-accessible
			STATUS current
			DESCRIPTION
				"Description."
			INDEX { voipPTPon, voipPTOnu }
			::= { priVoipParamTable 1 }

		
		PriVoipParamEntry ::=
			SEQUENCE { 
				voipPTPon
					Integer32,
				voipPTOnu
					Integer32,
				voipPTIpMode
					INTEGER,
				voipPTIp
					IpAddress,
				voipPTMask
					IpAddress,
				voipPTGw
					IpAddress,
				voipPTRtpIp
					IpAddress,
				voipPTRtpMask
					IpAddress,
				voipPTRtpGw
					IpAddress,
				voipPTDnsMaster
					IpAddress,
				voipPTDnsSlave
					IpAddress,
				voipPTDhcpOption60Enable
					INTEGER,
				voipPTDhcpOption60Base
					OCTET STRING,
				voipPTDhcpOption60Value
					OCTET STRING,
				voipPTPPPoEMode
					INTEGER,
				voipPTPPPoEUsername
					OCTET STRING,
				voipPTPPPoEPassword
					OCTET STRING,
				voipPTSVlanTpid
					Integer32,
				voipPTSVlanId
					Integer32,
				voipPTSVlanCos
					Integer32,
				voipPTCVlanTpid
					Integer32,
				voipPTCVlanId
					Integer32,
				voipPTCVlanCos
					Integer32,
				voipPTRtpSVlanTpid
					Integer32,
				voipPTRtpSVlanId
					Integer32,
				voipPTRtpSVlanCos
					Integer32,
				voipPTRtpCVlanTpid
					Integer32,
				voipPTRtpCVlanId
					Integer32,
				voipPTRtpCVlanCos
					Integer32
			 }

--          1.3.6.1.4.1.37950.1.1.5.12.3.2.13.1.1
-- 1.3.6.1.4.1.37950.1.1.5.12.3.2.13.1.1
-- 1.3.6.1.4.1.37950.1.1.5.12.3.2.13.1.1
-- 1.3.6.1.4.1.37950.1.1.5.12.3.2.13.1.1
-- 1.3.6.1.4.1.37950.1.1.5.12.3.2.13.1.1
-- 1.3.6.1.4.1.37950.1.1.5.12.3.2.13.1.1
-- 1.3.6.1.4.1.37950.1.1.5.12.3.2.13.1.1
-- 1.3.6.1.4.1.37950.1.1.5.12.3.2.13.1.1
-- 1.3.6.1.4.1.37950.1.1.5.12.3.2.13.1.1
		-- 1.3.6.1.4.1.37950.1.1.5.12.3.2.13.1.1
		voipPTPon OBJECT-TYPE
			SYNTAX Integer32 (1..8)
			MAX-ACCESS read-write
			STATUS current
			DESCRIPTION
				"Description."
			::= { priVoipParamEntry 1 }

		
--          1.3.6.1.4.1.37950.1.1.5.12.3.2.13.1.2
-- 1.3.6.1.4.1.37950.1.1.5.12.3.2.13.1.2
-- 1.3.6.1.4.1.37950.1.1.5.12.3.2.13.1.2
-- 1.3.6.1.4.1.37950.1.1.5.12.3.2.13.1.2
-- 1.3.6.1.4.1.37950.1.1.5.12.3.2.13.1.2
-- 1.3.6.1.4.1.37950.1.1.5.12.3.2.13.1.2
-- 1.3.6.1.4.1.37950.1.1.5.12.3.2.13.1.2
-- 1.3.6.1.4.1.37950.1.1.5.12.3.2.13.1.2
-- 1.3.6.1.4.1.37950.1.1.5.12.3.2.13.1.2
		-- 1.3.6.1.4.1.37950.1.1.5.12.3.2.13.1.2
		voipPTOnu OBJECT-TYPE
			SYNTAX Integer32 (1..65535)
			MAX-ACCESS read-write
			STATUS current
			DESCRIPTION
				"Description."
			::= { priVoipParamEntry 2 }

		
--          1.3.6.1.4.1.37950.1.1.5.12.3.2.13.1.3
-- 1.3.6.1.4.1.37950.1.1.5.12.3.2.13.1.3
-- 1.3.6.1.4.1.37950.1.1.5.12.3.2.13.1.3
-- 1.3.6.1.4.1.37950.1.1.5.12.3.2.13.1.3
-- 1.3.6.1.4.1.37950.1.1.5.12.3.2.13.1.3
-- 1.3.6.1.4.1.37950.1.1.5.12.3.2.13.1.3
-- 1.3.6.1.4.1.37950.1.1.5.12.3.2.13.1.3
-- 1.3.6.1.4.1.37950.1.1.5.12.3.2.13.1.3
-- 1.3.6.1.4.1.37950.1.1.5.12.3.2.13.1.3
		-- 1.3.6.1.4.1.37950.1.1.5.12.3.2.13.1.3
		voipPTIpMode OBJECT-TYPE
			SYNTAX INTEGER
				{
				static(1),
				dhcp(2),
				pppoe(3)
				}
			MAX-ACCESS read-write
			STATUS current
			DESCRIPTION
				"Description."
			::= { priVoipParamEntry 3 }

		
--          1.3.6.1.4.1.37950.1.1.5.12.3.2.13.1.4
-- 1.3.6.1.4.1.37950.1.1.5.12.3.2.13.1.4
-- 1.3.6.1.4.1.37950.1.1.5.12.3.2.13.1.4
-- 1.3.6.1.4.1.37950.1.1.5.12.3.2.13.1.4
-- 1.3.6.1.4.1.37950.1.1.5.12.3.2.13.1.4
-- 1.3.6.1.4.1.37950.1.1.5.12.3.2.13.1.4
-- 1.3.6.1.4.1.37950.1.1.5.12.3.2.13.1.4
-- 1.3.6.1.4.1.37950.1.1.5.12.3.2.13.1.4
-- 1.3.6.1.4.1.37950.1.1.5.12.3.2.13.1.4
		-- 1.3.6.1.4.1.37950.1.1.5.12.3.2.13.1.4
		voipPTIp OBJECT-TYPE
			SYNTAX IpAddress
			MAX-ACCESS read-write
			STATUS current
			DESCRIPTION
				"Description."
			::= { priVoipParamEntry 4 }

		
--          1.3.6.1.4.1.37950.1.1.5.12.3.2.13.1.5
-- 1.3.6.1.4.1.37950.1.1.5.12.3.2.13.1.5
-- 1.3.6.1.4.1.37950.1.1.5.12.3.2.13.1.5
-- 1.3.6.1.4.1.37950.1.1.5.12.3.2.13.1.5
-- 1.3.6.1.4.1.37950.1.1.5.12.3.2.13.1.5
-- 1.3.6.1.4.1.37950.1.1.5.12.3.2.13.1.5
-- 1.3.6.1.4.1.37950.1.1.5.12.3.2.13.1.5
-- 1.3.6.1.4.1.37950.1.1.5.12.3.2.13.1.5
-- 1.3.6.1.4.1.37950.1.1.5.12.3.2.13.1.5
		-- 1.3.6.1.4.1.37950.1.1.5.12.3.2.13.1.5
		voipPTMask OBJECT-TYPE
			SYNTAX IpAddress
			MAX-ACCESS read-write
			STATUS current
			DESCRIPTION
				"Description."
			::= { priVoipParamEntry 5 }

		
--          1.3.6.1.4.1.37950.1.1.5.12.3.2.13.1.6
-- 1.3.6.1.4.1.37950.1.1.5.12.3.2.13.1.6
-- 1.3.6.1.4.1.37950.1.1.5.12.3.2.13.1.6
-- 1.3.6.1.4.1.37950.1.1.5.12.3.2.13.1.6
-- 1.3.6.1.4.1.37950.1.1.5.12.3.2.13.1.6
-- 1.3.6.1.4.1.37950.1.1.5.12.3.2.13.1.6
-- 1.3.6.1.4.1.37950.1.1.5.12.3.2.13.1.6
-- 1.3.6.1.4.1.37950.1.1.5.12.3.2.13.1.6
-- 1.3.6.1.4.1.37950.1.1.5.12.3.2.13.1.6
		-- 1.3.6.1.4.1.37950.1.1.5.12.3.2.13.1.6
		voipPTGw OBJECT-TYPE
			SYNTAX IpAddress
			MAX-ACCESS read-write
			STATUS current
			DESCRIPTION
				"Description."
			::= { priVoipParamEntry 6 }

		
--          1.3.6.1.4.1.37950.1.1.5.12.3.2.13.1.7
-- 1.3.6.1.4.1.37950.1.1.5.12.3.2.13.1.7
-- 1.3.6.1.4.1.37950.1.1.5.12.3.2.13.1.7
-- 1.3.6.1.4.1.37950.1.1.5.12.3.2.13.1.7
-- 1.3.6.1.4.1.37950.1.1.5.12.3.2.13.1.7
-- 1.3.6.1.4.1.37950.1.1.5.12.3.2.13.1.7
-- 1.3.6.1.4.1.37950.1.1.5.12.3.2.13.1.7
-- 1.3.6.1.4.1.37950.1.1.5.12.3.2.13.1.7
-- 1.3.6.1.4.1.37950.1.1.5.12.3.2.13.1.7
		-- 1.3.6.1.4.1.37950.1.1.5.12.3.2.13.1.7
		voipPTRtpIp OBJECT-TYPE
			SYNTAX IpAddress
			MAX-ACCESS read-write
			STATUS current
			DESCRIPTION
				"Description."
			::= { priVoipParamEntry 7 }

		
--          1.3.6.1.4.1.37950.1.1.5.12.3.2.13.1.8
-- 1.3.6.1.4.1.37950.1.1.5.12.3.2.13.1.8
-- 1.3.6.1.4.1.37950.1.1.5.12.3.2.13.1.8
-- 1.3.6.1.4.1.37950.1.1.5.12.3.2.13.1.8
-- 1.3.6.1.4.1.37950.1.1.5.12.3.2.13.1.8
-- 1.3.6.1.4.1.37950.1.1.5.12.3.2.13.1.8
-- 1.3.6.1.4.1.37950.1.1.5.12.3.2.13.1.8
-- 1.3.6.1.4.1.37950.1.1.5.12.3.2.13.1.8
-- 1.3.6.1.4.1.37950.1.1.5.12.3.2.13.1.8
		-- 1.3.6.1.4.1.37950.1.1.5.12.3.2.13.1.8
		voipPTRtpMask OBJECT-TYPE
			SYNTAX IpAddress
			MAX-ACCESS read-write
			STATUS current
			DESCRIPTION
				"Description."
			::= { priVoipParamEntry 8 }

		
--          1.3.6.1.4.1.37950.1.1.5.12.3.2.13.1.9
-- 1.3.6.1.4.1.37950.1.1.5.12.3.2.13.1.9
-- 1.3.6.1.4.1.37950.1.1.5.12.3.2.13.1.9
-- 1.3.6.1.4.1.37950.1.1.5.12.3.2.13.1.9
-- 1.3.6.1.4.1.37950.1.1.5.12.3.2.13.1.9
-- 1.3.6.1.4.1.37950.1.1.5.12.3.2.13.1.9
-- 1.3.6.1.4.1.37950.1.1.5.12.3.2.13.1.9
-- 1.3.6.1.4.1.37950.1.1.5.12.3.2.13.1.9
-- 1.3.6.1.4.1.37950.1.1.5.12.3.2.13.1.9
		-- 1.3.6.1.4.1.37950.1.1.5.12.3.2.13.1.9
		voipPTRtpGw OBJECT-TYPE
			SYNTAX IpAddress
			MAX-ACCESS read-write
			STATUS current
			DESCRIPTION
				"Description."
			::= { priVoipParamEntry 9 }

		
--          1.3.6.1.4.1.37950.1.1.5.12.3.2.13.1.10
-- 1.3.6.1.4.1.37950.1.1.5.12.3.2.13.1.10
-- 1.3.6.1.4.1.37950.1.1.5.12.3.2.13.1.10
-- 1.3.6.1.4.1.37950.1.1.5.12.3.2.13.1.10
-- 1.3.6.1.4.1.37950.1.1.5.12.3.2.13.1.10
-- 1.3.6.1.4.1.37950.1.1.5.12.3.2.13.1.10
-- 1.3.6.1.4.1.37950.1.1.5.12.3.2.13.1.10
-- 1.3.6.1.4.1.37950.1.1.5.12.3.2.13.1.10
-- 1.3.6.1.4.1.37950.1.1.5.12.3.2.13.1.10
		-- 1.3.6.1.4.1.37950.1.1.5.12.3.2.13.1.10
		voipPTDnsMaster OBJECT-TYPE
			SYNTAX IpAddress
			MAX-ACCESS read-write
			STATUS current
			DESCRIPTION
				"Description."
			::= { priVoipParamEntry 10 }

		
--          1.3.6.1.4.1.37950.1.1.5.12.3.2.13.1.11
-- 1.3.6.1.4.1.37950.1.1.5.12.3.2.13.1.11
-- 1.3.6.1.4.1.37950.1.1.5.12.3.2.13.1.11
-- 1.3.6.1.4.1.37950.1.1.5.12.3.2.13.1.11
-- 1.3.6.1.4.1.37950.1.1.5.12.3.2.13.1.11
-- 1.3.6.1.4.1.37950.1.1.5.12.3.2.13.1.11
-- 1.3.6.1.4.1.37950.1.1.5.12.3.2.13.1.11
-- 1.3.6.1.4.1.37950.1.1.5.12.3.2.13.1.11
-- 1.3.6.1.4.1.37950.1.1.5.12.3.2.13.1.11
		-- 1.3.6.1.4.1.37950.1.1.5.12.3.2.13.1.11
		voipPTDnsSlave OBJECT-TYPE
			SYNTAX IpAddress
			MAX-ACCESS read-write
			STATUS current
			DESCRIPTION
				"Description."
			::= { priVoipParamEntry 11 }

		
--          1.3.6.1.4.1.37950.1.1.5.12.3.2.13.1.12
-- 1.3.6.1.4.1.37950.1.1.5.12.3.2.13.1.12
-- 1.3.6.1.4.1.37950.1.1.5.12.3.2.13.1.12
-- 1.3.6.1.4.1.37950.1.1.5.12.3.2.13.1.12
-- 1.3.6.1.4.1.37950.1.1.5.12.3.2.13.1.12
-- 1.3.6.1.4.1.37950.1.1.5.12.3.2.13.1.12
-- 1.3.6.1.4.1.37950.1.1.5.12.3.2.13.1.12
-- 1.3.6.1.4.1.37950.1.1.5.12.3.2.13.1.12
-- 1.3.6.1.4.1.37950.1.1.5.12.3.2.13.1.12
		-- 1.3.6.1.4.1.37950.1.1.5.12.3.2.13.1.12
		voipPTDhcpOption60Enable OBJECT-TYPE
			SYNTAX INTEGER
				{
				disable(0),
				enable(1)
				}
			MAX-ACCESS read-write
			STATUS current
			DESCRIPTION
				"Description."
			::= { priVoipParamEntry 12 }

		
--          1.3.6.1.4.1.37950.1.1.5.12.3.2.13.1.13
-- 1.3.6.1.4.1.37950.1.1.5.12.3.2.13.1.13
-- 1.3.6.1.4.1.37950.1.1.5.12.3.2.13.1.13
-- 1.3.6.1.4.1.37950.1.1.5.12.3.2.13.1.13
-- 1.3.6.1.4.1.37950.1.1.5.12.3.2.13.1.13
-- 1.3.6.1.4.1.37950.1.1.5.12.3.2.13.1.13
-- 1.3.6.1.4.1.37950.1.1.5.12.3.2.13.1.13
-- 1.3.6.1.4.1.37950.1.1.5.12.3.2.13.1.13
-- 1.3.6.1.4.1.37950.1.1.5.12.3.2.13.1.13
		-- 1.3.6.1.4.1.37950.1.1.5.12.3.2.13.1.13
		voipPTDhcpOption60Base OBJECT-TYPE
			SYNTAX OCTET STRING
			MAX-ACCESS read-write
			STATUS current
			DESCRIPTION
				"Description."
			::= { priVoipParamEntry 13 }

		
--          1.3.6.1.4.1.37950.1.1.5.12.3.2.13.1.14
-- 1.3.6.1.4.1.37950.1.1.5.12.3.2.13.1.14
-- 1.3.6.1.4.1.37950.1.1.5.12.3.2.13.1.14
-- 1.3.6.1.4.1.37950.1.1.5.12.3.2.13.1.14
-- 1.3.6.1.4.1.37950.1.1.5.12.3.2.13.1.14
-- 1.3.6.1.4.1.37950.1.1.5.12.3.2.13.1.14
-- 1.3.6.1.4.1.37950.1.1.5.12.3.2.13.1.14
-- 1.3.6.1.4.1.37950.1.1.5.12.3.2.13.1.14
-- 1.3.6.1.4.1.37950.1.1.5.12.3.2.13.1.14
		-- 1.3.6.1.4.1.37950.1.1.5.12.3.2.13.1.14
		voipPTDhcpOption60Value OBJECT-TYPE
			SYNTAX OCTET STRING
			MAX-ACCESS read-write
			STATUS current
			DESCRIPTION
				"Description."
			::= { priVoipParamEntry 14 }

		
--          1.3.6.1.4.1.37950.1.1.5.12.3.2.13.1.15
-- 1.3.6.1.4.1.37950.1.1.5.12.3.2.13.1.15
-- 1.3.6.1.4.1.37950.1.1.5.12.3.2.13.1.15
-- 1.3.6.1.4.1.37950.1.1.5.12.3.2.13.1.15
-- 1.3.6.1.4.1.37950.1.1.5.12.3.2.13.1.15
-- 1.3.6.1.4.1.37950.1.1.5.12.3.2.13.1.15
-- 1.3.6.1.4.1.37950.1.1.5.12.3.2.13.1.15
-- 1.3.6.1.4.1.37950.1.1.5.12.3.2.13.1.15
-- 1.3.6.1.4.1.37950.1.1.5.12.3.2.13.1.15
		-- 1.3.6.1.4.1.37950.1.1.5.12.3.2.13.1.15
		voipPTPPPoEMode OBJECT-TYPE
			SYNTAX INTEGER
				{
				auto(1),
				chap(2),
				pap(3)
				}
			MAX-ACCESS read-write
			STATUS current
			DESCRIPTION
				"Description."
			::= { priVoipParamEntry 15 }

		
--          1.3.6.1.4.1.37950.1.1.5.12.3.2.13.1.16
-- 1.3.6.1.4.1.37950.1.1.5.12.3.2.13.1.16
-- 1.3.6.1.4.1.37950.1.1.5.12.3.2.13.1.16
-- 1.3.6.1.4.1.37950.1.1.5.12.3.2.13.1.16
-- 1.3.6.1.4.1.37950.1.1.5.12.3.2.13.1.16
-- 1.3.6.1.4.1.37950.1.1.5.12.3.2.13.1.16
-- 1.3.6.1.4.1.37950.1.1.5.12.3.2.13.1.16
-- 1.3.6.1.4.1.37950.1.1.5.12.3.2.13.1.16
-- 1.3.6.1.4.1.37950.1.1.5.12.3.2.13.1.16
		-- 1.3.6.1.4.1.37950.1.1.5.12.3.2.13.1.16
		voipPTPPPoEUsername OBJECT-TYPE
			SYNTAX OCTET STRING
			MAX-ACCESS read-write
			STATUS current
			DESCRIPTION
				"Description."
			::= { priVoipParamEntry 16 }

		
--          1.3.6.1.4.1.37950.1.1.5.12.3.2.13.1.17
-- 1.3.6.1.4.1.37950.1.1.5.12.3.2.13.1.17
-- 1.3.6.1.4.1.37950.1.1.5.12.3.2.13.1.17
-- 1.3.6.1.4.1.37950.1.1.5.12.3.2.13.1.17
-- 1.3.6.1.4.1.37950.1.1.5.12.3.2.13.1.17
-- 1.3.6.1.4.1.37950.1.1.5.12.3.2.13.1.17
-- 1.3.6.1.4.1.37950.1.1.5.12.3.2.13.1.17
-- 1.3.6.1.4.1.37950.1.1.5.12.3.2.13.1.17
-- 1.3.6.1.4.1.37950.1.1.5.12.3.2.13.1.17
		-- 1.3.6.1.4.1.37950.1.1.5.12.3.2.13.1.17
		voipPTPPPoEPassword OBJECT-TYPE
			SYNTAX OCTET STRING
			MAX-ACCESS read-write
			STATUS current
			DESCRIPTION
				"Description."
			::= { priVoipParamEntry 17 }

		
--          1.3.6.1.4.1.37950.1.1.5.12.3.2.13.1.18
-- 1.3.6.1.4.1.37950.1.1.5.12.3.2.13.1.18
-- 1.3.6.1.4.1.37950.1.1.5.12.3.2.13.1.18
-- 1.3.6.1.4.1.37950.1.1.5.12.3.2.13.1.18
-- 1.3.6.1.4.1.37950.1.1.5.12.3.2.13.1.18
-- 1.3.6.1.4.1.37950.1.1.5.12.3.2.13.1.18
-- 1.3.6.1.4.1.37950.1.1.5.12.3.2.13.1.18
-- 1.3.6.1.4.1.37950.1.1.5.12.3.2.13.1.18
-- 1.3.6.1.4.1.37950.1.1.5.12.3.2.13.1.18
		-- 1.3.6.1.4.1.37950.1.1.5.12.3.2.13.1.18
		voipPTSVlanTpid OBJECT-TYPE
			SYNTAX Integer32
			MAX-ACCESS read-write
			STATUS current
			DESCRIPTION
				"Description."
			::= { priVoipParamEntry 18 }

		
--          1.3.6.1.4.1.37950.1.1.5.12.3.2.13.1.19
-- 1.3.6.1.4.1.37950.1.1.5.12.3.2.13.1.19
-- 1.3.6.1.4.1.37950.1.1.5.12.3.2.13.1.19
-- 1.3.6.1.4.1.37950.1.1.5.12.3.2.13.1.19
-- 1.3.6.1.4.1.37950.1.1.5.12.3.2.13.1.19
-- 1.3.6.1.4.1.37950.1.1.5.12.3.2.13.1.19
-- 1.3.6.1.4.1.37950.1.1.5.12.3.2.13.1.19
-- 1.3.6.1.4.1.37950.1.1.5.12.3.2.13.1.19
-- 1.3.6.1.4.1.37950.1.1.5.12.3.2.13.1.19
		-- 1.3.6.1.4.1.37950.1.1.5.12.3.2.13.1.19
		voipPTSVlanId OBJECT-TYPE
			SYNTAX Integer32 (0..4095)
			MAX-ACCESS read-write
			STATUS current
			DESCRIPTION
				"Description."
			::= { priVoipParamEntry 19 }

		
--          1.3.6.1.4.1.37950.1.1.5.12.3.2.13.1.20
-- 1.3.6.1.4.1.37950.1.1.5.12.3.2.13.1.20
-- 1.3.6.1.4.1.37950.1.1.5.12.3.2.13.1.20
-- 1.3.6.1.4.1.37950.1.1.5.12.3.2.13.1.20
-- 1.3.6.1.4.1.37950.1.1.5.12.3.2.13.1.20
-- 1.3.6.1.4.1.37950.1.1.5.12.3.2.13.1.20
-- 1.3.6.1.4.1.37950.1.1.5.12.3.2.13.1.20
-- 1.3.6.1.4.1.37950.1.1.5.12.3.2.13.1.20
-- 1.3.6.1.4.1.37950.1.1.5.12.3.2.13.1.20
		-- 1.3.6.1.4.1.37950.1.1.5.12.3.2.13.1.20
		voipPTSVlanCos OBJECT-TYPE
			SYNTAX Integer32 (0..7)
			MAX-ACCESS read-write
			STATUS current
			DESCRIPTION
				"Description."
			::= { priVoipParamEntry 20 }

		
--          1.3.6.1.4.1.37950.1.1.5.12.3.2.13.1.21
-- 1.3.6.1.4.1.37950.1.1.5.12.3.2.13.1.21
-- 1.3.6.1.4.1.37950.1.1.5.12.3.2.13.1.21
-- 1.3.6.1.4.1.37950.1.1.5.12.3.2.13.1.21
-- 1.3.6.1.4.1.37950.1.1.5.12.3.2.13.1.21
-- 1.3.6.1.4.1.37950.1.1.5.12.3.2.13.1.21
-- 1.3.6.1.4.1.37950.1.1.5.12.3.2.13.1.21
-- 1.3.6.1.4.1.37950.1.1.5.12.3.2.13.1.21
-- 1.3.6.1.4.1.37950.1.1.5.12.3.2.13.1.21
		-- 1.3.6.1.4.1.37950.1.1.5.12.3.2.13.1.21
		voipPTCVlanTpid OBJECT-TYPE
			SYNTAX Integer32
			MAX-ACCESS read-write
			STATUS current
			DESCRIPTION
				"Description."
			::= { priVoipParamEntry 21 }

		
--          1.3.6.1.4.1.37950.1.1.5.12.3.2.13.1.22
-- 1.3.6.1.4.1.37950.1.1.5.12.3.2.13.1.22
-- 1.3.6.1.4.1.37950.1.1.5.12.3.2.13.1.22
-- 1.3.6.1.4.1.37950.1.1.5.12.3.2.13.1.22
-- 1.3.6.1.4.1.37950.1.1.5.12.3.2.13.1.22
-- 1.3.6.1.4.1.37950.1.1.5.12.3.2.13.1.22
-- 1.3.6.1.4.1.37950.1.1.5.12.3.2.13.1.22
-- 1.3.6.1.4.1.37950.1.1.5.12.3.2.13.1.22
-- 1.3.6.1.4.1.37950.1.1.5.12.3.2.13.1.22
		-- 1.3.6.1.4.1.37950.1.1.5.12.3.2.13.1.22
		voipPTCVlanId OBJECT-TYPE
			SYNTAX Integer32 (0..4095)
			MAX-ACCESS read-write
			STATUS current
			DESCRIPTION
				"Description."
			::= { priVoipParamEntry 22 }

		
--          1.3.6.1.4.1.37950.1.1.5.12.3.2.13.1.23
-- 1.3.6.1.4.1.37950.1.1.5.12.3.2.13.1.23
-- 1.3.6.1.4.1.37950.1.1.5.12.3.2.13.1.23
-- 1.3.6.1.4.1.37950.1.1.5.12.3.2.13.1.23
-- 1.3.6.1.4.1.37950.1.1.5.12.3.2.13.1.23
-- 1.3.6.1.4.1.37950.1.1.5.12.3.2.13.1.23
-- 1.3.6.1.4.1.37950.1.1.5.12.3.2.13.1.23
-- 1.3.6.1.4.1.37950.1.1.5.12.3.2.13.1.23
-- 1.3.6.1.4.1.37950.1.1.5.12.3.2.13.1.23
		-- 1.3.6.1.4.1.37950.1.1.5.12.3.2.13.1.23
		voipPTCVlanCos OBJECT-TYPE
			SYNTAX Integer32 (0..7)
			MAX-ACCESS read-write
			STATUS current
			DESCRIPTION
				"Description."
			::= { priVoipParamEntry 23 }

		
--          1.3.6.1.4.1.37950.1.1.5.12.3.2.13.1.24
-- 1.3.6.1.4.1.37950.1.1.5.12.3.2.13.1.24
-- 1.3.6.1.4.1.37950.1.1.5.12.3.2.13.1.24
-- 1.3.6.1.4.1.37950.1.1.5.12.3.2.13.1.24
-- 1.3.6.1.4.1.37950.1.1.5.12.3.2.13.1.24
-- 1.3.6.1.4.1.37950.1.1.5.12.3.2.13.1.24
-- 1.3.6.1.4.1.37950.1.1.5.12.3.2.13.1.24
-- 1.3.6.1.4.1.37950.1.1.5.12.3.2.13.1.24
-- 1.3.6.1.4.1.37950.1.1.5.12.3.2.13.1.24
		-- 1.3.6.1.4.1.37950.1.1.5.12.3.2.13.1.24
		voipPTRtpSVlanTpid OBJECT-TYPE
			SYNTAX Integer32
			MAX-ACCESS read-write
			STATUS current
			DESCRIPTION
				"Description."
			::= { priVoipParamEntry 24 }

		
--          1.3.6.1.4.1.37950.1.1.5.12.3.2.13.1.25
-- 1.3.6.1.4.1.37950.1.1.5.12.3.2.13.1.25
-- 1.3.6.1.4.1.37950.1.1.5.12.3.2.13.1.25
-- 1.3.6.1.4.1.37950.1.1.5.12.3.2.13.1.25
-- 1.3.6.1.4.1.37950.1.1.5.12.3.2.13.1.25
-- 1.3.6.1.4.1.37950.1.1.5.12.3.2.13.1.25
-- 1.3.6.1.4.1.37950.1.1.5.12.3.2.13.1.25
-- 1.3.6.1.4.1.37950.1.1.5.12.3.2.13.1.25
-- 1.3.6.1.4.1.37950.1.1.5.12.3.2.13.1.25
		-- 1.3.6.1.4.1.37950.1.1.5.12.3.2.13.1.25
		voipPTRtpSVlanId OBJECT-TYPE
			SYNTAX Integer32 (0..4095)
			MAX-ACCESS read-write
			STATUS current
			DESCRIPTION
				"Description."
			::= { priVoipParamEntry 25 }

		
--          1.3.6.1.4.1.37950.1.1.5.12.3.2.13.1.26
-- 1.3.6.1.4.1.37950.1.1.5.12.3.2.13.1.26
-- 1.3.6.1.4.1.37950.1.1.5.12.3.2.13.1.26
-- 1.3.6.1.4.1.37950.1.1.5.12.3.2.13.1.26
-- 1.3.6.1.4.1.37950.1.1.5.12.3.2.13.1.26
-- 1.3.6.1.4.1.37950.1.1.5.12.3.2.13.1.26
-- 1.3.6.1.4.1.37950.1.1.5.12.3.2.13.1.26
-- 1.3.6.1.4.1.37950.1.1.5.12.3.2.13.1.26
-- 1.3.6.1.4.1.37950.1.1.5.12.3.2.13.1.26
		-- 1.3.6.1.4.1.37950.1.1.5.12.3.2.13.1.26
		voipPTRtpSVlanCos OBJECT-TYPE
			SYNTAX Integer32 (0..7)
			MAX-ACCESS read-write
			STATUS current
			DESCRIPTION
				"Description."
			::= { priVoipParamEntry 26 }

		
--          1.3.6.1.4.1.37950.1.1.5.12.3.2.13.1.27
-- 1.3.6.1.4.1.37950.1.1.5.12.3.2.13.1.27
-- 1.3.6.1.4.1.37950.1.1.5.12.3.2.13.1.27
-- 1.3.6.1.4.1.37950.1.1.5.12.3.2.13.1.27
-- 1.3.6.1.4.1.37950.1.1.5.12.3.2.13.1.27
-- 1.3.6.1.4.1.37950.1.1.5.12.3.2.13.1.27
-- 1.3.6.1.4.1.37950.1.1.5.12.3.2.13.1.27
-- 1.3.6.1.4.1.37950.1.1.5.12.3.2.13.1.27
-- 1.3.6.1.4.1.37950.1.1.5.12.3.2.13.1.27
		-- 1.3.6.1.4.1.37950.1.1.5.12.3.2.13.1.27
		voipPTRtpCVlanTpid OBJECT-TYPE
			SYNTAX Integer32
			MAX-ACCESS read-write
			STATUS current
			DESCRIPTION
				"Description."
			::= { priVoipParamEntry 27 }

		
--          1.3.6.1.4.1.37950.1.1.5.12.3.2.13.1.28
-- 1.3.6.1.4.1.37950.1.1.5.12.3.2.13.1.28
-- 1.3.6.1.4.1.37950.1.1.5.12.3.2.13.1.28
-- 1.3.6.1.4.1.37950.1.1.5.12.3.2.13.1.28
-- 1.3.6.1.4.1.37950.1.1.5.12.3.2.13.1.28
-- 1.3.6.1.4.1.37950.1.1.5.12.3.2.13.1.28
-- 1.3.6.1.4.1.37950.1.1.5.12.3.2.13.1.28
-- 1.3.6.1.4.1.37950.1.1.5.12.3.2.13.1.28
-- 1.3.6.1.4.1.37950.1.1.5.12.3.2.13.1.28
		-- 1.3.6.1.4.1.37950.1.1.5.12.3.2.13.1.28
		voipPTRtpCVlanId OBJECT-TYPE
			SYNTAX Integer32 (0..4095)
			MAX-ACCESS read-write
			STATUS current
			DESCRIPTION
				"Description."
			::= { priVoipParamEntry 28 }

		
--          1.3.6.1.4.1.37950.1.1.5.12.3.2.13.1.29
-- 1.3.6.1.4.1.37950.1.1.5.12.3.2.13.1.29
-- 1.3.6.1.4.1.37950.1.1.5.12.3.2.13.1.29
-- 1.3.6.1.4.1.37950.1.1.5.12.3.2.13.1.29
-- 1.3.6.1.4.1.37950.1.1.5.12.3.2.13.1.29
-- 1.3.6.1.4.1.37950.1.1.5.12.3.2.13.1.29
-- 1.3.6.1.4.1.37950.1.1.5.12.3.2.13.1.29
-- 1.3.6.1.4.1.37950.1.1.5.12.3.2.13.1.29
-- 1.3.6.1.4.1.37950.1.1.5.12.3.2.13.1.29
		-- 1.3.6.1.4.1.37950.1.1.5.12.3.2.13.1.29
		voipPTRtpCVlanCos OBJECT-TYPE
			SYNTAX Integer32 (0..7)
			MAX-ACCESS read-write
			STATUS current
			DESCRIPTION
				"Description."
			::= { priVoipParamEntry 29 }

		
--          1.3.6.1.4.1.37950.1.1.5.12.3.2.14
-- 1.3.6.1.4.1.37950.1.1.5.12.3.2.14
-- 1.3.6.1.4.1.37950.1.1.5.12.3.2.14
-- 1.3.6.1.4.1.37950.1.1.5.12.3.2.14
-- 1.3.6.1.4.1.37950.1.1.5.12.3.2.14
-- 1.3.6.1.4.1.37950.1.1.5.12.3.2.14
-- 1.3.6.1.4.1.37950.1.1.5.12.3.2.14
-- 1.3.6.1.4.1.37950.1.1.5.12.3.2.14
-- 1.3.6.1.4.1.37950.1.1.5.12.3.2.14
		-- 1.3.6.1.4.1.37950.1.1.5.12.3.2.14
		priSipParamTable OBJECT-TYPE
			SYNTAX SEQUENCE OF PriSipParamEntry
			MAX-ACCESS not-accessible
			STATUS current
			DESCRIPTION
				"Description."
			::= { onuPriGlobalInfo 14 }

		
--          1.3.6.1.4.1.37950.1.1.5.12.3.2.14.1
-- 1.3.6.1.4.1.37950.1.1.5.12.3.2.14.1
-- 1.3.6.1.4.1.37950.1.1.5.12.3.2.14.1
-- 1.3.6.1.4.1.37950.1.1.5.12.3.2.14.1
-- 1.3.6.1.4.1.37950.1.1.5.12.3.2.14.1
-- 1.3.6.1.4.1.37950.1.1.5.12.3.2.14.1
-- 1.3.6.1.4.1.37950.1.1.5.12.3.2.14.1
-- 1.3.6.1.4.1.37950.1.1.5.12.3.2.14.1
-- 1.3.6.1.4.1.37950.1.1.5.12.3.2.14.1
		-- 1.3.6.1.4.1.37950.1.1.5.12.3.2.14.1
		priSipParamEntry OBJECT-TYPE
			SYNTAX PriSipParamEntry
			MAX-ACCESS not-accessible
			STATUS current
			DESCRIPTION
				"Description."
			INDEX { sipPTPon, sipPTOnu }
			::= { priSipParamTable 1 }

		
		PriSipParamEntry ::=
			SEQUENCE { 
				sipPTPon
					Integer32,
				sipPTOnu
					Integer32,
				sipPTProxyServName
					OCTET STRING,
				sipPTProxyServPort
					Integer32,
				sipPTBakProxyServName
					OCTET STRING,
				sipPTBakProxyServPort
					Integer32,
				sipPTRegServName
					OCTET STRING,
				sipPTRegServPort
					Integer32,
				sipPTBakRegServName
					OCTET STRING,
				sipPTBakRegServPort
					Integer32,
				sipPTOutBndServName
					OCTET STRING,
				sipPTOutBndServPort
					Integer32,
				sipPTMgPort
					Integer32,
				activeSipProxyServer
					OCTET STRING,
				sipPTRegInterValue
					Integer32,
				sipPTHBeatCfg
					INTEGER,
				sipPTHBeatCycle
					Integer32,
				sipPTHBeatCount
					Integer32
			 }

--          1.3.6.1.4.1.37950.1.1.5.12.3.2.14.1.1
-- 1.3.6.1.4.1.37950.1.1.5.12.3.2.14.1.1
-- 1.3.6.1.4.1.37950.1.1.5.12.3.2.14.1.1
-- 1.3.6.1.4.1.37950.1.1.5.12.3.2.14.1.1
-- 1.3.6.1.4.1.37950.1.1.5.12.3.2.14.1.1
-- 1.3.6.1.4.1.37950.1.1.5.12.3.2.14.1.1
-- 1.3.6.1.4.1.37950.1.1.5.12.3.2.14.1.1
-- 1.3.6.1.4.1.37950.1.1.5.12.3.2.14.1.1
-- 1.3.6.1.4.1.37950.1.1.5.12.3.2.14.1.1
		-- 1.3.6.1.4.1.37950.1.1.5.12.3.2.14.1.1
		sipPTPon OBJECT-TYPE
			SYNTAX Integer32 (1..8)
			MAX-ACCESS read-write
			STATUS current
			DESCRIPTION
				"Description."
			::= { priSipParamEntry 1 }

		
--          1.3.6.1.4.1.37950.1.1.5.12.3.2.14.1.2
-- 1.3.6.1.4.1.37950.1.1.5.12.3.2.14.1.2
-- 1.3.6.1.4.1.37950.1.1.5.12.3.2.14.1.2
-- 1.3.6.1.4.1.37950.1.1.5.12.3.2.14.1.2
-- 1.3.6.1.4.1.37950.1.1.5.12.3.2.14.1.2
-- 1.3.6.1.4.1.37950.1.1.5.12.3.2.14.1.2
-- 1.3.6.1.4.1.37950.1.1.5.12.3.2.14.1.2
-- 1.3.6.1.4.1.37950.1.1.5.12.3.2.14.1.2
-- 1.3.6.1.4.1.37950.1.1.5.12.3.2.14.1.2
		-- 1.3.6.1.4.1.37950.1.1.5.12.3.2.14.1.2
		sipPTOnu OBJECT-TYPE
			SYNTAX Integer32 (1..65535)
			MAX-ACCESS read-write
			STATUS current
			DESCRIPTION
				"Description."
			::= { priSipParamEntry 2 }

		
--          1.3.6.1.4.1.37950.1.1.5.12.3.2.14.1.3
-- 1.3.6.1.4.1.37950.1.1.5.12.3.2.14.1.3
-- 1.3.6.1.4.1.37950.1.1.5.12.3.2.14.1.3
-- 1.3.6.1.4.1.37950.1.1.5.12.3.2.14.1.3
-- 1.3.6.1.4.1.37950.1.1.5.12.3.2.14.1.3
-- 1.3.6.1.4.1.37950.1.1.5.12.3.2.14.1.3
-- 1.3.6.1.4.1.37950.1.1.5.12.3.2.14.1.3
-- 1.3.6.1.4.1.37950.1.1.5.12.3.2.14.1.3
-- 1.3.6.1.4.1.37950.1.1.5.12.3.2.14.1.3
		-- 1.3.6.1.4.1.37950.1.1.5.12.3.2.14.1.3
		sipPTProxyServName OBJECT-TYPE
			SYNTAX OCTET STRING
			MAX-ACCESS read-write
			STATUS current
			DESCRIPTION
				"Description."
			::= { priSipParamEntry 3 }

		
--          1.3.6.1.4.1.37950.1.1.5.12.3.2.14.1.4
-- 1.3.6.1.4.1.37950.1.1.5.12.3.2.14.1.4
-- 1.3.6.1.4.1.37950.1.1.5.12.3.2.14.1.4
-- 1.3.6.1.4.1.37950.1.1.5.12.3.2.14.1.4
-- 1.3.6.1.4.1.37950.1.1.5.12.3.2.14.1.4
-- 1.3.6.1.4.1.37950.1.1.5.12.3.2.14.1.4
-- 1.3.6.1.4.1.37950.1.1.5.12.3.2.14.1.4
-- 1.3.6.1.4.1.37950.1.1.5.12.3.2.14.1.4
-- 1.3.6.1.4.1.37950.1.1.5.12.3.2.14.1.4
		-- 1.3.6.1.4.1.37950.1.1.5.12.3.2.14.1.4
		sipPTProxyServPort OBJECT-TYPE
			SYNTAX Integer32 (0..65535)
			MAX-ACCESS read-write
			STATUS current
			DESCRIPTION
				"Description."
			::= { priSipParamEntry 4 }

		
--          1.3.6.1.4.1.37950.1.1.5.12.3.2.14.1.5
-- 1.3.6.1.4.1.37950.1.1.5.12.3.2.14.1.5
-- 1.3.6.1.4.1.37950.1.1.5.12.3.2.14.1.5
-- 1.3.6.1.4.1.37950.1.1.5.12.3.2.14.1.5
-- 1.3.6.1.4.1.37950.1.1.5.12.3.2.14.1.5
-- 1.3.6.1.4.1.37950.1.1.5.12.3.2.14.1.5
-- 1.3.6.1.4.1.37950.1.1.5.12.3.2.14.1.5
-- 1.3.6.1.4.1.37950.1.1.5.12.3.2.14.1.5
-- 1.3.6.1.4.1.37950.1.1.5.12.3.2.14.1.5
		-- 1.3.6.1.4.1.37950.1.1.5.12.3.2.14.1.5
		sipPTBakProxyServName OBJECT-TYPE
			SYNTAX OCTET STRING
			MAX-ACCESS read-write
			STATUS current
			DESCRIPTION
				"Description."
			::= { priSipParamEntry 5 }

		
--          1.3.6.1.4.1.37950.1.1.5.12.3.2.14.1.6
-- 1.3.6.1.4.1.37950.1.1.5.12.3.2.14.1.6
-- 1.3.6.1.4.1.37950.1.1.5.12.3.2.14.1.6
-- 1.3.6.1.4.1.37950.1.1.5.12.3.2.14.1.6
-- 1.3.6.1.4.1.37950.1.1.5.12.3.2.14.1.6
-- 1.3.6.1.4.1.37950.1.1.5.12.3.2.14.1.6
-- 1.3.6.1.4.1.37950.1.1.5.12.3.2.14.1.6
-- 1.3.6.1.4.1.37950.1.1.5.12.3.2.14.1.6
-- 1.3.6.1.4.1.37950.1.1.5.12.3.2.14.1.6
		-- 1.3.6.1.4.1.37950.1.1.5.12.3.2.14.1.6
		sipPTBakProxyServPort OBJECT-TYPE
			SYNTAX Integer32 (0..65535)
			MAX-ACCESS read-write
			STATUS current
			DESCRIPTION
				"Description."
			::= { priSipParamEntry 6 }

		
--          1.3.6.1.4.1.37950.1.1.5.12.3.2.14.1.7
-- 1.3.6.1.4.1.37950.1.1.5.12.3.2.14.1.7
-- 1.3.6.1.4.1.37950.1.1.5.12.3.2.14.1.7
-- 1.3.6.1.4.1.37950.1.1.5.12.3.2.14.1.7
-- 1.3.6.1.4.1.37950.1.1.5.12.3.2.14.1.7
-- 1.3.6.1.4.1.37950.1.1.5.12.3.2.14.1.7
-- 1.3.6.1.4.1.37950.1.1.5.12.3.2.14.1.7
-- 1.3.6.1.4.1.37950.1.1.5.12.3.2.14.1.7
-- 1.3.6.1.4.1.37950.1.1.5.12.3.2.14.1.7
		-- 1.3.6.1.4.1.37950.1.1.5.12.3.2.14.1.7
		sipPTRegServName OBJECT-TYPE
			SYNTAX OCTET STRING
			MAX-ACCESS read-write
			STATUS current
			DESCRIPTION
				"Description."
			::= { priSipParamEntry 7 }

		
--          1.3.6.1.4.1.37950.1.1.5.12.3.2.14.1.8
-- 1.3.6.1.4.1.37950.1.1.5.12.3.2.14.1.8
-- 1.3.6.1.4.1.37950.1.1.5.12.3.2.14.1.8
-- 1.3.6.1.4.1.37950.1.1.5.12.3.2.14.1.8
-- 1.3.6.1.4.1.37950.1.1.5.12.3.2.14.1.8
-- 1.3.6.1.4.1.37950.1.1.5.12.3.2.14.1.8
-- 1.3.6.1.4.1.37950.1.1.5.12.3.2.14.1.8
-- 1.3.6.1.4.1.37950.1.1.5.12.3.2.14.1.8
-- 1.3.6.1.4.1.37950.1.1.5.12.3.2.14.1.8
		-- 1.3.6.1.4.1.37950.1.1.5.12.3.2.14.1.8
		sipPTRegServPort OBJECT-TYPE
			SYNTAX Integer32 (0..65535)
			MAX-ACCESS read-write
			STATUS current
			DESCRIPTION
				"Description."
			::= { priSipParamEntry 8 }

		
--          1.3.6.1.4.1.37950.1.1.5.12.3.2.14.1.9
-- 1.3.6.1.4.1.37950.1.1.5.12.3.2.14.1.9
-- 1.3.6.1.4.1.37950.1.1.5.12.3.2.14.1.9
-- 1.3.6.1.4.1.37950.1.1.5.12.3.2.14.1.9
-- 1.3.6.1.4.1.37950.1.1.5.12.3.2.14.1.9
-- 1.3.6.1.4.1.37950.1.1.5.12.3.2.14.1.9
-- 1.3.6.1.4.1.37950.1.1.5.12.3.2.14.1.9
-- 1.3.6.1.4.1.37950.1.1.5.12.3.2.14.1.9
-- 1.3.6.1.4.1.37950.1.1.5.12.3.2.14.1.9
		-- 1.3.6.1.4.1.37950.1.1.5.12.3.2.14.1.9
		sipPTBakRegServName OBJECT-TYPE
			SYNTAX OCTET STRING
			MAX-ACCESS read-write
			STATUS current
			DESCRIPTION
				"Description."
			::= { priSipParamEntry 9 }

		
--          1.3.6.1.4.1.37950.1.1.5.12.3.2.14.1.10
-- 1.3.6.1.4.1.37950.1.1.5.12.3.2.14.1.10
-- 1.3.6.1.4.1.37950.1.1.5.12.3.2.14.1.10
-- 1.3.6.1.4.1.37950.1.1.5.12.3.2.14.1.10
-- 1.3.6.1.4.1.37950.1.1.5.12.3.2.14.1.10
-- 1.3.6.1.4.1.37950.1.1.5.12.3.2.14.1.10
-- 1.3.6.1.4.1.37950.1.1.5.12.3.2.14.1.10
-- 1.3.6.1.4.1.37950.1.1.5.12.3.2.14.1.10
-- 1.3.6.1.4.1.37950.1.1.5.12.3.2.14.1.10
		-- 1.3.6.1.4.1.37950.1.1.5.12.3.2.14.1.10
		sipPTBakRegServPort OBJECT-TYPE
			SYNTAX Integer32 (0..65535)
			MAX-ACCESS read-write
			STATUS current
			DESCRIPTION
				"Description."
			::= { priSipParamEntry 10 }

		
--          1.3.6.1.4.1.37950.1.1.5.12.3.2.14.1.11
-- 1.3.6.1.4.1.37950.1.1.5.12.3.2.14.1.11
-- 1.3.6.1.4.1.37950.1.1.5.12.3.2.14.1.11
-- 1.3.6.1.4.1.37950.1.1.5.12.3.2.14.1.11
-- 1.3.6.1.4.1.37950.1.1.5.12.3.2.14.1.11
-- 1.3.6.1.4.1.37950.1.1.5.12.3.2.14.1.11
-- 1.3.6.1.4.1.37950.1.1.5.12.3.2.14.1.11
-- 1.3.6.1.4.1.37950.1.1.5.12.3.2.14.1.11
-- 1.3.6.1.4.1.37950.1.1.5.12.3.2.14.1.11
		-- 1.3.6.1.4.1.37950.1.1.5.12.3.2.14.1.11
		sipPTOutBndServName OBJECT-TYPE
			SYNTAX OCTET STRING
			MAX-ACCESS read-write
			STATUS current
			DESCRIPTION
				"Description."
			::= { priSipParamEntry 11 }

		
--          1.3.6.1.4.1.37950.1.1.5.12.3.2.14.1.12
-- 1.3.6.1.4.1.37950.1.1.5.12.3.2.14.1.12
-- 1.3.6.1.4.1.37950.1.1.5.12.3.2.14.1.12
-- 1.3.6.1.4.1.37950.1.1.5.12.3.2.14.1.12
-- 1.3.6.1.4.1.37950.1.1.5.12.3.2.14.1.12
-- 1.3.6.1.4.1.37950.1.1.5.12.3.2.14.1.12
-- 1.3.6.1.4.1.37950.1.1.5.12.3.2.14.1.12
-- 1.3.6.1.4.1.37950.1.1.5.12.3.2.14.1.12
-- 1.3.6.1.4.1.37950.1.1.5.12.3.2.14.1.12
		-- 1.3.6.1.4.1.37950.1.1.5.12.3.2.14.1.12
		sipPTOutBndServPort OBJECT-TYPE
			SYNTAX Integer32 (0..65535)
			MAX-ACCESS read-write
			STATUS current
			DESCRIPTION
				"Description."
			::= { priSipParamEntry 12 }

		
--          1.3.6.1.4.1.37950.1.1.5.12.3.2.14.1.13
-- 1.3.6.1.4.1.37950.1.1.5.12.3.2.14.1.13
-- 1.3.6.1.4.1.37950.1.1.5.12.3.2.14.1.13
-- 1.3.6.1.4.1.37950.1.1.5.12.3.2.14.1.13
-- 1.3.6.1.4.1.37950.1.1.5.12.3.2.14.1.13
-- 1.3.6.1.4.1.37950.1.1.5.12.3.2.14.1.13
-- 1.3.6.1.4.1.37950.1.1.5.12.3.2.14.1.13
-- 1.3.6.1.4.1.37950.1.1.5.12.3.2.14.1.13
-- 1.3.6.1.4.1.37950.1.1.5.12.3.2.14.1.13
		-- 1.3.6.1.4.1.37950.1.1.5.12.3.2.14.1.13
		sipPTMgPort OBJECT-TYPE
			SYNTAX Integer32 (0..65535)
			MAX-ACCESS read-write
			STATUS current
			DESCRIPTION
				"Description."
			::= { priSipParamEntry 13 }

		
--          1.3.6.1.4.1.37950.1.1.5.12.3.2.14.1.14
-- 1.3.6.1.4.1.37950.1.1.5.12.3.2.14.1.14
-- 1.3.6.1.4.1.37950.1.1.5.12.3.2.14.1.14
-- 1.3.6.1.4.1.37950.1.1.5.12.3.2.14.1.14
-- 1.3.6.1.4.1.37950.1.1.5.12.3.2.14.1.14
-- 1.3.6.1.4.1.37950.1.1.5.12.3.2.14.1.14
-- 1.3.6.1.4.1.37950.1.1.5.12.3.2.14.1.14
-- 1.3.6.1.4.1.37950.1.1.5.12.3.2.14.1.14
-- 1.3.6.1.4.1.37950.1.1.5.12.3.2.14.1.14
		-- 1.3.6.1.4.1.37950.1.1.5.12.3.2.14.1.14
		activeSipProxyServer OBJECT-TYPE
			SYNTAX OCTET STRING
			MAX-ACCESS read-write
			STATUS current
			DESCRIPTION
				"Description."
			::= { priSipParamEntry 14 }

		
--          1.3.6.1.4.1.37950.1.1.5.12.3.2.14.1.15
-- 1.3.6.1.4.1.37950.1.1.5.12.3.2.14.1.15
-- 1.3.6.1.4.1.37950.1.1.5.12.3.2.14.1.15
-- 1.3.6.1.4.1.37950.1.1.5.12.3.2.14.1.15
-- 1.3.6.1.4.1.37950.1.1.5.12.3.2.14.1.15
-- 1.3.6.1.4.1.37950.1.1.5.12.3.2.14.1.15
-- 1.3.6.1.4.1.37950.1.1.5.12.3.2.14.1.15
-- 1.3.6.1.4.1.37950.1.1.5.12.3.2.14.1.15
-- 1.3.6.1.4.1.37950.1.1.5.12.3.2.14.1.15
		-- 1.3.6.1.4.1.37950.1.1.5.12.3.2.14.1.15
		sipPTRegInterValue OBJECT-TYPE
			SYNTAX Integer32 (0..10000000)
			MAX-ACCESS read-write
			STATUS current
			DESCRIPTION
				"Description."
			::= { priSipParamEntry 15 }

		
--          1.3.6.1.4.1.37950.1.1.5.12.3.2.14.1.16
-- 1.3.6.1.4.1.37950.1.1.5.12.3.2.14.1.16
-- 1.3.6.1.4.1.37950.1.1.5.12.3.2.14.1.16
-- 1.3.6.1.4.1.37950.1.1.5.12.3.2.14.1.16
-- 1.3.6.1.4.1.37950.1.1.5.12.3.2.14.1.16
-- 1.3.6.1.4.1.37950.1.1.5.12.3.2.14.1.16
-- 1.3.6.1.4.1.37950.1.1.5.12.3.2.14.1.16
-- 1.3.6.1.4.1.37950.1.1.5.12.3.2.14.1.16
-- 1.3.6.1.4.1.37950.1.1.5.12.3.2.14.1.16
		-- 1.3.6.1.4.1.37950.1.1.5.12.3.2.14.1.16
		sipPTHBeatCfg OBJECT-TYPE
			SYNTAX INTEGER
				{
				disable(0),
				active(1),
				passive(2)
				}
			MAX-ACCESS read-write
			STATUS current
			DESCRIPTION
				"Description."
			::= { priSipParamEntry 16 }

		
--          1.3.6.1.4.1.37950.1.1.5.12.3.2.14.1.17
-- 1.3.6.1.4.1.37950.1.1.5.12.3.2.14.1.17
-- 1.3.6.1.4.1.37950.1.1.5.12.3.2.14.1.17
-- 1.3.6.1.4.1.37950.1.1.5.12.3.2.14.1.17
-- 1.3.6.1.4.1.37950.1.1.5.12.3.2.14.1.17
-- 1.3.6.1.4.1.37950.1.1.5.12.3.2.14.1.17
-- 1.3.6.1.4.1.37950.1.1.5.12.3.2.14.1.17
-- 1.3.6.1.4.1.37950.1.1.5.12.3.2.14.1.17
-- 1.3.6.1.4.1.37950.1.1.5.12.3.2.14.1.17
		-- 1.3.6.1.4.1.37950.1.1.5.12.3.2.14.1.17
		sipPTHBeatCycle OBJECT-TYPE
			SYNTAX Integer32 (1..65525)
			MAX-ACCESS read-write
			STATUS current
			DESCRIPTION
				"Description."
			::= { priSipParamEntry 17 }

		
--          1.3.6.1.4.1.37950.1.1.5.12.3.2.14.1.18
-- 1.3.6.1.4.1.37950.1.1.5.12.3.2.14.1.18
-- 1.3.6.1.4.1.37950.1.1.5.12.3.2.14.1.18
-- 1.3.6.1.4.1.37950.1.1.5.12.3.2.14.1.18
-- 1.3.6.1.4.1.37950.1.1.5.12.3.2.14.1.18
-- 1.3.6.1.4.1.37950.1.1.5.12.3.2.14.1.18
-- 1.3.6.1.4.1.37950.1.1.5.12.3.2.14.1.18
-- 1.3.6.1.4.1.37950.1.1.5.12.3.2.14.1.18
-- 1.3.6.1.4.1.37950.1.1.5.12.3.2.14.1.18
		-- 1.3.6.1.4.1.37950.1.1.5.12.3.2.14.1.18
		sipPTHBeatCount OBJECT-TYPE
			SYNTAX Integer32 (1..65535)
			MAX-ACCESS read-write
			STATUS current
			DESCRIPTION
				"Description."
			::= { priSipParamEntry 18 }

		
--         1.3.6.1.4.1.37950.1.1.5.12.3.2.15
-- 1.3.6.1.4.1.37950.1.1.5.12.3.2.15
-- 1.3.6.1.4.1.37950.1.1.5.12.3.2.15
-- 1.3.6.1.4.1.37950.1.1.5.12.3.2.15
-- 1.3.6.1.4.1.37950.1.1.5.12.3.2.15
-- 1.3.6.1.4.1.37950.1.1.5.12.3.2.15
-- 1.3.6.1.4.1.37950.1.1.5.12.3.2.15
-- 1.3.6.1.4.1.37950.1.1.5.12.3.2.15
		-- 1.3.6.1.4.1.37950.1.1.5.12.3.2.15
		priUsernameTable OBJECT-TYPE
			SYNTAX SEQUENCE OF PriUsernameEntry
			MAX-ACCESS not-accessible
			STATUS current
			DESCRIPTION
				"Description."
			::= { onuPriGlobalInfo 15 }

		
--         1.3.6.1.4.1.37950.1.1.5.12.3.2.15.1
-- 1.3.6.1.4.1.37950.1.1.5.12.3.2.15.1
-- 1.3.6.1.4.1.37950.1.1.5.12.3.2.15.1
-- 1.3.6.1.4.1.37950.1.1.5.12.3.2.15.1
-- 1.3.6.1.4.1.37950.1.1.5.12.3.2.15.1
-- 1.3.6.1.4.1.37950.1.1.5.12.3.2.15.1
-- 1.3.6.1.4.1.37950.1.1.5.12.3.2.15.1
-- 1.3.6.1.4.1.37950.1.1.5.12.3.2.15.1
		-- 1.3.6.1.4.1.37950.1.1.5.12.3.2.15.1
		priUsernameEntry OBJECT-TYPE
			SYNTAX PriUsernameEntry
			MAX-ACCESS not-accessible
			STATUS current
			DESCRIPTION
				"Description."
			INDEX { usernamePon, usernameOnu }
			::= { priUsernameTable 1 }

		
		PriUsernameEntry ::=
			SEQUENCE { 
				usernamePon
					Unsigned32,
				usernameOnu
					Unsigned32,
				priUsernameAdminCtl
					INTEGER,
				priUsernameAdminName
					OCTET STRING,
				priUsernameAdminPwd
					OCTET STRING,
				priUsernameUserCtl
					INTEGER,
				priUsernameUserName
					OCTET STRING,
				priUsernameUserPwd
					OCTET STRING
			 }

--         1.3.6.1.4.1.37950.1.1.5.12.3.2.15.1.1
-- 1.3.6.1.4.1.37950.1.1.5.12.3.2.15.1.1
-- 1.3.6.1.4.1.37950.1.1.5.12.3.2.15.1.1
-- 1.3.6.1.4.1.37950.1.1.5.12.3.2.15.1.1
-- 1.3.6.1.4.1.37950.1.1.5.12.3.2.15.1.1
-- 1.3.6.1.4.1.37950.1.1.5.12.3.2.15.1.1
-- 1.3.6.1.4.1.37950.1.1.5.12.3.2.15.1.1
-- 1.3.6.1.4.1.37950.1.1.5.12.3.2.15.1.1
		-- 1.3.6.1.4.1.37950.1.1.5.12.3.2.15.1.1
		usernamePon OBJECT-TYPE
			SYNTAX Unsigned32
			MAX-ACCESS read-only
			STATUS current
			DESCRIPTION
				"Description."
			::= { priUsernameEntry 1 }

		
--         1.3.6.1.4.1.37950.1.1.5.12.3.2.15.1.2
-- 1.3.6.1.4.1.37950.1.1.5.12.3.2.15.1.2
-- 1.3.6.1.4.1.37950.1.1.5.12.3.2.15.1.2
-- 1.3.6.1.4.1.37950.1.1.5.12.3.2.15.1.2
-- 1.3.6.1.4.1.37950.1.1.5.12.3.2.15.1.2
-- 1.3.6.1.4.1.37950.1.1.5.12.3.2.15.1.2
-- 1.3.6.1.4.1.37950.1.1.5.12.3.2.15.1.2
-- 1.3.6.1.4.1.37950.1.1.5.12.3.2.15.1.2
		-- 1.3.6.1.4.1.37950.1.1.5.12.3.2.15.1.2
		usernameOnu OBJECT-TYPE
			SYNTAX Unsigned32
			MAX-ACCESS read-only
			STATUS current
			DESCRIPTION
				"Description."
			::= { priUsernameEntry 2 }

		
--         1.3.6.1.4.1.37950.1.1.5.12.3.2.15.1.3
-- 1.3.6.1.4.1.37950.1.1.5.12.3.2.15.1.3
-- 1.3.6.1.4.1.37950.1.1.5.12.3.2.15.1.3
-- 1.3.6.1.4.1.37950.1.1.5.12.3.2.15.1.3
-- 1.3.6.1.4.1.37950.1.1.5.12.3.2.15.1.3
-- 1.3.6.1.4.1.37950.1.1.5.12.3.2.15.1.3
-- 1.3.6.1.4.1.37950.1.1.5.12.3.2.15.1.3
-- 1.3.6.1.4.1.37950.1.1.5.12.3.2.15.1.3
		-- 1.3.6.1.4.1.37950.1.1.5.12.3.2.15.1.3
		priUsernameAdminCtl OBJECT-TYPE
			SYNTAX INTEGER
				{
				disable(0),
				enable(1)
				}
			MAX-ACCESS read-only
			STATUS current
			DESCRIPTION
				"Description."
			::= { priUsernameEntry 3 }

		
--         1.3.6.1.4.1.37950.1.1.5.12.3.2.15.1.4
-- 1.3.6.1.4.1.37950.1.1.5.12.3.2.15.1.4
-- 1.3.6.1.4.1.37950.1.1.5.12.3.2.15.1.4
-- 1.3.6.1.4.1.37950.1.1.5.12.3.2.15.1.4
-- 1.3.6.1.4.1.37950.1.1.5.12.3.2.15.1.4
-- 1.3.6.1.4.1.37950.1.1.5.12.3.2.15.1.4
-- 1.3.6.1.4.1.37950.1.1.5.12.3.2.15.1.4
-- 1.3.6.1.4.1.37950.1.1.5.12.3.2.15.1.4
		-- 1.3.6.1.4.1.37950.1.1.5.12.3.2.15.1.4
		priUsernameAdminName OBJECT-TYPE
			SYNTAX OCTET STRING
			MAX-ACCESS read-only
			STATUS current
			DESCRIPTION
				"Description."
			::= { priUsernameEntry 4 }

		
--         1.3.6.1.4.1.37950.1.1.5.12.3.2.15.1.5
-- 1.3.6.1.4.1.37950.1.1.5.12.3.2.15.1.5
-- 1.3.6.1.4.1.37950.1.1.5.12.3.2.15.1.5
-- 1.3.6.1.4.1.37950.1.1.5.12.3.2.15.1.5
-- 1.3.6.1.4.1.37950.1.1.5.12.3.2.15.1.5
-- 1.3.6.1.4.1.37950.1.1.5.12.3.2.15.1.5
-- 1.3.6.1.4.1.37950.1.1.5.12.3.2.15.1.5
-- 1.3.6.1.4.1.37950.1.1.5.12.3.2.15.1.5
		-- 1.3.6.1.4.1.37950.1.1.5.12.3.2.15.1.5
		priUsernameAdminPwd OBJECT-TYPE
			SYNTAX OCTET STRING
			MAX-ACCESS read-only
			STATUS current
			DESCRIPTION
				"Description."
			::= { priUsernameEntry 5 }

		
--         1.3.6.1.4.1.37950.1.1.5.12.3.2.15.1.6
-- 1.3.6.1.4.1.37950.1.1.5.12.3.2.15.1.6
-- 1.3.6.1.4.1.37950.1.1.5.12.3.2.15.1.6
-- 1.3.6.1.4.1.37950.1.1.5.12.3.2.15.1.6
-- 1.3.6.1.4.1.37950.1.1.5.12.3.2.15.1.6
-- 1.3.6.1.4.1.37950.1.1.5.12.3.2.15.1.6
-- 1.3.6.1.4.1.37950.1.1.5.12.3.2.15.1.6
-- 1.3.6.1.4.1.37950.1.1.5.12.3.2.15.1.6
		-- 1.3.6.1.4.1.37950.1.1.5.12.3.2.15.1.6
		priUsernameUserCtl OBJECT-TYPE
			SYNTAX INTEGER
				{
				disable(0),
				enable(1)
				}
			MAX-ACCESS read-only
			STATUS current
			DESCRIPTION
				"Description."
			::= { priUsernameEntry 6 }

		
--         1.3.6.1.4.1.37950.1.1.5.12.3.2.15.1.7
-- 1.3.6.1.4.1.37950.1.1.5.12.3.2.15.1.7
-- 1.3.6.1.4.1.37950.1.1.5.12.3.2.15.1.7
-- 1.3.6.1.4.1.37950.1.1.5.12.3.2.15.1.7
-- 1.3.6.1.4.1.37950.1.1.5.12.3.2.15.1.7
-- 1.3.6.1.4.1.37950.1.1.5.12.3.2.15.1.7
-- 1.3.6.1.4.1.37950.1.1.5.12.3.2.15.1.7
-- 1.3.6.1.4.1.37950.1.1.5.12.3.2.15.1.7
		-- 1.3.6.1.4.1.37950.1.1.5.12.3.2.15.1.7
		priUsernameUserName OBJECT-TYPE
			SYNTAX OCTET STRING
			MAX-ACCESS read-write
			STATUS current
			DESCRIPTION
				"Description."
			::= { priUsernameEntry 7 }

		
--         1.3.6.1.4.1.37950.1.1.5.12.3.2.15.1.8
-- 1.3.6.1.4.1.37950.1.1.5.12.3.2.15.1.8
-- 1.3.6.1.4.1.37950.1.1.5.12.3.2.15.1.8
-- 1.3.6.1.4.1.37950.1.1.5.12.3.2.15.1.8
-- 1.3.6.1.4.1.37950.1.1.5.12.3.2.15.1.8
-- 1.3.6.1.4.1.37950.1.1.5.12.3.2.15.1.8
-- 1.3.6.1.4.1.37950.1.1.5.12.3.2.15.1.8
-- 1.3.6.1.4.1.37950.1.1.5.12.3.2.15.1.8
		-- 1.3.6.1.4.1.37950.1.1.5.12.3.2.15.1.8
		priUsernameUserPwd OBJECT-TYPE
			SYNTAX OCTET STRING
			MAX-ACCESS read-only
			STATUS current
			DESCRIPTION
				"Description."
			::= { priUsernameEntry 8 }

		
--         1.3.6.1.4.1.37950.1.1.5.12.3.2.16
-- 1.3.6.1.4.1.37950.1.1.5.12.3.2.16
-- 1.3.6.1.4.1.37950.1.1.5.12.3.2.16
-- 1.3.6.1.4.1.37950.1.1.5.12.3.2.16
-- 1.3.6.1.4.1.37950.1.1.5.12.3.2.16
-- 1.3.6.1.4.1.37950.1.1.5.12.3.2.16
-- 1.3.6.1.4.1.37950.1.1.5.12.3.2.16
-- 1.3.6.1.4.1.37950.1.1.5.12.3.2.16
		-- 1.3.6.1.4.1.37950.1.1.5.12.3.2.16
		priFirewallTable OBJECT-TYPE
			SYNTAX SEQUENCE OF PriFirewallEntry
			MAX-ACCESS not-accessible
			STATUS current
			DESCRIPTION
				"Description."
			::= { onuPriGlobalInfo 16 }

		
--         1.3.6.1.4.1.37950.1.1.5.12.3.2.16.1
-- 1.3.6.1.4.1.37950.1.1.5.12.3.2.16.1
-- 1.3.6.1.4.1.37950.1.1.5.12.3.2.16.1
-- 1.3.6.1.4.1.37950.1.1.5.12.3.2.16.1
-- 1.3.6.1.4.1.37950.1.1.5.12.3.2.16.1
-- 1.3.6.1.4.1.37950.1.1.5.12.3.2.16.1
-- 1.3.6.1.4.1.37950.1.1.5.12.3.2.16.1
-- 1.3.6.1.4.1.37950.1.1.5.12.3.2.16.1
		-- 1.3.6.1.4.1.37950.1.1.5.12.3.2.16.1
		priFirewallEntry OBJECT-TYPE
			SYNTAX PriFirewallEntry
			MAX-ACCESS not-accessible
			STATUS current
			DESCRIPTION
				"Description."
			INDEX { priFirewallPon, priFirewallOnu }
			::= { priFirewallTable 1 }

		
		PriFirewallEntry ::=
			SEQUENCE { 
				priFirewallPon
					Unsigned32,
				priFirewallOnu
					Unsigned32,
				priFirewallLevel
					INTEGER
			 }

--         1.3.6.1.4.1.37950.1.1.5.12.3.2.16.1.1
-- 1.3.6.1.4.1.37950.1.1.5.12.3.2.16.1.1
-- 1.3.6.1.4.1.37950.1.1.5.12.3.2.16.1.1
-- 1.3.6.1.4.1.37950.1.1.5.12.3.2.16.1.1
-- 1.3.6.1.4.1.37950.1.1.5.12.3.2.16.1.1
-- 1.3.6.1.4.1.37950.1.1.5.12.3.2.16.1.1
-- 1.3.6.1.4.1.37950.1.1.5.12.3.2.16.1.1
-- 1.3.6.1.4.1.37950.1.1.5.12.3.2.16.1.1
		-- 1.3.6.1.4.1.37950.1.1.5.12.3.2.16.1.1
		priFirewallPon OBJECT-TYPE
			SYNTAX Unsigned32
			MAX-ACCESS read-only
			STATUS current
			DESCRIPTION
				"Description."
			::= { priFirewallEntry 1 }

		
--         1.3.6.1.4.1.37950.1.1.5.12.3.2.16.1.2
-- 1.3.6.1.4.1.37950.1.1.5.12.3.2.16.1.2
-- 1.3.6.1.4.1.37950.1.1.5.12.3.2.16.1.2
-- 1.3.6.1.4.1.37950.1.1.5.12.3.2.16.1.2
-- 1.3.6.1.4.1.37950.1.1.5.12.3.2.16.1.2
-- 1.3.6.1.4.1.37950.1.1.5.12.3.2.16.1.2
-- 1.3.6.1.4.1.37950.1.1.5.12.3.2.16.1.2
-- 1.3.6.1.4.1.37950.1.1.5.12.3.2.16.1.2
		-- 1.3.6.1.4.1.37950.1.1.5.12.3.2.16.1.2
		priFirewallOnu OBJECT-TYPE
			SYNTAX Unsigned32
			MAX-ACCESS read-only
			STATUS current
			DESCRIPTION
				"Description."
			::= { priFirewallEntry 2 }

		
--         1.3.6.1.4.1.37950.1.1.5.12.3.2.16.1.3
-- 1.3.6.1.4.1.37950.1.1.5.12.3.2.16.1.3
-- 1.3.6.1.4.1.37950.1.1.5.12.3.2.16.1.3
-- 1.3.6.1.4.1.37950.1.1.5.12.3.2.16.1.3
-- 1.3.6.1.4.1.37950.1.1.5.12.3.2.16.1.3
-- 1.3.6.1.4.1.37950.1.1.5.12.3.2.16.1.3
-- 1.3.6.1.4.1.37950.1.1.5.12.3.2.16.1.3
-- 1.3.6.1.4.1.37950.1.1.5.12.3.2.16.1.3
		-- 1.3.6.1.4.1.37950.1.1.5.12.3.2.16.1.3
		priFirewallLevel OBJECT-TYPE
			SYNTAX INTEGER
				{
				disable(0),
				low(1),
				middle(2),
				high(3)
				}
			MAX-ACCESS read-only
			STATUS current
			DESCRIPTION
				"Description."
			::= { priFirewallEntry 3 }

		
--         1.3.6.1.4.1.37950.1.1.5.12.3.2.17
-- 1.3.6.1.4.1.37950.1.1.5.12.3.2.17
-- 1.3.6.1.4.1.37950.1.1.5.12.3.2.17
-- 1.3.6.1.4.1.37950.1.1.5.12.3.2.17
-- 1.3.6.1.4.1.37950.1.1.5.12.3.2.17
-- 1.3.6.1.4.1.37950.1.1.5.12.3.2.17
-- 1.3.6.1.4.1.37950.1.1.5.12.3.2.17
-- 1.3.6.1.4.1.37950.1.1.5.12.3.2.17
		-- 1.3.6.1.4.1.37950.1.1.5.12.3.2.17
		priAclTable OBJECT-TYPE
			SYNTAX SEQUENCE OF PriAclEntry
			MAX-ACCESS not-accessible
			STATUS current
			DESCRIPTION
				"Description."
			::= { onuPriGlobalInfo 17 }

		
--         1.3.6.1.4.1.37950.1.1.5.12.3.2.17.1
-- 1.3.6.1.4.1.37950.1.1.5.12.3.2.17.1
-- 1.3.6.1.4.1.37950.1.1.5.12.3.2.17.1
-- 1.3.6.1.4.1.37950.1.1.5.12.3.2.17.1
-- 1.3.6.1.4.1.37950.1.1.5.12.3.2.17.1
-- 1.3.6.1.4.1.37950.1.1.5.12.3.2.17.1
-- 1.3.6.1.4.1.37950.1.1.5.12.3.2.17.1
-- 1.3.6.1.4.1.37950.1.1.5.12.3.2.17.1
		-- 1.3.6.1.4.1.37950.1.1.5.12.3.2.17.1
		priAclEntry OBJECT-TYPE
			SYNTAX PriAclEntry
			MAX-ACCESS not-accessible
			STATUS current
			DESCRIPTION
				"Description."
			INDEX { priAclPon, priAclOnu, priAclProtocolType }
			::= { priAclTable 1 }

		
		PriAclEntry ::=
			SEQUENCE { 
				priAclPon
					Unsigned32,
				priAclOnu
					Unsigned32,
				priAclProtocolType
					INTEGER,
				priAclControl
					INTEGER,
				priAclLanControl
					INTEGER,
				priAclWanControl
					INTEGER,
				priAclIpv4Control
					INTEGER,
				priAclIPv4Address
					IpAddress,
				priAclIPv4MaskAddr
					IpAddress,
				priAclIpv6Control
					INTEGER,
				priAclIPv6Address
					OCTET STRING,
				priAclPort
					Unsigned32
			 }

--         1.3.6.1.4.1.37950.1.1.5.12.3.2.17.1.1
-- 1.3.6.1.4.1.37950.1.1.5.12.3.2.17.1.1
-- 1.3.6.1.4.1.37950.1.1.5.12.3.2.17.1.1
-- 1.3.6.1.4.1.37950.1.1.5.12.3.2.17.1.1
-- 1.3.6.1.4.1.37950.1.1.5.12.3.2.17.1.1
-- 1.3.6.1.4.1.37950.1.1.5.12.3.2.17.1.1
-- 1.3.6.1.4.1.37950.1.1.5.12.3.2.17.1.1
-- 1.3.6.1.4.1.37950.1.1.5.12.3.2.17.1.1
		-- 1.3.6.1.4.1.37950.1.1.5.12.3.2.17.1.1
		priAclPon OBJECT-TYPE
			SYNTAX Unsigned32
			MAX-ACCESS read-only
			STATUS current
			DESCRIPTION
				"Description."
			::= { priAclEntry 1 }

		
--         1.3.6.1.4.1.37950.1.1.5.12.3.2.17.1.2
-- 1.3.6.1.4.1.37950.1.1.5.12.3.2.17.1.2
-- 1.3.6.1.4.1.37950.1.1.5.12.3.2.17.1.2
-- 1.3.6.1.4.1.37950.1.1.5.12.3.2.17.1.2
-- 1.3.6.1.4.1.37950.1.1.5.12.3.2.17.1.2
-- 1.3.6.1.4.1.37950.1.1.5.12.3.2.17.1.2
-- 1.3.6.1.4.1.37950.1.1.5.12.3.2.17.1.2
-- 1.3.6.1.4.1.37950.1.1.5.12.3.2.17.1.2
		-- 1.3.6.1.4.1.37950.1.1.5.12.3.2.17.1.2
		priAclOnu OBJECT-TYPE
			SYNTAX Unsigned32
			MAX-ACCESS read-only
			STATUS current
			DESCRIPTION
				"Description."
			::= { priAclEntry 2 }

		
--         1.3.6.1.4.1.37950.1.1.5.12.3.2.17.1.3
-- 1.3.6.1.4.1.37950.1.1.5.12.3.2.17.1.3
-- 1.3.6.1.4.1.37950.1.1.5.12.3.2.17.1.3
-- 1.3.6.1.4.1.37950.1.1.5.12.3.2.17.1.3
-- 1.3.6.1.4.1.37950.1.1.5.12.3.2.17.1.3
-- 1.3.6.1.4.1.37950.1.1.5.12.3.2.17.1.3
-- 1.3.6.1.4.1.37950.1.1.5.12.3.2.17.1.3
-- 1.3.6.1.4.1.37950.1.1.5.12.3.2.17.1.3
		-- 1.3.6.1.4.1.37950.1.1.5.12.3.2.17.1.3
		priAclProtocolType OBJECT-TYPE
			SYNTAX INTEGER
				{
				telnet(0),
				ftp(1),
				http(2),
				https(3),
				tftp(4),
				ping(5)
				}
			MAX-ACCESS read-only
			STATUS current
			DESCRIPTION
				"Description."
			::= { priAclEntry 3 }

		
--         1.3.6.1.4.1.37950.1.1.5.12.3.2.17.1.4
-- 1.3.6.1.4.1.37950.1.1.5.12.3.2.17.1.4
-- 1.3.6.1.4.1.37950.1.1.5.12.3.2.17.1.4
-- 1.3.6.1.4.1.37950.1.1.5.12.3.2.17.1.4
-- 1.3.6.1.4.1.37950.1.1.5.12.3.2.17.1.4
-- 1.3.6.1.4.1.37950.1.1.5.12.3.2.17.1.4
-- 1.3.6.1.4.1.37950.1.1.5.12.3.2.17.1.4
-- 1.3.6.1.4.1.37950.1.1.5.12.3.2.17.1.4
		-- 1.3.6.1.4.1.37950.1.1.5.12.3.2.17.1.4
		priAclControl OBJECT-TYPE
			SYNTAX INTEGER
				{
				disable(0),
				enable(1)
				}
			MAX-ACCESS read-only
			STATUS current
			DESCRIPTION
				"Description."
			::= { priAclEntry 4 }

		
--         1.3.6.1.4.1.37950.1.1.5.12.3.2.17.1.5
-- 1.3.6.1.4.1.37950.1.1.5.12.3.2.17.1.5
-- 1.3.6.1.4.1.37950.1.1.5.12.3.2.17.1.5
-- 1.3.6.1.4.1.37950.1.1.5.12.3.2.17.1.5
-- 1.3.6.1.4.1.37950.1.1.5.12.3.2.17.1.5
-- 1.3.6.1.4.1.37950.1.1.5.12.3.2.17.1.5
-- 1.3.6.1.4.1.37950.1.1.5.12.3.2.17.1.5
-- 1.3.6.1.4.1.37950.1.1.5.12.3.2.17.1.5
		-- 1.3.6.1.4.1.37950.1.1.5.12.3.2.17.1.5
		priAclLanControl OBJECT-TYPE
			SYNTAX INTEGER
				{
				disable(0),
				enable(1)
				}
			MAX-ACCESS read-only
			STATUS current
			DESCRIPTION
				"Description."
			::= { priAclEntry 5 }

		
--         1.3.6.1.4.1.37950.1.1.5.12.3.2.17.1.6
-- 1.3.6.1.4.1.37950.1.1.5.12.3.2.17.1.6
-- 1.3.6.1.4.1.37950.1.1.5.12.3.2.17.1.6
-- 1.3.6.1.4.1.37950.1.1.5.12.3.2.17.1.6
-- 1.3.6.1.4.1.37950.1.1.5.12.3.2.17.1.6
-- 1.3.6.1.4.1.37950.1.1.5.12.3.2.17.1.6
-- 1.3.6.1.4.1.37950.1.1.5.12.3.2.17.1.6
-- 1.3.6.1.4.1.37950.1.1.5.12.3.2.17.1.6
		-- 1.3.6.1.4.1.37950.1.1.5.12.3.2.17.1.6
		priAclWanControl OBJECT-TYPE
			SYNTAX INTEGER
				{
				disable(0),
				enable(1)
				}
			MAX-ACCESS read-only
			STATUS current
			DESCRIPTION
				"Description."
			::= { priAclEntry 6 }

		
--         1.3.6.1.4.1.37950.1.1.5.12.3.2.17.1.7
-- 1.3.6.1.4.1.37950.1.1.5.12.3.2.17.1.7
-- 1.3.6.1.4.1.37950.1.1.5.12.3.2.17.1.7
-- 1.3.6.1.4.1.37950.1.1.5.12.3.2.17.1.7
-- 1.3.6.1.4.1.37950.1.1.5.12.3.2.17.1.7
-- 1.3.6.1.4.1.37950.1.1.5.12.3.2.17.1.7
-- 1.3.6.1.4.1.37950.1.1.5.12.3.2.17.1.7
-- 1.3.6.1.4.1.37950.1.1.5.12.3.2.17.1.7
		-- 1.3.6.1.4.1.37950.1.1.5.12.3.2.17.1.7
		priAclIpv4Control OBJECT-TYPE
			SYNTAX INTEGER
				{
				disable(0),
				enable(1)
				}
			MAX-ACCESS read-only
			STATUS current
			DESCRIPTION
				"Description."
			::= { priAclEntry 7 }

		
--         1.3.6.1.4.1.37950.1.1.5.12.3.2.17.1.8
-- 1.3.6.1.4.1.37950.1.1.5.12.3.2.17.1.8
-- 1.3.6.1.4.1.37950.1.1.5.12.3.2.17.1.8
-- 1.3.6.1.4.1.37950.1.1.5.12.3.2.17.1.8
-- 1.3.6.1.4.1.37950.1.1.5.12.3.2.17.1.8
-- 1.3.6.1.4.1.37950.1.1.5.12.3.2.17.1.8
-- 1.3.6.1.4.1.37950.1.1.5.12.3.2.17.1.8
-- 1.3.6.1.4.1.37950.1.1.5.12.3.2.17.1.8
		-- 1.3.6.1.4.1.37950.1.1.5.12.3.2.17.1.8
		priAclIPv4Address OBJECT-TYPE
			SYNTAX IpAddress
			MAX-ACCESS read-only
			STATUS current
			DESCRIPTION
				"Description."
			::= { priAclEntry 8 }

		
--         1.3.6.1.4.1.37950.1.1.5.12.3.2.17.1.9
-- 1.3.6.1.4.1.37950.1.1.5.12.3.2.17.1.9
-- 1.3.6.1.4.1.37950.1.1.5.12.3.2.17.1.9
-- 1.3.6.1.4.1.37950.1.1.5.12.3.2.17.1.9
-- 1.3.6.1.4.1.37950.1.1.5.12.3.2.17.1.9
-- 1.3.6.1.4.1.37950.1.1.5.12.3.2.17.1.9
-- 1.3.6.1.4.1.37950.1.1.5.12.3.2.17.1.9
-- 1.3.6.1.4.1.37950.1.1.5.12.3.2.17.1.9
		-- 1.3.6.1.4.1.37950.1.1.5.12.3.2.17.1.9
		priAclIPv4MaskAddr OBJECT-TYPE
			SYNTAX IpAddress
			MAX-ACCESS read-only
			STATUS current
			DESCRIPTION
				"Description."
			::= { priAclEntry 9 }

		
--         1.3.6.1.4.1.37950.1.1.5.12.3.2.17.1.10
-- 1.3.6.1.4.1.37950.1.1.5.12.3.2.17.1.10
-- 1.3.6.1.4.1.37950.1.1.5.12.3.2.17.1.10
-- 1.3.6.1.4.1.37950.1.1.5.12.3.2.17.1.10
-- 1.3.6.1.4.1.37950.1.1.5.12.3.2.17.1.10
-- 1.3.6.1.4.1.37950.1.1.5.12.3.2.17.1.10
-- 1.3.6.1.4.1.37950.1.1.5.12.3.2.17.1.10
-- 1.3.6.1.4.1.37950.1.1.5.12.3.2.17.1.10
		-- 1.3.6.1.4.1.37950.1.1.5.12.3.2.17.1.10
		priAclIpv6Control OBJECT-TYPE
			SYNTAX INTEGER
				{
				disable(0),
				enable(1)
				}
			MAX-ACCESS read-only
			STATUS current
			DESCRIPTION
				"Description."
			::= { priAclEntry 10 }

		
--         1.3.6.1.4.1.37950.1.1.5.12.3.2.17.1.11
-- 1.3.6.1.4.1.37950.1.1.5.12.3.2.17.1.11
-- 1.3.6.1.4.1.37950.1.1.5.12.3.2.17.1.11
-- 1.3.6.1.4.1.37950.1.1.5.12.3.2.17.1.11
-- 1.3.6.1.4.1.37950.1.1.5.12.3.2.17.1.11
-- 1.3.6.1.4.1.37950.1.1.5.12.3.2.17.1.11
-- 1.3.6.1.4.1.37950.1.1.5.12.3.2.17.1.11
-- 1.3.6.1.4.1.37950.1.1.5.12.3.2.17.1.11
		-- 1.3.6.1.4.1.37950.1.1.5.12.3.2.17.1.11
		priAclIPv6Address OBJECT-TYPE
			SYNTAX OCTET STRING
			MAX-ACCESS read-only
			STATUS current
			DESCRIPTION
				"Description."
			::= { priAclEntry 11 }

		
--         1.3.6.1.4.1.37950.1.1.5.12.3.2.17.1.12
-- 1.3.6.1.4.1.37950.1.1.5.12.3.2.17.1.12
-- 1.3.6.1.4.1.37950.1.1.5.12.3.2.17.1.12
-- 1.3.6.1.4.1.37950.1.1.5.12.3.2.17.1.12
-- 1.3.6.1.4.1.37950.1.1.5.12.3.2.17.1.12
-- 1.3.6.1.4.1.37950.1.1.5.12.3.2.17.1.12
-- 1.3.6.1.4.1.37950.1.1.5.12.3.2.17.1.12
-- 1.3.6.1.4.1.37950.1.1.5.12.3.2.17.1.12
		-- 1.3.6.1.4.1.37950.1.1.5.12.3.2.17.1.12
		priAclPort OBJECT-TYPE
			SYNTAX Unsigned32
			MAX-ACCESS read-only
			STATUS current
			DESCRIPTION
				"Description."
			::= { priAclEntry 12 }

		
--         1.3.6.1.4.1.37950.1.1.5.12.3.2.18
-- 1.3.6.1.4.1.37950.1.1.5.12.3.2.18
-- 1.3.6.1.4.1.37950.1.1.5.12.3.2.18
-- 1.3.6.1.4.1.37950.1.1.5.12.3.2.18
-- 1.3.6.1.4.1.37950.1.1.5.12.3.2.18
-- 1.3.6.1.4.1.37950.1.1.5.12.3.2.18
-- 1.3.6.1.4.1.37950.1.1.5.12.3.2.18
-- 1.3.6.1.4.1.37950.1.1.5.12.3.2.18
		-- 1.3.6.1.4.1.37950.1.1.5.12.3.2.18
		priDhcpv6ServerTable OBJECT-TYPE
			SYNTAX SEQUENCE OF PriDhcpv6ServerEntry
			MAX-ACCESS not-accessible
			STATUS current
			DESCRIPTION
				"Description."
			::= { onuPriGlobalInfo 18 }

		
--         1.3.6.1.4.1.37950.1.1.5.12.3.2.18.1
-- 1.3.6.1.4.1.37950.1.1.5.12.3.2.18.1
-- 1.3.6.1.4.1.37950.1.1.5.12.3.2.18.1
-- 1.3.6.1.4.1.37950.1.1.5.12.3.2.18.1
-- 1.3.6.1.4.1.37950.1.1.5.12.3.2.18.1
-- 1.3.6.1.4.1.37950.1.1.5.12.3.2.18.1
-- 1.3.6.1.4.1.37950.1.1.5.12.3.2.18.1
-- 1.3.6.1.4.1.37950.1.1.5.12.3.2.18.1
		-- 1.3.6.1.4.1.37950.1.1.5.12.3.2.18.1
		priDhcpv6ServerEntry OBJECT-TYPE
			SYNTAX PriDhcpv6ServerEntry
			MAX-ACCESS not-accessible
			STATUS current
			DESCRIPTION
				"Description."
			INDEX { priDhcpv6ServerPon, priDhcpv6ServerOnu }
			::= { priDhcpv6ServerTable 1 }

		
		PriDhcpv6ServerEntry ::=
			SEQUENCE { 
				priDhcpv6ServerPon
					Integer32,
				priDhcpv6ServerOnu
					Integer32,
				priDhcpv6LanIp
					OCTET STRING,
				priDhcpv6LanPrefixlen
					INTEGER,
				priDhcpv6PrefixMode
					INTEGER,
				priDhcpv6PrefixModeIp
					OCTET STRING,
				priDhcpv6Enable
					INTEGER,
				priDhcpv6Preference
					Unsigned32,
				priDhcpv6BeginIp
					OCTET STRING,
				priDhcpv6EndIp
					OCTET STRING,
				priDhcpv6PoolType
					INTEGER,
				priDhcpv6MasterDns
					OCTET STRING,
				priDhcpv6SlaveDns
					OCTET STRING,
				priDhcpv6Gateway
					OCTET STRING,
				priDhcpv6RelayIp
					OCTET STRING,
				priDhcpv6RA
					INTEGER,
				priDhcpv6RAManage
					INTEGER,
				priDhcpv6RAOther
					INTEGER,
				priDhcpv6RAMaxInterval
					Integer32,
				priDhcpv6RAMinInterval
					Integer32,
				priDhcpv6Valid
					Unsigned32,
				priDhcpv6DnsMode
					INTEGER
			 }

--         1.3.6.1.4.1.37950.1.1.5.12.3.2.18.1.1
-- 1.3.6.1.4.1.37950.1.1.5.12.3.2.18.1.1
-- 1.3.6.1.4.1.37950.1.1.5.12.3.2.18.1.1
-- 1.3.6.1.4.1.37950.1.1.5.12.3.2.18.1.1
-- 1.3.6.1.4.1.37950.1.1.5.12.3.2.18.1.1
-- 1.3.6.1.4.1.37950.1.1.5.12.3.2.18.1.1
-- 1.3.6.1.4.1.37950.1.1.5.12.3.2.18.1.1
-- 1.3.6.1.4.1.37950.1.1.5.12.3.2.18.1.1
		-- 1.3.6.1.4.1.37950.1.1.5.12.3.2.18.1.1
		priDhcpv6ServerPon OBJECT-TYPE
			SYNTAX Integer32
			MAX-ACCESS read-write
			STATUS current
			DESCRIPTION
				"Description."
			::= { priDhcpv6ServerEntry 1 }

		
--         1.3.6.1.4.1.37950.1.1.5.12.3.2.18.1.2
-- 1.3.6.1.4.1.37950.1.1.5.12.3.2.18.1.2
-- 1.3.6.1.4.1.37950.1.1.5.12.3.2.18.1.2
-- 1.3.6.1.4.1.37950.1.1.5.12.3.2.18.1.2
-- 1.3.6.1.4.1.37950.1.1.5.12.3.2.18.1.2
-- 1.3.6.1.4.1.37950.1.1.5.12.3.2.18.1.2
-- 1.3.6.1.4.1.37950.1.1.5.12.3.2.18.1.2
-- 1.3.6.1.4.1.37950.1.1.5.12.3.2.18.1.2
		-- 1.3.6.1.4.1.37950.1.1.5.12.3.2.18.1.2
		priDhcpv6ServerOnu OBJECT-TYPE
			SYNTAX Integer32
			MAX-ACCESS read-write
			STATUS current
			DESCRIPTION
				"Description."
			::= { priDhcpv6ServerEntry 2 }

		
--         1.3.6.1.4.1.37950.1.1.5.12.3.2.18.1.3
-- 1.3.6.1.4.1.37950.1.1.5.12.3.2.18.1.3
-- 1.3.6.1.4.1.37950.1.1.5.12.3.2.18.1.3
-- 1.3.6.1.4.1.37950.1.1.5.12.3.2.18.1.3
-- 1.3.6.1.4.1.37950.1.1.5.12.3.2.18.1.3
-- 1.3.6.1.4.1.37950.1.1.5.12.3.2.18.1.3
-- 1.3.6.1.4.1.37950.1.1.5.12.3.2.18.1.3
-- 1.3.6.1.4.1.37950.1.1.5.12.3.2.18.1.3
		-- 1.3.6.1.4.1.37950.1.1.5.12.3.2.18.1.3
		priDhcpv6LanIp OBJECT-TYPE
			SYNTAX OCTET STRING
			MAX-ACCESS read-write
			STATUS current
			DESCRIPTION
				"Description."
			::= { priDhcpv6ServerEntry 3 }

		
--         1.3.6.1.4.1.37950.1.1.5.12.3.2.18.1.4
-- 1.3.6.1.4.1.37950.1.1.5.12.3.2.18.1.4
-- 1.3.6.1.4.1.37950.1.1.5.12.3.2.18.1.4
-- 1.3.6.1.4.1.37950.1.1.5.12.3.2.18.1.4
-- 1.3.6.1.4.1.37950.1.1.5.12.3.2.18.1.4
-- 1.3.6.1.4.1.37950.1.1.5.12.3.2.18.1.4
-- 1.3.6.1.4.1.37950.1.1.5.12.3.2.18.1.4
-- 1.3.6.1.4.1.37950.1.1.5.12.3.2.18.1.4
		-- 1.3.6.1.4.1.37950.1.1.5.12.3.2.18.1.4
		priDhcpv6LanPrefixlen OBJECT-TYPE
			SYNTAX INTEGER
			MAX-ACCESS read-write
			STATUS current
			DESCRIPTION
				"Description."
			::= { priDhcpv6ServerEntry 4 }

		
--         1.3.6.1.4.1.37950.1.1.5.12.3.2.18.1.5
-- 1.3.6.1.4.1.37950.1.1.5.12.3.2.18.1.5
-- 1.3.6.1.4.1.37950.1.1.5.12.3.2.18.1.5
-- 1.3.6.1.4.1.37950.1.1.5.12.3.2.18.1.5
-- 1.3.6.1.4.1.37950.1.1.5.12.3.2.18.1.5
-- 1.3.6.1.4.1.37950.1.1.5.12.3.2.18.1.5
-- 1.3.6.1.4.1.37950.1.1.5.12.3.2.18.1.5
-- 1.3.6.1.4.1.37950.1.1.5.12.3.2.18.1.5
		-- 1.3.6.1.4.1.37950.1.1.5.12.3.2.18.1.5
		priDhcpv6PrefixMode OBJECT-TYPE
			SYNTAX INTEGER
				{
				disable(0),
				static(1)
				}
			MAX-ACCESS read-write
			STATUS current
			DESCRIPTION
				"Description."
			::= { priDhcpv6ServerEntry 5 }

		
--         1.3.6.1.4.1.37950.1.1.5.12.3.2.18.1.6
-- 1.3.6.1.4.1.37950.1.1.5.12.3.2.18.1.6
-- 1.3.6.1.4.1.37950.1.1.5.12.3.2.18.1.6
-- 1.3.6.1.4.1.37950.1.1.5.12.3.2.18.1.6
-- 1.3.6.1.4.1.37950.1.1.5.12.3.2.18.1.6
-- 1.3.6.1.4.1.37950.1.1.5.12.3.2.18.1.6
-- 1.3.6.1.4.1.37950.1.1.5.12.3.2.18.1.6
-- 1.3.6.1.4.1.37950.1.1.5.12.3.2.18.1.6
		-- 1.3.6.1.4.1.37950.1.1.5.12.3.2.18.1.6
		priDhcpv6PrefixModeIp OBJECT-TYPE
			SYNTAX OCTET STRING
			MAX-ACCESS read-write
			STATUS current
			DESCRIPTION
				"Description."
			::= { priDhcpv6ServerEntry 6 }

		
--         1.3.6.1.4.1.37950.1.1.5.12.3.2.18.1.7
-- 1.3.6.1.4.1.37950.1.1.5.12.3.2.18.1.7
-- 1.3.6.1.4.1.37950.1.1.5.12.3.2.18.1.7
-- 1.3.6.1.4.1.37950.1.1.5.12.3.2.18.1.7
-- 1.3.6.1.4.1.37950.1.1.5.12.3.2.18.1.7
-- 1.3.6.1.4.1.37950.1.1.5.12.3.2.18.1.7
-- 1.3.6.1.4.1.37950.1.1.5.12.3.2.18.1.7
-- 1.3.6.1.4.1.37950.1.1.5.12.3.2.18.1.7
		-- 1.3.6.1.4.1.37950.1.1.5.12.3.2.18.1.7
		priDhcpv6Enable OBJECT-TYPE
			SYNTAX INTEGER
				{
				disable(0),
				enable(1),
				relay(2)
				}
			MAX-ACCESS read-write
			STATUS current
			DESCRIPTION
				"Description."
			::= { priDhcpv6ServerEntry 7 }

		
--         1.3.6.1.4.1.37950.1.1.5.12.3.2.18.1.8
-- 1.3.6.1.4.1.37950.1.1.5.12.3.2.18.1.8
-- 1.3.6.1.4.1.37950.1.1.5.12.3.2.18.1.8
-- 1.3.6.1.4.1.37950.1.1.5.12.3.2.18.1.8
-- 1.3.6.1.4.1.37950.1.1.5.12.3.2.18.1.8
-- 1.3.6.1.4.1.37950.1.1.5.12.3.2.18.1.8
-- 1.3.6.1.4.1.37950.1.1.5.12.3.2.18.1.8
-- 1.3.6.1.4.1.37950.1.1.5.12.3.2.18.1.8
		-- 1.3.6.1.4.1.37950.1.1.5.12.3.2.18.1.8
		priDhcpv6Preference OBJECT-TYPE
			SYNTAX Unsigned32
			MAX-ACCESS read-write
			STATUS current
			DESCRIPTION
				"Description."
			::= { priDhcpv6ServerEntry 8 }

		
--         1.3.6.1.4.1.37950.1.1.5.12.3.2.18.1.9
-- 1.3.6.1.4.1.37950.1.1.5.12.3.2.18.1.9
-- 1.3.6.1.4.1.37950.1.1.5.12.3.2.18.1.9
-- 1.3.6.1.4.1.37950.1.1.5.12.3.2.18.1.9
-- 1.3.6.1.4.1.37950.1.1.5.12.3.2.18.1.9
-- 1.3.6.1.4.1.37950.1.1.5.12.3.2.18.1.9
-- 1.3.6.1.4.1.37950.1.1.5.12.3.2.18.1.9
-- 1.3.6.1.4.1.37950.1.1.5.12.3.2.18.1.9
		-- 1.3.6.1.4.1.37950.1.1.5.12.3.2.18.1.9
		priDhcpv6BeginIp OBJECT-TYPE
			SYNTAX OCTET STRING
			MAX-ACCESS read-write
			STATUS current
			DESCRIPTION
				"Description."
			::= { priDhcpv6ServerEntry 9 }

		
--         1.3.6.1.4.1.37950.1.1.5.12.3.2.18.1.10
-- 1.3.6.1.4.1.37950.1.1.5.12.3.2.18.1.10
-- 1.3.6.1.4.1.37950.1.1.5.12.3.2.18.1.10
-- 1.3.6.1.4.1.37950.1.1.5.12.3.2.18.1.10
-- 1.3.6.1.4.1.37950.1.1.5.12.3.2.18.1.10
-- 1.3.6.1.4.1.37950.1.1.5.12.3.2.18.1.10
-- 1.3.6.1.4.1.37950.1.1.5.12.3.2.18.1.10
-- 1.3.6.1.4.1.37950.1.1.5.12.3.2.18.1.10
		-- 1.3.6.1.4.1.37950.1.1.5.12.3.2.18.1.10
		priDhcpv6EndIp OBJECT-TYPE
			SYNTAX OCTET STRING
			MAX-ACCESS read-write
			STATUS current
			DESCRIPTION
				"Description."
			::= { priDhcpv6ServerEntry 10 }

		
--         1.3.6.1.4.1.37950.1.1.5.12.3.2.18.1.11
-- 1.3.6.1.4.1.37950.1.1.5.12.3.2.18.1.11
-- 1.3.6.1.4.1.37950.1.1.5.12.3.2.18.1.11
-- 1.3.6.1.4.1.37950.1.1.5.12.3.2.18.1.11
-- 1.3.6.1.4.1.37950.1.1.5.12.3.2.18.1.11
-- 1.3.6.1.4.1.37950.1.1.5.12.3.2.18.1.11
-- 1.3.6.1.4.1.37950.1.1.5.12.3.2.18.1.11
-- 1.3.6.1.4.1.37950.1.1.5.12.3.2.18.1.11
		-- 1.3.6.1.4.1.37950.1.1.5.12.3.2.18.1.11
		priDhcpv6PoolType OBJECT-TYPE
			SYNTAX INTEGER
				{
				pc(0),
				camera(1),
				stb(2),
				ip-phone(3)
				}
			MAX-ACCESS read-write
			STATUS current
			DESCRIPTION
				"Description."
			::= { priDhcpv6ServerEntry 11 }

		
--         1.3.6.1.4.1.37950.1.1.5.12.3.2.18.1.12
-- 1.3.6.1.4.1.37950.1.1.5.12.3.2.18.1.12
-- 1.3.6.1.4.1.37950.1.1.5.12.3.2.18.1.12
-- 1.3.6.1.4.1.37950.1.1.5.12.3.2.18.1.12
-- 1.3.6.1.4.1.37950.1.1.5.12.3.2.18.1.12
-- 1.3.6.1.4.1.37950.1.1.5.12.3.2.18.1.12
-- 1.3.6.1.4.1.37950.1.1.5.12.3.2.18.1.12
-- 1.3.6.1.4.1.37950.1.1.5.12.3.2.18.1.12
		-- 1.3.6.1.4.1.37950.1.1.5.12.3.2.18.1.12
		priDhcpv6MasterDns OBJECT-TYPE
			SYNTAX OCTET STRING
			MAX-ACCESS read-write
			STATUS current
			DESCRIPTION
				"Description."
			::= { priDhcpv6ServerEntry 12 }

		
--         1.3.6.1.4.1.37950.1.1.5.12.3.2.18.1.13
-- 1.3.6.1.4.1.37950.1.1.5.12.3.2.18.1.13
-- 1.3.6.1.4.1.37950.1.1.5.12.3.2.18.1.13
-- 1.3.6.1.4.1.37950.1.1.5.12.3.2.18.1.13
-- 1.3.6.1.4.1.37950.1.1.5.12.3.2.18.1.13
-- 1.3.6.1.4.1.37950.1.1.5.12.3.2.18.1.13
-- 1.3.6.1.4.1.37950.1.1.5.12.3.2.18.1.13
-- 1.3.6.1.4.1.37950.1.1.5.12.3.2.18.1.13
		-- 1.3.6.1.4.1.37950.1.1.5.12.3.2.18.1.13
		priDhcpv6SlaveDns OBJECT-TYPE
			SYNTAX OCTET STRING
			MAX-ACCESS read-write
			STATUS current
			DESCRIPTION
				"Description."
			::= { priDhcpv6ServerEntry 13 }

		
--         1.3.6.1.4.1.37950.1.1.5.12.3.2.18.1.14
-- 1.3.6.1.4.1.37950.1.1.5.12.3.2.18.1.14
-- 1.3.6.1.4.1.37950.1.1.5.12.3.2.18.1.14
-- 1.3.6.1.4.1.37950.1.1.5.12.3.2.18.1.14
-- 1.3.6.1.4.1.37950.1.1.5.12.3.2.18.1.14
-- 1.3.6.1.4.1.37950.1.1.5.12.3.2.18.1.14
-- 1.3.6.1.4.1.37950.1.1.5.12.3.2.18.1.14
-- 1.3.6.1.4.1.37950.1.1.5.12.3.2.18.1.14
		-- 1.3.6.1.4.1.37950.1.1.5.12.3.2.18.1.14
		priDhcpv6Gateway OBJECT-TYPE
			SYNTAX OCTET STRING
			MAX-ACCESS read-write
			STATUS current
			DESCRIPTION
				"Description."
			::= { priDhcpv6ServerEntry 14 }

		
--         1.3.6.1.4.1.37950.1.1.5.12.3.2.18.1.15
-- 1.3.6.1.4.1.37950.1.1.5.12.3.2.18.1.15
-- 1.3.6.1.4.1.37950.1.1.5.12.3.2.18.1.15
-- 1.3.6.1.4.1.37950.1.1.5.12.3.2.18.1.15
-- 1.3.6.1.4.1.37950.1.1.5.12.3.2.18.1.15
-- 1.3.6.1.4.1.37950.1.1.5.12.3.2.18.1.15
-- 1.3.6.1.4.1.37950.1.1.5.12.3.2.18.1.15
-- 1.3.6.1.4.1.37950.1.1.5.12.3.2.18.1.15
		-- 1.3.6.1.4.1.37950.1.1.5.12.3.2.18.1.15
		priDhcpv6RelayIp OBJECT-TYPE
			SYNTAX OCTET STRING
			MAX-ACCESS read-write
			STATUS current
			DESCRIPTION
				"Description."
			::= { priDhcpv6ServerEntry 15 }

		
--         1.3.6.1.4.1.37950.1.1.5.12.3.2.18.1.16
-- 1.3.6.1.4.1.37950.1.1.5.12.3.2.18.1.16
-- 1.3.6.1.4.1.37950.1.1.5.12.3.2.18.1.16
-- 1.3.6.1.4.1.37950.1.1.5.12.3.2.18.1.16
-- 1.3.6.1.4.1.37950.1.1.5.12.3.2.18.1.16
-- 1.3.6.1.4.1.37950.1.1.5.12.3.2.18.1.16
-- 1.3.6.1.4.1.37950.1.1.5.12.3.2.18.1.16
-- 1.3.6.1.4.1.37950.1.1.5.12.3.2.18.1.16
		-- 1.3.6.1.4.1.37950.1.1.5.12.3.2.18.1.16
		priDhcpv6RA OBJECT-TYPE
			SYNTAX INTEGER
				{
				disable(0),
				enable(1)
				}
			MAX-ACCESS read-write
			STATUS current
			DESCRIPTION
				"Description."
			::= { priDhcpv6ServerEntry 16 }

		
--         1.3.6.1.4.1.37950.1.1.5.12.3.2.18.1.17
-- 1.3.6.1.4.1.37950.1.1.5.12.3.2.18.1.17
-- 1.3.6.1.4.1.37950.1.1.5.12.3.2.18.1.17
-- 1.3.6.1.4.1.37950.1.1.5.12.3.2.18.1.17
-- 1.3.6.1.4.1.37950.1.1.5.12.3.2.18.1.17
-- 1.3.6.1.4.1.37950.1.1.5.12.3.2.18.1.17
-- 1.3.6.1.4.1.37950.1.1.5.12.3.2.18.1.17
-- 1.3.6.1.4.1.37950.1.1.5.12.3.2.18.1.17
		-- 1.3.6.1.4.1.37950.1.1.5.12.3.2.18.1.17
		priDhcpv6RAManage OBJECT-TYPE
			SYNTAX INTEGER
				{
				disable(0),
				enable(1)
				}
			MAX-ACCESS read-write
			STATUS current
			DESCRIPTION
				"Description."
			::= { priDhcpv6ServerEntry 17 }

		
--         1.3.6.1.4.1.37950.1.1.5.12.3.2.18.1.18
-- 1.3.6.1.4.1.37950.1.1.5.12.3.2.18.1.18
-- 1.3.6.1.4.1.37950.1.1.5.12.3.2.18.1.18
-- 1.3.6.1.4.1.37950.1.1.5.12.3.2.18.1.18
-- 1.3.6.1.4.1.37950.1.1.5.12.3.2.18.1.18
-- 1.3.6.1.4.1.37950.1.1.5.12.3.2.18.1.18
-- 1.3.6.1.4.1.37950.1.1.5.12.3.2.18.1.18
-- 1.3.6.1.4.1.37950.1.1.5.12.3.2.18.1.18
		-- 1.3.6.1.4.1.37950.1.1.5.12.3.2.18.1.18
		priDhcpv6RAOther OBJECT-TYPE
			SYNTAX INTEGER
				{
				disable(0),
				enable(1)
				}
			MAX-ACCESS read-write
			STATUS current
			DESCRIPTION
				"Description."
			::= { priDhcpv6ServerEntry 18 }

		
--         1.3.6.1.4.1.37950.1.1.5.12.3.2.18.1.19
-- 1.3.6.1.4.1.37950.1.1.5.12.3.2.18.1.19
-- 1.3.6.1.4.1.37950.1.1.5.12.3.2.18.1.19
-- 1.3.6.1.4.1.37950.1.1.5.12.3.2.18.1.19
-- 1.3.6.1.4.1.37950.1.1.5.12.3.2.18.1.19
-- 1.3.6.1.4.1.37950.1.1.5.12.3.2.18.1.19
-- 1.3.6.1.4.1.37950.1.1.5.12.3.2.18.1.19
-- 1.3.6.1.4.1.37950.1.1.5.12.3.2.18.1.19
		-- 1.3.6.1.4.1.37950.1.1.5.12.3.2.18.1.19
		priDhcpv6RAMaxInterval OBJECT-TYPE
			SYNTAX Integer32
			MAX-ACCESS read-write
			STATUS current
			DESCRIPTION
				"Description."
			::= { priDhcpv6ServerEntry 19 }

		
--         1.3.6.1.4.1.37950.1.1.5.12.3.2.18.1.20
-- 1.3.6.1.4.1.37950.1.1.5.12.3.2.18.1.20
-- 1.3.6.1.4.1.37950.1.1.5.12.3.2.18.1.20
-- 1.3.6.1.4.1.37950.1.1.5.12.3.2.18.1.20
-- 1.3.6.1.4.1.37950.1.1.5.12.3.2.18.1.20
-- 1.3.6.1.4.1.37950.1.1.5.12.3.2.18.1.20
-- 1.3.6.1.4.1.37950.1.1.5.12.3.2.18.1.20
-- 1.3.6.1.4.1.37950.1.1.5.12.3.2.18.1.20
		-- 1.3.6.1.4.1.37950.1.1.5.12.3.2.18.1.20
		priDhcpv6RAMinInterval OBJECT-TYPE
			SYNTAX Integer32
			MAX-ACCESS read-write
			STATUS current
			DESCRIPTION
				"Description."
			::= { priDhcpv6ServerEntry 20 }

		
--         1.3.6.1.4.1.37950.1.1.5.12.3.2.18.1.21
-- 1.3.6.1.4.1.37950.1.1.5.12.3.2.18.1.21
-- 1.3.6.1.4.1.37950.1.1.5.12.3.2.18.1.21
-- 1.3.6.1.4.1.37950.1.1.5.12.3.2.18.1.21
-- 1.3.6.1.4.1.37950.1.1.5.12.3.2.18.1.21
-- 1.3.6.1.4.1.37950.1.1.5.12.3.2.18.1.21
-- 1.3.6.1.4.1.37950.1.1.5.12.3.2.18.1.21
-- 1.3.6.1.4.1.37950.1.1.5.12.3.2.18.1.21
		-- 1.3.6.1.4.1.37950.1.1.5.12.3.2.18.1.21
		priDhcpv6Valid OBJECT-TYPE
			SYNTAX Unsigned32
			MAX-ACCESS read-write
			STATUS current
			DESCRIPTION
				"Description."
			::= { priDhcpv6ServerEntry 21 }

		
--         1.3.6.1.4.1.37950.1.1.5.12.3.2.18.1.22
-- 1.3.6.1.4.1.37950.1.1.5.12.3.2.18.1.22
-- 1.3.6.1.4.1.37950.1.1.5.12.3.2.18.1.22
-- 1.3.6.1.4.1.37950.1.1.5.12.3.2.18.1.22
-- 1.3.6.1.4.1.37950.1.1.5.12.3.2.18.1.22
-- 1.3.6.1.4.1.37950.1.1.5.12.3.2.18.1.22
-- 1.3.6.1.4.1.37950.1.1.5.12.3.2.18.1.22
-- 1.3.6.1.4.1.37950.1.1.5.12.3.2.18.1.22
		-- 1.3.6.1.4.1.37950.1.1.5.12.3.2.18.1.22
		priDhcpv6DnsMode OBJECT-TYPE
			SYNTAX INTEGER
				{
				wanconnection(0),
				static(1),
				hgwproxy(2)
				}
			MAX-ACCESS read-write
			STATUS current
			DESCRIPTION
				"Description."
			::= { priDhcpv6ServerEntry 22 }

		
--         1.3.6.1.4.1.37950.1.1.5.12.3.2.19
-- 1.3.6.1.4.1.37950.1.1.5.12.3.2.19
-- 1.3.6.1.4.1.37950.1.1.5.12.3.2.19
-- 1.3.6.1.4.1.37950.1.1.5.12.3.2.19
-- 1.3.6.1.4.1.37950.1.1.5.12.3.2.19
-- 1.3.6.1.4.1.37950.1.1.5.12.3.2.19
-- 1.3.6.1.4.1.37950.1.1.5.12.3.2.19
-- 1.3.6.1.4.1.37950.1.1.5.12.3.2.19
		-- 1.3.6.1.4.1.37950.1.1.5.12.3.2.19
		priWifiSwitchTable OBJECT-TYPE
			SYNTAX SEQUENCE OF PriWifiSwitchEntry
			MAX-ACCESS not-accessible
			STATUS current
			DESCRIPTION
				"Description."
			::= { onuPriGlobalInfo 19 }

		
--         1.3.6.1.4.1.37950.1.1.5.12.3.2.19.1
-- 1.3.6.1.4.1.37950.1.1.5.12.3.2.19.1
-- 1.3.6.1.4.1.37950.1.1.5.12.3.2.19.1
-- 1.3.6.1.4.1.37950.1.1.5.12.3.2.19.1
-- 1.3.6.1.4.1.37950.1.1.5.12.3.2.19.1
-- 1.3.6.1.4.1.37950.1.1.5.12.3.2.19.1
-- 1.3.6.1.4.1.37950.1.1.5.12.3.2.19.1
-- 1.3.6.1.4.1.37950.1.1.5.12.3.2.19.1
		-- 1.3.6.1.4.1.37950.1.1.5.12.3.2.19.1
		priWifiSwitchEntry OBJECT-TYPE
			SYNTAX PriWifiSwitchEntry
			MAX-ACCESS not-accessible
			STATUS current
			DESCRIPTION
				"Description."
			INDEX { priWifiSwitchPonS, priWifiSwitchOnuS }
			::= { priWifiSwitchTable 1 }

		
		PriWifiSwitchEntry ::=
			SEQUENCE { 
				priWifiSwitchPonS
					INTEGER,
				priWifiSwitchOnuS
					INTEGER,
				priWifiSwitchAPModuleS
					INTEGER,
				priWifiSwitchCountry
					INTEGER,
				priWifiSwitchChannelS
					INTEGER,
				priWifiSwitchStandardS
					INTEGER,
				priWifiSwitchPower1
					INTEGER,
				priWifiSwitchChannelWidth
					INTEGER,
				priWifiSwitchEasyMeshStatus
					INTEGER
			 }

--         1.3.6.1.4.1.37950.1.1.5.12.3.2.19.1.1
-- 1.3.6.1.4.1.37950.1.1.5.12.3.2.19.1.1
-- 1.3.6.1.4.1.37950.1.1.5.12.3.2.19.1.1
-- 1.3.6.1.4.1.37950.1.1.5.12.3.2.19.1.1
-- 1.3.6.1.4.1.37950.1.1.5.12.3.2.19.1.1
-- 1.3.6.1.4.1.37950.1.1.5.12.3.2.19.1.1
-- 1.3.6.1.4.1.37950.1.1.5.12.3.2.19.1.1
-- 1.3.6.1.4.1.37950.1.1.5.12.3.2.19.1.1
		-- 1.3.6.1.4.1.37950.1.1.5.12.3.2.19.1.1
		priWifiSwitchPonS OBJECT-TYPE
			SYNTAX INTEGER (1..16)
			MAX-ACCESS read-write
			STATUS current
			DESCRIPTION
				"Description."
			::= { priWifiSwitchEntry 1 }

		
--         1.3.6.1.4.1.37950.1.1.5.12.3.2.19.1.2
-- 1.3.6.1.4.1.37950.1.1.5.12.3.2.19.1.2
-- 1.3.6.1.4.1.37950.1.1.5.12.3.2.19.1.2
-- 1.3.6.1.4.1.37950.1.1.5.12.3.2.19.1.2
-- 1.3.6.1.4.1.37950.1.1.5.12.3.2.19.1.2
-- 1.3.6.1.4.1.37950.1.1.5.12.3.2.19.1.2
-- 1.3.6.1.4.1.37950.1.1.5.12.3.2.19.1.2
-- 1.3.6.1.4.1.37950.1.1.5.12.3.2.19.1.2
		-- 1.3.6.1.4.1.37950.1.1.5.12.3.2.19.1.2
		priWifiSwitchOnuS OBJECT-TYPE
			SYNTAX INTEGER (1..65535)
			MAX-ACCESS read-write
			STATUS current
			DESCRIPTION
				"Description."
			::= { priWifiSwitchEntry 2 }

		
--         1.3.6.1.4.1.37950.1.1.5.12.3.2.19.1.3
-- 1.3.6.1.4.1.37950.1.1.5.12.3.2.19.1.3
-- 1.3.6.1.4.1.37950.1.1.5.12.3.2.19.1.3
-- 1.3.6.1.4.1.37950.1.1.5.12.3.2.19.1.3
-- 1.3.6.1.4.1.37950.1.1.5.12.3.2.19.1.3
-- 1.3.6.1.4.1.37950.1.1.5.12.3.2.19.1.3
-- 1.3.6.1.4.1.37950.1.1.5.12.3.2.19.1.3
-- 1.3.6.1.4.1.37950.1.1.5.12.3.2.19.1.3
		-- 1.3.6.1.4.1.37950.1.1.5.12.3.2.19.1.3
		priWifiSwitchAPModuleS OBJECT-TYPE
			SYNTAX INTEGER
				{
				disable(0),
				enable(1)
				}
			MAX-ACCESS read-write
			STATUS current
			DESCRIPTION
				"Description."
			::= { priWifiSwitchEntry 3 }

		
--         1.3.6.1.4.1.37950.1.1.5.12.3.2.19.1.4
-- 1.3.6.1.4.1.37950.1.1.5.12.3.2.19.1.4
-- 1.3.6.1.4.1.37950.1.1.5.12.3.2.19.1.4
-- 1.3.6.1.4.1.37950.1.1.5.12.3.2.19.1.4
-- 1.3.6.1.4.1.37950.1.1.5.12.3.2.19.1.4
-- 1.3.6.1.4.1.37950.1.1.5.12.3.2.19.1.4
-- 1.3.6.1.4.1.37950.1.1.5.12.3.2.19.1.4
-- 1.3.6.1.4.1.37950.1.1.5.12.3.2.19.1.4
		-- 1.3.6.1.4.1.37950.1.1.5.12.3.2.19.1.4
		priWifiSwitchCountry OBJECT-TYPE
			SYNTAX INTEGER
				{
				etsi(0),
				fcc(1),
				ic(2),
				spain(3),
				france(4),
				mkk(5),
				isreal(6),
				mkk2(7),
				mkk3(8),
				russian(9),
				cn(10),
				global(11),
				world-wide(12),
				mkk1(13),
				ncc(14)
				}
			MAX-ACCESS read-write
			STATUS current
			DESCRIPTION
				"Description."
			::= { priWifiSwitchEntry 4 }

		
--         1.3.6.1.4.1.37950.1.1.5.12.3.2.19.1.5
-- 1.3.6.1.4.1.37950.1.1.5.12.3.2.19.1.5
-- 1.3.6.1.4.1.37950.1.1.5.12.3.2.19.1.5
-- 1.3.6.1.4.1.37950.1.1.5.12.3.2.19.1.5
-- 1.3.6.1.4.1.37950.1.1.5.12.3.2.19.1.5
-- 1.3.6.1.4.1.37950.1.1.5.12.3.2.19.1.5
-- 1.3.6.1.4.1.37950.1.1.5.12.3.2.19.1.5
-- 1.3.6.1.4.1.37950.1.1.5.12.3.2.19.1.5
		-- 1.3.6.1.4.1.37950.1.1.5.12.3.2.19.1.5
		priWifiSwitchChannelS OBJECT-TYPE
			SYNTAX INTEGER (0..13)
			MAX-ACCESS read-write
			STATUS current
			DESCRIPTION
				"Description."
			::= { priWifiSwitchEntry 5 }

		
--         1.3.6.1.4.1.37950.1.1.5.12.3.2.19.1.6
-- 1.3.6.1.4.1.37950.1.1.5.12.3.2.19.1.6
-- 1.3.6.1.4.1.37950.1.1.5.12.3.2.19.1.6
-- 1.3.6.1.4.1.37950.1.1.5.12.3.2.19.1.6
-- 1.3.6.1.4.1.37950.1.1.5.12.3.2.19.1.6
-- 1.3.6.1.4.1.37950.1.1.5.12.3.2.19.1.6
-- 1.3.6.1.4.1.37950.1.1.5.12.3.2.19.1.6
-- 1.3.6.1.4.1.37950.1.1.5.12.3.2.19.1.6
		-- 1.3.6.1.4.1.37950.1.1.5.12.3.2.19.1.6
		priWifiSwitchStandardS OBJECT-TYPE
			SYNTAX INTEGER
				{
				s80211b(0),
				s80211g(1),
				s80211bg(2),
				s80211n(3),
				s80211bgn(4),
				s80211ac(5),
				s80211a(6),
				s80211an(7),
				s80211nac(8),
				s80211anac(9),
				s80211aan(10),
				s80211ax(11),
				s80211anacax(12)
				}
			MAX-ACCESS read-write
			STATUS current
			DESCRIPTION
				"Description."
			::= { priWifiSwitchEntry 6 }

		
--         1.3.6.1.4.1.37950.1.1.5.12.3.2.19.1.7
-- 1.3.6.1.4.1.37950.1.1.5.12.3.2.19.1.7
-- 1.3.6.1.4.1.37950.1.1.5.12.3.2.19.1.7
-- 1.3.6.1.4.1.37950.1.1.5.12.3.2.19.1.7
-- 1.3.6.1.4.1.37950.1.1.5.12.3.2.19.1.7
-- 1.3.6.1.4.1.37950.1.1.5.12.3.2.19.1.7
-- 1.3.6.1.4.1.37950.1.1.5.12.3.2.19.1.7
-- 1.3.6.1.4.1.37950.1.1.5.12.3.2.19.1.7
		-- 1.3.6.1.4.1.37950.1.1.5.12.3.2.19.1.7
		priWifiSwitchPower1 OBJECT-TYPE
			SYNTAX INTEGER (0..20)
			MAX-ACCESS read-write
			STATUS current
			DESCRIPTION
				"Description."
			::= { priWifiSwitchEntry 7 }

		
--         1.3.6.1.4.1.37950.1.1.5.12.3.2.19.1.8
-- 1.3.6.1.4.1.37950.1.1.5.12.3.2.19.1.8
-- 1.3.6.1.4.1.37950.1.1.5.12.3.2.19.1.8
-- 1.3.6.1.4.1.37950.1.1.5.12.3.2.19.1.8
-- 1.3.6.1.4.1.37950.1.1.5.12.3.2.19.1.8
-- 1.3.6.1.4.1.37950.1.1.5.12.3.2.19.1.8
-- 1.3.6.1.4.1.37950.1.1.5.12.3.2.19.1.8
-- 1.3.6.1.4.1.37950.1.1.5.12.3.2.19.1.8
		-- 1.3.6.1.4.1.37950.1.1.5.12.3.2.19.1.8
		priWifiSwitchChannelWidth OBJECT-TYPE
			SYNTAX INTEGER
				{
				s20(0),
				s40(1),
				s80(2),
				s20-40(3)
				}
			MAX-ACCESS read-write
			STATUS current
			DESCRIPTION
				"Description."
			::= { priWifiSwitchEntry 8 }

		
--         1.3.6.1.4.1.37950.1.1.5.12.3.2.19.1.9
-- 1.3.6.1.4.1.37950.1.1.5.12.3.2.19.1.9
-- 1.3.6.1.4.1.37950.1.1.5.12.3.2.19.1.9
-- 1.3.6.1.4.1.37950.1.1.5.12.3.2.19.1.9
-- 1.3.6.1.4.1.37950.1.1.5.12.3.2.19.1.9
-- 1.3.6.1.4.1.37950.1.1.5.12.3.2.19.1.9
-- 1.3.6.1.4.1.37950.1.1.5.12.3.2.19.1.9
-- 1.3.6.1.4.1.37950.1.1.5.12.3.2.19.1.9
		-- 1.3.6.1.4.1.37950.1.1.5.12.3.2.19.1.9
		priWifiSwitchEasyMeshStatus OBJECT-TYPE
			SYNTAX INTEGER
				{
				disable(0),
				enable(1)
				}
			MAX-ACCESS read-write
			STATUS current
			DESCRIPTION
				"Description."
			::= { priWifiSwitchEntry 9 }

		
--           1.3.6.1.4.1.37950.1.1.5.12.3.2.6
-- 1.3.6.1.4.1.37950.1.1.5.12.3.2.20
-- 1.3.6.1.4.1.37950.1.1.5.12.3.2.20
-- 1.3.6.1.4.1.37950.1.1.5.12.3.2.20
-- 1.3.6.1.4.1.37950.1.1.5.12.3.2.20
-- 1.3.6.1.4.1.37950.1.1.5.12.3.2.20
-- 1.3.6.1.4.1.37950.1.1.5.12.3.2.20
-- 1.3.6.1.4.1.37950.1.1.5.12.3.2.20
-- 1.3.6.1.4.1.37950.1.1.5.12.3.2.20
		-- 1.3.6.1.4.1.37950.1.1.5.12.3.2.20
		priWanConnV6Table OBJECT-TYPE
			SYNTAX SEQUENCE OF PriWanConnV6Entry
			MAX-ACCESS not-accessible
			STATUS current
			DESCRIPTION
				"Description."
			::= { onuPriGlobalInfo 20 }

		
--           1.3.6.1.4.1.37950.1.1.5.12.3.2.6.1
-- 1.3.6.1.4.1.37950.1.1.5.12.3.2.20.1
-- 1.3.6.1.4.1.37950.1.1.5.12.3.2.20.1
-- 1.3.6.1.4.1.37950.1.1.5.12.3.2.20.1
-- 1.3.6.1.4.1.37950.1.1.5.12.3.2.20.1
-- 1.3.6.1.4.1.37950.1.1.5.12.3.2.20.1
-- 1.3.6.1.4.1.37950.1.1.5.12.3.2.20.1
-- 1.3.6.1.4.1.37950.1.1.5.12.3.2.20.1
-- 1.3.6.1.4.1.37950.1.1.5.12.3.2.20.1
		-- 1.3.6.1.4.1.37950.1.1.5.12.3.2.20.1
		priWanConnV6Entry OBJECT-TYPE
			SYNTAX PriWanConnV6Entry
			MAX-ACCESS not-accessible
			STATUS current
			DESCRIPTION
				"Description."
			INDEX { priV6ConnPonS, priV6ConnOnuS, priV6ConnIndexS }
			::= { priWanConnV6Table 1 }

		
		PriWanConnV6Entry ::=
			SEQUENCE { 
				priV6ConnPonS
					INTEGER,
				priV6ConnOnuS
					INTEGER,
				priV6ConnIndexS
					Integer32,
				priV6ConnBindLanS
					INTEGER,
				priV6ConnBindSsidS
					INTEGER,
				priV6WanModeS
					INTEGER,
				priV6ConnTypeS
					INTEGER,
				priV6ConnVlanIdS
					INTEGER,
				priV6ConnVlanCosS
					INTEGER,
				priV6ConnIpProtocolS
					INTEGER,
				priV6wanConnModeS
					INTEGER,
				priV6ConnIpAddressIpv4S
					IpAddress,
				priV6ConnIpNetMaskIpv4S
					IpAddress,
				priV6ConnGatewayIpv4S
					IpAddress,
				priV6ConnDnsEnableIpv4S
					INTEGER,
				priV6ConnMasterDnsIpv4S
					IpAddress,
				priV6ConnSlaveDnsIpv4S
					IpAddress,
				priV6ConnNatEnableS
					INTEGER,
				priV6ConnAddressIpv6S
					OCTET STRING,
				priV6ConnPrefixLenIpv6S
					INTEGER,
				priV6ConnGatewayIpv6S
					OCTET STRING,
				priV6ConnDnsEnableIpv6S
					INTEGER,
				priV6ConnMsaterDnsIpv6S
					OCTET STRING,
				priV6ConnSlaveDnsIpv6S
					OCTET STRING,
				priV6ConnSlaacS
					INTEGER,
				priV6ConnPppoeProxyS
					INTEGER,
				priV6ConnPppoeUsernameS
					OCTET STRING,
				priV6ConnPppoePasswordS
					OCTET STRING,
				priV6ConnPppoeSerNameS
					OCTET STRING,
				priV6ConnPppoeModeS
					INTEGER,
				priV6ConnDhcpv6ClientAddressS
					INTEGER,
				priV6ConnDhcpv6ClientPrefixS
					INTEGER,
				priV6ConnDsLiteEnableS
					INTEGER,
				priV6ConnDsLiteAftrModeS
					INTEGER,
				priV6ConnDsLiteAddressTypeS
					INTEGER,
				priV6ConnDsLiteAddressS
					OCTET STRING,
				priv6ConnQosEnableS
					INTEGER,
				priV6ConnVlanModeS
					INTEGER,
				priV6ConnTranslationEnableS
					INTEGER,
				priV6ConnTranslationVlanS
					INTEGER,
				priV6ConnTranslationCosS
					INTEGER,
				priV6ConnQinqEnableS
					INTEGER,
				priV6ConnQinqTpidS
					INTEGER,
				priV6ConnSvlanIdS
					INTEGER,
				priV6ConnSvlanCosS
					INTEGER,
				priV6ConnRouteMtuS
					Integer32,
				priv6ConnNameS
					OCTET STRING,
				priV6ConnStatusS
					INTEGER,
				priV6ConnMacAddrS
					OCTET STRING
			 }

--           1.3.6.1.4.1.37950.1.1.5.12.3.2.6.1.1
-- 1.3.6.1.4.1.37950.1.1.5.12.3.2.20.1.1
-- 1.3.6.1.4.1.37950.1.1.5.12.3.2.20.1.1
-- 1.3.6.1.4.1.37950.1.1.5.12.3.2.20.1.1
-- 1.3.6.1.4.1.37950.1.1.5.12.3.2.20.1.1
-- 1.3.6.1.4.1.37950.1.1.5.12.3.2.20.1.1
-- 1.3.6.1.4.1.37950.1.1.5.12.3.2.20.1.1
-- 1.3.6.1.4.1.37950.1.1.5.12.3.2.20.1.1
-- 1.3.6.1.4.1.37950.1.1.5.12.3.2.20.1.1
		-- 1.3.6.1.4.1.37950.1.1.5.12.3.2.20.1.1
		priV6ConnPonS OBJECT-TYPE
			SYNTAX INTEGER (1..16)
			MAX-ACCESS read-write
			STATUS current
			DESCRIPTION
				"Description."
			::= { priWanConnV6Entry 1 }

		
--           1.3.6.1.4.1.37950.1.1.5.12.3.2.6.1.2
-- 1.3.6.1.4.1.37950.1.1.5.12.3.2.20.1.2
-- 1.3.6.1.4.1.37950.1.1.5.12.3.2.20.1.2
-- 1.3.6.1.4.1.37950.1.1.5.12.3.2.20.1.2
-- 1.3.6.1.4.1.37950.1.1.5.12.3.2.20.1.2
-- 1.3.6.1.4.1.37950.1.1.5.12.3.2.20.1.2
-- 1.3.6.1.4.1.37950.1.1.5.12.3.2.20.1.2
-- 1.3.6.1.4.1.37950.1.1.5.12.3.2.20.1.2
-- 1.3.6.1.4.1.37950.1.1.5.12.3.2.20.1.2
		-- 1.3.6.1.4.1.37950.1.1.5.12.3.2.20.1.2
		priV6ConnOnuS OBJECT-TYPE
			SYNTAX INTEGER (1..65535)
			MAX-ACCESS read-write
			STATUS current
			DESCRIPTION
				"Description."
			::= { priWanConnV6Entry 2 }

		
--           1.3.6.1.4.1.37950.1.1.5.12.3.2.6.1.3
-- 1.3.6.1.4.1.37950.1.1.5.12.3.2.20.1.3
-- 1.3.6.1.4.1.37950.1.1.5.12.3.2.20.1.3
-- 1.3.6.1.4.1.37950.1.1.5.12.3.2.20.1.3
-- 1.3.6.1.4.1.37950.1.1.5.12.3.2.20.1.3
-- 1.3.6.1.4.1.37950.1.1.5.12.3.2.20.1.3
-- 1.3.6.1.4.1.37950.1.1.5.12.3.2.20.1.3
-- 1.3.6.1.4.1.37950.1.1.5.12.3.2.20.1.3
-- 1.3.6.1.4.1.37950.1.1.5.12.3.2.20.1.3
		-- 1.3.6.1.4.1.37950.1.1.5.12.3.2.20.1.3
		priV6ConnIndexS OBJECT-TYPE
			SYNTAX Integer32 (1..8)
			MAX-ACCESS read-write
			STATUS current
			DESCRIPTION
				"Description."
			::= { priWanConnV6Entry 3 }

		
--           1.3.6.1.4.1.37950.1.1.5.12.3.2.6.1.4
-- 1.3.6.1.4.1.37950.1.1.5.12.3.2.20.1.4
-- 1.3.6.1.4.1.37950.1.1.5.12.3.2.20.1.4
-- 1.3.6.1.4.1.37950.1.1.5.12.3.2.20.1.4
-- 1.3.6.1.4.1.37950.1.1.5.12.3.2.20.1.4
-- 1.3.6.1.4.1.37950.1.1.5.12.3.2.20.1.4
-- 1.3.6.1.4.1.37950.1.1.5.12.3.2.20.1.4
-- 1.3.6.1.4.1.37950.1.1.5.12.3.2.20.1.4
-- 1.3.6.1.4.1.37950.1.1.5.12.3.2.20.1.4
		-- 1.3.6.1.4.1.37950.1.1.5.12.3.2.20.1.4
		priV6ConnBindLanS OBJECT-TYPE
			SYNTAX INTEGER (0..15)
			MAX-ACCESS read-write
			STATUS current
			DESCRIPTION
				"Description."
			::= { priWanConnV6Entry 4 }

		
--           1.3.6.1.4.1.37950.1.1.5.12.3.2.6.1.5
-- 1.3.6.1.4.1.37950.1.1.5.12.3.2.20.1.5
-- 1.3.6.1.4.1.37950.1.1.5.12.3.2.20.1.5
-- 1.3.6.1.4.1.37950.1.1.5.12.3.2.20.1.5
-- 1.3.6.1.4.1.37950.1.1.5.12.3.2.20.1.5
-- 1.3.6.1.4.1.37950.1.1.5.12.3.2.20.1.5
-- 1.3.6.1.4.1.37950.1.1.5.12.3.2.20.1.5
-- 1.3.6.1.4.1.37950.1.1.5.12.3.2.20.1.5
-- 1.3.6.1.4.1.37950.1.1.5.12.3.2.20.1.5
		-- 1.3.6.1.4.1.37950.1.1.5.12.3.2.20.1.5
		priV6ConnBindSsidS OBJECT-TYPE
			SYNTAX INTEGER (0..65535)
			MAX-ACCESS read-write
			STATUS current
			DESCRIPTION
				"Description."
			::= { priWanConnV6Entry 5 }

		
--           1.3.6.1.4.1.37950.1.1.5.12.3.2.6.1.6
-- 1.3.6.1.4.1.37950.1.1.5.12.3.2.20.1.6
-- 1.3.6.1.4.1.37950.1.1.5.12.3.2.20.1.6
-- 1.3.6.1.4.1.37950.1.1.5.12.3.2.20.1.6
-- 1.3.6.1.4.1.37950.1.1.5.12.3.2.20.1.6
-- 1.3.6.1.4.1.37950.1.1.5.12.3.2.20.1.6
-- 1.3.6.1.4.1.37950.1.1.5.12.3.2.20.1.6
-- 1.3.6.1.4.1.37950.1.1.5.12.3.2.20.1.6
-- 1.3.6.1.4.1.37950.1.1.5.12.3.2.20.1.6
		-- 1.3.6.1.4.1.37950.1.1.5.12.3.2.20.1.6
		priV6WanModeS OBJECT-TYPE
			SYNTAX INTEGER
				{
				internet(0),
				multicast(1),
				tr069(2),
				tr069-internet(3),
				tr069-voip(4),
				voip-internet(5),
				tr069-voip-internet(6),
				voip(7),
				other(100)
				}
			MAX-ACCESS read-write
			STATUS current
			DESCRIPTION
				"Description."
			::= { priWanConnV6Entry 6 }

		
--           1.3.6.1.4.1.37950.1.1.5.12.3.2.6.1.7
-- 1.3.6.1.4.1.37950.1.1.5.12.3.2.20.1.7
-- 1.3.6.1.4.1.37950.1.1.5.12.3.2.20.1.7
-- 1.3.6.1.4.1.37950.1.1.5.12.3.2.20.1.7
-- 1.3.6.1.4.1.37950.1.1.5.12.3.2.20.1.7
-- 1.3.6.1.4.1.37950.1.1.5.12.3.2.20.1.7
-- 1.3.6.1.4.1.37950.1.1.5.12.3.2.20.1.7
-- 1.3.6.1.4.1.37950.1.1.5.12.3.2.20.1.7
-- 1.3.6.1.4.1.37950.1.1.5.12.3.2.20.1.7
		-- 1.3.6.1.4.1.37950.1.1.5.12.3.2.20.1.7
		priV6ConnTypeS OBJECT-TYPE
			SYNTAX INTEGER
				{
				bridge(0),
				route(1)
				}
			MAX-ACCESS read-write
			STATUS current
			DESCRIPTION
				"Description."
			::= { priWanConnV6Entry 7 }

		
--           1.3.6.1.4.1.37950.1.1.5.12.3.2.6.1.8
-- 1.3.6.1.4.1.37950.1.1.5.12.3.2.20.1.8
-- 1.3.6.1.4.1.37950.1.1.5.12.3.2.20.1.8
-- 1.3.6.1.4.1.37950.1.1.5.12.3.2.20.1.8
-- 1.3.6.1.4.1.37950.1.1.5.12.3.2.20.1.8
-- 1.3.6.1.4.1.37950.1.1.5.12.3.2.20.1.8
-- 1.3.6.1.4.1.37950.1.1.5.12.3.2.20.1.8
-- 1.3.6.1.4.1.37950.1.1.5.12.3.2.20.1.8
-- 1.3.6.1.4.1.37950.1.1.5.12.3.2.20.1.8
		-- 1.3.6.1.4.1.37950.1.1.5.12.3.2.20.1.8
		priV6ConnVlanIdS OBJECT-TYPE
			SYNTAX INTEGER (0..4095)
			MAX-ACCESS read-write
			STATUS current
			DESCRIPTION
				"Description."
			::= { priWanConnV6Entry 8 }

		
--           1.3.6.1.4.1.37950.1.1.5.12.3.2.6.1.9
-- 1.3.6.1.4.1.37950.1.1.5.12.3.2.20.1.9
-- 1.3.6.1.4.1.37950.1.1.5.12.3.2.20.1.9
-- 1.3.6.1.4.1.37950.1.1.5.12.3.2.20.1.9
-- 1.3.6.1.4.1.37950.1.1.5.12.3.2.20.1.9
-- 1.3.6.1.4.1.37950.1.1.5.12.3.2.20.1.9
-- 1.3.6.1.4.1.37950.1.1.5.12.3.2.20.1.9
-- 1.3.6.1.4.1.37950.1.1.5.12.3.2.20.1.9
-- 1.3.6.1.4.1.37950.1.1.5.12.3.2.20.1.9
		-- 1.3.6.1.4.1.37950.1.1.5.12.3.2.20.1.9
		priV6ConnVlanCosS OBJECT-TYPE
			SYNTAX INTEGER (0..7)
			MAX-ACCESS read-write
			STATUS current
			DESCRIPTION
				"Description."
			::= { priWanConnV6Entry 9 }

		
--          1.3.6.1.4.1.37950.1.1.5.12.3.2.6.1.33
-- 1.3.6.1.4.1.37950.1.1.5.12.3.2.20.1.10
-- 1.3.6.1.4.1.37950.1.1.5.12.3.2.20.1.10
-- 1.3.6.1.4.1.37950.1.1.5.12.3.2.20.1.10
-- 1.3.6.1.4.1.37950.1.1.5.12.3.2.20.1.10
-- 1.3.6.1.4.1.37950.1.1.5.12.3.2.20.1.10
-- 1.3.6.1.4.1.37950.1.1.5.12.3.2.20.1.10
-- 1.3.6.1.4.1.37950.1.1.5.12.3.2.20.1.10
-- 1.3.6.1.4.1.37950.1.1.5.12.3.2.20.1.10
		-- 1.3.6.1.4.1.37950.1.1.5.12.3.2.20.1.10
		priV6ConnIpProtocolS OBJECT-TYPE
			SYNTAX INTEGER
				{
				ipv4(0),
				ipv6(1),
				ipv4-ipv6(2)
				}
			MAX-ACCESS read-write
			STATUS current
			DESCRIPTION
				"Description."
			::= { priWanConnV6Entry 10 }

		
--           1.3.6.1.4.1.37950.1.1.5.12.3.2.6.1.11
-- 1.3.6.1.4.1.37950.1.1.5.12.3.2.20.1.11
-- 1.3.6.1.4.1.37950.1.1.5.12.3.2.20.1.11
-- 1.3.6.1.4.1.37950.1.1.5.12.3.2.20.1.11
-- 1.3.6.1.4.1.37950.1.1.5.12.3.2.20.1.11
-- 1.3.6.1.4.1.37950.1.1.5.12.3.2.20.1.11
-- 1.3.6.1.4.1.37950.1.1.5.12.3.2.20.1.11
-- 1.3.6.1.4.1.37950.1.1.5.12.3.2.20.1.11
-- 1.3.6.1.4.1.37950.1.1.5.12.3.2.20.1.11
		-- 1.3.6.1.4.1.37950.1.1.5.12.3.2.20.1.11
		priV6wanConnModeS OBJECT-TYPE
			SYNTAX INTEGER
				{
				dhcp(0),
				static(1),
				pppoe(2)
				}
			MAX-ACCESS read-write
			STATUS current
			DESCRIPTION
				"Description."
			::= { priWanConnV6Entry 11 }

		
--           1.3.6.1.4.1.37950.1.1.5.12.3.2.6.1.12
-- 1.3.6.1.4.1.37950.1.1.5.12.3.2.20.1.12
-- 1.3.6.1.4.1.37950.1.1.5.12.3.2.20.1.12
-- 1.3.6.1.4.1.37950.1.1.5.12.3.2.20.1.12
-- 1.3.6.1.4.1.37950.1.1.5.12.3.2.20.1.12
-- 1.3.6.1.4.1.37950.1.1.5.12.3.2.20.1.12
-- 1.3.6.1.4.1.37950.1.1.5.12.3.2.20.1.12
-- 1.3.6.1.4.1.37950.1.1.5.12.3.2.20.1.12
-- 1.3.6.1.4.1.37950.1.1.5.12.3.2.20.1.12
		-- 1.3.6.1.4.1.37950.1.1.5.12.3.2.20.1.12
		priV6ConnIpAddressIpv4S OBJECT-TYPE
			SYNTAX IpAddress
			MAX-ACCESS read-write
			STATUS current
			DESCRIPTION
				"Description."
			::= { priWanConnV6Entry 12 }

		
--           1.3.6.1.4.1.37950.1.1.5.12.3.2.6.1.13
-- 1.3.6.1.4.1.37950.1.1.5.12.3.2.20.1.13
-- 1.3.6.1.4.1.37950.1.1.5.12.3.2.20.1.13
-- 1.3.6.1.4.1.37950.1.1.5.12.3.2.20.1.13
-- 1.3.6.1.4.1.37950.1.1.5.12.3.2.20.1.13
-- 1.3.6.1.4.1.37950.1.1.5.12.3.2.20.1.13
-- 1.3.6.1.4.1.37950.1.1.5.12.3.2.20.1.13
-- 1.3.6.1.4.1.37950.1.1.5.12.3.2.20.1.13
-- 1.3.6.1.4.1.37950.1.1.5.12.3.2.20.1.13
		-- 1.3.6.1.4.1.37950.1.1.5.12.3.2.20.1.13
		priV6ConnIpNetMaskIpv4S OBJECT-TYPE
			SYNTAX IpAddress
			MAX-ACCESS read-write
			STATUS current
			DESCRIPTION
				"Description."
			::= { priWanConnV6Entry 13 }

		
--           1.3.6.1.4.1.37950.1.1.5.12.3.2.6.1.14
-- 1.3.6.1.4.1.37950.1.1.5.12.3.2.20.1.14
-- 1.3.6.1.4.1.37950.1.1.5.12.3.2.20.1.14
-- 1.3.6.1.4.1.37950.1.1.5.12.3.2.20.1.14
-- 1.3.6.1.4.1.37950.1.1.5.12.3.2.20.1.14
-- 1.3.6.1.4.1.37950.1.1.5.12.3.2.20.1.14
-- 1.3.6.1.4.1.37950.1.1.5.12.3.2.20.1.14
-- 1.3.6.1.4.1.37950.1.1.5.12.3.2.20.1.14
-- 1.3.6.1.4.1.37950.1.1.5.12.3.2.20.1.14
		-- 1.3.6.1.4.1.37950.1.1.5.12.3.2.20.1.14
		priV6ConnGatewayIpv4S OBJECT-TYPE
			SYNTAX IpAddress
			MAX-ACCESS read-write
			STATUS current
			DESCRIPTION
				"Description."
			::= { priWanConnV6Entry 14 }

		
--           1.3.6.1.4.1.37950.1.1.5.12.3.2.6.1.27
-- 1.3.6.1.4.1.37950.1.1.5.12.3.2.20.1.15
-- 1.3.6.1.4.1.37950.1.1.5.12.3.2.20.1.15
-- 1.3.6.1.4.1.37950.1.1.5.12.3.2.20.1.15
-- 1.3.6.1.4.1.37950.1.1.5.12.3.2.20.1.15
-- 1.3.6.1.4.1.37950.1.1.5.12.3.2.20.1.15
-- 1.3.6.1.4.1.37950.1.1.5.12.3.2.20.1.15
-- 1.3.6.1.4.1.37950.1.1.5.12.3.2.20.1.15
-- 1.3.6.1.4.1.37950.1.1.5.12.3.2.20.1.15
		-- 1.3.6.1.4.1.37950.1.1.5.12.3.2.20.1.15
		priV6ConnDnsEnableIpv4S OBJECT-TYPE
			SYNTAX INTEGER
				{
				disable(0),
				enable(1)
				}
			MAX-ACCESS read-write
			STATUS current
			DESCRIPTION
				"Description."
			::= { priWanConnV6Entry 15 }

		
--           1.3.6.1.4.1.37950.1.1.5.12.3.2.6.1.15
-- 1.3.6.1.4.1.37950.1.1.5.12.3.2.20.1.16
-- 1.3.6.1.4.1.37950.1.1.5.12.3.2.20.1.16
-- 1.3.6.1.4.1.37950.1.1.5.12.3.2.20.1.16
-- 1.3.6.1.4.1.37950.1.1.5.12.3.2.20.1.16
-- 1.3.6.1.4.1.37950.1.1.5.12.3.2.20.1.16
-- 1.3.6.1.4.1.37950.1.1.5.12.3.2.20.1.16
-- 1.3.6.1.4.1.37950.1.1.5.12.3.2.20.1.16
-- 1.3.6.1.4.1.37950.1.1.5.12.3.2.20.1.16
		-- 1.3.6.1.4.1.37950.1.1.5.12.3.2.20.1.16
		priV6ConnMasterDnsIpv4S OBJECT-TYPE
			SYNTAX IpAddress
			MAX-ACCESS read-write
			STATUS current
			DESCRIPTION
				"Description."
			::= { priWanConnV6Entry 16 }

		
--           1.3.6.1.4.1.37950.1.1.5.12.3.2.6.1.16
-- 1.3.6.1.4.1.37950.1.1.5.12.3.2.20.1.17
-- 1.3.6.1.4.1.37950.1.1.5.12.3.2.20.1.17
-- 1.3.6.1.4.1.37950.1.1.5.12.3.2.20.1.17
-- 1.3.6.1.4.1.37950.1.1.5.12.3.2.20.1.17
-- 1.3.6.1.4.1.37950.1.1.5.12.3.2.20.1.17
-- 1.3.6.1.4.1.37950.1.1.5.12.3.2.20.1.17
-- 1.3.6.1.4.1.37950.1.1.5.12.3.2.20.1.17
-- 1.3.6.1.4.1.37950.1.1.5.12.3.2.20.1.17
		-- 1.3.6.1.4.1.37950.1.1.5.12.3.2.20.1.17
		priV6ConnSlaveDnsIpv4S OBJECT-TYPE
			SYNTAX IpAddress
			MAX-ACCESS read-write
			STATUS current
			DESCRIPTION
				"Description."
			::= { priWanConnV6Entry 17 }

		
--           1.3.6.1.4.1.37950.1.1.5.12.3.2.6.1.10
-- 1.3.6.1.4.1.37950.1.1.5.12.3.2.20.1.18
-- 1.3.6.1.4.1.37950.1.1.5.12.3.2.20.1.18
-- 1.3.6.1.4.1.37950.1.1.5.12.3.2.20.1.18
-- 1.3.6.1.4.1.37950.1.1.5.12.3.2.20.1.18
-- 1.3.6.1.4.1.37950.1.1.5.12.3.2.20.1.18
-- 1.3.6.1.4.1.37950.1.1.5.12.3.2.20.1.18
-- 1.3.6.1.4.1.37950.1.1.5.12.3.2.20.1.18
-- 1.3.6.1.4.1.37950.1.1.5.12.3.2.20.1.18
		-- 1.3.6.1.4.1.37950.1.1.5.12.3.2.20.1.18
		priV6ConnNatEnableS OBJECT-TYPE
			SYNTAX INTEGER
				{
				disable(0),
				enable(1)
				}
			MAX-ACCESS read-write
			STATUS current
			DESCRIPTION
				"Description."
			::= { priWanConnV6Entry 18 }

		
--           1.3.6.1.4.1.37950.1.1.5.12.3.2.6.1.16
-- 1.3.6.1.4.1.37950.1.1.5.12.3.2.20.1.19
-- 1.3.6.1.4.1.37950.1.1.5.12.3.2.20.1.19
-- 1.3.6.1.4.1.37950.1.1.5.12.3.2.20.1.19
-- 1.3.6.1.4.1.37950.1.1.5.12.3.2.20.1.19
-- 1.3.6.1.4.1.37950.1.1.5.12.3.2.20.1.19
-- 1.3.6.1.4.1.37950.1.1.5.12.3.2.20.1.19
-- 1.3.6.1.4.1.37950.1.1.5.12.3.2.20.1.19
-- 1.3.6.1.4.1.37950.1.1.5.12.3.2.20.1.19
		-- 1.3.6.1.4.1.37950.1.1.5.12.3.2.20.1.19
		priV6ConnAddressIpv6S OBJECT-TYPE
			SYNTAX OCTET STRING
			MAX-ACCESS read-write
			STATUS current
			DESCRIPTION
				"Description."
			::= { priWanConnV6Entry 19 }

		
--           1.3.6.1.4.1.37950.1.1.5.12.3.2.6.1.16
-- 1.3.6.1.4.1.37950.1.1.5.12.3.2.20.1.20
-- 1.3.6.1.4.1.37950.1.1.5.12.3.2.20.1.20
-- 1.3.6.1.4.1.37950.1.1.5.12.3.2.20.1.20
-- 1.3.6.1.4.1.37950.1.1.5.12.3.2.20.1.20
-- 1.3.6.1.4.1.37950.1.1.5.12.3.2.20.1.20
-- 1.3.6.1.4.1.37950.1.1.5.12.3.2.20.1.20
-- 1.3.6.1.4.1.37950.1.1.5.12.3.2.20.1.20
-- 1.3.6.1.4.1.37950.1.1.5.12.3.2.20.1.20
		-- 1.3.6.1.4.1.37950.1.1.5.12.3.2.20.1.20
		priV6ConnPrefixLenIpv6S OBJECT-TYPE
			SYNTAX INTEGER (0..128)
			MAX-ACCESS read-write
			STATUS current
			DESCRIPTION
				"Description."
			::= { priWanConnV6Entry 20 }

		
--           1.3.6.1.4.1.37950.1.1.5.12.3.2.6.1.16
-- 1.3.6.1.4.1.37950.1.1.5.12.3.2.20.1.21
-- 1.3.6.1.4.1.37950.1.1.5.12.3.2.20.1.21
-- 1.3.6.1.4.1.37950.1.1.5.12.3.2.20.1.21
-- 1.3.6.1.4.1.37950.1.1.5.12.3.2.20.1.21
-- 1.3.6.1.4.1.37950.1.1.5.12.3.2.20.1.21
-- 1.3.6.1.4.1.37950.1.1.5.12.3.2.20.1.21
-- 1.3.6.1.4.1.37950.1.1.5.12.3.2.20.1.21
-- 1.3.6.1.4.1.37950.1.1.5.12.3.2.20.1.21
		-- 1.3.6.1.4.1.37950.1.1.5.12.3.2.20.1.21
		priV6ConnGatewayIpv6S OBJECT-TYPE
			SYNTAX OCTET STRING
			MAX-ACCESS read-write
			STATUS current
			DESCRIPTION
				"Description."
			::= { priWanConnV6Entry 21 }

		
--           1.3.6.1.4.1.37950.1.1.5.12.3.2.6.1.27
-- 1.3.6.1.4.1.37950.1.1.5.12.3.2.20.1.22
-- 1.3.6.1.4.1.37950.1.1.5.12.3.2.20.1.22
-- 1.3.6.1.4.1.37950.1.1.5.12.3.2.20.1.22
-- 1.3.6.1.4.1.37950.1.1.5.12.3.2.20.1.22
-- 1.3.6.1.4.1.37950.1.1.5.12.3.2.20.1.22
-- 1.3.6.1.4.1.37950.1.1.5.12.3.2.20.1.22
-- 1.3.6.1.4.1.37950.1.1.5.12.3.2.20.1.22
-- 1.3.6.1.4.1.37950.1.1.5.12.3.2.20.1.22
		-- 1.3.6.1.4.1.37950.1.1.5.12.3.2.20.1.22
		priV6ConnDnsEnableIpv6S OBJECT-TYPE
			SYNTAX INTEGER
				{
				disable(0),
				enable(1)
				}
			MAX-ACCESS read-write
			STATUS current
			DESCRIPTION
				"Description."
			::= { priWanConnV6Entry 22 }

		
--           1.3.6.1.4.1.37950.1.1.5.12.3.2.6.1.16
-- 1.3.6.1.4.1.37950.1.1.5.12.3.2.20.1.23
-- 1.3.6.1.4.1.37950.1.1.5.12.3.2.20.1.23
-- 1.3.6.1.4.1.37950.1.1.5.12.3.2.20.1.23
-- 1.3.6.1.4.1.37950.1.1.5.12.3.2.20.1.23
-- 1.3.6.1.4.1.37950.1.1.5.12.3.2.20.1.23
-- 1.3.6.1.4.1.37950.1.1.5.12.3.2.20.1.23
-- 1.3.6.1.4.1.37950.1.1.5.12.3.2.20.1.23
-- 1.3.6.1.4.1.37950.1.1.5.12.3.2.20.1.23
		-- 1.3.6.1.4.1.37950.1.1.5.12.3.2.20.1.23
		priV6ConnMsaterDnsIpv6S OBJECT-TYPE
			SYNTAX OCTET STRING
			MAX-ACCESS read-write
			STATUS current
			DESCRIPTION
				"Description."
			::= { priWanConnV6Entry 23 }

		
--           1.3.6.1.4.1.37950.1.1.5.12.3.2.6.1.16
-- 1.3.6.1.4.1.37950.1.1.5.12.3.2.20.1.24
-- 1.3.6.1.4.1.37950.1.1.5.12.3.2.20.1.24
-- 1.3.6.1.4.1.37950.1.1.5.12.3.2.20.1.24
-- 1.3.6.1.4.1.37950.1.1.5.12.3.2.20.1.24
-- 1.3.6.1.4.1.37950.1.1.5.12.3.2.20.1.24
-- 1.3.6.1.4.1.37950.1.1.5.12.3.2.20.1.24
-- 1.3.6.1.4.1.37950.1.1.5.12.3.2.20.1.24
-- 1.3.6.1.4.1.37950.1.1.5.12.3.2.20.1.24
		-- 1.3.6.1.4.1.37950.1.1.5.12.3.2.20.1.24
		priV6ConnSlaveDnsIpv6S OBJECT-TYPE
			SYNTAX OCTET STRING
			MAX-ACCESS read-write
			STATUS current
			DESCRIPTION
				"Description."
			::= { priWanConnV6Entry 24 }

		
--           1.3.6.1.4.1.37950.1.1.5.12.3.2.6.1.21
-- 1.3.6.1.4.1.37950.1.1.5.12.3.2.20.1.25
-- 1.3.6.1.4.1.37950.1.1.5.12.3.2.20.1.25
-- 1.3.6.1.4.1.37950.1.1.5.12.3.2.20.1.25
-- 1.3.6.1.4.1.37950.1.1.5.12.3.2.20.1.25
-- 1.3.6.1.4.1.37950.1.1.5.12.3.2.20.1.25
-- 1.3.6.1.4.1.37950.1.1.5.12.3.2.20.1.25
-- 1.3.6.1.4.1.37950.1.1.5.12.3.2.20.1.25
-- 1.3.6.1.4.1.37950.1.1.5.12.3.2.20.1.25
		-- 1.3.6.1.4.1.37950.1.1.5.12.3.2.20.1.25
		priV6ConnSlaacS OBJECT-TYPE
			SYNTAX INTEGER
				{
				disable(0),
				enable(1)
				}
			MAX-ACCESS read-write
			STATUS current
			DESCRIPTION
				"Description."
			::= { priWanConnV6Entry 25 }

		
--           1.3.6.1.4.1.37950.1.1.5.12.3.2.6.1.17
-- 1.3.6.1.4.1.37950.1.1.5.12.3.2.20.1.26
-- 1.3.6.1.4.1.37950.1.1.5.12.3.2.20.1.26
-- 1.3.6.1.4.1.37950.1.1.5.12.3.2.20.1.26
-- 1.3.6.1.4.1.37950.1.1.5.12.3.2.20.1.26
-- 1.3.6.1.4.1.37950.1.1.5.12.3.2.20.1.26
-- 1.3.6.1.4.1.37950.1.1.5.12.3.2.20.1.26
-- 1.3.6.1.4.1.37950.1.1.5.12.3.2.20.1.26
-- 1.3.6.1.4.1.37950.1.1.5.12.3.2.20.1.26
		-- 1.3.6.1.4.1.37950.1.1.5.12.3.2.20.1.26
		priV6ConnPppoeProxyS OBJECT-TYPE
			SYNTAX INTEGER
				{
				disable(0),
				enable(1)
				}
			MAX-ACCESS read-write
			STATUS current
			DESCRIPTION
				"Description."
			::= { priWanConnV6Entry 26 }

		
--           1.3.6.1.4.1.37950.1.1.5.12.3.2.6.1.18
-- 1.3.6.1.4.1.37950.1.1.5.12.3.2.20.1.27
-- 1.3.6.1.4.1.37950.1.1.5.12.3.2.20.1.27
-- 1.3.6.1.4.1.37950.1.1.5.12.3.2.20.1.27
-- 1.3.6.1.4.1.37950.1.1.5.12.3.2.20.1.27
-- 1.3.6.1.4.1.37950.1.1.5.12.3.2.20.1.27
-- 1.3.6.1.4.1.37950.1.1.5.12.3.2.20.1.27
-- 1.3.6.1.4.1.37950.1.1.5.12.3.2.20.1.27
-- 1.3.6.1.4.1.37950.1.1.5.12.3.2.20.1.27
		-- 1.3.6.1.4.1.37950.1.1.5.12.3.2.20.1.27
		priV6ConnPppoeUsernameS OBJECT-TYPE
			SYNTAX OCTET STRING
			MAX-ACCESS read-write
			STATUS current
			DESCRIPTION
				"Description."
			::= { priWanConnV6Entry 27 }

		
--           1.3.6.1.4.1.37950.1.1.5.12.3.2.6.1.19
-- 1.3.6.1.4.1.37950.1.1.5.12.3.2.20.1.28
-- 1.3.6.1.4.1.37950.1.1.5.12.3.2.20.1.28
-- 1.3.6.1.4.1.37950.1.1.5.12.3.2.20.1.28
-- 1.3.6.1.4.1.37950.1.1.5.12.3.2.20.1.28
-- 1.3.6.1.4.1.37950.1.1.5.12.3.2.20.1.28
-- 1.3.6.1.4.1.37950.1.1.5.12.3.2.20.1.28
-- 1.3.6.1.4.1.37950.1.1.5.12.3.2.20.1.28
-- 1.3.6.1.4.1.37950.1.1.5.12.3.2.20.1.28
		-- 1.3.6.1.4.1.37950.1.1.5.12.3.2.20.1.28
		priV6ConnPppoePasswordS OBJECT-TYPE
			SYNTAX OCTET STRING
			MAX-ACCESS read-write
			STATUS current
			DESCRIPTION
				"Description."
			::= { priWanConnV6Entry 28 }

		
--           1.3.6.1.4.1.37950.1.1.5.12.3.2.6.1.20
-- 1.3.6.1.4.1.37950.1.1.5.12.3.2.20.1.29
-- 1.3.6.1.4.1.37950.1.1.5.12.3.2.20.1.29
-- 1.3.6.1.4.1.37950.1.1.5.12.3.2.20.1.29
-- 1.3.6.1.4.1.37950.1.1.5.12.3.2.20.1.29
-- 1.3.6.1.4.1.37950.1.1.5.12.3.2.20.1.29
-- 1.3.6.1.4.1.37950.1.1.5.12.3.2.20.1.29
-- 1.3.6.1.4.1.37950.1.1.5.12.3.2.20.1.29
-- 1.3.6.1.4.1.37950.1.1.5.12.3.2.20.1.29
		-- 1.3.6.1.4.1.37950.1.1.5.12.3.2.20.1.29
		priV6ConnPppoeSerNameS OBJECT-TYPE
			SYNTAX OCTET STRING
			MAX-ACCESS read-write
			STATUS current
			DESCRIPTION
				"Description."
			::= { priWanConnV6Entry 29 }

		
--           1.3.6.1.4.1.37950.1.1.5.12.3.2.6.1.21
-- 1.3.6.1.4.1.37950.1.1.5.12.3.2.20.1.30
-- 1.3.6.1.4.1.37950.1.1.5.12.3.2.20.1.30
-- 1.3.6.1.4.1.37950.1.1.5.12.3.2.20.1.30
-- 1.3.6.1.4.1.37950.1.1.5.12.3.2.20.1.30
-- 1.3.6.1.4.1.37950.1.1.5.12.3.2.20.1.30
-- 1.3.6.1.4.1.37950.1.1.5.12.3.2.20.1.30
-- 1.3.6.1.4.1.37950.1.1.5.12.3.2.20.1.30
-- 1.3.6.1.4.1.37950.1.1.5.12.3.2.20.1.30
		-- 1.3.6.1.4.1.37950.1.1.5.12.3.2.20.1.30
		priV6ConnPppoeModeS OBJECT-TYPE
			SYNTAX INTEGER
				{
				autoConnect(0),
				flowConnect(1)
				}
			MAX-ACCESS read-write
			STATUS current
			DESCRIPTION
				"Description."
			::= { priWanConnV6Entry 30 }

		
--           1.3.6.1.4.1.37950.1.1.5.12.3.2.6.1.21
-- 1.3.6.1.4.1.37950.1.1.5.12.3.2.20.1.31
-- 1.3.6.1.4.1.37950.1.1.5.12.3.2.20.1.31
-- 1.3.6.1.4.1.37950.1.1.5.12.3.2.20.1.31
-- 1.3.6.1.4.1.37950.1.1.5.12.3.2.20.1.31
-- 1.3.6.1.4.1.37950.1.1.5.12.3.2.20.1.31
-- 1.3.6.1.4.1.37950.1.1.5.12.3.2.20.1.31
-- 1.3.6.1.4.1.37950.1.1.5.12.3.2.20.1.31
-- 1.3.6.1.4.1.37950.1.1.5.12.3.2.20.1.31
		-- 1.3.6.1.4.1.37950.1.1.5.12.3.2.20.1.31
		priV6ConnDhcpv6ClientAddressS OBJECT-TYPE
			SYNTAX INTEGER
				{
				disable(0),
				enable(1)
				}
			MAX-ACCESS read-write
			STATUS current
			DESCRIPTION
				"Description."
			::= { priWanConnV6Entry 31 }

		
--           1.3.6.1.4.1.37950.1.1.5.12.3.2.6.1.21
-- 1.3.6.1.4.1.37950.1.1.5.12.3.2.20.1.32
-- 1.3.6.1.4.1.37950.1.1.5.12.3.2.20.1.32
-- 1.3.6.1.4.1.37950.1.1.5.12.3.2.20.1.32
-- 1.3.6.1.4.1.37950.1.1.5.12.3.2.20.1.32
-- 1.3.6.1.4.1.37950.1.1.5.12.3.2.20.1.32
-- 1.3.6.1.4.1.37950.1.1.5.12.3.2.20.1.32
-- 1.3.6.1.4.1.37950.1.1.5.12.3.2.20.1.32
-- 1.3.6.1.4.1.37950.1.1.5.12.3.2.20.1.32
		-- 1.3.6.1.4.1.37950.1.1.5.12.3.2.20.1.32
		priV6ConnDhcpv6ClientPrefixS OBJECT-TYPE
			SYNTAX INTEGER
				{
				disable(0),
				enable(1)
				}
			MAX-ACCESS read-write
			STATUS current
			DESCRIPTION
				"Description."
			::= { priWanConnV6Entry 32 }

		
--           1.3.6.1.4.1.37950.1.1.5.12.3.2.6.1.21
-- 1.3.6.1.4.1.37950.1.1.5.12.3.2.20.1.33
-- 1.3.6.1.4.1.37950.1.1.5.12.3.2.20.1.33
-- 1.3.6.1.4.1.37950.1.1.5.12.3.2.20.1.33
-- 1.3.6.1.4.1.37950.1.1.5.12.3.2.20.1.33
-- 1.3.6.1.4.1.37950.1.1.5.12.3.2.20.1.33
-- 1.3.6.1.4.1.37950.1.1.5.12.3.2.20.1.33
-- 1.3.6.1.4.1.37950.1.1.5.12.3.2.20.1.33
-- 1.3.6.1.4.1.37950.1.1.5.12.3.2.20.1.33
		-- 1.3.6.1.4.1.37950.1.1.5.12.3.2.20.1.33
		priV6ConnDsLiteEnableS OBJECT-TYPE
			SYNTAX INTEGER
				{
				disable(0),
				enable(1)
				}
			MAX-ACCESS read-write
			STATUS current
			DESCRIPTION
				"Description."
			::= { priWanConnV6Entry 33 }

		
--           1.3.6.1.4.1.37950.1.1.5.12.3.2.6.1.21
-- 1.3.6.1.4.1.37950.1.1.5.12.3.2.20.1.34
-- 1.3.6.1.4.1.37950.1.1.5.12.3.2.20.1.34
-- 1.3.6.1.4.1.37950.1.1.5.12.3.2.20.1.34
-- 1.3.6.1.4.1.37950.1.1.5.12.3.2.20.1.34
-- 1.3.6.1.4.1.37950.1.1.5.12.3.2.20.1.34
-- 1.3.6.1.4.1.37950.1.1.5.12.3.2.20.1.34
-- 1.3.6.1.4.1.37950.1.1.5.12.3.2.20.1.34
-- 1.3.6.1.4.1.37950.1.1.5.12.3.2.20.1.34
		-- 1.3.6.1.4.1.37950.1.1.5.12.3.2.20.1.34
		priV6ConnDsLiteAftrModeS OBJECT-TYPE
			SYNTAX INTEGER
				{
				dhcpv6(0),
				manual(1)
				}
			MAX-ACCESS read-write
			STATUS current
			DESCRIPTION
				"Description."
			::= { priWanConnV6Entry 34 }

		
--           1.3.6.1.4.1.37950.1.1.5.12.3.2.6.1.21
-- 1.3.6.1.4.1.37950.1.1.5.12.3.2.20.1.35
-- 1.3.6.1.4.1.37950.1.1.5.12.3.2.20.1.35
-- 1.3.6.1.4.1.37950.1.1.5.12.3.2.20.1.35
-- 1.3.6.1.4.1.37950.1.1.5.12.3.2.20.1.35
-- 1.3.6.1.4.1.37950.1.1.5.12.3.2.20.1.35
-- 1.3.6.1.4.1.37950.1.1.5.12.3.2.20.1.35
-- 1.3.6.1.4.1.37950.1.1.5.12.3.2.20.1.35
-- 1.3.6.1.4.1.37950.1.1.5.12.3.2.20.1.35
		-- 1.3.6.1.4.1.37950.1.1.5.12.3.2.20.1.35
		priV6ConnDsLiteAddressTypeS OBJECT-TYPE
			SYNTAX INTEGER
				{
				ipv6(0),
				dns(1)
				}
			MAX-ACCESS read-write
			STATUS current
			DESCRIPTION
				"Description."
			::= { priWanConnV6Entry 35 }

		
--           1.3.6.1.4.1.37950.1.1.5.12.3.2.6.1.21
-- 1.3.6.1.4.1.37950.1.1.5.12.3.2.20.1.36
-- 1.3.6.1.4.1.37950.1.1.5.12.3.2.20.1.36
-- 1.3.6.1.4.1.37950.1.1.5.12.3.2.20.1.36
-- 1.3.6.1.4.1.37950.1.1.5.12.3.2.20.1.36
-- 1.3.6.1.4.1.37950.1.1.5.12.3.2.20.1.36
-- 1.3.6.1.4.1.37950.1.1.5.12.3.2.20.1.36
-- 1.3.6.1.4.1.37950.1.1.5.12.3.2.20.1.36
-- 1.3.6.1.4.1.37950.1.1.5.12.3.2.20.1.36
		-- 1.3.6.1.4.1.37950.1.1.5.12.3.2.20.1.36
		priV6ConnDsLiteAddressS OBJECT-TYPE
			SYNTAX OCTET STRING
			MAX-ACCESS read-write
			STATUS current
			DESCRIPTION
				"Description."
			::= { priWanConnV6Entry 36 }

		
--           1.3.6.1.4.1.37950.1.1.5.12.3.2.6.1.22
-- 1.3.6.1.4.1.37950.1.1.5.12.3.2.20.1.37
-- 1.3.6.1.4.1.37950.1.1.5.12.3.2.20.1.37
-- 1.3.6.1.4.1.37950.1.1.5.12.3.2.20.1.37
-- 1.3.6.1.4.1.37950.1.1.5.12.3.2.20.1.37
-- 1.3.6.1.4.1.37950.1.1.5.12.3.2.20.1.37
-- 1.3.6.1.4.1.37950.1.1.5.12.3.2.20.1.37
-- 1.3.6.1.4.1.37950.1.1.5.12.3.2.20.1.37
-- 1.3.6.1.4.1.37950.1.1.5.12.3.2.20.1.37
		-- 1.3.6.1.4.1.37950.1.1.5.12.3.2.20.1.37
		priv6ConnQosEnableS OBJECT-TYPE
			SYNTAX INTEGER
				{
				disable(0),
				enable(1)
				}
			MAX-ACCESS read-write
			STATUS current
			DESCRIPTION
				"Description."
			::= { priWanConnV6Entry 37 }

		
--           1.3.6.1.4.1.37950.1.1.5.12.3.2.6.1.23
-- 1.3.6.1.4.1.37950.1.1.5.12.3.2.20.1.38
-- 1.3.6.1.4.1.37950.1.1.5.12.3.2.20.1.38
-- 1.3.6.1.4.1.37950.1.1.5.12.3.2.20.1.38
-- 1.3.6.1.4.1.37950.1.1.5.12.3.2.20.1.38
-- 1.3.6.1.4.1.37950.1.1.5.12.3.2.20.1.38
-- 1.3.6.1.4.1.37950.1.1.5.12.3.2.20.1.38
-- 1.3.6.1.4.1.37950.1.1.5.12.3.2.20.1.38
-- 1.3.6.1.4.1.37950.1.1.5.12.3.2.20.1.38
		-- 1.3.6.1.4.1.37950.1.1.5.12.3.2.20.1.38
		priV6ConnVlanModeS OBJECT-TYPE
			SYNTAX INTEGER
				{
				disable(0),
				tag(1),
				transparent(2)
				}
			MAX-ACCESS read-write
			STATUS current
			DESCRIPTION
				"Description."
			::= { priWanConnV6Entry 38 }

		
--           1.3.6.1.4.1.37950.1.1.5.12.3.2.6.1.24
-- 1.3.6.1.4.1.37950.1.1.5.12.3.2.20.1.39
-- 1.3.6.1.4.1.37950.1.1.5.12.3.2.20.1.39
-- 1.3.6.1.4.1.37950.1.1.5.12.3.2.20.1.39
-- 1.3.6.1.4.1.37950.1.1.5.12.3.2.20.1.39
-- 1.3.6.1.4.1.37950.1.1.5.12.3.2.20.1.39
-- 1.3.6.1.4.1.37950.1.1.5.12.3.2.20.1.39
-- 1.3.6.1.4.1.37950.1.1.5.12.3.2.20.1.39
-- 1.3.6.1.4.1.37950.1.1.5.12.3.2.20.1.39
		-- 1.3.6.1.4.1.37950.1.1.5.12.3.2.20.1.39
		priV6ConnTranslationEnableS OBJECT-TYPE
			SYNTAX INTEGER
				{
				disable(0),
				enable(1)
				}
			MAX-ACCESS read-write
			STATUS current
			DESCRIPTION
				"Description."
			::= { priWanConnV6Entry 39 }

		
--           1.3.6.1.4.1.37950.1.1.5.12.3.2.6.1.25
-- 1.3.6.1.4.1.37950.1.1.5.12.3.2.20.1.40
-- 1.3.6.1.4.1.37950.1.1.5.12.3.2.20.1.40
-- 1.3.6.1.4.1.37950.1.1.5.12.3.2.20.1.40
-- 1.3.6.1.4.1.37950.1.1.5.12.3.2.20.1.40
-- 1.3.6.1.4.1.37950.1.1.5.12.3.2.20.1.40
-- 1.3.6.1.4.1.37950.1.1.5.12.3.2.20.1.40
-- 1.3.6.1.4.1.37950.1.1.5.12.3.2.20.1.40
-- 1.3.6.1.4.1.37950.1.1.5.12.3.2.20.1.40
		-- 1.3.6.1.4.1.37950.1.1.5.12.3.2.20.1.40
		priV6ConnTranslationVlanS OBJECT-TYPE
			SYNTAX INTEGER (1..4095)
			MAX-ACCESS read-write
			STATUS current
			DESCRIPTION
				"Description."
			::= { priWanConnV6Entry 40 }

		
--           1.3.6.1.4.1.37950.1.1.5.12.3.2.6.1.26
-- 1.3.6.1.4.1.37950.1.1.5.12.3.2.20.1.41
-- 1.3.6.1.4.1.37950.1.1.5.12.3.2.20.1.41
-- 1.3.6.1.4.1.37950.1.1.5.12.3.2.20.1.41
-- 1.3.6.1.4.1.37950.1.1.5.12.3.2.20.1.41
-- 1.3.6.1.4.1.37950.1.1.5.12.3.2.20.1.41
-- 1.3.6.1.4.1.37950.1.1.5.12.3.2.20.1.41
-- 1.3.6.1.4.1.37950.1.1.5.12.3.2.20.1.41
-- 1.3.6.1.4.1.37950.1.1.5.12.3.2.20.1.41
		-- 1.3.6.1.4.1.37950.1.1.5.12.3.2.20.1.41
		priV6ConnTranslationCosS OBJECT-TYPE
			SYNTAX INTEGER (0..7)
			MAX-ACCESS read-write
			STATUS current
			DESCRIPTION
				"Description."
			::= { priWanConnV6Entry 41 }

		
--           1.3.6.1.4.1.37950.1.1.5.12.3.2.6.1.27
-- 1.3.6.1.4.1.37950.1.1.5.12.3.2.20.1.42
-- 1.3.6.1.4.1.37950.1.1.5.12.3.2.20.1.42
-- 1.3.6.1.4.1.37950.1.1.5.12.3.2.20.1.42
-- 1.3.6.1.4.1.37950.1.1.5.12.3.2.20.1.42
-- 1.3.6.1.4.1.37950.1.1.5.12.3.2.20.1.42
-- 1.3.6.1.4.1.37950.1.1.5.12.3.2.20.1.42
-- 1.3.6.1.4.1.37950.1.1.5.12.3.2.20.1.42
-- 1.3.6.1.4.1.37950.1.1.5.12.3.2.20.1.42
		-- 1.3.6.1.4.1.37950.1.1.5.12.3.2.20.1.42
		priV6ConnQinqEnableS OBJECT-TYPE
			SYNTAX INTEGER
				{
				disable(0),
				enable(1)
				}
			MAX-ACCESS read-write
			STATUS current
			DESCRIPTION
				"Description."
			::= { priWanConnV6Entry 42 }

		
--           1.3.6.1.4.1.37950.1.1.5.12.3.2.6.1.28
-- 1.3.6.1.4.1.37950.1.1.5.12.3.2.20.1.43
-- 1.3.6.1.4.1.37950.1.1.5.12.3.2.20.1.43
-- 1.3.6.1.4.1.37950.1.1.5.12.3.2.20.1.43
-- 1.3.6.1.4.1.37950.1.1.5.12.3.2.20.1.43
-- 1.3.6.1.4.1.37950.1.1.5.12.3.2.20.1.43
-- 1.3.6.1.4.1.37950.1.1.5.12.3.2.20.1.43
-- 1.3.6.1.4.1.37950.1.1.5.12.3.2.20.1.43
-- 1.3.6.1.4.1.37950.1.1.5.12.3.2.20.1.43
		-- 1.3.6.1.4.1.37950.1.1.5.12.3.2.20.1.43
		priV6ConnQinqTpidS OBJECT-TYPE
			SYNTAX INTEGER (1..65534)
			MAX-ACCESS read-write
			STATUS current
			DESCRIPTION
				"Description."
			::= { priWanConnV6Entry 43 }

		
--           1.3.6.1.4.1.37950.1.1.5.12.3.2.6.1.29
-- 1.3.6.1.4.1.37950.1.1.5.12.3.2.20.1.44
-- 1.3.6.1.4.1.37950.1.1.5.12.3.2.20.1.44
-- 1.3.6.1.4.1.37950.1.1.5.12.3.2.20.1.44
-- 1.3.6.1.4.1.37950.1.1.5.12.3.2.20.1.44
-- 1.3.6.1.4.1.37950.1.1.5.12.3.2.20.1.44
-- 1.3.6.1.4.1.37950.1.1.5.12.3.2.20.1.44
-- 1.3.6.1.4.1.37950.1.1.5.12.3.2.20.1.44
-- 1.3.6.1.4.1.37950.1.1.5.12.3.2.20.1.44
		-- 1.3.6.1.4.1.37950.1.1.5.12.3.2.20.1.44
		priV6ConnSvlanIdS OBJECT-TYPE
			SYNTAX INTEGER (1..4095)
			MAX-ACCESS read-write
			STATUS current
			DESCRIPTION
				"Description."
			::= { priWanConnV6Entry 44 }

		
--           1.3.6.1.4.1.37950.1.1.5.12.3.2.6.1.30
-- 1.3.6.1.4.1.37950.1.1.5.12.3.2.20.1.45
-- 1.3.6.1.4.1.37950.1.1.5.12.3.2.20.1.45
-- 1.3.6.1.4.1.37950.1.1.5.12.3.2.20.1.45
-- 1.3.6.1.4.1.37950.1.1.5.12.3.2.20.1.45
-- 1.3.6.1.4.1.37950.1.1.5.12.3.2.20.1.45
-- 1.3.6.1.4.1.37950.1.1.5.12.3.2.20.1.45
-- 1.3.6.1.4.1.37950.1.1.5.12.3.2.20.1.45
-- 1.3.6.1.4.1.37950.1.1.5.12.3.2.20.1.45
		-- 1.3.6.1.4.1.37950.1.1.5.12.3.2.20.1.45
		priV6ConnSvlanCosS OBJECT-TYPE
			SYNTAX INTEGER (0..7)
			MAX-ACCESS read-write
			STATUS current
			DESCRIPTION
				"Description."
			::= { priWanConnV6Entry 45 }

		
--           1.3.6.1.4.1.37950.1.1.5.12.3.2.6.1.30
-- 1.3.6.1.4.1.37950.1.1.5.12.3.2.20.1.46
-- 1.3.6.1.4.1.37950.1.1.5.12.3.2.20.1.46
-- 1.3.6.1.4.1.37950.1.1.5.12.3.2.20.1.46
-- 1.3.6.1.4.1.37950.1.1.5.12.3.2.20.1.46
-- 1.3.6.1.4.1.37950.1.1.5.12.3.2.20.1.46
-- 1.3.6.1.4.1.37950.1.1.5.12.3.2.20.1.46
-- 1.3.6.1.4.1.37950.1.1.5.12.3.2.20.1.46
-- 1.3.6.1.4.1.37950.1.1.5.12.3.2.20.1.46
		-- 1.3.6.1.4.1.37950.1.1.5.12.3.2.20.1.46
		priV6ConnRouteMtuS OBJECT-TYPE
			SYNTAX Integer32 (576..1500)
			MAX-ACCESS read-write
			STATUS current
			DESCRIPTION
				"Description."
			::= { priWanConnV6Entry 46 }

		
--           1.3.6.1.4.1.37950.1.1.5.12.3.2.6.1.31
-- 1.3.6.1.4.1.37950.1.1.5.12.3.2.20.1.47
-- 1.3.6.1.4.1.37950.1.1.5.12.3.2.20.1.47
-- 1.3.6.1.4.1.37950.1.1.5.12.3.2.20.1.47
-- 1.3.6.1.4.1.37950.1.1.5.12.3.2.20.1.47
-- 1.3.6.1.4.1.37950.1.1.5.12.3.2.20.1.47
-- 1.3.6.1.4.1.37950.1.1.5.12.3.2.20.1.47
-- 1.3.6.1.4.1.37950.1.1.5.12.3.2.20.1.47
-- 1.3.6.1.4.1.37950.1.1.5.12.3.2.20.1.47
		-- 1.3.6.1.4.1.37950.1.1.5.12.3.2.20.1.47
		priv6ConnNameS OBJECT-TYPE
			SYNTAX OCTET STRING
			MAX-ACCESS read-write
			STATUS current
			DESCRIPTION
				"Description."
			::= { priWanConnV6Entry 47 }

		
--           1.3.6.1.4.1.37950.1.1.5.12.3.2.6.1.32
-- 1.3.6.1.4.1.37950.1.1.5.12.3.2.20.1.48
-- 1.3.6.1.4.1.37950.1.1.5.12.3.2.20.1.48
-- 1.3.6.1.4.1.37950.1.1.5.12.3.2.20.1.48
-- 1.3.6.1.4.1.37950.1.1.5.12.3.2.20.1.48
-- 1.3.6.1.4.1.37950.1.1.5.12.3.2.20.1.48
-- 1.3.6.1.4.1.37950.1.1.5.12.3.2.20.1.48
-- 1.3.6.1.4.1.37950.1.1.5.12.3.2.20.1.48
-- 1.3.6.1.4.1.37950.1.1.5.12.3.2.20.1.48
		-- 1.3.6.1.4.1.37950.1.1.5.12.3.2.20.1.48
		priV6ConnStatusS OBJECT-TYPE
			SYNTAX INTEGER
				{
				disconnected(0),
				connected(1)
				}
			MAX-ACCESS read-write
			STATUS current
			DESCRIPTION
				"Description."
			::= { priWanConnV6Entry 48 }

		
--          1.3.6.1.4.1.37950.1.1.5.12.3.2.6.1.33
-- 1.3.6.1.4.1.37950.1.1.5.12.3.2.20.1.49
-- 1.3.6.1.4.1.37950.1.1.5.12.3.2.20.1.49
-- 1.3.6.1.4.1.37950.1.1.5.12.3.2.20.1.49
-- 1.3.6.1.4.1.37950.1.1.5.12.3.2.20.1.49
-- 1.3.6.1.4.1.37950.1.1.5.12.3.2.20.1.49
-- 1.3.6.1.4.1.37950.1.1.5.12.3.2.20.1.49
-- 1.3.6.1.4.1.37950.1.1.5.12.3.2.20.1.49
-- 1.3.6.1.4.1.37950.1.1.5.12.3.2.20.1.49
		-- 1.3.6.1.4.1.37950.1.1.5.12.3.2.20.1.49
		priV6ConnMacAddrS OBJECT-TYPE
			SYNTAX OCTET STRING
			MAX-ACCESS read-write
			STATUS current
			DESCRIPTION
				"Description."
			::= { priWanConnV6Entry 49 }

		
--         1.3.6.1.4.1.37950.1.1.5.12.3.2.21
-- 1.3.6.1.4.1.37950.1.1.5.12.3.2.21
-- 1.3.6.1.4.1.37950.1.1.5.12.3.2.21
-- 1.3.6.1.4.1.37950.1.1.5.12.3.2.21
-- 1.3.6.1.4.1.37950.1.1.5.12.3.2.21
-- 1.3.6.1.4.1.37950.1.1.5.12.3.2.21
-- 1.3.6.1.4.1.37950.1.1.5.12.3.2.21
-- 1.3.6.1.4.1.37950.1.1.5.12.3.2.21
		-- 1.3.6.1.4.1.37950.1.1.5.12.3.2.21
		priTr069ManageTable OBJECT-TYPE
			SYNTAX SEQUENCE OF PriTr069ManageEntry
			MAX-ACCESS not-accessible
			STATUS current
			DESCRIPTION
				"Description."
			::= { onuPriGlobalInfo 21 }

		
--         1.3.6.1.4.1.37950.1.1.5.12.3.2.21.1
-- 1.3.6.1.4.1.37950.1.1.5.12.3.2.21.1
-- 1.3.6.1.4.1.37950.1.1.5.12.3.2.21.1
-- 1.3.6.1.4.1.37950.1.1.5.12.3.2.21.1
-- 1.3.6.1.4.1.37950.1.1.5.12.3.2.21.1
-- 1.3.6.1.4.1.37950.1.1.5.12.3.2.21.1
-- 1.3.6.1.4.1.37950.1.1.5.12.3.2.21.1
-- 1.3.6.1.4.1.37950.1.1.5.12.3.2.21.1
		-- 1.3.6.1.4.1.37950.1.1.5.12.3.2.21.1
		priTr069ManageEntry OBJECT-TYPE
			SYNTAX PriTr069ManageEntry
			MAX-ACCESS not-accessible
			STATUS current
			DESCRIPTION
				"Description."
			INDEX { priMngPon, priMngOnu }
			::= { priTr069ManageTable 1 }

		
		PriTr069ManageEntry ::=
			SEQUENCE { 
				priMngPon
					Integer32,
				priMngOnu
					Integer32,
				priMngAcsAddressS
					OCTET STRING,
				priMngAcsUsernameS
					OCTET STRING,
				priMngAcsPasswordS
					OCTET STRING,
				priMngCertificateEnS
					INTEGER,
				priMngInformEnS
					INTEGER,
				priMngInformIntervalTimeS
					Unsigned32,
				priMngRevConnUsernameS
					OCTET STRING,
				priMngRevConnPasswordS
					OCTET STRING,
				priMngStatusS
					INTEGER
			 }

--         1.3.6.1.4.1.37950.1.1.5.12.3.2.21.1.1
-- 1.3.6.1.4.1.37950.1.1.5.12.3.2.21.1.1
-- 1.3.6.1.4.1.37950.1.1.5.12.3.2.21.1.1
-- 1.3.6.1.4.1.37950.1.1.5.12.3.2.21.1.1
-- 1.3.6.1.4.1.37950.1.1.5.12.3.2.21.1.1
-- 1.3.6.1.4.1.37950.1.1.5.12.3.2.21.1.1
-- 1.3.6.1.4.1.37950.1.1.5.12.3.2.21.1.1
-- 1.3.6.1.4.1.37950.1.1.5.12.3.2.21.1.1
		-- 1.3.6.1.4.1.37950.1.1.5.12.3.2.21.1.1
		priMngPon OBJECT-TYPE
			SYNTAX Integer32 (1..16)
			MAX-ACCESS read-only
			STATUS current
			DESCRIPTION
				"Description."
			::= { priTr069ManageEntry 1 }

		
--         1.3.6.1.4.1.37950.1.1.5.12.3.2.21.1.2
-- 1.3.6.1.4.1.37950.1.1.5.12.3.2.21.1.2
-- 1.3.6.1.4.1.37950.1.1.5.12.3.2.21.1.2
-- 1.3.6.1.4.1.37950.1.1.5.12.3.2.21.1.2
-- 1.3.6.1.4.1.37950.1.1.5.12.3.2.21.1.2
-- 1.3.6.1.4.1.37950.1.1.5.12.3.2.21.1.2
-- 1.3.6.1.4.1.37950.1.1.5.12.3.2.21.1.2
-- 1.3.6.1.4.1.37950.1.1.5.12.3.2.21.1.2
		-- 1.3.6.1.4.1.37950.1.1.5.12.3.2.21.1.2
		priMngOnu OBJECT-TYPE
			SYNTAX Integer32 (1..65535)
			MAX-ACCESS read-only
			STATUS current
			DESCRIPTION
				"Description."
			::= { priTr069ManageEntry 2 }

		
--         1.3.6.1.4.1.37950.1.1.5.12.3.2.21.1.3
-- 1.3.6.1.4.1.37950.1.1.5.12.3.2.21.1.3
-- 1.3.6.1.4.1.37950.1.1.5.12.3.2.21.1.3
-- 1.3.6.1.4.1.37950.1.1.5.12.3.2.21.1.3
-- 1.3.6.1.4.1.37950.1.1.5.12.3.2.21.1.3
-- 1.3.6.1.4.1.37950.1.1.5.12.3.2.21.1.3
-- 1.3.6.1.4.1.37950.1.1.5.12.3.2.21.1.3
-- 1.3.6.1.4.1.37950.1.1.5.12.3.2.21.1.3
		-- 1.3.6.1.4.1.37950.1.1.5.12.3.2.21.1.3
		priMngAcsAddressS OBJECT-TYPE
			SYNTAX OCTET STRING
			MAX-ACCESS read-only
			STATUS current
			DESCRIPTION
				"Description."
			::= { priTr069ManageEntry 3 }

		
--         1.3.6.1.4.1.37950.1.1.5.12.3.2.21.1.4
-- 1.3.6.1.4.1.37950.1.1.5.12.3.2.21.1.4
-- 1.3.6.1.4.1.37950.1.1.5.12.3.2.21.1.4
-- 1.3.6.1.4.1.37950.1.1.5.12.3.2.21.1.4
-- 1.3.6.1.4.1.37950.1.1.5.12.3.2.21.1.4
-- 1.3.6.1.4.1.37950.1.1.5.12.3.2.21.1.4
-- 1.3.6.1.4.1.37950.1.1.5.12.3.2.21.1.4
-- 1.3.6.1.4.1.37950.1.1.5.12.3.2.21.1.4
		-- 1.3.6.1.4.1.37950.1.1.5.12.3.2.21.1.4
		priMngAcsUsernameS OBJECT-TYPE
			SYNTAX OCTET STRING
			MAX-ACCESS read-only
			STATUS current
			DESCRIPTION
				"Description."
			::= { priTr069ManageEntry 4 }

		
--         1.3.6.1.4.1.37950.1.1.5.12.3.2.21.1.5
-- 1.3.6.1.4.1.37950.1.1.5.12.3.2.21.1.5
-- 1.3.6.1.4.1.37950.1.1.5.12.3.2.21.1.5
-- 1.3.6.1.4.1.37950.1.1.5.12.3.2.21.1.5
-- 1.3.6.1.4.1.37950.1.1.5.12.3.2.21.1.5
-- 1.3.6.1.4.1.37950.1.1.5.12.3.2.21.1.5
-- 1.3.6.1.4.1.37950.1.1.5.12.3.2.21.1.5
-- 1.3.6.1.4.1.37950.1.1.5.12.3.2.21.1.5
		-- 1.3.6.1.4.1.37950.1.1.5.12.3.2.21.1.5
		priMngAcsPasswordS OBJECT-TYPE
			SYNTAX OCTET STRING
			MAX-ACCESS read-only
			STATUS current
			DESCRIPTION
				"Description."
			::= { priTr069ManageEntry 5 }

		
--         1.3.6.1.4.1.37950.1.1.5.12.3.2.21.1.6
-- 1.3.6.1.4.1.37950.1.1.5.12.3.2.21.1.6
-- 1.3.6.1.4.1.37950.1.1.5.12.3.2.21.1.6
-- 1.3.6.1.4.1.37950.1.1.5.12.3.2.21.1.6
-- 1.3.6.1.4.1.37950.1.1.5.12.3.2.21.1.6
-- 1.3.6.1.4.1.37950.1.1.5.12.3.2.21.1.6
-- 1.3.6.1.4.1.37950.1.1.5.12.3.2.21.1.6
-- 1.3.6.1.4.1.37950.1.1.5.12.3.2.21.1.6
		-- 1.3.6.1.4.1.37950.1.1.5.12.3.2.21.1.6
		priMngCertificateEnS OBJECT-TYPE
			SYNTAX INTEGER
				{
				disable(0),
				enable(1)
				}
			MAX-ACCESS read-only
			STATUS current
			DESCRIPTION
				"Description."
			::= { priTr069ManageEntry 6 }

		
--         1.3.6.1.4.1.37950.1.1.5.12.3.2.21.1.7
-- 1.3.6.1.4.1.37950.1.1.5.12.3.2.21.1.7
-- 1.3.6.1.4.1.37950.1.1.5.12.3.2.21.1.7
-- 1.3.6.1.4.1.37950.1.1.5.12.3.2.21.1.7
-- 1.3.6.1.4.1.37950.1.1.5.12.3.2.21.1.7
-- 1.3.6.1.4.1.37950.1.1.5.12.3.2.21.1.7
-- 1.3.6.1.4.1.37950.1.1.5.12.3.2.21.1.7
-- 1.3.6.1.4.1.37950.1.1.5.12.3.2.21.1.7
		-- 1.3.6.1.4.1.37950.1.1.5.12.3.2.21.1.7
		priMngInformEnS OBJECT-TYPE
			SYNTAX INTEGER
				{
				disable(0),
				enable(1)
				}
			MAX-ACCESS read-only
			STATUS current
			DESCRIPTION
				"Description."
			::= { priTr069ManageEntry 7 }

		
--         1.3.6.1.4.1.37950.1.1.5.12.3.2.21.1.8
-- 1.3.6.1.4.1.37950.1.1.5.12.3.2.21.1.8
-- 1.3.6.1.4.1.37950.1.1.5.12.3.2.21.1.8
-- 1.3.6.1.4.1.37950.1.1.5.12.3.2.21.1.8
-- 1.3.6.1.4.1.37950.1.1.5.12.3.2.21.1.8
-- 1.3.6.1.4.1.37950.1.1.5.12.3.2.21.1.8
-- 1.3.6.1.4.1.37950.1.1.5.12.3.2.21.1.8
-- 1.3.6.1.4.1.37950.1.1.5.12.3.2.21.1.8
		-- 1.3.6.1.4.1.37950.1.1.5.12.3.2.21.1.8
		priMngInformIntervalTimeS OBJECT-TYPE
			SYNTAX Unsigned32 (0..4294967295)
			MAX-ACCESS read-only
			STATUS current
			DESCRIPTION
				"Description."
			::= { priTr069ManageEntry 8 }

		
--         1.3.6.1.4.1.37950.1.1.5.12.3.2.21.1.9
-- 1.3.6.1.4.1.37950.1.1.5.12.3.2.21.1.9
-- 1.3.6.1.4.1.37950.1.1.5.12.3.2.21.1.9
-- 1.3.6.1.4.1.37950.1.1.5.12.3.2.21.1.9
-- 1.3.6.1.4.1.37950.1.1.5.12.3.2.21.1.9
-- 1.3.6.1.4.1.37950.1.1.5.12.3.2.21.1.9
-- 1.3.6.1.4.1.37950.1.1.5.12.3.2.21.1.9
-- 1.3.6.1.4.1.37950.1.1.5.12.3.2.21.1.9
		-- 1.3.6.1.4.1.37950.1.1.5.12.3.2.21.1.9
		priMngRevConnUsernameS OBJECT-TYPE
			SYNTAX OCTET STRING
			MAX-ACCESS read-only
			STATUS current
			DESCRIPTION
				"Description."
			::= { priTr069ManageEntry 9 }

		
--         1.3.6.1.4.1.37950.1.1.5.12.3.2.21.1.10
-- 1.3.6.1.4.1.37950.1.1.5.12.3.2.21.1.10
-- 1.3.6.1.4.1.37950.1.1.5.12.3.2.21.1.10
-- 1.3.6.1.4.1.37950.1.1.5.12.3.2.21.1.10
-- 1.3.6.1.4.1.37950.1.1.5.12.3.2.21.1.10
-- 1.3.6.1.4.1.37950.1.1.5.12.3.2.21.1.10
-- 1.3.6.1.4.1.37950.1.1.5.12.3.2.21.1.10
-- 1.3.6.1.4.1.37950.1.1.5.12.3.2.21.1.10
		-- 1.3.6.1.4.1.37950.1.1.5.12.3.2.21.1.10
		priMngRevConnPasswordS OBJECT-TYPE
			SYNTAX OCTET STRING
			MAX-ACCESS read-only
			STATUS current
			DESCRIPTION
				"Description."
			::= { priTr069ManageEntry 10 }

		
--         1.3.6.1.4.1.37950.1.1.5.12.3.2.21.1.11
-- 1.3.6.1.4.1.37950.1.1.5.12.3.2.21.1.11
-- 1.3.6.1.4.1.37950.1.1.5.12.3.2.21.1.11
-- 1.3.6.1.4.1.37950.1.1.5.12.3.2.21.1.11
-- 1.3.6.1.4.1.37950.1.1.5.12.3.2.21.1.11
-- 1.3.6.1.4.1.37950.1.1.5.12.3.2.21.1.11
-- 1.3.6.1.4.1.37950.1.1.5.12.3.2.21.1.11
-- 1.3.6.1.4.1.37950.1.1.5.12.3.2.21.1.11
		-- 1.3.6.1.4.1.37950.1.1.5.12.3.2.21.1.11
		priMngStatusS OBJECT-TYPE
			SYNTAX INTEGER
				{
				disable(0),
				enable(1)
				}
			MAX-ACCESS read-only
			STATUS current
			DESCRIPTION
				"Description."
			::= { priTr069ManageEntry 11 }

		
--         1.3.6.1.4.1.37950.1.1.5.12.3.2.22
-- 1.3.6.1.4.1.37950.1.1.5.12.3.2.22
-- 1.3.6.1.4.1.37950.1.1.5.12.3.2.22
-- 1.3.6.1.4.1.37950.1.1.5.12.3.2.22
-- 1.3.6.1.4.1.37950.1.1.5.12.3.2.22
-- 1.3.6.1.4.1.37950.1.1.5.12.3.2.22
-- 1.3.6.1.4.1.37950.1.1.5.12.3.2.22
-- 1.3.6.1.4.1.37950.1.1.5.12.3.2.22
		-- 1.3.6.1.4.1.37950.1.1.5.12.3.2.22
		priTr069StunTable OBJECT-TYPE
			SYNTAX SEQUENCE OF PriTr069StunEntry
			MAX-ACCESS not-accessible
			STATUS current
			DESCRIPTION
				"Description."
			::= { onuPriGlobalInfo 22 }

		
--         1.3.6.1.4.1.37950.1.1.5.12.3.2.22.1
-- 1.3.6.1.4.1.37950.1.1.5.12.3.2.22.1
-- 1.3.6.1.4.1.37950.1.1.5.12.3.2.22.1
-- 1.3.6.1.4.1.37950.1.1.5.12.3.2.22.1
-- 1.3.6.1.4.1.37950.1.1.5.12.3.2.22.1
-- 1.3.6.1.4.1.37950.1.1.5.12.3.2.22.1
-- 1.3.6.1.4.1.37950.1.1.5.12.3.2.22.1
-- 1.3.6.1.4.1.37950.1.1.5.12.3.2.22.1
		-- 1.3.6.1.4.1.37950.1.1.5.12.3.2.22.1
		priTr069StunEntry OBJECT-TYPE
			SYNTAX PriTr069StunEntry
			MAX-ACCESS not-accessible
			STATUS current
			DESCRIPTION
				"Description."
			INDEX { priStunPon, priStunOnu }
			::= { priTr069StunTable 1 }

		
		PriTr069StunEntry ::=
			SEQUENCE { 
				priStunPon
					Integer32,
				priStunOnu
					Integer32,
				priStunAddressS
					OCTET STRING,
				priStunPortS
					Integer32,
				priStunUsernameS
					OCTET STRING,
				priStunPasswordS
					OCTET STRING,
				priStunStatusS
					INTEGER
			 }

--         1.3.6.1.4.1.37950.1.1.5.12.3.2.22.1.1
-- 1.3.6.1.4.1.37950.1.1.5.12.3.2.22.1.1
-- 1.3.6.1.4.1.37950.1.1.5.12.3.2.22.1.1
-- 1.3.6.1.4.1.37950.1.1.5.12.3.2.22.1.1
-- 1.3.6.1.4.1.37950.1.1.5.12.3.2.22.1.1
-- 1.3.6.1.4.1.37950.1.1.5.12.3.2.22.1.1
-- 1.3.6.1.4.1.37950.1.1.5.12.3.2.22.1.1
-- 1.3.6.1.4.1.37950.1.1.5.12.3.2.22.1.1
		-- 1.3.6.1.4.1.37950.1.1.5.12.3.2.22.1.1
		priStunPon OBJECT-TYPE
			SYNTAX Integer32 (1..16)
			MAX-ACCESS read-only
			STATUS current
			DESCRIPTION
				"Description."
			::= { priTr069StunEntry 1 }

		
--         1.3.6.1.4.1.37950.1.1.5.12.3.2.22.1.2
-- 1.3.6.1.4.1.37950.1.1.5.12.3.2.22.1.2
-- 1.3.6.1.4.1.37950.1.1.5.12.3.2.22.1.2
-- 1.3.6.1.4.1.37950.1.1.5.12.3.2.22.1.2
-- 1.3.6.1.4.1.37950.1.1.5.12.3.2.22.1.2
-- 1.3.6.1.4.1.37950.1.1.5.12.3.2.22.1.2
-- 1.3.6.1.4.1.37950.1.1.5.12.3.2.22.1.2
-- 1.3.6.1.4.1.37950.1.1.5.12.3.2.22.1.2
		-- 1.3.6.1.4.1.37950.1.1.5.12.3.2.22.1.2
		priStunOnu OBJECT-TYPE
			SYNTAX Integer32 (1..65535)
			MAX-ACCESS read-only
			STATUS current
			DESCRIPTION
				"Description."
			::= { priTr069StunEntry 2 }

		
--         1.3.6.1.4.1.37950.1.1.5.12.3.2.22.1.3
-- 1.3.6.1.4.1.37950.1.1.5.12.3.2.22.1.3
-- 1.3.6.1.4.1.37950.1.1.5.12.3.2.22.1.3
-- 1.3.6.1.4.1.37950.1.1.5.12.3.2.22.1.3
-- 1.3.6.1.4.1.37950.1.1.5.12.3.2.22.1.3
-- 1.3.6.1.4.1.37950.1.1.5.12.3.2.22.1.3
-- 1.3.6.1.4.1.37950.1.1.5.12.3.2.22.1.3
-- 1.3.6.1.4.1.37950.1.1.5.12.3.2.22.1.3
		-- 1.3.6.1.4.1.37950.1.1.5.12.3.2.22.1.3
		priStunAddressS OBJECT-TYPE
			SYNTAX OCTET STRING
			MAX-ACCESS read-only
			STATUS current
			DESCRIPTION
				"Description."
			::= { priTr069StunEntry 3 }

		
--         1.3.6.1.4.1.37950.1.1.5.12.3.2.22.1.4
-- 1.3.6.1.4.1.37950.1.1.5.12.3.2.22.1.4
-- 1.3.6.1.4.1.37950.1.1.5.12.3.2.22.1.4
-- 1.3.6.1.4.1.37950.1.1.5.12.3.2.22.1.4
-- 1.3.6.1.4.1.37950.1.1.5.12.3.2.22.1.4
-- 1.3.6.1.4.1.37950.1.1.5.12.3.2.22.1.4
-- 1.3.6.1.4.1.37950.1.1.5.12.3.2.22.1.4
-- 1.3.6.1.4.1.37950.1.1.5.12.3.2.22.1.4
		-- 1.3.6.1.4.1.37950.1.1.5.12.3.2.22.1.4
		priStunPortS OBJECT-TYPE
			SYNTAX Integer32 (1..65535)
			MAX-ACCESS read-only
			STATUS current
			DESCRIPTION
				"Description."
			::= { priTr069StunEntry 4 }

		
--         1.3.6.1.4.1.37950.1.1.5.12.3.2.22.1.5
-- 1.3.6.1.4.1.37950.1.1.5.12.3.2.22.1.5
-- 1.3.6.1.4.1.37950.1.1.5.12.3.2.22.1.5
-- 1.3.6.1.4.1.37950.1.1.5.12.3.2.22.1.5
-- 1.3.6.1.4.1.37950.1.1.5.12.3.2.22.1.5
-- 1.3.6.1.4.1.37950.1.1.5.12.3.2.22.1.5
-- 1.3.6.1.4.1.37950.1.1.5.12.3.2.22.1.5
-- 1.3.6.1.4.1.37950.1.1.5.12.3.2.22.1.5
		-- 1.3.6.1.4.1.37950.1.1.5.12.3.2.22.1.5
		priStunUsernameS OBJECT-TYPE
			SYNTAX OCTET STRING
			MAX-ACCESS read-only
			STATUS current
			DESCRIPTION
				"Description."
			::= { priTr069StunEntry 5 }

		
--         1.3.6.1.4.1.37950.1.1.5.12.3.2.22.1.6
-- 1.3.6.1.4.1.37950.1.1.5.12.3.2.22.1.6
-- 1.3.6.1.4.1.37950.1.1.5.12.3.2.22.1.6
-- 1.3.6.1.4.1.37950.1.1.5.12.3.2.22.1.6
-- 1.3.6.1.4.1.37950.1.1.5.12.3.2.22.1.6
-- 1.3.6.1.4.1.37950.1.1.5.12.3.2.22.1.6
-- 1.3.6.1.4.1.37950.1.1.5.12.3.2.22.1.6
-- 1.3.6.1.4.1.37950.1.1.5.12.3.2.22.1.6
		-- 1.3.6.1.4.1.37950.1.1.5.12.3.2.22.1.6
		priStunPasswordS OBJECT-TYPE
			SYNTAX OCTET STRING
			MAX-ACCESS read-only
			STATUS current
			DESCRIPTION
				"Description."
			::= { priTr069StunEntry 6 }

		
--         1.3.6.1.4.1.37950.1.1.5.12.3.2.22.1.7
-- 1.3.6.1.4.1.37950.1.1.5.12.3.2.22.1.7
-- 1.3.6.1.4.1.37950.1.1.5.12.3.2.22.1.7
-- 1.3.6.1.4.1.37950.1.1.5.12.3.2.22.1.7
-- 1.3.6.1.4.1.37950.1.1.5.12.3.2.22.1.7
-- 1.3.6.1.4.1.37950.1.1.5.12.3.2.22.1.7
-- 1.3.6.1.4.1.37950.1.1.5.12.3.2.22.1.7
-- 1.3.6.1.4.1.37950.1.1.5.12.3.2.22.1.7
		-- 1.3.6.1.4.1.37950.1.1.5.12.3.2.22.1.7
		priStunStatusS OBJECT-TYPE
			SYNTAX INTEGER
				{
				disable(0),
				enable(1)
				}
			MAX-ACCESS read-only
			STATUS current
			DESCRIPTION
				"Description."
			::= { priTr069StunEntry 7 }

		
--         1.3.6.1.4.1.37950.1.1.5.12.3.2.23
-- 1.3.6.1.4.1.37950.1.1.5.12.3.2.23
-- 1.3.6.1.4.1.37950.1.1.5.12.3.2.23
-- 1.3.6.1.4.1.37950.1.1.5.12.3.2.23
-- 1.3.6.1.4.1.37950.1.1.5.12.3.2.23
-- 1.3.6.1.4.1.37950.1.1.5.12.3.2.23
-- 1.3.6.1.4.1.37950.1.1.5.12.3.2.23
-- 1.3.6.1.4.1.37950.1.1.5.12.3.2.23
		-- 1.3.6.1.4.1.37950.1.1.5.12.3.2.23
		priWanConnCfgTable OBJECT-TYPE
			SYNTAX SEQUENCE OF PriWanConnCfgEntry
			MAX-ACCESS not-accessible
			STATUS current
			DESCRIPTION
				"Description."
			::= { onuPriGlobalInfo 23 }

		
--         1.3.6.1.4.1.37950.1.1.5.12.3.2.23.1
-- 1.3.6.1.4.1.37950.1.1.5.12.3.2.23.1
-- 1.3.6.1.4.1.37950.1.1.5.12.3.2.23.1
-- 1.3.6.1.4.1.37950.1.1.5.12.3.2.23.1
-- 1.3.6.1.4.1.37950.1.1.5.12.3.2.23.1
-- 1.3.6.1.4.1.37950.1.1.5.12.3.2.23.1
-- 1.3.6.1.4.1.37950.1.1.5.12.3.2.23.1
-- 1.3.6.1.4.1.37950.1.1.5.12.3.2.23.1
		-- 1.3.6.1.4.1.37950.1.1.5.12.3.2.23.1
		priWanConnCfgEntry OBJECT-TYPE
			SYNTAX PriWanConnCfgEntry
			MAX-ACCESS not-accessible
			STATUS current
			DESCRIPTION
				"Description."
			INDEX { priWanConnCfgPon, priWanConnCfgOnu }
			::= { priWanConnCfgTable 1 }

		
		PriWanConnCfgEntry ::=
			SEQUENCE { 
				priWanConnCfgPon
					INTEGER,
				priWanConnCfgOnu
					INTEGER,
				priWanConnCfgNum
					INTEGER
			 }

--         1.3.6.1.4.1.37950.1.1.5.12.3.2.23.1.1
-- 1.3.6.1.4.1.37950.1.1.5.12.3.2.23.1.1
-- 1.3.6.1.4.1.37950.1.1.5.12.3.2.23.1.1
-- 1.3.6.1.4.1.37950.1.1.5.12.3.2.23.1.1
-- 1.3.6.1.4.1.37950.1.1.5.12.3.2.23.1.1
-- 1.3.6.1.4.1.37950.1.1.5.12.3.2.23.1.1
-- 1.3.6.1.4.1.37950.1.1.5.12.3.2.23.1.1
-- 1.3.6.1.4.1.37950.1.1.5.12.3.2.23.1.1
		-- 1.3.6.1.4.1.37950.1.1.5.12.3.2.23.1.1
		priWanConnCfgPon OBJECT-TYPE
			SYNTAX INTEGER
			MAX-ACCESS read-write
			STATUS current
			DESCRIPTION
				"Description."
			::= { priWanConnCfgEntry 1 }

		
--         1.3.6.1.4.1.37950.1.1.5.12.3.2.23.1.2
-- 1.3.6.1.4.1.37950.1.1.5.12.3.2.23.1.2
-- 1.3.6.1.4.1.37950.1.1.5.12.3.2.23.1.2
-- 1.3.6.1.4.1.37950.1.1.5.12.3.2.23.1.2
-- 1.3.6.1.4.1.37950.1.1.5.12.3.2.23.1.2
-- 1.3.6.1.4.1.37950.1.1.5.12.3.2.23.1.2
-- 1.3.6.1.4.1.37950.1.1.5.12.3.2.23.1.2
-- 1.3.6.1.4.1.37950.1.1.5.12.3.2.23.1.2
		-- 1.3.6.1.4.1.37950.1.1.5.12.3.2.23.1.2
		priWanConnCfgOnu OBJECT-TYPE
			SYNTAX INTEGER
			MAX-ACCESS read-write
			STATUS current
			DESCRIPTION
				"Description."
			::= { priWanConnCfgEntry 2 }

		
--         1.3.6.1.4.1.37950.1.1.5.12.3.2.23.1.3
-- 1.3.6.1.4.1.37950.1.1.5.12.3.2.23.1.3
-- 1.3.6.1.4.1.37950.1.1.5.12.3.2.23.1.3
-- 1.3.6.1.4.1.37950.1.1.5.12.3.2.23.1.3
-- 1.3.6.1.4.1.37950.1.1.5.12.3.2.23.1.3
-- 1.3.6.1.4.1.37950.1.1.5.12.3.2.23.1.3
-- 1.3.6.1.4.1.37950.1.1.5.12.3.2.23.1.3
-- 1.3.6.1.4.1.37950.1.1.5.12.3.2.23.1.3
		-- 1.3.6.1.4.1.37950.1.1.5.12.3.2.23.1.3
		priWanConnCfgNum OBJECT-TYPE
			SYNTAX INTEGER
			MAX-ACCESS read-write
			STATUS current
			DESCRIPTION
				"Description."
			::= { priWanConnCfgEntry 3 }

		
--         1.3.6.1.4.1.37950.1.1.5.12.3.2.24
-- 1.3.6.1.4.1.37950.1.1.5.12.3.2.24
-- 1.3.6.1.4.1.37950.1.1.5.12.3.2.24
-- 1.3.6.1.4.1.37950.1.1.5.12.3.2.24
-- 1.3.6.1.4.1.37950.1.1.5.12.3.2.24
-- 1.3.6.1.4.1.37950.1.1.5.12.3.2.24
-- 1.3.6.1.4.1.37950.1.1.5.12.3.2.24
-- 1.3.6.1.4.1.37950.1.1.5.12.3.2.24
		-- 1.3.6.1.4.1.37950.1.1.5.12.3.2.24
		priWanConnCfgV6Table OBJECT-TYPE
			SYNTAX SEQUENCE OF PriWanConnCfgV6Entry
			MAX-ACCESS not-accessible
			STATUS current
			DESCRIPTION
				"Description."
			::= { onuPriGlobalInfo 24 }

		
--         1.3.6.1.4.1.37950.1.1.5.12.3.2.24.1
-- 1.3.6.1.4.1.37950.1.1.5.12.3.2.24.1
-- 1.3.6.1.4.1.37950.1.1.5.12.3.2.24.1
-- 1.3.6.1.4.1.37950.1.1.5.12.3.2.24.1
-- 1.3.6.1.4.1.37950.1.1.5.12.3.2.24.1
-- 1.3.6.1.4.1.37950.1.1.5.12.3.2.24.1
-- 1.3.6.1.4.1.37950.1.1.5.12.3.2.24.1
-- 1.3.6.1.4.1.37950.1.1.5.12.3.2.24.1
		-- 1.3.6.1.4.1.37950.1.1.5.12.3.2.24.1
		priWanConnCfgV6Entry OBJECT-TYPE
			SYNTAX PriWanConnCfgV6Entry
			MAX-ACCESS not-accessible
			STATUS current
			DESCRIPTION
				"Description."
			INDEX { priWanConnCfgV6Pon, priWanConnCfgV6Onu }
			::= { priWanConnCfgV6Table 1 }

		
		PriWanConnCfgV6Entry ::=
			SEQUENCE { 
				priWanConnCfgV6Pon
					INTEGER,
				priWanConnCfgV6Onu
					INTEGER,
				priWanConnCfgV6Num
					INTEGER
			 }

--         1.3.6.1.4.1.37950.1.1.5.12.3.2.24.1.1
-- 1.3.6.1.4.1.37950.1.1.5.12.3.2.24.1.1
-- 1.3.6.1.4.1.37950.1.1.5.12.3.2.24.1.1
-- 1.3.6.1.4.1.37950.1.1.5.12.3.2.24.1.1
-- 1.3.6.1.4.1.37950.1.1.5.12.3.2.24.1.1
-- 1.3.6.1.4.1.37950.1.1.5.12.3.2.24.1.1
-- 1.3.6.1.4.1.37950.1.1.5.12.3.2.24.1.1
-- 1.3.6.1.4.1.37950.1.1.5.12.3.2.24.1.1
		-- 1.3.6.1.4.1.37950.1.1.5.12.3.2.24.1.1
		priWanConnCfgV6Pon OBJECT-TYPE
			SYNTAX INTEGER
			MAX-ACCESS read-write
			STATUS current
			DESCRIPTION
				"Description."
			::= { priWanConnCfgV6Entry 1 }

		
--         1.3.6.1.4.1.37950.1.1.5.12.3.2.24.1.2
-- 1.3.6.1.4.1.37950.1.1.5.12.3.2.24.1.2
-- 1.3.6.1.4.1.37950.1.1.5.12.3.2.24.1.2
-- 1.3.6.1.4.1.37950.1.1.5.12.3.2.24.1.2
-- 1.3.6.1.4.1.37950.1.1.5.12.3.2.24.1.2
-- 1.3.6.1.4.1.37950.1.1.5.12.3.2.24.1.2
-- 1.3.6.1.4.1.37950.1.1.5.12.3.2.24.1.2
-- 1.3.6.1.4.1.37950.1.1.5.12.3.2.24.1.2
		-- 1.3.6.1.4.1.37950.1.1.5.12.3.2.24.1.2
		priWanConnCfgV6Onu OBJECT-TYPE
			SYNTAX INTEGER
			MAX-ACCESS read-write
			STATUS current
			DESCRIPTION
				"Description."
			::= { priWanConnCfgV6Entry 2 }

		
--         1.3.6.1.4.1.37950.1.1.5.12.3.2.24.1.3
-- 1.3.6.1.4.1.37950.1.1.5.12.3.2.24.1.3
-- 1.3.6.1.4.1.37950.1.1.5.12.3.2.24.1.3
-- 1.3.6.1.4.1.37950.1.1.5.12.3.2.24.1.3
-- 1.3.6.1.4.1.37950.1.1.5.12.3.2.24.1.3
-- 1.3.6.1.4.1.37950.1.1.5.12.3.2.24.1.3
-- 1.3.6.1.4.1.37950.1.1.5.12.3.2.24.1.3
-- 1.3.6.1.4.1.37950.1.1.5.12.3.2.24.1.3
		-- 1.3.6.1.4.1.37950.1.1.5.12.3.2.24.1.3
		priWanConnCfgV6Num OBJECT-TYPE
			SYNTAX INTEGER
			MAX-ACCESS read-write
			STATUS current
			DESCRIPTION
				"Description."
			::= { priWanConnCfgV6Entry 3 }

		
--       1.3.6.1.4.1.37950.1.1.5.12.3.2.25
-- 1.3.6.1.4.1.37950.1.1.5.12.3.2.25
-- 1.3.6.1.4.1.37950.1.1.5.12.3.2.25
-- 1.3.6.1.4.1.37950.1.1.5.12.3.2.25
-- 1.3.6.1.4.1.37950.1.1.5.12.3.2.25
-- 1.3.6.1.4.1.37950.1.1.5.12.3.2.25
		-- 1.3.6.1.4.1.37950.1.1.5.12.3.2.25
		priSelfDiagnosisTable OBJECT-TYPE
			SYNTAX SEQUENCE OF PriSelfDiagnosisEntry
			MAX-ACCESS not-accessible
			STATUS current
			DESCRIPTION
				"Description."
			::= { onuPriGlobalInfo 25 }

		
--       1.3.6.1.4.1.37950.1.1.5.12.3.2.25.1
-- 1.3.6.1.4.1.37950.1.1.5.12.3.2.25.1
-- 1.3.6.1.4.1.37950.1.1.5.12.3.2.25.1
-- 1.3.6.1.4.1.37950.1.1.5.12.3.2.25.1
-- 1.3.6.1.4.1.37950.1.1.5.12.3.2.25.1
-- 1.3.6.1.4.1.37950.1.1.5.12.3.2.25.1
		-- 1.3.6.1.4.1.37950.1.1.5.12.3.2.25.1
		priSelfDiagnosisEntry OBJECT-TYPE
			SYNTAX PriSelfDiagnosisEntry
			MAX-ACCESS not-accessible
			STATUS current
			DESCRIPTION
				"Description."
			INDEX { priSelfDiagPon, priSelfDiagOnu }
			::= { priSelfDiagnosisTable 1 }

		
		PriSelfDiagnosisEntry ::=
			SEQUENCE { 
				priSelfDiagPon
					INTEGER,
				priSelfDiagOnu
					INTEGER,
				priSelfDiagSessionID
					Integer32,
				priSelfDiagTransportProtocol
					INTEGER,
				priSelfDiagDiagnosisMethod
					INTEGER,
				priSelfDiagDiagnosisAction
					INTEGER,
				priSelfDiagAction
					INTEGER,
				priSelfDiagURL
					OCTET STRING,
				priSelfDiagUseWanIndex
					Integer32,
				priSelfDiagCurrentState
					INTEGER,
				priSelfDiagLogFilename
					OCTET STRING
			 }

--         1.3.6.1.4.1.37950.1.1.5.12.3.2.24.1.1
-- 1.3.6.1.4.1.37950.1.1.5.12.3.2.24.1.1
-- 1.3.6.1.4.1.37950.1.1.5.12.3.2.25.1.1
-- 1.3.6.1.4.1.37950.1.1.5.12.3.2.25.1.1
-- 1.3.6.1.4.1.37950.1.1.5.12.3.2.25.1.1
-- 1.3.6.1.4.1.37950.1.1.5.12.3.2.25.1.1
-- 1.3.6.1.4.1.37950.1.1.5.12.3.2.25.1.1
-- 1.3.6.1.4.1.37950.1.1.5.12.3.2.25.1.1
		-- 1.3.6.1.4.1.37950.1.1.5.12.3.2.25.1.1
		priSelfDiagPon OBJECT-TYPE
			SYNTAX INTEGER (1..16)
			MAX-ACCESS read-write
			STATUS current
			DESCRIPTION
				"Description."
			::= { priSelfDiagnosisEntry 1 }

		
--         1.3.6.1.4.1.37950.1.1.5.12.3.2.24.1.2
-- 1.3.6.1.4.1.37950.1.1.5.12.3.2.24.1.2
-- 1.3.6.1.4.1.37950.1.1.5.12.3.2.25.1.2
-- 1.3.6.1.4.1.37950.1.1.5.12.3.2.25.1.2
-- 1.3.6.1.4.1.37950.1.1.5.12.3.2.25.1.2
-- 1.3.6.1.4.1.37950.1.1.5.12.3.2.25.1.2
-- 1.3.6.1.4.1.37950.1.1.5.12.3.2.25.1.2
-- 1.3.6.1.4.1.37950.1.1.5.12.3.2.25.1.2
		-- 1.3.6.1.4.1.37950.1.1.5.12.3.2.25.1.2
		priSelfDiagOnu OBJECT-TYPE
			SYNTAX INTEGER (1..65535)
			MAX-ACCESS read-write
			STATUS current
			DESCRIPTION
				"Description."
			::= { priSelfDiagnosisEntry 2 }

		
--       1.3.6.1.4.1.37950.1.1.5.12.3.2.25.1.3
-- 1.3.6.1.4.1.37950.1.1.5.12.3.2.25.1.3
-- 1.3.6.1.4.1.37950.1.1.5.12.3.2.25.1.3
-- 1.3.6.1.4.1.37950.1.1.5.12.3.2.25.1.3
-- 1.3.6.1.4.1.37950.1.1.5.12.3.2.25.1.3
-- 1.3.6.1.4.1.37950.1.1.5.12.3.2.25.1.3
		-- 1.3.6.1.4.1.37950.1.1.5.12.3.2.25.1.3
		priSelfDiagSessionID OBJECT-TYPE
			SYNTAX Integer32 (1..255)
			MAX-ACCESS read-write
			STATUS current
			DESCRIPTION
				"Description."
			::= { priSelfDiagnosisEntry 3 }

		
--       1.3.6.1.4.1.37950.1.1.5.12.3.2.25.1.4
-- 1.3.6.1.4.1.37950.1.1.5.12.3.2.25.1.4
-- 1.3.6.1.4.1.37950.1.1.5.12.3.2.25.1.4
-- 1.3.6.1.4.1.37950.1.1.5.12.3.2.25.1.4
-- 1.3.6.1.4.1.37950.1.1.5.12.3.2.25.1.4
-- 1.3.6.1.4.1.37950.1.1.5.12.3.2.25.1.4
		-- 1.3.6.1.4.1.37950.1.1.5.12.3.2.25.1.4
		priSelfDiagTransportProtocol OBJECT-TYPE
			SYNTAX INTEGER
				{
				ftp(0),
				tftp(1)
				}
			MAX-ACCESS read-write
			STATUS current
			DESCRIPTION
				"Description."
			::= { priSelfDiagnosisEntry 4 }

		
--       1.3.6.1.4.1.37950.1.1.5.12.3.2.25.1.5
-- 1.3.6.1.4.1.37950.1.1.5.12.3.2.25.1.5
-- 1.3.6.1.4.1.37950.1.1.5.12.3.2.25.1.5
-- 1.3.6.1.4.1.37950.1.1.5.12.3.2.25.1.5
-- 1.3.6.1.4.1.37950.1.1.5.12.3.2.25.1.5
-- 1.3.6.1.4.1.37950.1.1.5.12.3.2.25.1.5
		-- 1.3.6.1.4.1.37950.1.1.5.12.3.2.25.1.5
		priSelfDiagDiagnosisMethod OBJECT-TYPE
			SYNTAX INTEGER
				{
				all(0),
				port-status(1),
				pon-status(2),
				wan-status(3),
				sys-status(4),
				wan-params(5),
				dns-status(6),
				dhcp-config(7),
				pppoe-status(8),
				route-status(9)
				}
			MAX-ACCESS read-write
			STATUS current
			DESCRIPTION
				"Description."
			::= { priSelfDiagnosisEntry 5 }

		
--       1.3.6.1.4.1.37950.1.1.5.12.3.2.25.1.6
-- 1.3.6.1.4.1.37950.1.1.5.12.3.2.25.1.6
-- 1.3.6.1.4.1.37950.1.1.5.12.3.2.25.1.6
-- 1.3.6.1.4.1.37950.1.1.5.12.3.2.25.1.6
-- 1.3.6.1.4.1.37950.1.1.5.12.3.2.25.1.6
-- 1.3.6.1.4.1.37950.1.1.5.12.3.2.25.1.6
		-- 1.3.6.1.4.1.37950.1.1.5.12.3.2.25.1.6
		priSelfDiagDiagnosisAction OBJECT-TYPE
			SYNTAX INTEGER
				{
				action-diag(0),
				action-fix(1)
				}
			MAX-ACCESS read-write
			STATUS current
			DESCRIPTION
				"Description."
			::= { priSelfDiagnosisEntry 6 }

		
--       1.3.6.1.4.1.37950.1.1.5.12.3.2.25.1.7
-- 1.3.6.1.4.1.37950.1.1.5.12.3.2.25.1.7
-- 1.3.6.1.4.1.37950.1.1.5.12.3.2.25.1.7
-- 1.3.6.1.4.1.37950.1.1.5.12.3.2.25.1.7
-- 1.3.6.1.4.1.37950.1.1.5.12.3.2.25.1.7
-- 1.3.6.1.4.1.37950.1.1.5.12.3.2.25.1.7
		-- 1.3.6.1.4.1.37950.1.1.5.12.3.2.25.1.7
		priSelfDiagAction OBJECT-TYPE
			SYNTAX INTEGER
				{
				perform-diagnostic(0),
				upload-log(1)
				}
			MAX-ACCESS read-write
			STATUS current
			DESCRIPTION
				"Description."
			::= { priSelfDiagnosisEntry 7 }

		
--       1.3.6.1.4.1.37950.1.1.5.12.3.2.25.1.8
-- 1.3.6.1.4.1.37950.1.1.5.12.3.2.25.1.8
-- 1.3.6.1.4.1.37950.1.1.5.12.3.2.25.1.8
-- 1.3.6.1.4.1.37950.1.1.5.12.3.2.25.1.8
-- 1.3.6.1.4.1.37950.1.1.5.12.3.2.25.1.8
-- 1.3.6.1.4.1.37950.1.1.5.12.3.2.25.1.8
		-- 1.3.6.1.4.1.37950.1.1.5.12.3.2.25.1.8
		priSelfDiagURL OBJECT-TYPE
			SYNTAX OCTET STRING
			MAX-ACCESS read-write
			STATUS current
			DESCRIPTION
				"Description."
			::= { priSelfDiagnosisEntry 8 }

		
--       1.3.6.1.4.1.37950.1.1.5.12.3.2.25.1.9
-- 1.3.6.1.4.1.37950.1.1.5.12.3.2.25.1.9
-- 1.3.6.1.4.1.37950.1.1.5.12.3.2.25.1.9
-- 1.3.6.1.4.1.37950.1.1.5.12.3.2.25.1.9
-- 1.3.6.1.4.1.37950.1.1.5.12.3.2.25.1.9
-- 1.3.6.1.4.1.37950.1.1.5.12.3.2.25.1.9
		-- 1.3.6.1.4.1.37950.1.1.5.12.3.2.25.1.9
		priSelfDiagUseWanIndex OBJECT-TYPE
			SYNTAX Integer32 (1..8)
			MAX-ACCESS read-write
			STATUS current
			DESCRIPTION
				"Description."
			::= { priSelfDiagnosisEntry 9 }

		
--       1.3.6.1.4.1.37950.1.1.5.12.3.2.25.1.10
-- 1.3.6.1.4.1.37950.1.1.5.12.3.2.25.1.10
-- 1.3.6.1.4.1.37950.1.1.5.12.3.2.25.1.10
-- 1.3.6.1.4.1.37950.1.1.5.12.3.2.25.1.10
-- 1.3.6.1.4.1.37950.1.1.5.12.3.2.25.1.10
-- 1.3.6.1.4.1.37950.1.1.5.12.3.2.25.1.10
		-- 1.3.6.1.4.1.37950.1.1.5.12.3.2.25.1.10
		priSelfDiagCurrentState OBJECT-TYPE
			SYNTAX INTEGER
				{
				no-diagnosis(0),
				under-diagnosis(1),
				completed-diagnosis(2),
				log-uploaded-ok(3),
				log-uploading(4),
				log-uploading-failed(5)
				}
			MAX-ACCESS read-write
			STATUS current
			DESCRIPTION
				"Description."
			::= { priSelfDiagnosisEntry 10 }

		
--       1.3.6.1.4.1.37950.1.1.5.12.3.2.25.1.11
-- 1.3.6.1.4.1.37950.1.1.5.12.3.2.25.1.11
-- 1.3.6.1.4.1.37950.1.1.5.12.3.2.25.1.11
-- 1.3.6.1.4.1.37950.1.1.5.12.3.2.25.1.11
-- 1.3.6.1.4.1.37950.1.1.5.12.3.2.25.1.11
-- 1.3.6.1.4.1.37950.1.1.5.12.3.2.25.1.11
		-- 1.3.6.1.4.1.37950.1.1.5.12.3.2.25.1.11
		priSelfDiagLogFilename OBJECT-TYPE
			SYNTAX OCTET STRING
			MAX-ACCESS read-write
			STATUS current
			DESCRIPTION
				"Description."
			::= { priSelfDiagnosisEntry 11 }

		
--       1.3.6.1.4.1.37950.1.1.5.12.3.2.26
-- 1.3.6.1.4.1.37950.1.1.5.12.3.2.26
-- 1.3.6.1.4.1.37950.1.1.5.12.3.2.26
-- 1.3.6.1.4.1.37950.1.1.5.12.3.2.26
-- 1.3.6.1.4.1.37950.1.1.5.12.3.2.26
-- 1.3.6.1.4.1.37950.1.1.5.12.3.2.26
		-- 1.3.6.1.4.1.37950.1.1.5.12.3.2.26
		priSelfDiagnosisCapturePackTable OBJECT-TYPE
			SYNTAX SEQUENCE OF PriSelfDiagnosisCapturePackEntry
			MAX-ACCESS not-accessible
			STATUS current
			DESCRIPTION
				"Description."
			::= { onuPriGlobalInfo 26 }

		
--       1.3.6.1.4.1.37950.1.1.5.12.3.2.26.1
-- 1.3.6.1.4.1.37950.1.1.5.12.3.2.26.1
-- 1.3.6.1.4.1.37950.1.1.5.12.3.2.26.1
-- 1.3.6.1.4.1.37950.1.1.5.12.3.2.26.1
-- 1.3.6.1.4.1.37950.1.1.5.12.3.2.26.1
-- 1.3.6.1.4.1.37950.1.1.5.12.3.2.26.1
		-- 1.3.6.1.4.1.37950.1.1.5.12.3.2.26.1
		priSelfDiagnosisCapturePackEntry OBJECT-TYPE
			SYNTAX PriSelfDiagnosisCapturePackEntry
			MAX-ACCESS not-accessible
			STATUS current
			DESCRIPTION
				"Description."
			INDEX { priSelfDiagCapturePackPon, priSelfDiagCapturePackOnu }
			::= { priSelfDiagnosisCapturePackTable 1 }

		
		PriSelfDiagnosisCapturePackEntry ::=
			SEQUENCE { 
				priSelfDiagCapturePackPon
					INTEGER,
				priSelfDiagCapturePackOnu
					INTEGER,
				priSelfDiagCapturePackSessionID
					Integer32,
				priSelfDiagCapturePackTransportProtocol
					INTEGER,
				priSelfDiagCapturePackCaptureMode
					INTEGER,
				priSelfDiagCapturePackCaptureInterface
					INTEGER,
				priSelfDiagCapturePackAction
					INTEGER,
				priSelfDiagCapturePackURL
					OCTET STRING,
				priSelfDiagCapturePackUseWanIndex
					Integer32,
				priSelfDiagCapturePackCurrentState
					INTEGER,
				priSelfDiagCapturePackCaptureFilename
					OCTET STRING
			 }

--         1.3.6.1.4.1.37950.1.1.5.12.3.2.24.1.1
-- 1.3.6.1.4.1.37950.1.1.5.12.3.2.24.1.1
-- 1.3.6.1.4.1.37950.1.1.5.12.3.2.26.1.1
-- 1.3.6.1.4.1.37950.1.1.5.12.3.2.26.1.1
-- 1.3.6.1.4.1.37950.1.1.5.12.3.2.26.1.1
-- 1.3.6.1.4.1.37950.1.1.5.12.3.2.26.1.1
-- 1.3.6.1.4.1.37950.1.1.5.12.3.2.26.1.1
-- 1.3.6.1.4.1.37950.1.1.5.12.3.2.26.1.1
		-- 1.3.6.1.4.1.37950.1.1.5.12.3.2.26.1.1
		priSelfDiagCapturePackPon OBJECT-TYPE
			SYNTAX INTEGER (1..16)
			MAX-ACCESS read-write
			STATUS current
			DESCRIPTION
				"Description."
			::= { priSelfDiagnosisCapturePackEntry 1 }

		
--         1.3.6.1.4.1.37950.1.1.5.12.3.2.24.1.2
-- 1.3.6.1.4.1.37950.1.1.5.12.3.2.24.1.2
-- 1.3.6.1.4.1.37950.1.1.5.12.3.2.26.1.2
-- 1.3.6.1.4.1.37950.1.1.5.12.3.2.26.1.2
-- 1.3.6.1.4.1.37950.1.1.5.12.3.2.26.1.2
-- 1.3.6.1.4.1.37950.1.1.5.12.3.2.26.1.2
-- 1.3.6.1.4.1.37950.1.1.5.12.3.2.26.1.2
-- 1.3.6.1.4.1.37950.1.1.5.12.3.2.26.1.2
		-- 1.3.6.1.4.1.37950.1.1.5.12.3.2.26.1.2
		priSelfDiagCapturePackOnu OBJECT-TYPE
			SYNTAX INTEGER (1..65535)
			MAX-ACCESS read-write
			STATUS current
			DESCRIPTION
				"Description."
			::= { priSelfDiagnosisCapturePackEntry 2 }

		
--       1.3.6.1.4.1.37950.1.1.5.12.3.2.26.1.3
-- 1.3.6.1.4.1.37950.1.1.5.12.3.2.26.1.3
-- 1.3.6.1.4.1.37950.1.1.5.12.3.2.26.1.3
-- 1.3.6.1.4.1.37950.1.1.5.12.3.2.26.1.3
-- 1.3.6.1.4.1.37950.1.1.5.12.3.2.26.1.3
-- 1.3.6.1.4.1.37950.1.1.5.12.3.2.26.1.3
		-- 1.3.6.1.4.1.37950.1.1.5.12.3.2.26.1.3
		priSelfDiagCapturePackSessionID OBJECT-TYPE
			SYNTAX Integer32 (1..255)
			MAX-ACCESS read-write
			STATUS current
			DESCRIPTION
				"Description."
			::= { priSelfDiagnosisCapturePackEntry 3 }

		
--       1.3.6.1.4.1.37950.1.1.5.12.3.2.26.1.4
-- 1.3.6.1.4.1.37950.1.1.5.12.3.2.26.1.4
-- 1.3.6.1.4.1.37950.1.1.5.12.3.2.26.1.4
-- 1.3.6.1.4.1.37950.1.1.5.12.3.2.26.1.4
-- 1.3.6.1.4.1.37950.1.1.5.12.3.2.26.1.4
-- 1.3.6.1.4.1.37950.1.1.5.12.3.2.26.1.4
		-- 1.3.6.1.4.1.37950.1.1.5.12.3.2.26.1.4
		priSelfDiagCapturePackTransportProtocol OBJECT-TYPE
			SYNTAX INTEGER
				{
				ftp(0),
				tftp(1)
				}
			MAX-ACCESS read-write
			STATUS current
			DESCRIPTION
				"Description."
			::= { priSelfDiagnosisCapturePackEntry 4 }

		
--       1.3.6.1.4.1.37950.1.1.5.12.3.2.26.1.5
-- 1.3.6.1.4.1.37950.1.1.5.12.3.2.26.1.5
-- 1.3.6.1.4.1.37950.1.1.5.12.3.2.26.1.5
-- 1.3.6.1.4.1.37950.1.1.5.12.3.2.26.1.5
-- 1.3.6.1.4.1.37950.1.1.5.12.3.2.26.1.5
-- 1.3.6.1.4.1.37950.1.1.5.12.3.2.26.1.5
		-- 1.3.6.1.4.1.37950.1.1.5.12.3.2.26.1.5
		priSelfDiagCapturePackCaptureMode OBJECT-TYPE
			SYNTAX INTEGER
				{
				counting(0),
				circulation(1)
				}
			MAX-ACCESS read-write
			STATUS current
			DESCRIPTION
				"Description."
			::= { priSelfDiagnosisCapturePackEntry 5 }

		
--       1.3.6.1.4.1.37950.1.1.5.12.3.2.26.1.6
-- 1.3.6.1.4.1.37950.1.1.5.12.3.2.26.1.6
-- 1.3.6.1.4.1.37950.1.1.5.12.3.2.26.1.6
-- 1.3.6.1.4.1.37950.1.1.5.12.3.2.26.1.6
-- 1.3.6.1.4.1.37950.1.1.5.12.3.2.26.1.6
-- 1.3.6.1.4.1.37950.1.1.5.12.3.2.26.1.6
		-- 1.3.6.1.4.1.37950.1.1.5.12.3.2.26.1.6
		priSelfDiagCapturePackCaptureInterface OBJECT-TYPE
			SYNTAX INTEGER
				{
				any(0),
				wan-of-index-1(1),
				wan-of-index-2(2),
				wan-of-index-3(3),
				wan-of-index-4(4),
				wan-of-index-5(5),
				wan-of-index-6(6),
				wan-of-index-7(7),
				wan-of-index-8(8)
				}
			MAX-ACCESS read-write
			STATUS current
			DESCRIPTION
				"Description."
			::= { priSelfDiagnosisCapturePackEntry 6 }

		
--       1.3.6.1.4.1.37950.1.1.5.12.3.2.26.1.7
-- 1.3.6.1.4.1.37950.1.1.5.12.3.2.26.1.7
-- 1.3.6.1.4.1.37950.1.1.5.12.3.2.26.1.7
-- 1.3.6.1.4.1.37950.1.1.5.12.3.2.26.1.7
-- 1.3.6.1.4.1.37950.1.1.5.12.3.2.26.1.7
-- 1.3.6.1.4.1.37950.1.1.5.12.3.2.26.1.7
		-- 1.3.6.1.4.1.37950.1.1.5.12.3.2.26.1.7
		priSelfDiagCapturePackAction OBJECT-TYPE
			SYNTAX INTEGER
				{
				stop-capturing(0),
				start-capturing(1),
				upload-log(2)
				}
			MAX-ACCESS read-write
			STATUS current
			DESCRIPTION
				"Description."
			::= { priSelfDiagnosisCapturePackEntry 7 }

		
--       1.3.6.1.4.1.37950.1.1.5.12.3.2.26.1.8
-- 1.3.6.1.4.1.37950.1.1.5.12.3.2.26.1.8
-- 1.3.6.1.4.1.37950.1.1.5.12.3.2.26.1.8
-- 1.3.6.1.4.1.37950.1.1.5.12.3.2.26.1.8
-- 1.3.6.1.4.1.37950.1.1.5.12.3.2.26.1.8
-- 1.3.6.1.4.1.37950.1.1.5.12.3.2.26.1.8
		-- 1.3.6.1.4.1.37950.1.1.5.12.3.2.26.1.8
		priSelfDiagCapturePackURL OBJECT-TYPE
			SYNTAX OCTET STRING
			MAX-ACCESS read-write
			STATUS current
			DESCRIPTION
				"Description."
			::= { priSelfDiagnosisCapturePackEntry 8 }

		
--       1.3.6.1.4.1.37950.1.1.5.12.3.2.26.1.9
-- 1.3.6.1.4.1.37950.1.1.5.12.3.2.26.1.9
-- 1.3.6.1.4.1.37950.1.1.5.12.3.2.26.1.9
-- 1.3.6.1.4.1.37950.1.1.5.12.3.2.26.1.9
-- 1.3.6.1.4.1.37950.1.1.5.12.3.2.26.1.9
-- 1.3.6.1.4.1.37950.1.1.5.12.3.2.26.1.9
		-- 1.3.6.1.4.1.37950.1.1.5.12.3.2.26.1.9
		priSelfDiagCapturePackUseWanIndex OBJECT-TYPE
			SYNTAX Integer32 (1..8)
			MAX-ACCESS read-write
			STATUS current
			DESCRIPTION
				"Description."
			::= { priSelfDiagnosisCapturePackEntry 9 }

		
--       1.3.6.1.4.1.37950.1.1.5.12.3.2.26.1.10
-- 1.3.6.1.4.1.37950.1.1.5.12.3.2.26.1.10
-- 1.3.6.1.4.1.37950.1.1.5.12.3.2.26.1.10
-- 1.3.6.1.4.1.37950.1.1.5.12.3.2.26.1.10
-- 1.3.6.1.4.1.37950.1.1.5.12.3.2.26.1.10
-- 1.3.6.1.4.1.37950.1.1.5.12.3.2.26.1.10
		-- 1.3.6.1.4.1.37950.1.1.5.12.3.2.26.1.10
		priSelfDiagCapturePackCurrentState OBJECT-TYPE
			SYNTAX INTEGER
				{
				idle(0),
				catching(1),
				completed-capture(2),
				uploaded-ok(3),
				is-uploading(4),
				uploaded-failed(5)
				}
			MAX-ACCESS read-write
			STATUS current
			DESCRIPTION
				"Description."
			::= { priSelfDiagnosisCapturePackEntry 10 }

		
--       1.3.6.1.4.1.37950.1.1.5.12.3.2.26.1.11
-- 1.3.6.1.4.1.37950.1.1.5.12.3.2.26.1.11
-- 1.3.6.1.4.1.37950.1.1.5.12.3.2.26.1.11
-- 1.3.6.1.4.1.37950.1.1.5.12.3.2.26.1.11
-- 1.3.6.1.4.1.37950.1.1.5.12.3.2.26.1.11
-- 1.3.6.1.4.1.37950.1.1.5.12.3.2.26.1.11
		-- 1.3.6.1.4.1.37950.1.1.5.12.3.2.26.1.11
		priSelfDiagCapturePackCaptureFilename OBJECT-TYPE
			SYNTAX OCTET STRING
			MAX-ACCESS read-write
			STATUS current
			DESCRIPTION
				"Description."
			::= { priSelfDiagnosisCapturePackEntry 11 }

		
--         1.3.6.1.4.1.37950.1.1.5.12.3.2.7
-- 1.3.6.1.4.1.37950.1.1.5.12.3.2.7
-- 1.3.6.1.4.1.37950.1.1.5.12.3.2.27
-- 1.3.6.1.4.1.37950.1.1.5.12.3.2.27
-- 1.3.6.1.4.1.37950.1.1.5.12.3.2.27
-- 1.3.6.1.4.1.37950.1.1.5.12.3.2.27
-- 1.3.6.1.4.1.37950.1.1.5.12.3.2.27
-- 1.3.6.1.4.1.37950.1.1.5.12.3.2.27
		-- 1.3.6.1.4.1.37950.1.1.5.12.3.2.27
		priNatTypeTable OBJECT-TYPE
			SYNTAX SEQUENCE OF PriNatTypeEntry
			MAX-ACCESS not-accessible
			STATUS current
			DESCRIPTION
				"Description."
			::= { onuPriGlobalInfo 27 }

		
--          1.3.6.1.4.1.37950.1.1.5.12.3.2.7.1
-- 1.3.6.1.4.1.37950.1.1.5.12.3.2.7.1
-- 1.3.6.1.4.1.37950.1.1.5.12.3.2.7.1
-- 1.3.6.1.4.1.37950.1.1.5.12.3.2.27.1
-- 1.3.6.1.4.1.37950.1.1.5.12.3.2.27.1
-- 1.3.6.1.4.1.37950.1.1.5.12.3.2.27.1
-- 1.3.6.1.4.1.37950.1.1.5.12.3.2.27.1
-- 1.3.6.1.4.1.37950.1.1.5.12.3.2.27.1
-- 1.3.6.1.4.1.37950.1.1.5.12.3.2.27.1
		-- 1.3.6.1.4.1.37950.1.1.5.12.3.2.27.1
		priNatTypeEntry OBJECT-TYPE
			SYNTAX PriNatTypeEntry
			MAX-ACCESS not-accessible
			STATUS current
			DESCRIPTION
				"Description."
			INDEX { priNatTypePonIDS, priNatTypeOnuIDS }
			::= { priNatTypeTable 1 }

		
		PriNatTypeEntry ::=
			SEQUENCE { 
				priNatTypePonIDS
					INTEGER,
				priNatTypeOnuIDS
					INTEGER,
				priNatTypeS
					INTEGER
			 }

--          1.3.6.1.4.1.37950.1.1.5.12.3.2.7.1.1
-- 1.3.6.1.4.1.37950.1.1.5.12.3.2.7.1.1
-- 1.3.6.1.4.1.37950.1.1.5.12.3.2.7.1.1
-- 1.3.6.1.4.1.37950.1.1.5.12.3.2.27.1.1
-- 1.3.6.1.4.1.37950.1.1.5.12.3.2.27.1.1
-- 1.3.6.1.4.1.37950.1.1.5.12.3.2.27.1.1
-- 1.3.6.1.4.1.37950.1.1.5.12.3.2.27.1.1
-- 1.3.6.1.4.1.37950.1.1.5.12.3.2.27.1.1
-- 1.3.6.1.4.1.37950.1.1.5.12.3.2.27.1.1
		-- 1.3.6.1.4.1.37950.1.1.5.12.3.2.27.1.1
		priNatTypePonIDS OBJECT-TYPE
			SYNTAX INTEGER (1..16)
			MAX-ACCESS read-write
			STATUS current
			DESCRIPTION
				"Description."
			::= { priNatTypeEntry 1 }

		
--          1.3.6.1.4.1.37950.1.1.5.12.3.2.7.1.2
-- 1.3.6.1.4.1.37950.1.1.5.12.3.2.7.1.2
-- 1.3.6.1.4.1.37950.1.1.5.12.3.2.7.1.2
-- 1.3.6.1.4.1.37950.1.1.5.12.3.2.27.1.2
-- 1.3.6.1.4.1.37950.1.1.5.12.3.2.27.1.2
-- 1.3.6.1.4.1.37950.1.1.5.12.3.2.27.1.2
-- 1.3.6.1.4.1.37950.1.1.5.12.3.2.27.1.2
-- 1.3.6.1.4.1.37950.1.1.5.12.3.2.27.1.2
-- 1.3.6.1.4.1.37950.1.1.5.12.3.2.27.1.2
		-- 1.3.6.1.4.1.37950.1.1.5.12.3.2.27.1.2
		priNatTypeOnuIDS OBJECT-TYPE
			SYNTAX INTEGER (1..65535)
			MAX-ACCESS read-write
			STATUS current
			DESCRIPTION
				"Description."
			::= { priNatTypeEntry 2 }

		
--          1.3.6.1.4.1.37950.1.1.5.12.3.2.7.1.3
-- 1.3.6.1.4.1.37950.1.1.5.12.3.2.7.1.3
-- 1.3.6.1.4.1.37950.1.1.5.12.3.2.7.1.3
-- 1.3.6.1.4.1.37950.1.1.5.12.3.2.27.1.3
-- 1.3.6.1.4.1.37950.1.1.5.12.3.2.27.1.3
-- 1.3.6.1.4.1.37950.1.1.5.12.3.2.27.1.3
-- 1.3.6.1.4.1.37950.1.1.5.12.3.2.27.1.3
-- 1.3.6.1.4.1.37950.1.1.5.12.3.2.27.1.3
-- 1.3.6.1.4.1.37950.1.1.5.12.3.2.27.1.3
		-- 1.3.6.1.4.1.37950.1.1.5.12.3.2.27.1.3
		priNatTypeS OBJECT-TYPE
			SYNTAX INTEGER
				{
				nat1(1),
				nat2(2),
				nat3(3),
				nat4-napt(4)
				}
			MAX-ACCESS read-write
			STATUS current
			DESCRIPTION
				"Description."
			::= { priNatTypeEntry 3 }

		
--         1.3.6.1.4.1.37950.1.1.5.12.3.2.7
-- 1.3.6.1.4.1.37950.1.1.5.12.3.2.7
-- 1.3.6.1.4.1.37950.1.1.5.12.3.2.28
-- 1.3.6.1.4.1.37950.1.1.5.12.3.2.28
-- 1.3.6.1.4.1.37950.1.1.5.12.3.2.28
-- 1.3.6.1.4.1.37950.1.1.5.12.3.2.28
-- 1.3.6.1.4.1.37950.1.1.5.12.3.2.28
-- 1.3.6.1.4.1.37950.1.1.5.12.3.2.28
		-- 1.3.6.1.4.1.37950.1.1.5.12.3.2.28
		priUPnPTable OBJECT-TYPE
			SYNTAX SEQUENCE OF PriUPnPEntry
			MAX-ACCESS not-accessible
			STATUS current
			DESCRIPTION
				"Description."
			::= { onuPriGlobalInfo 28 }

		
--          1.3.6.1.4.1.37950.1.1.5.12.3.2.7.1
-- 1.3.6.1.4.1.37950.1.1.5.12.3.2.7.1
-- 1.3.6.1.4.1.37950.1.1.5.12.3.2.7.1
-- 1.3.6.1.4.1.37950.1.1.5.12.3.2.28.1
-- 1.3.6.1.4.1.37950.1.1.5.12.3.2.28.1
-- 1.3.6.1.4.1.37950.1.1.5.12.3.2.28.1
-- 1.3.6.1.4.1.37950.1.1.5.12.3.2.28.1
-- 1.3.6.1.4.1.37950.1.1.5.12.3.2.28.1
-- 1.3.6.1.4.1.37950.1.1.5.12.3.2.28.1
		-- 1.3.6.1.4.1.37950.1.1.5.12.3.2.28.1
		priUPnPEntry OBJECT-TYPE
			SYNTAX PriUPnPEntry
			MAX-ACCESS not-accessible
			STATUS current
			DESCRIPTION
				"Description."
			INDEX { priUpnpPonIDS, priUpnpOnuIDS }
			::= { priUPnPTable 1 }

		
		PriUPnPEntry ::=
			SEQUENCE { 
				priUpnpPonIDS
					INTEGER,
				priUpnpOnuIDS
					INTEGER,
				priUpnpStatusS
					INTEGER,
				priUpnpWanIndexS
					Integer32
			 }

--          1.3.6.1.4.1.37950.1.1.5.12.3.2.7.1.1
-- 1.3.6.1.4.1.37950.1.1.5.12.3.2.7.1.1
-- 1.3.6.1.4.1.37950.1.1.5.12.3.2.7.1.1
-- 1.3.6.1.4.1.37950.1.1.5.12.3.2.28.1.1
-- 1.3.6.1.4.1.37950.1.1.5.12.3.2.28.1.1
-- 1.3.6.1.4.1.37950.1.1.5.12.3.2.28.1.1
-- 1.3.6.1.4.1.37950.1.1.5.12.3.2.28.1.1
-- 1.3.6.1.4.1.37950.1.1.5.12.3.2.28.1.1
-- 1.3.6.1.4.1.37950.1.1.5.12.3.2.28.1.1
		-- 1.3.6.1.4.1.37950.1.1.5.12.3.2.28.1.1
		priUpnpPonIDS OBJECT-TYPE
			SYNTAX INTEGER (1..16)
			MAX-ACCESS read-write
			STATUS current
			DESCRIPTION
				"Description."
			::= { priUPnPEntry 1 }

		
--          1.3.6.1.4.1.37950.1.1.5.12.3.2.7.1.2
-- 1.3.6.1.4.1.37950.1.1.5.12.3.2.7.1.2
-- 1.3.6.1.4.1.37950.1.1.5.12.3.2.7.1.2
-- 1.3.6.1.4.1.37950.1.1.5.12.3.2.28.1.2
-- 1.3.6.1.4.1.37950.1.1.5.12.3.2.28.1.2
-- 1.3.6.1.4.1.37950.1.1.5.12.3.2.28.1.2
-- 1.3.6.1.4.1.37950.1.1.5.12.3.2.28.1.2
-- 1.3.6.1.4.1.37950.1.1.5.12.3.2.28.1.2
-- 1.3.6.1.4.1.37950.1.1.5.12.3.2.28.1.2
		-- 1.3.6.1.4.1.37950.1.1.5.12.3.2.28.1.2
		priUpnpOnuIDS OBJECT-TYPE
			SYNTAX INTEGER (1..65535)
			MAX-ACCESS read-write
			STATUS current
			DESCRIPTION
				"Description."
			::= { priUPnPEntry 2 }

		
--          1.3.6.1.4.1.37950.1.1.5.12.3.2.7.1.3
-- 1.3.6.1.4.1.37950.1.1.5.12.3.2.7.1.3
-- 1.3.6.1.4.1.37950.1.1.5.12.3.2.7.1.3
-- 1.3.6.1.4.1.37950.1.1.5.12.3.2.28.1.3
-- 1.3.6.1.4.1.37950.1.1.5.12.3.2.28.1.3
-- 1.3.6.1.4.1.37950.1.1.5.12.3.2.28.1.3
-- 1.3.6.1.4.1.37950.1.1.5.12.3.2.28.1.3
-- 1.3.6.1.4.1.37950.1.1.5.12.3.2.28.1.3
-- 1.3.6.1.4.1.37950.1.1.5.12.3.2.28.1.3
		-- 1.3.6.1.4.1.37950.1.1.5.12.3.2.28.1.3
		priUpnpStatusS OBJECT-TYPE
			SYNTAX INTEGER
				{
				disable(0),
				enable(1)
				}
			MAX-ACCESS read-write
			STATUS current
			DESCRIPTION
				"Description."
			::= { priUPnPEntry 3 }

		
--       1.3.6.1.4.1.37950.1.1.5.12.3.2.28.1.4
-- 1.3.6.1.4.1.37950.1.1.5.12.3.2.28.1.4
-- 1.3.6.1.4.1.37950.1.1.5.12.3.2.28.1.4
-- 1.3.6.1.4.1.37950.1.1.5.12.3.2.28.1.4
-- 1.3.6.1.4.1.37950.1.1.5.12.3.2.28.1.4
-- 1.3.6.1.4.1.37950.1.1.5.12.3.2.28.1.4
		-- 1.3.6.1.4.1.37950.1.1.5.12.3.2.28.1.4
		priUpnpWanIndexS OBJECT-TYPE
			SYNTAX Integer32 (1..8)
			MAX-ACCESS read-write
			STATUS current
			DESCRIPTION
				"Description."
			::= { priUPnPEntry 4 }

		
--           1.3.6.1.4.1.37950.1.1.5.12.4
-- 1.3.6.1.4.1.37950.1.1.5.12.4
-- 1.3.6.1.4.1.37950.1.1.5.12.4
-- 1.3.6.1.4.1.37950.1.1.5.12.4
-- 1.3.6.1.4.1.37950.1.1.5.12.4
-- 1.3.6.1.4.1.37950.1.1.5.12.4
-- 1.3.6.1.4.1.37950.1.1.5.12.4
-- 1.3.6.1.4.1.37950.1.1.5.12.4
-- 1.3.6.1.4.1.37950.1.1.5.12.4
		-- 1.3.6.1.4.1.37950.1.1.5.12.4
		onuPriPort OBJECT IDENTIFIER ::= { v1600dOnuMgmt 4 }

		
--           1.3.6.1.4.1.37950.1.1.5.12.4.1
-- 1.3.6.1.4.1.37950.1.1.5.12.4.1
-- 1.3.6.1.4.1.37950.1.1.5.12.4.1
-- 1.3.6.1.4.1.37950.1.1.5.12.4.1
-- 1.3.6.1.4.1.37950.1.1.5.12.4.1
-- 1.3.6.1.4.1.37950.1.1.5.12.4.1
-- 1.3.6.1.4.1.37950.1.1.5.12.4.1
-- 1.3.6.1.4.1.37950.1.1.5.12.4.1
-- 1.3.6.1.4.1.37950.1.1.5.12.4.1
		-- 1.3.6.1.4.1.37950.1.1.5.12.4.1
		onuPriPortCfg OBJECT IDENTIFIER ::= { onuPriPort 1 }

		
--           1.3.6.1.4.1.37950.1.1.5.12.4.1.1
-- 1.3.6.1.4.1.37950.1.1.5.12.4.1.1
-- 1.3.6.1.4.1.37950.1.1.5.12.4.1.1
-- 1.3.6.1.4.1.37950.1.1.5.12.4.1.1
-- 1.3.6.1.4.1.37950.1.1.5.12.4.1.1
-- 1.3.6.1.4.1.37950.1.1.5.12.4.1.1
-- 1.3.6.1.4.1.37950.1.1.5.12.4.1.1
-- 1.3.6.1.4.1.37950.1.1.5.12.4.1.1
-- 1.3.6.1.4.1.37950.1.1.5.12.4.1.1
		-- 1.3.6.1.4.1.37950.1.1.5.12.4.1.1
		onuPriPortMacLimit OBJECT IDENTIFIER ::= { onuPriPortCfg 1 }

		
--           1.3.6.1.4.1.37950.1.1.5.12.4.1.1.1
-- 1.3.6.1.4.1.37950.1.1.5.12.4.1.1.1
-- 1.3.6.1.4.1.37950.1.1.5.12.4.1.1.1
-- 1.3.6.1.4.1.37950.1.1.5.12.4.1.1.1
-- 1.3.6.1.4.1.37950.1.1.5.12.4.1.1.1
-- 1.3.6.1.4.1.37950.1.1.5.12.4.1.1.1
-- 1.3.6.1.4.1.37950.1.1.5.12.4.1.1.1
-- 1.3.6.1.4.1.37950.1.1.5.12.4.1.1.1
-- 1.3.6.1.4.1.37950.1.1.5.12.4.1.1.1
		-- 1.3.6.1.4.1.37950.1.1.5.12.4.1.1.1
		priMacLimitPon OBJECT-TYPE
			SYNTAX INTEGER (1..16)
			MAX-ACCESS read-write
			STATUS current
			DESCRIPTION
				"Description."
			::= { onuPriPortMacLimit 1 }

		
--           1.3.6.1.4.1.37950.1.1.5.12.4.1.1.2
-- 1.3.6.1.4.1.37950.1.1.5.12.4.1.1.2
-- 1.3.6.1.4.1.37950.1.1.5.12.4.1.1.2
-- 1.3.6.1.4.1.37950.1.1.5.12.4.1.1.2
-- 1.3.6.1.4.1.37950.1.1.5.12.4.1.1.2
-- 1.3.6.1.4.1.37950.1.1.5.12.4.1.1.2
-- 1.3.6.1.4.1.37950.1.1.5.12.4.1.1.2
-- 1.3.6.1.4.1.37950.1.1.5.12.4.1.1.2
-- 1.3.6.1.4.1.37950.1.1.5.12.4.1.1.2
		-- 1.3.6.1.4.1.37950.1.1.5.12.4.1.1.2
		priMacLimitOnu OBJECT-TYPE
			SYNTAX INTEGER (1..65535)
			MAX-ACCESS read-write
			STATUS current
			DESCRIPTION
				"Description."
			::= { onuPriPortMacLimit 2 }

		
--           1.3.6.1.4.1.37950.1.1.5.12.4.1.1.3
-- 1.3.6.1.4.1.37950.1.1.5.12.4.1.1.3
-- 1.3.6.1.4.1.37950.1.1.5.12.4.1.1.3
-- 1.3.6.1.4.1.37950.1.1.5.12.4.1.1.3
-- 1.3.6.1.4.1.37950.1.1.5.12.4.1.1.3
-- 1.3.6.1.4.1.37950.1.1.5.12.4.1.1.3
-- 1.3.6.1.4.1.37950.1.1.5.12.4.1.1.3
-- 1.3.6.1.4.1.37950.1.1.5.12.4.1.1.3
-- 1.3.6.1.4.1.37950.1.1.5.12.4.1.1.3
		-- 1.3.6.1.4.1.37950.1.1.5.12.4.1.1.3
		priMacLimitEthNo OBJECT-TYPE
			SYNTAX INTEGER (1..255)
			MAX-ACCESS read-write
			STATUS current
			DESCRIPTION
				"Description."
			::= { onuPriPortMacLimit 3 }

		
--           1.3.6.1.4.1.37950.1.1.5.12.4.1.1.4
-- 1.3.6.1.4.1.37950.1.1.5.12.4.1.1.4
-- 1.3.6.1.4.1.37950.1.1.5.12.4.1.1.4
-- 1.3.6.1.4.1.37950.1.1.5.12.4.1.1.4
-- 1.3.6.1.4.1.37950.1.1.5.12.4.1.1.4
-- 1.3.6.1.4.1.37950.1.1.5.12.4.1.1.4
-- 1.3.6.1.4.1.37950.1.1.5.12.4.1.1.4
-- 1.3.6.1.4.1.37950.1.1.5.12.4.1.1.4
-- 1.3.6.1.4.1.37950.1.1.5.12.4.1.1.4
		-- 1.3.6.1.4.1.37950.1.1.5.12.4.1.1.4
		priMacLimit OBJECT-TYPE
			SYNTAX INTEGER (0..65535)
			MAX-ACCESS read-write
			STATUS current
			DESCRIPTION
				"Description."
			::= { onuPriPortMacLimit 4 }

		
--           1.3.6.1.4.1.37950.1.1.5.12.4.1.1.5
-- 1.3.6.1.4.1.37950.1.1.5.12.4.1.1.5
-- 1.3.6.1.4.1.37950.1.1.5.12.4.1.1.5
-- 1.3.6.1.4.1.37950.1.1.5.12.4.1.1.5
-- 1.3.6.1.4.1.37950.1.1.5.12.4.1.1.5
-- 1.3.6.1.4.1.37950.1.1.5.12.4.1.1.5
-- 1.3.6.1.4.1.37950.1.1.5.12.4.1.1.5
-- 1.3.6.1.4.1.37950.1.1.5.12.4.1.1.5
-- 1.3.6.1.4.1.37950.1.1.5.12.4.1.1.5
		-- 1.3.6.1.4.1.37950.1.1.5.12.4.1.1.5
		priMacLimitAction OBJECT-TYPE
			SYNTAX INTEGER
				{
				add(1),
				remove(2)
				}
			MAX-ACCESS read-write
			STATUS current
			DESCRIPTION
				"Description."
			::= { onuPriPortMacLimit 5 }

		
--           1.3.6.1.4.1.37950.1.1.5.12.4.1.2
-- 1.3.6.1.4.1.37950.1.1.5.12.4.1.2
-- 1.3.6.1.4.1.37950.1.1.5.12.4.1.2
-- 1.3.6.1.4.1.37950.1.1.5.12.4.1.2
-- 1.3.6.1.4.1.37950.1.1.5.12.4.1.2
-- 1.3.6.1.4.1.37950.1.1.5.12.4.1.2
-- 1.3.6.1.4.1.37950.1.1.5.12.4.1.2
-- 1.3.6.1.4.1.37950.1.1.5.12.4.1.2
-- 1.3.6.1.4.1.37950.1.1.5.12.4.1.2
		-- 1.3.6.1.4.1.37950.1.1.5.12.4.1.2
		onuPriPortPkgSuppress OBJECT IDENTIFIER ::= { onuPriPortCfg 2 }

		
--           1.3.6.1.4.1.37950.1.1.5.12.4.1.2.1
-- 1.3.6.1.4.1.37950.1.1.5.12.4.1.2.1
-- 1.3.6.1.4.1.37950.1.1.5.12.4.1.2.1
-- 1.3.6.1.4.1.37950.1.1.5.12.4.1.2.1
-- 1.3.6.1.4.1.37950.1.1.5.12.4.1.2.1
-- 1.3.6.1.4.1.37950.1.1.5.12.4.1.2.1
-- 1.3.6.1.4.1.37950.1.1.5.12.4.1.2.1
-- 1.3.6.1.4.1.37950.1.1.5.12.4.1.2.1
-- 1.3.6.1.4.1.37950.1.1.5.12.4.1.2.1
		-- 1.3.6.1.4.1.37950.1.1.5.12.4.1.2.1
		priPkgSuppressPon OBJECT-TYPE
			SYNTAX INTEGER (1..16)
			MAX-ACCESS read-write
			STATUS current
			DESCRIPTION
				"Description."
			::= { onuPriPortPkgSuppress 1 }

		
--           1.3.6.1.4.1.37950.1.1.5.12.4.1.2.2
-- 1.3.6.1.4.1.37950.1.1.5.12.4.1.2.2
-- 1.3.6.1.4.1.37950.1.1.5.12.4.1.2.2
-- 1.3.6.1.4.1.37950.1.1.5.12.4.1.2.2
-- 1.3.6.1.4.1.37950.1.1.5.12.4.1.2.2
-- 1.3.6.1.4.1.37950.1.1.5.12.4.1.2.2
-- 1.3.6.1.4.1.37950.1.1.5.12.4.1.2.2
-- 1.3.6.1.4.1.37950.1.1.5.12.4.1.2.2
-- 1.3.6.1.4.1.37950.1.1.5.12.4.1.2.2
		-- 1.3.6.1.4.1.37950.1.1.5.12.4.1.2.2
		priPkgSuppressOnu OBJECT-TYPE
			SYNTAX INTEGER (1..65535)
			MAX-ACCESS read-write
			STATUS current
			DESCRIPTION
				"Description."
			::= { onuPriPortPkgSuppress 2 }

		
--           1.3.6.1.4.1.37950.1.1.5.12.4.1.2.3
-- 1.3.6.1.4.1.37950.1.1.5.12.4.1.2.3
-- 1.3.6.1.4.1.37950.1.1.5.12.4.1.2.3
-- 1.3.6.1.4.1.37950.1.1.5.12.4.1.2.3
-- 1.3.6.1.4.1.37950.1.1.5.12.4.1.2.3
-- 1.3.6.1.4.1.37950.1.1.5.12.4.1.2.3
-- 1.3.6.1.4.1.37950.1.1.5.12.4.1.2.3
-- 1.3.6.1.4.1.37950.1.1.5.12.4.1.2.3
-- 1.3.6.1.4.1.37950.1.1.5.12.4.1.2.3
		-- 1.3.6.1.4.1.37950.1.1.5.12.4.1.2.3
		priPkgSuppressEthNo OBJECT-TYPE
			SYNTAX INTEGER (1..255)
			MAX-ACCESS read-write
			STATUS current
			DESCRIPTION
				"Description."
			::= { onuPriPortPkgSuppress 3 }

		
--           1.3.6.1.4.1.37950.1.1.5.12.4.1.2.4
-- 1.3.6.1.4.1.37950.1.1.5.12.4.1.2.4
-- 1.3.6.1.4.1.37950.1.1.5.12.4.1.2.4
-- 1.3.6.1.4.1.37950.1.1.5.12.4.1.2.4
-- 1.3.6.1.4.1.37950.1.1.5.12.4.1.2.4
-- 1.3.6.1.4.1.37950.1.1.5.12.4.1.2.4
-- 1.3.6.1.4.1.37950.1.1.5.12.4.1.2.4
-- 1.3.6.1.4.1.37950.1.1.5.12.4.1.2.4
-- 1.3.6.1.4.1.37950.1.1.5.12.4.1.2.4
		-- 1.3.6.1.4.1.37950.1.1.5.12.4.1.2.4
		priPkgBroadcast OBJECT-TYPE
			SYNTAX INTEGER (0..1024000)
			MAX-ACCESS read-write
			STATUS current
			DESCRIPTION
				"Description."
			::= { onuPriPortPkgSuppress 4 }

		
--           1.3.6.1.4.1.37950.1.1.5.12.4.1.2.5
-- 1.3.6.1.4.1.37950.1.1.5.12.4.1.2.5
-- 1.3.6.1.4.1.37950.1.1.5.12.4.1.2.5
-- 1.3.6.1.4.1.37950.1.1.5.12.4.1.2.5
-- 1.3.6.1.4.1.37950.1.1.5.12.4.1.2.5
-- 1.3.6.1.4.1.37950.1.1.5.12.4.1.2.5
-- 1.3.6.1.4.1.37950.1.1.5.12.4.1.2.5
-- 1.3.6.1.4.1.37950.1.1.5.12.4.1.2.5
-- 1.3.6.1.4.1.37950.1.1.5.12.4.1.2.5
		-- 1.3.6.1.4.1.37950.1.1.5.12.4.1.2.5
		priPkgMulticast OBJECT-TYPE
			SYNTAX INTEGER (0..1024000)
			MAX-ACCESS read-write
			STATUS current
			DESCRIPTION
				"Description."
			::= { onuPriPortPkgSuppress 5 }

		
--           1.3.6.1.4.1.37950.1.1.5.12.4.1.2.6
-- 1.3.6.1.4.1.37950.1.1.5.12.4.1.2.6
-- 1.3.6.1.4.1.37950.1.1.5.12.4.1.2.6
-- 1.3.6.1.4.1.37950.1.1.5.12.4.1.2.6
-- 1.3.6.1.4.1.37950.1.1.5.12.4.1.2.6
-- 1.3.6.1.4.1.37950.1.1.5.12.4.1.2.6
-- 1.3.6.1.4.1.37950.1.1.5.12.4.1.2.6
-- 1.3.6.1.4.1.37950.1.1.5.12.4.1.2.6
-- 1.3.6.1.4.1.37950.1.1.5.12.4.1.2.6
		-- 1.3.6.1.4.1.37950.1.1.5.12.4.1.2.6
		priPkgUnknown OBJECT-TYPE
			SYNTAX INTEGER (0..1024000)
			MAX-ACCESS read-write
			STATUS current
			DESCRIPTION
				"Description."
			::= { onuPriPortPkgSuppress 6 }

		
--           1.3.6.1.4.1.37950.1.1.5.12.4.1.2.7
-- 1.3.6.1.4.1.37950.1.1.5.12.4.1.2.7
-- 1.3.6.1.4.1.37950.1.1.5.12.4.1.2.7
-- 1.3.6.1.4.1.37950.1.1.5.12.4.1.2.7
-- 1.3.6.1.4.1.37950.1.1.5.12.4.1.2.7
-- 1.3.6.1.4.1.37950.1.1.5.12.4.1.2.7
-- 1.3.6.1.4.1.37950.1.1.5.12.4.1.2.7
-- 1.3.6.1.4.1.37950.1.1.5.12.4.1.2.7
-- 1.3.6.1.4.1.37950.1.1.5.12.4.1.2.7
		-- 1.3.6.1.4.1.37950.1.1.5.12.4.1.2.7
		priPkgSuppressAction OBJECT-TYPE
			SYNTAX INTEGER
				{
				add(1),
				remove(2)
				}
			MAX-ACCESS read-write
			STATUS current
			DESCRIPTION
				"Description."
			::= { onuPriPortPkgSuppress 7 }

		
--           1.3.6.1.4.1.37950.1.1.5.12.4.1.3
-- 1.3.6.1.4.1.37950.1.1.5.12.4.1.3
-- 1.3.6.1.4.1.37950.1.1.5.12.4.1.3
-- 1.3.6.1.4.1.37950.1.1.5.12.4.1.3
-- 1.3.6.1.4.1.37950.1.1.5.12.4.1.3
-- 1.3.6.1.4.1.37950.1.1.5.12.4.1.3
-- 1.3.6.1.4.1.37950.1.1.5.12.4.1.3
-- 1.3.6.1.4.1.37950.1.1.5.12.4.1.3
-- 1.3.6.1.4.1.37950.1.1.5.12.4.1.3
		-- 1.3.6.1.4.1.37950.1.1.5.12.4.1.3
		onuPriPortModeControl OBJECT IDENTIFIER ::= { onuPriPortCfg 3 }

		
--           1.3.6.1.4.1.37950.1.1.5.12.4.1.3.1
-- 1.3.6.1.4.1.37950.1.1.5.12.4.1.3.1
-- 1.3.6.1.4.1.37950.1.1.5.12.4.1.3.1
-- 1.3.6.1.4.1.37950.1.1.5.12.4.1.3.1
-- 1.3.6.1.4.1.37950.1.1.5.12.4.1.3.1
-- 1.3.6.1.4.1.37950.1.1.5.12.4.1.3.1
-- 1.3.6.1.4.1.37950.1.1.5.12.4.1.3.1
-- 1.3.6.1.4.1.37950.1.1.5.12.4.1.3.1
-- 1.3.6.1.4.1.37950.1.1.5.12.4.1.3.1
		-- 1.3.6.1.4.1.37950.1.1.5.12.4.1.3.1
		priModeControlPon OBJECT-TYPE
			SYNTAX INTEGER (1..16)
			MAX-ACCESS read-write
			STATUS current
			DESCRIPTION
				"Description."
			::= { onuPriPortModeControl 1 }

		
--           1.3.6.1.4.1.37950.1.1.5.12.4.1.3.2
-- 1.3.6.1.4.1.37950.1.1.5.12.4.1.3.2
-- 1.3.6.1.4.1.37950.1.1.5.12.4.1.3.2
-- 1.3.6.1.4.1.37950.1.1.5.12.4.1.3.2
-- 1.3.6.1.4.1.37950.1.1.5.12.4.1.3.2
-- 1.3.6.1.4.1.37950.1.1.5.12.4.1.3.2
-- 1.3.6.1.4.1.37950.1.1.5.12.4.1.3.2
-- 1.3.6.1.4.1.37950.1.1.5.12.4.1.3.2
-- 1.3.6.1.4.1.37950.1.1.5.12.4.1.3.2
		-- 1.3.6.1.4.1.37950.1.1.5.12.4.1.3.2
		priModeControlOnu OBJECT-TYPE
			SYNTAX INTEGER (1..65535)
			MAX-ACCESS read-write
			STATUS current
			DESCRIPTION
				"Description."
			::= { onuPriPortModeControl 2 }

		
--           1.3.6.1.4.1.37950.1.1.5.12.4.1.3.3
-- 1.3.6.1.4.1.37950.1.1.5.12.4.1.3.3
-- 1.3.6.1.4.1.37950.1.1.5.12.4.1.3.3
-- 1.3.6.1.4.1.37950.1.1.5.12.4.1.3.3
-- 1.3.6.1.4.1.37950.1.1.5.12.4.1.3.3
-- 1.3.6.1.4.1.37950.1.1.5.12.4.1.3.3
-- 1.3.6.1.4.1.37950.1.1.5.12.4.1.3.3
-- 1.3.6.1.4.1.37950.1.1.5.12.4.1.3.3
-- 1.3.6.1.4.1.37950.1.1.5.12.4.1.3.3
		-- 1.3.6.1.4.1.37950.1.1.5.12.4.1.3.3
		priModeControlEthNo OBJECT-TYPE
			SYNTAX INTEGER (1..255)
			MAX-ACCESS read-write
			STATUS current
			DESCRIPTION
				"Description."
			::= { onuPriPortModeControl 3 }

		
--           1.3.6.1.4.1.37950.1.1.5.12.4.1.3.4
-- 1.3.6.1.4.1.37950.1.1.5.12.4.1.3.4
-- 1.3.6.1.4.1.37950.1.1.5.12.4.1.3.4
-- 1.3.6.1.4.1.37950.1.1.5.12.4.1.3.4
-- 1.3.6.1.4.1.37950.1.1.5.12.4.1.3.4
-- 1.3.6.1.4.1.37950.1.1.5.12.4.1.3.4
-- 1.3.6.1.4.1.37950.1.1.5.12.4.1.3.4
-- 1.3.6.1.4.1.37950.1.1.5.12.4.1.3.4
-- 1.3.6.1.4.1.37950.1.1.5.12.4.1.3.4
		-- 1.3.6.1.4.1.37950.1.1.5.12.4.1.3.4
		priModeControl OBJECT-TYPE
			SYNTAX INTEGER
				{
				s10hd(1),
				s10fd(2),
				s100hd(3),
				s100fd(4),
				s1000hd(5),
				s1000fd(6),
				s10000fd(7)
				}
			MAX-ACCESS read-write
			STATUS current
			DESCRIPTION
				"Description."
			::= { onuPriPortModeControl 4 }

		
--           1.3.6.1.4.1.37950.1.1.5.12.4.1.3.5
-- 1.3.6.1.4.1.37950.1.1.5.12.4.1.3.5
-- 1.3.6.1.4.1.37950.1.1.5.12.4.1.3.5
-- 1.3.6.1.4.1.37950.1.1.5.12.4.1.3.5
-- 1.3.6.1.4.1.37950.1.1.5.12.4.1.3.5
-- 1.3.6.1.4.1.37950.1.1.5.12.4.1.3.5
-- 1.3.6.1.4.1.37950.1.1.5.12.4.1.3.5
-- 1.3.6.1.4.1.37950.1.1.5.12.4.1.3.5
-- 1.3.6.1.4.1.37950.1.1.5.12.4.1.3.5
		-- 1.3.6.1.4.1.37950.1.1.5.12.4.1.3.5
		priModeControlAction OBJECT-TYPE
			SYNTAX INTEGER
				{
				add(1),
				remove(2)
				}
			MAX-ACCESS read-write
			STATUS current
			DESCRIPTION
				"Description."
			::= { onuPriPortModeControl 5 }

		
--           1.3.6.1.4.1.37950.1.1.5.12.4.1.4
-- 1.3.6.1.4.1.37950.1.1.5.12.4.1.4
-- 1.3.6.1.4.1.37950.1.1.5.12.4.1.4
-- 1.3.6.1.4.1.37950.1.1.5.12.4.1.4
-- 1.3.6.1.4.1.37950.1.1.5.12.4.1.4
-- 1.3.6.1.4.1.37950.1.1.5.12.4.1.4
-- 1.3.6.1.4.1.37950.1.1.5.12.4.1.4
-- 1.3.6.1.4.1.37950.1.1.5.12.4.1.4
-- 1.3.6.1.4.1.37950.1.1.5.12.4.1.4
		-- 1.3.6.1.4.1.37950.1.1.5.12.4.1.4
		onuPriPotsParameter OBJECT IDENTIFIER ::= { onuPriPortCfg 4 }

		
--           1.3.6.1.4.1.37950.1.1.5.12.4.1.4.1
-- 1.3.6.1.4.1.37950.1.1.5.12.4.1.4.1
-- 1.3.6.1.4.1.37950.1.1.5.12.4.1.4.1
-- 1.3.6.1.4.1.37950.1.1.5.12.4.1.4.1
-- 1.3.6.1.4.1.37950.1.1.5.12.4.1.4.1
-- 1.3.6.1.4.1.37950.1.1.5.12.4.1.4.1
-- 1.3.6.1.4.1.37950.1.1.5.12.4.1.4.1
-- 1.3.6.1.4.1.37950.1.1.5.12.4.1.4.1
-- 1.3.6.1.4.1.37950.1.1.5.12.4.1.4.1
		-- 1.3.6.1.4.1.37950.1.1.5.12.4.1.4.1
		priPotsParameterPon OBJECT-TYPE
			SYNTAX Integer32 (1..16)
			MAX-ACCESS read-write
			STATUS current
			DESCRIPTION
				"Description."
			::= { onuPriPotsParameter 1 }

		
--           1.3.6.1.4.1.37950.1.1.5.12.4.1.4.2
-- 1.3.6.1.4.1.37950.1.1.5.12.4.1.4.2
-- 1.3.6.1.4.1.37950.1.1.5.12.4.1.4.2
-- 1.3.6.1.4.1.37950.1.1.5.12.4.1.4.2
-- 1.3.6.1.4.1.37950.1.1.5.12.4.1.4.2
-- 1.3.6.1.4.1.37950.1.1.5.12.4.1.4.2
-- 1.3.6.1.4.1.37950.1.1.5.12.4.1.4.2
-- 1.3.6.1.4.1.37950.1.1.5.12.4.1.4.2
-- 1.3.6.1.4.1.37950.1.1.5.12.4.1.4.2
		-- 1.3.6.1.4.1.37950.1.1.5.12.4.1.4.2
		priPotsParameterOnu OBJECT-TYPE
			SYNTAX Integer32 (1..65535)
			MAX-ACCESS read-write
			STATUS current
			DESCRIPTION
				"Description."
			::= { onuPriPotsParameter 2 }

		
--           1.3.6.1.4.1.37950.1.1.5.12.4.1.4.3
-- 1.3.6.1.4.1.37950.1.1.5.12.4.1.4.3
-- 1.3.6.1.4.1.37950.1.1.5.12.4.1.4.3
-- 1.3.6.1.4.1.37950.1.1.5.12.4.1.4.3
-- 1.3.6.1.4.1.37950.1.1.5.12.4.1.4.3
-- 1.3.6.1.4.1.37950.1.1.5.12.4.1.4.3
-- 1.3.6.1.4.1.37950.1.1.5.12.4.1.4.3
-- 1.3.6.1.4.1.37950.1.1.5.12.4.1.4.3
-- 1.3.6.1.4.1.37950.1.1.5.12.4.1.4.3
		-- 1.3.6.1.4.1.37950.1.1.5.12.4.1.4.3
		priPotsParameterPotsNo OBJECT-TYPE
			SYNTAX Integer32 (1..255)
			MAX-ACCESS read-write
			STATUS current
			DESCRIPTION
				"Description."
			::= { onuPriPotsParameter 3 }

		
--           1.3.6.1.4.1.37950.1.1.5.12.4.1.4.4
-- 1.3.6.1.4.1.37950.1.1.5.12.4.1.4.4
-- 1.3.6.1.4.1.37950.1.1.5.12.4.1.4.4
-- 1.3.6.1.4.1.37950.1.1.5.12.4.1.4.4
-- 1.3.6.1.4.1.37950.1.1.5.12.4.1.4.4
-- 1.3.6.1.4.1.37950.1.1.5.12.4.1.4.4
-- 1.3.6.1.4.1.37950.1.1.5.12.4.1.4.4
-- 1.3.6.1.4.1.37950.1.1.5.12.4.1.4.4
-- 1.3.6.1.4.1.37950.1.1.5.12.4.1.4.4
		-- 1.3.6.1.4.1.37950.1.1.5.12.4.1.4.4
		priPotsParameterVar OBJECT-TYPE
			SYNTAX INTEGER
				{
				disable(0),
				enable(1)
				}
			MAX-ACCESS read-write
			STATUS current
			DESCRIPTION
				"Description."
			::= { onuPriPotsParameter 4 }

		
--           1.3.6.1.4.1.37950.1.1.5.12.4.1.4.5
-- 1.3.6.1.4.1.37950.1.1.5.12.4.1.4.5
-- 1.3.6.1.4.1.37950.1.1.5.12.4.1.4.5
-- 1.3.6.1.4.1.37950.1.1.5.12.4.1.4.5
-- 1.3.6.1.4.1.37950.1.1.5.12.4.1.4.5
-- 1.3.6.1.4.1.37950.1.1.5.12.4.1.4.5
-- 1.3.6.1.4.1.37950.1.1.5.12.4.1.4.5
-- 1.3.6.1.4.1.37950.1.1.5.12.4.1.4.5
-- 1.3.6.1.4.1.37950.1.1.5.12.4.1.4.5
		-- 1.3.6.1.4.1.37950.1.1.5.12.4.1.4.5
		priPotsParameterEchoCancle OBJECT-TYPE
			SYNTAX INTEGER
				{
				disable(0),
				enable(1)
				}
			MAX-ACCESS read-write
			STATUS current
			DESCRIPTION
				"Description."
			::= { onuPriPotsParameter 5 }

		
--          1.3.6.1.4.1.37950.1.1.5.12.4.1.4.6
-- 1.3.6.1.4.1.37950.1.1.5.12.4.1.4.6
-- 1.3.6.1.4.1.37950.1.1.5.12.4.1.4.6
-- 1.3.6.1.4.1.37950.1.1.5.12.4.1.4.6
-- 1.3.6.1.4.1.37950.1.1.5.12.4.1.4.6
-- 1.3.6.1.4.1.37950.1.1.5.12.4.1.4.6
-- 1.3.6.1.4.1.37950.1.1.5.12.4.1.4.6
-- 1.3.6.1.4.1.37950.1.1.5.12.4.1.4.6
-- 1.3.6.1.4.1.37950.1.1.5.12.4.1.4.6
		-- 1.3.6.1.4.1.37950.1.1.5.12.4.1.4.6
		priPotsPtInutGain OBJECT-TYPE
			SYNTAX Integer32 (-32..32)
			MAX-ACCESS read-write
			STATUS current
			DESCRIPTION
				"Description."
			::= { onuPriPotsParameter 6 }

		
--          1.3.6.1.4.1.37950.1.1.5.12.4.1.4.7
-- 1.3.6.1.4.1.37950.1.1.5.12.4.1.4.7
-- 1.3.6.1.4.1.37950.1.1.5.12.4.1.4.7
-- 1.3.6.1.4.1.37950.1.1.5.12.4.1.4.7
-- 1.3.6.1.4.1.37950.1.1.5.12.4.1.4.7
-- 1.3.6.1.4.1.37950.1.1.5.12.4.1.4.7
-- 1.3.6.1.4.1.37950.1.1.5.12.4.1.4.7
-- 1.3.6.1.4.1.37950.1.1.5.12.4.1.4.7
-- 1.3.6.1.4.1.37950.1.1.5.12.4.1.4.7
		-- 1.3.6.1.4.1.37950.1.1.5.12.4.1.4.7
		priPotsPtOutputGain OBJECT-TYPE
			SYNTAX Integer32 (-32..32)
			MAX-ACCESS read-write
			STATUS current
			DESCRIPTION
				"Description."
			::= { onuPriPotsParameter 7 }

		
--          1.3.6.1.4.1.37950.1.1.5.12.4.1.4.8
-- 1.3.6.1.4.1.37950.1.1.5.12.4.1.4.8
-- 1.3.6.1.4.1.37950.1.1.5.12.4.1.4.8
-- 1.3.6.1.4.1.37950.1.1.5.12.4.1.4.8
-- 1.3.6.1.4.1.37950.1.1.5.12.4.1.4.8
-- 1.3.6.1.4.1.37950.1.1.5.12.4.1.4.8
-- 1.3.6.1.4.1.37950.1.1.5.12.4.1.4.8
-- 1.3.6.1.4.1.37950.1.1.5.12.4.1.4.8
-- 1.3.6.1.4.1.37950.1.1.5.12.4.1.4.8
		-- 1.3.6.1.4.1.37950.1.1.5.12.4.1.4.8
		priPotsPtDtmfMode OBJECT-TYPE
			SYNTAX INTEGER
				{
				transparent(0),
				rfc2833(1),
				rfc2833-redundancy(2),
				outband(3)
				}
			MAX-ACCESS read-write
			STATUS current
			DESCRIPTION
				"Description."
			::= { onuPriPotsParameter 8 }

		
--          1.3.6.1.4.1.37950.1.1.5.12.4.1.4.9
-- 1.3.6.1.4.1.37950.1.1.5.12.4.1.4.9
-- 1.3.6.1.4.1.37950.1.1.5.12.4.1.4.9
-- 1.3.6.1.4.1.37950.1.1.5.12.4.1.4.9
-- 1.3.6.1.4.1.37950.1.1.5.12.4.1.4.9
-- 1.3.6.1.4.1.37950.1.1.5.12.4.1.4.9
-- 1.3.6.1.4.1.37950.1.1.5.12.4.1.4.9
-- 1.3.6.1.4.1.37950.1.1.5.12.4.1.4.9
-- 1.3.6.1.4.1.37950.1.1.5.12.4.1.4.9
		-- 1.3.6.1.4.1.37950.1.1.5.12.4.1.4.9
		priPotsPtAction OBJECT-TYPE
			SYNTAX INTEGER
				{
				commit(1),
				remove(2)
				}
			MAX-ACCESS read-write
			STATUS current
			DESCRIPTION
				"Description."
			::= { onuPriPotsParameter 9 }

		
--          1.3.6.1.4.1.37950.1.1.5.12.4.1.5
-- 1.3.6.1.4.1.37950.1.1.5.12.4.1.5
-- 1.3.6.1.4.1.37950.1.1.5.12.4.1.5
-- 1.3.6.1.4.1.37950.1.1.5.12.4.1.5
-- 1.3.6.1.4.1.37950.1.1.5.12.4.1.5
-- 1.3.6.1.4.1.37950.1.1.5.12.4.1.5
-- 1.3.6.1.4.1.37950.1.1.5.12.4.1.5
-- 1.3.6.1.4.1.37950.1.1.5.12.4.1.5
-- 1.3.6.1.4.1.37950.1.1.5.12.4.1.5
		-- 1.3.6.1.4.1.37950.1.1.5.12.4.1.5
		onuPriPotsAction OBJECT IDENTIFIER ::= { onuPriPortCfg 5 }

		
--          1.3.6.1.4.1.37950.1.1.5.12.4.1.5.1
-- 1.3.6.1.4.1.37950.1.1.5.12.4.1.5.1
-- 1.3.6.1.4.1.37950.1.1.5.12.4.1.5.1
-- 1.3.6.1.4.1.37950.1.1.5.12.4.1.5.1
-- 1.3.6.1.4.1.37950.1.1.5.12.4.1.5.1
-- 1.3.6.1.4.1.37950.1.1.5.12.4.1.5.1
-- 1.3.6.1.4.1.37950.1.1.5.12.4.1.5.1
-- 1.3.6.1.4.1.37950.1.1.5.12.4.1.5.1
-- 1.3.6.1.4.1.37950.1.1.5.12.4.1.5.1
		-- 1.3.6.1.4.1.37950.1.1.5.12.4.1.5.1
		priPotsActionPon OBJECT-TYPE
			SYNTAX Integer32 (1..16)
			MAX-ACCESS read-write
			STATUS current
			DESCRIPTION
				"Description."
			::= { onuPriPotsAction 1 }

		
--          1.3.6.1.4.1.37950.1.1.5.12.4.1.5.2
-- 1.3.6.1.4.1.37950.1.1.5.12.4.1.5.2
-- 1.3.6.1.4.1.37950.1.1.5.12.4.1.5.2
-- 1.3.6.1.4.1.37950.1.1.5.12.4.1.5.2
-- 1.3.6.1.4.1.37950.1.1.5.12.4.1.5.2
-- 1.3.6.1.4.1.37950.1.1.5.12.4.1.5.2
-- 1.3.6.1.4.1.37950.1.1.5.12.4.1.5.2
-- 1.3.6.1.4.1.37950.1.1.5.12.4.1.5.2
-- 1.3.6.1.4.1.37950.1.1.5.12.4.1.5.2
		-- 1.3.6.1.4.1.37950.1.1.5.12.4.1.5.2
		priPotsActionOnu OBJECT-TYPE
			SYNTAX Integer32 (1..65535)
			MAX-ACCESS read-write
			STATUS current
			DESCRIPTION
				"Description."
			::= { onuPriPotsAction 2 }

		
--          1.3.6.1.4.1.37950.1.1.5.12.4.1.5.3
-- 1.3.6.1.4.1.37950.1.1.5.12.4.1.5.3
-- 1.3.6.1.4.1.37950.1.1.5.12.4.1.5.3
-- 1.3.6.1.4.1.37950.1.1.5.12.4.1.5.3
-- 1.3.6.1.4.1.37950.1.1.5.12.4.1.5.3
-- 1.3.6.1.4.1.37950.1.1.5.12.4.1.5.3
-- 1.3.6.1.4.1.37950.1.1.5.12.4.1.5.3
-- 1.3.6.1.4.1.37950.1.1.5.12.4.1.5.3
-- 1.3.6.1.4.1.37950.1.1.5.12.4.1.5.3
		-- 1.3.6.1.4.1.37950.1.1.5.12.4.1.5.3
		priPotsActionPotsNo OBJECT-TYPE
			SYNTAX Integer32 (1..255)
			MAX-ACCESS read-write
			STATUS current
			DESCRIPTION
				"Description."
			::= { onuPriPotsAction 3 }

		
--          1.3.6.1.4.1.37950.1.1.5.12.4.1.5.4
-- 1.3.6.1.4.1.37950.1.1.5.12.4.1.5.4
-- 1.3.6.1.4.1.37950.1.1.5.12.4.1.5.4
-- 1.3.6.1.4.1.37950.1.1.5.12.4.1.5.4
-- 1.3.6.1.4.1.37950.1.1.5.12.4.1.5.4
-- 1.3.6.1.4.1.37950.1.1.5.12.4.1.5.4
-- 1.3.6.1.4.1.37950.1.1.5.12.4.1.5.4
-- 1.3.6.1.4.1.37950.1.1.5.12.4.1.5.4
-- 1.3.6.1.4.1.37950.1.1.5.12.4.1.5.4
		-- 1.3.6.1.4.1.37950.1.1.5.12.4.1.5.4
		priPotsActionRegister OBJECT-TYPE
			SYNTAX INTEGER
				{
				unregister(0),
				register(1)
				}
			MAX-ACCESS read-write
			STATUS current
			DESCRIPTION
				"Description."
			::= { onuPriPotsAction 4 }

		
--          1.3.6.1.4.1.37950.1.1.5.12.4.1.5.5
-- 1.3.6.1.4.1.37950.1.1.5.12.4.1.5.5
-- 1.3.6.1.4.1.37950.1.1.5.12.4.1.5.5
-- 1.3.6.1.4.1.37950.1.1.5.12.4.1.5.5
-- 1.3.6.1.4.1.37950.1.1.5.12.4.1.5.5
-- 1.3.6.1.4.1.37950.1.1.5.12.4.1.5.5
-- 1.3.6.1.4.1.37950.1.1.5.12.4.1.5.5
-- 1.3.6.1.4.1.37950.1.1.5.12.4.1.5.5
-- 1.3.6.1.4.1.37950.1.1.5.12.4.1.5.5
		-- 1.3.6.1.4.1.37950.1.1.5.12.4.1.5.5
		priPotsActionAction OBJECT-TYPE
			SYNTAX INTEGER { commit(1) }
			MAX-ACCESS read-write
			STATUS current
			DESCRIPTION
				"Description."
			::= { onuPriPotsAction 5 }

		
--          1.3.6.1.4.1.37950.1.1.5.12.4.2
-- 1.3.6.1.4.1.37950.1.1.5.12.4.2
-- 1.3.6.1.4.1.37950.1.1.5.12.4.2
-- 1.3.6.1.4.1.37950.1.1.5.12.4.2
-- 1.3.6.1.4.1.37950.1.1.5.12.4.2
-- 1.3.6.1.4.1.37950.1.1.5.12.4.2
-- 1.3.6.1.4.1.37950.1.1.5.12.4.2
-- 1.3.6.1.4.1.37950.1.1.5.12.4.2
-- 1.3.6.1.4.1.37950.1.1.5.12.4.2
		-- 1.3.6.1.4.1.37950.1.1.5.12.4.2
		onuPriPortInfo OBJECT IDENTIFIER ::= { onuPriPort 2 }

		
--          1.3.6.1.4.1.37950.1.1.5.12.4.2.1
-- 1.3.6.1.4.1.37950.1.1.5.12.4.2.1
-- 1.3.6.1.4.1.37950.1.1.5.12.4.2.1
-- 1.3.6.1.4.1.37950.1.1.5.12.4.2.1
-- 1.3.6.1.4.1.37950.1.1.5.12.4.2.1
-- 1.3.6.1.4.1.37950.1.1.5.12.4.2.1
-- 1.3.6.1.4.1.37950.1.1.5.12.4.2.1
-- 1.3.6.1.4.1.37950.1.1.5.12.4.2.1
-- 1.3.6.1.4.1.37950.1.1.5.12.4.2.1
		-- 1.3.6.1.4.1.37950.1.1.5.12.4.2.1
		priPortMacLimitTable OBJECT-TYPE
			SYNTAX SEQUENCE OF PriPortMacLimitEntry
			MAX-ACCESS not-accessible
			STATUS current
			DESCRIPTION
				"Description."
			::= { onuPriPortInfo 1 }

		
--          1.3.6.1.4.1.37950.1.1.5.12.4.2.1.1
-- 1.3.6.1.4.1.37950.1.1.5.12.4.2.1.1
-- 1.3.6.1.4.1.37950.1.1.5.12.4.2.1.1
-- 1.3.6.1.4.1.37950.1.1.5.12.4.2.1.1
-- 1.3.6.1.4.1.37950.1.1.5.12.4.2.1.1
-- 1.3.6.1.4.1.37950.1.1.5.12.4.2.1.1
-- 1.3.6.1.4.1.37950.1.1.5.12.4.2.1.1
-- 1.3.6.1.4.1.37950.1.1.5.12.4.2.1.1
-- 1.3.6.1.4.1.37950.1.1.5.12.4.2.1.1
		-- 1.3.6.1.4.1.37950.1.1.5.12.4.2.1.1
		priPortMacLimitEntry OBJECT-TYPE
			SYNTAX PriPortMacLimitEntry
			MAX-ACCESS not-accessible
			STATUS current
			DESCRIPTION
				"Description."
			INDEX { priPortMacLimitPonS, priPortMacLimitOnuS, priPortMacLimitEthNoS }
			::= { priPortMacLimitTable 1 }

		
		PriPortMacLimitEntry ::=
			SEQUENCE { 
				priPortMacLimitPonS
					INTEGER,
				priPortMacLimitOnuS
					INTEGER,
				priPortMacLimitEthNoS
					INTEGER,
				priPortMacLimitS
					INTEGER
			 }

--          1.3.6.1.4.1.37950.1.1.5.12.4.2.1.1.1
-- 1.3.6.1.4.1.37950.1.1.5.12.4.2.1.1.1
-- 1.3.6.1.4.1.37950.1.1.5.12.4.2.1.1.1
-- 1.3.6.1.4.1.37950.1.1.5.12.4.2.1.1.1
-- 1.3.6.1.4.1.37950.1.1.5.12.4.2.1.1.1
-- 1.3.6.1.4.1.37950.1.1.5.12.4.2.1.1.1
-- 1.3.6.1.4.1.37950.1.1.5.12.4.2.1.1.1
-- 1.3.6.1.4.1.37950.1.1.5.12.4.2.1.1.1
-- 1.3.6.1.4.1.37950.1.1.5.12.4.2.1.1.1
		-- 1.3.6.1.4.1.37950.1.1.5.12.4.2.1.1.1
		priPortMacLimitPonS OBJECT-TYPE
			SYNTAX INTEGER (1..16)
			MAX-ACCESS read-write
			STATUS current
			DESCRIPTION
				"Description."
			::= { priPortMacLimitEntry 1 }

		
--          1.3.6.1.4.1.37950.1.1.5.12.4.2.1.1.2
-- 1.3.6.1.4.1.37950.1.1.5.12.4.2.1.1.2
-- 1.3.6.1.4.1.37950.1.1.5.12.4.2.1.1.2
-- 1.3.6.1.4.1.37950.1.1.5.12.4.2.1.1.2
-- 1.3.6.1.4.1.37950.1.1.5.12.4.2.1.1.2
-- 1.3.6.1.4.1.37950.1.1.5.12.4.2.1.1.2
-- 1.3.6.1.4.1.37950.1.1.5.12.4.2.1.1.2
-- 1.3.6.1.4.1.37950.1.1.5.12.4.2.1.1.2
-- 1.3.6.1.4.1.37950.1.1.5.12.4.2.1.1.2
		-- 1.3.6.1.4.1.37950.1.1.5.12.4.2.1.1.2
		priPortMacLimitOnuS OBJECT-TYPE
			SYNTAX INTEGER (1..65535)
			MAX-ACCESS read-write
			STATUS current
			DESCRIPTION
				"Description."
			::= { priPortMacLimitEntry 2 }

		
--          1.3.6.1.4.1.37950.1.1.5.12.4.2.1.1.3
-- 1.3.6.1.4.1.37950.1.1.5.12.4.2.1.1.3
-- 1.3.6.1.4.1.37950.1.1.5.12.4.2.1.1.3
-- 1.3.6.1.4.1.37950.1.1.5.12.4.2.1.1.3
-- 1.3.6.1.4.1.37950.1.1.5.12.4.2.1.1.3
-- 1.3.6.1.4.1.37950.1.1.5.12.4.2.1.1.3
-- 1.3.6.1.4.1.37950.1.1.5.12.4.2.1.1.3
-- 1.3.6.1.4.1.37950.1.1.5.12.4.2.1.1.3
-- 1.3.6.1.4.1.37950.1.1.5.12.4.2.1.1.3
		-- 1.3.6.1.4.1.37950.1.1.5.12.4.2.1.1.3
		priPortMacLimitEthNoS OBJECT-TYPE
			SYNTAX INTEGER (1..255)
			MAX-ACCESS read-write
			STATUS current
			DESCRIPTION
				"Description."
			::= { priPortMacLimitEntry 3 }

		
--          1.3.6.1.4.1.37950.1.1.5.12.4.2.1.1.4
-- 1.3.6.1.4.1.37950.1.1.5.12.4.2.1.1.4
-- 1.3.6.1.4.1.37950.1.1.5.12.4.2.1.1.4
-- 1.3.6.1.4.1.37950.1.1.5.12.4.2.1.1.4
-- 1.3.6.1.4.1.37950.1.1.5.12.4.2.1.1.4
-- 1.3.6.1.4.1.37950.1.1.5.12.4.2.1.1.4
-- 1.3.6.1.4.1.37950.1.1.5.12.4.2.1.1.4
-- 1.3.6.1.4.1.37950.1.1.5.12.4.2.1.1.4
-- 1.3.6.1.4.1.37950.1.1.5.12.4.2.1.1.4
		-- 1.3.6.1.4.1.37950.1.1.5.12.4.2.1.1.4
		priPortMacLimitS OBJECT-TYPE
			SYNTAX INTEGER (0..65535)
			MAX-ACCESS read-write
			STATUS current
			DESCRIPTION
				"Description."
			::= { priPortMacLimitEntry 4 }

		
--          1.3.6.1.4.1.37950.1.1.5.12.4.2.2
-- 1.3.6.1.4.1.37950.1.1.5.12.4.2.2
-- 1.3.6.1.4.1.37950.1.1.5.12.4.2.2
-- 1.3.6.1.4.1.37950.1.1.5.12.4.2.2
-- 1.3.6.1.4.1.37950.1.1.5.12.4.2.2
-- 1.3.6.1.4.1.37950.1.1.5.12.4.2.2
-- 1.3.6.1.4.1.37950.1.1.5.12.4.2.2
-- 1.3.6.1.4.1.37950.1.1.5.12.4.2.2
-- 1.3.6.1.4.1.37950.1.1.5.12.4.2.2
		-- 1.3.6.1.4.1.37950.1.1.5.12.4.2.2
		priPortPkgSuppressTable OBJECT-TYPE
			SYNTAX SEQUENCE OF PriPortPkgSuppressEntry
			MAX-ACCESS not-accessible
			STATUS current
			DESCRIPTION
				"Description."
			::= { onuPriPortInfo 2 }

		
--          1.3.6.1.4.1.37950.1.1.5.12.4.2.2.1
-- 1.3.6.1.4.1.37950.1.1.5.12.4.2.2.1
-- 1.3.6.1.4.1.37950.1.1.5.12.4.2.2.1
-- 1.3.6.1.4.1.37950.1.1.5.12.4.2.2.1
-- 1.3.6.1.4.1.37950.1.1.5.12.4.2.2.1
-- 1.3.6.1.4.1.37950.1.1.5.12.4.2.2.1
-- 1.3.6.1.4.1.37950.1.1.5.12.4.2.2.1
-- 1.3.6.1.4.1.37950.1.1.5.12.4.2.2.1
-- 1.3.6.1.4.1.37950.1.1.5.12.4.2.2.1
		-- 1.3.6.1.4.1.37950.1.1.5.12.4.2.2.1
		priPortPkgSuppressEntry OBJECT-TYPE
			SYNTAX PriPortPkgSuppressEntry
			MAX-ACCESS not-accessible
			STATUS current
			DESCRIPTION
				"Description."
			INDEX { priPortPkgSuppressPonS, priPortPkgSuppressOnuS, priPortPkgSuppressEthNoS }
			::= { priPortPkgSuppressTable 1 }

		
		PriPortPkgSuppressEntry ::=
			SEQUENCE { 
				priPortPkgSuppressPonS
					INTEGER,
				priPortPkgSuppressOnuS
					INTEGER,
				priPortPkgSuppressEthNoS
					INTEGER,
				priPortPkgSuppressBroadcastS
					INTEGER,
				priPortPkgSuppressMulticastS
					INTEGER,
				priPortPkgSuppressUnkownS
					INTEGER
			 }

--          1.3.6.1.4.1.37950.1.1.5.12.4.2.2.1.1
-- 1.3.6.1.4.1.37950.1.1.5.12.4.2.2.1.1
-- 1.3.6.1.4.1.37950.1.1.5.12.4.2.2.1.1
-- 1.3.6.1.4.1.37950.1.1.5.12.4.2.2.1.1
-- 1.3.6.1.4.1.37950.1.1.5.12.4.2.2.1.1
-- 1.3.6.1.4.1.37950.1.1.5.12.4.2.2.1.1
-- 1.3.6.1.4.1.37950.1.1.5.12.4.2.2.1.1
-- 1.3.6.1.4.1.37950.1.1.5.12.4.2.2.1.1
-- 1.3.6.1.4.1.37950.1.1.5.12.4.2.2.1.1
		-- 1.3.6.1.4.1.37950.1.1.5.12.4.2.2.1.1
		priPortPkgSuppressPonS OBJECT-TYPE
			SYNTAX INTEGER (1..16)
			MAX-ACCESS read-write
			STATUS current
			DESCRIPTION
				"Description."
			::= { priPortPkgSuppressEntry 1 }

		
--          1.3.6.1.4.1.37950.1.1.5.12.4.2.2.1.2
-- 1.3.6.1.4.1.37950.1.1.5.12.4.2.2.1.2
-- 1.3.6.1.4.1.37950.1.1.5.12.4.2.2.1.2
-- 1.3.6.1.4.1.37950.1.1.5.12.4.2.2.1.2
-- 1.3.6.1.4.1.37950.1.1.5.12.4.2.2.1.2
-- 1.3.6.1.4.1.37950.1.1.5.12.4.2.2.1.2
-- 1.3.6.1.4.1.37950.1.1.5.12.4.2.2.1.2
-- 1.3.6.1.4.1.37950.1.1.5.12.4.2.2.1.2
-- 1.3.6.1.4.1.37950.1.1.5.12.4.2.2.1.2
		-- 1.3.6.1.4.1.37950.1.1.5.12.4.2.2.1.2
		priPortPkgSuppressOnuS OBJECT-TYPE
			SYNTAX INTEGER (1..65535)
			MAX-ACCESS read-write
			STATUS current
			DESCRIPTION
				"Description."
			::= { priPortPkgSuppressEntry 2 }

		
--          1.3.6.1.4.1.37950.1.1.5.12.4.2.2.1.3
-- 1.3.6.1.4.1.37950.1.1.5.12.4.2.2.1.3
-- 1.3.6.1.4.1.37950.1.1.5.12.4.2.2.1.3
-- 1.3.6.1.4.1.37950.1.1.5.12.4.2.2.1.3
-- 1.3.6.1.4.1.37950.1.1.5.12.4.2.2.1.3
-- 1.3.6.1.4.1.37950.1.1.5.12.4.2.2.1.3
-- 1.3.6.1.4.1.37950.1.1.5.12.4.2.2.1.3
-- 1.3.6.1.4.1.37950.1.1.5.12.4.2.2.1.3
-- 1.3.6.1.4.1.37950.1.1.5.12.4.2.2.1.3
		-- 1.3.6.1.4.1.37950.1.1.5.12.4.2.2.1.3
		priPortPkgSuppressEthNoS OBJECT-TYPE
			SYNTAX INTEGER (1..255)
			MAX-ACCESS read-write
			STATUS current
			DESCRIPTION
				"Description."
			::= { priPortPkgSuppressEntry 3 }

		
--          1.3.6.1.4.1.37950.1.1.5.12.4.2.2.1.4
-- 1.3.6.1.4.1.37950.1.1.5.12.4.2.2.1.4
-- 1.3.6.1.4.1.37950.1.1.5.12.4.2.2.1.4
-- 1.3.6.1.4.1.37950.1.1.5.12.4.2.2.1.4
-- 1.3.6.1.4.1.37950.1.1.5.12.4.2.2.1.4
-- 1.3.6.1.4.1.37950.1.1.5.12.4.2.2.1.4
-- 1.3.6.1.4.1.37950.1.1.5.12.4.2.2.1.4
-- 1.3.6.1.4.1.37950.1.1.5.12.4.2.2.1.4
-- 1.3.6.1.4.1.37950.1.1.5.12.4.2.2.1.4
		-- 1.3.6.1.4.1.37950.1.1.5.12.4.2.2.1.4
		priPortPkgSuppressBroadcastS OBJECT-TYPE
			SYNTAX INTEGER (0..1024000)
			MAX-ACCESS read-write
			STATUS current
			DESCRIPTION
				"Description."
			::= { priPortPkgSuppressEntry 4 }

		
--          1.3.6.1.4.1.37950.1.1.5.12.4.2.2.1.5
-- 1.3.6.1.4.1.37950.1.1.5.12.4.2.2.1.5
-- 1.3.6.1.4.1.37950.1.1.5.12.4.2.2.1.5
-- 1.3.6.1.4.1.37950.1.1.5.12.4.2.2.1.5
-- 1.3.6.1.4.1.37950.1.1.5.12.4.2.2.1.5
-- 1.3.6.1.4.1.37950.1.1.5.12.4.2.2.1.5
-- 1.3.6.1.4.1.37950.1.1.5.12.4.2.2.1.5
-- 1.3.6.1.4.1.37950.1.1.5.12.4.2.2.1.5
-- 1.3.6.1.4.1.37950.1.1.5.12.4.2.2.1.5
		-- 1.3.6.1.4.1.37950.1.1.5.12.4.2.2.1.5
		priPortPkgSuppressMulticastS OBJECT-TYPE
			SYNTAX INTEGER (0..1024000)
			MAX-ACCESS read-write
			STATUS current
			DESCRIPTION
				"Description."
			::= { priPortPkgSuppressEntry 5 }

		
--          1.3.6.1.4.1.37950.1.1.5.12.4.2.2.1.6
-- 1.3.6.1.4.1.37950.1.1.5.12.4.2.2.1.6
-- 1.3.6.1.4.1.37950.1.1.5.12.4.2.2.1.6
-- 1.3.6.1.4.1.37950.1.1.5.12.4.2.2.1.6
-- 1.3.6.1.4.1.37950.1.1.5.12.4.2.2.1.6
-- 1.3.6.1.4.1.37950.1.1.5.12.4.2.2.1.6
-- 1.3.6.1.4.1.37950.1.1.5.12.4.2.2.1.6
-- 1.3.6.1.4.1.37950.1.1.5.12.4.2.2.1.6
-- 1.3.6.1.4.1.37950.1.1.5.12.4.2.2.1.6
		-- 1.3.6.1.4.1.37950.1.1.5.12.4.2.2.1.6
		priPortPkgSuppressUnkownS OBJECT-TYPE
			SYNTAX INTEGER (0..1024000)
			MAX-ACCESS read-write
			STATUS current
			DESCRIPTION
				"Description."
			::= { priPortPkgSuppressEntry 6 }

		
--          1.3.6.1.4.1.37950.1.1.5.12.4.2.3
-- 1.3.6.1.4.1.37950.1.1.5.12.4.2.3
-- 1.3.6.1.4.1.37950.1.1.5.12.4.2.3
-- 1.3.6.1.4.1.37950.1.1.5.12.4.2.3
-- 1.3.6.1.4.1.37950.1.1.5.12.4.2.3
-- 1.3.6.1.4.1.37950.1.1.5.12.4.2.3
-- 1.3.6.1.4.1.37950.1.1.5.12.4.2.3
-- 1.3.6.1.4.1.37950.1.1.5.12.4.2.3
-- 1.3.6.1.4.1.37950.1.1.5.12.4.2.3
		-- 1.3.6.1.4.1.37950.1.1.5.12.4.2.3
		priPortModeControlTable OBJECT-TYPE
			SYNTAX SEQUENCE OF PriPortModeControlEntry
			MAX-ACCESS not-accessible
			STATUS current
			DESCRIPTION
				"Description."
			::= { onuPriPortInfo 3 }

		
--          1.3.6.1.4.1.37950.1.1.5.12.4.2.3.1
-- 1.3.6.1.4.1.37950.1.1.5.12.4.2.3.1
-- 1.3.6.1.4.1.37950.1.1.5.12.4.2.3.1
-- 1.3.6.1.4.1.37950.1.1.5.12.4.2.3.1
-- 1.3.6.1.4.1.37950.1.1.5.12.4.2.3.1
-- 1.3.6.1.4.1.37950.1.1.5.12.4.2.3.1
-- 1.3.6.1.4.1.37950.1.1.5.12.4.2.3.1
-- 1.3.6.1.4.1.37950.1.1.5.12.4.2.3.1
-- 1.3.6.1.4.1.37950.1.1.5.12.4.2.3.1
		-- 1.3.6.1.4.1.37950.1.1.5.12.4.2.3.1
		priPortModeControlEntry OBJECT-TYPE
			SYNTAX PriPortModeControlEntry
			MAX-ACCESS not-accessible
			STATUS current
			DESCRIPTION
				"Description."
			INDEX { priPortModeControlPonS, priPortModeControlOnuS, priPortModeControlEthNoS }
			::= { priPortModeControlTable 1 }

		
		PriPortModeControlEntry ::=
			SEQUENCE { 
				priPortModeControlPonS
					INTEGER,
				priPortModeControlOnuS
					INTEGER,
				priPortModeControlEthNoS
					Integer32,
				priPortModeControlS
					INTEGER
			 }

--          1.3.6.1.4.1.37950.1.1.5.12.4.2.3.1.1
-- 1.3.6.1.4.1.37950.1.1.5.12.4.2.3.1.1
-- 1.3.6.1.4.1.37950.1.1.5.12.4.2.3.1.1
-- 1.3.6.1.4.1.37950.1.1.5.12.4.2.3.1.1
-- 1.3.6.1.4.1.37950.1.1.5.12.4.2.3.1.1
-- 1.3.6.1.4.1.37950.1.1.5.12.4.2.3.1.1
-- 1.3.6.1.4.1.37950.1.1.5.12.4.2.3.1.1
-- 1.3.6.1.4.1.37950.1.1.5.12.4.2.3.1.1
-- 1.3.6.1.4.1.37950.1.1.5.12.4.2.3.1.1
		-- 1.3.6.1.4.1.37950.1.1.5.12.4.2.3.1.1
		priPortModeControlPonS OBJECT-TYPE
			SYNTAX INTEGER (1..16)
			MAX-ACCESS read-write
			STATUS current
			DESCRIPTION
				"Description."
			::= { priPortModeControlEntry 1 }

		
--          1.3.6.1.4.1.37950.1.1.5.12.4.2.3.1.2
-- 1.3.6.1.4.1.37950.1.1.5.12.4.2.3.1.2
-- 1.3.6.1.4.1.37950.1.1.5.12.4.2.3.1.2
-- 1.3.6.1.4.1.37950.1.1.5.12.4.2.3.1.2
-- 1.3.6.1.4.1.37950.1.1.5.12.4.2.3.1.2
-- 1.3.6.1.4.1.37950.1.1.5.12.4.2.3.1.2
-- 1.3.6.1.4.1.37950.1.1.5.12.4.2.3.1.2
-- 1.3.6.1.4.1.37950.1.1.5.12.4.2.3.1.2
-- 1.3.6.1.4.1.37950.1.1.5.12.4.2.3.1.2
		-- 1.3.6.1.4.1.37950.1.1.5.12.4.2.3.1.2
		priPortModeControlOnuS OBJECT-TYPE
			SYNTAX INTEGER (1..65535)
			MAX-ACCESS read-write
			STATUS current
			DESCRIPTION
				"Description."
			::= { priPortModeControlEntry 2 }

		
--          1.3.6.1.4.1.37950.1.1.5.12.4.2.3.1.3
-- 1.3.6.1.4.1.37950.1.1.5.12.4.2.3.1.3
-- 1.3.6.1.4.1.37950.1.1.5.12.4.2.3.1.3
-- 1.3.6.1.4.1.37950.1.1.5.12.4.2.3.1.3
-- 1.3.6.1.4.1.37950.1.1.5.12.4.2.3.1.3
-- 1.3.6.1.4.1.37950.1.1.5.12.4.2.3.1.3
-- 1.3.6.1.4.1.37950.1.1.5.12.4.2.3.1.3
-- 1.3.6.1.4.1.37950.1.1.5.12.4.2.3.1.3
-- 1.3.6.1.4.1.37950.1.1.5.12.4.2.3.1.3
		-- 1.3.6.1.4.1.37950.1.1.5.12.4.2.3.1.3
		priPortModeControlEthNoS OBJECT-TYPE
			SYNTAX Integer32
			MAX-ACCESS read-write
			STATUS current
			DESCRIPTION
				"Description."
			::= { priPortModeControlEntry 3 }

		
--          1.3.6.1.4.1.37950.1.1.5.12.4.2.3.1.4
-- 1.3.6.1.4.1.37950.1.1.5.12.4.2.3.1.4
-- 1.3.6.1.4.1.37950.1.1.5.12.4.2.3.1.4
-- 1.3.6.1.4.1.37950.1.1.5.12.4.2.3.1.4
-- 1.3.6.1.4.1.37950.1.1.5.12.4.2.3.1.4
-- 1.3.6.1.4.1.37950.1.1.5.12.4.2.3.1.4
-- 1.3.6.1.4.1.37950.1.1.5.12.4.2.3.1.4
-- 1.3.6.1.4.1.37950.1.1.5.12.4.2.3.1.4
-- 1.3.6.1.4.1.37950.1.1.5.12.4.2.3.1.4
		-- 1.3.6.1.4.1.37950.1.1.5.12.4.2.3.1.4
		priPortModeControlS OBJECT-TYPE
			SYNTAX INTEGER
				{
				s10hd(1),
				s10fd(2),
				s100hd(3),
				s100fd(4),
				s1000hd(5),
				s1000fd(6),
				s10000fd(7)
				}
			MAX-ACCESS read-write
			STATUS current
			DESCRIPTION
				"Description."
			::= { priPortModeControlEntry 4 }

		
--          1.3.6.1.4.1.37950.1.1.5.12.4.2.4
-- 1.3.6.1.4.1.37950.1.1.5.12.4.2.4
-- 1.3.6.1.4.1.37950.1.1.5.12.4.2.4
-- 1.3.6.1.4.1.37950.1.1.5.12.4.2.4
-- 1.3.6.1.4.1.37950.1.1.5.12.4.2.4
-- 1.3.6.1.4.1.37950.1.1.5.12.4.2.4
-- 1.3.6.1.4.1.37950.1.1.5.12.4.2.4
-- 1.3.6.1.4.1.37950.1.1.5.12.4.2.4
-- 1.3.6.1.4.1.37950.1.1.5.12.4.2.4
		-- 1.3.6.1.4.1.37950.1.1.5.12.4.2.4
		priPortModeStatusTable OBJECT-TYPE
			SYNTAX SEQUENCE OF PriPortModeStatusEntry
			MAX-ACCESS not-accessible
			STATUS current
			DESCRIPTION
				"Description."
			::= { onuPriPortInfo 4 }

		
--          1.3.6.1.4.1.37950.1.1.5.12.4.2.4.1
-- 1.3.6.1.4.1.37950.1.1.5.12.4.2.4.1
-- 1.3.6.1.4.1.37950.1.1.5.12.4.2.4.1
-- 1.3.6.1.4.1.37950.1.1.5.12.4.2.4.1
-- 1.3.6.1.4.1.37950.1.1.5.12.4.2.4.1
-- 1.3.6.1.4.1.37950.1.1.5.12.4.2.4.1
-- 1.3.6.1.4.1.37950.1.1.5.12.4.2.4.1
-- 1.3.6.1.4.1.37950.1.1.5.12.4.2.4.1
-- 1.3.6.1.4.1.37950.1.1.5.12.4.2.4.1
		-- 1.3.6.1.4.1.37950.1.1.5.12.4.2.4.1
		priPortModeStatusEntry OBJECT-TYPE
			SYNTAX PriPortModeStatusEntry
			MAX-ACCESS not-accessible
			STATUS current
			DESCRIPTION
				"Description."
			INDEX { priPortModeStatusPonS, priPortModeStatusOnuS, priPortModeStatusEthNoS }
			::= { priPortModeStatusTable 1 }

		
		PriPortModeStatusEntry ::=
			SEQUENCE { 
				priPortModeStatusPonS
					INTEGER,
				priPortModeStatusOnuS
					INTEGER,
				priPortModeStatusEthNoS
					Integer32,
				priPortModeStatusS
					INTEGER
			 }

--          1.3.6.1.4.1.37950.1.1.5.12.4.2.4.1.1
-- 1.3.6.1.4.1.37950.1.1.5.12.4.2.4.1.1
-- 1.3.6.1.4.1.37950.1.1.5.12.4.2.4.1.1
-- 1.3.6.1.4.1.37950.1.1.5.12.4.2.4.1.1
-- 1.3.6.1.4.1.37950.1.1.5.12.4.2.4.1.1
-- 1.3.6.1.4.1.37950.1.1.5.12.4.2.4.1.1
-- 1.3.6.1.4.1.37950.1.1.5.12.4.2.4.1.1
-- 1.3.6.1.4.1.37950.1.1.5.12.4.2.4.1.1
-- 1.3.6.1.4.1.37950.1.1.5.12.4.2.4.1.1
		-- 1.3.6.1.4.1.37950.1.1.5.12.4.2.4.1.1
		priPortModeStatusPonS OBJECT-TYPE
			SYNTAX INTEGER (1..16)
			MAX-ACCESS read-write
			STATUS current
			DESCRIPTION
				"Description."
			::= { priPortModeStatusEntry 1 }

		
--          1.3.6.1.4.1.37950.1.1.5.12.4.2.4.1.2
-- 1.3.6.1.4.1.37950.1.1.5.12.4.2.4.1.2
-- 1.3.6.1.4.1.37950.1.1.5.12.4.2.4.1.2
-- 1.3.6.1.4.1.37950.1.1.5.12.4.2.4.1.2
-- 1.3.6.1.4.1.37950.1.1.5.12.4.2.4.1.2
-- 1.3.6.1.4.1.37950.1.1.5.12.4.2.4.1.2
-- 1.3.6.1.4.1.37950.1.1.5.12.4.2.4.1.2
-- 1.3.6.1.4.1.37950.1.1.5.12.4.2.4.1.2
-- 1.3.6.1.4.1.37950.1.1.5.12.4.2.4.1.2
		-- 1.3.6.1.4.1.37950.1.1.5.12.4.2.4.1.2
		priPortModeStatusOnuS OBJECT-TYPE
			SYNTAX INTEGER (1..65535)
			MAX-ACCESS read-write
			STATUS current
			DESCRIPTION
				"Description."
			::= { priPortModeStatusEntry 2 }

		
--          1.3.6.1.4.1.37950.1.1.5.12.4.2.4.1.3
-- 1.3.6.1.4.1.37950.1.1.5.12.4.2.4.1.3
-- 1.3.6.1.4.1.37950.1.1.5.12.4.2.4.1.3
-- 1.3.6.1.4.1.37950.1.1.5.12.4.2.4.1.3
-- 1.3.6.1.4.1.37950.1.1.5.12.4.2.4.1.3
-- 1.3.6.1.4.1.37950.1.1.5.12.4.2.4.1.3
-- 1.3.6.1.4.1.37950.1.1.5.12.4.2.4.1.3
-- 1.3.6.1.4.1.37950.1.1.5.12.4.2.4.1.3
-- 1.3.6.1.4.1.37950.1.1.5.12.4.2.4.1.3
		-- 1.3.6.1.4.1.37950.1.1.5.12.4.2.4.1.3
		priPortModeStatusEthNoS OBJECT-TYPE
			SYNTAX Integer32
			MAX-ACCESS read-write
			STATUS current
			DESCRIPTION
				"Description."
			::= { priPortModeStatusEntry 3 }

		
--          1.3.6.1.4.1.37950.1.1.5.12.4.2.4.1.4
-- 1.3.6.1.4.1.37950.1.1.5.12.4.2.4.1.4
-- 1.3.6.1.4.1.37950.1.1.5.12.4.2.4.1.4
-- 1.3.6.1.4.1.37950.1.1.5.12.4.2.4.1.4
-- 1.3.6.1.4.1.37950.1.1.5.12.4.2.4.1.4
-- 1.3.6.1.4.1.37950.1.1.5.12.4.2.4.1.4
-- 1.3.6.1.4.1.37950.1.1.5.12.4.2.4.1.4
-- 1.3.6.1.4.1.37950.1.1.5.12.4.2.4.1.4
-- 1.3.6.1.4.1.37950.1.1.5.12.4.2.4.1.4
		-- 1.3.6.1.4.1.37950.1.1.5.12.4.2.4.1.4
		priPortModeStatusS OBJECT-TYPE
			SYNTAX INTEGER
				{
				s10hd(1),
				s10fd(2),
				s100hd(3),
				s100fd(4),
				s1000hd(5),
				s1000fd(6),
				s10000fd(7)
				}
			MAX-ACCESS read-write
			STATUS current
			DESCRIPTION
				"Description."
			::= { priPortModeStatusEntry 4 }

		
--          1.3.6.1.4.1.37950.1.1.5.12.4.2.5
-- 1.3.6.1.4.1.37950.1.1.5.12.4.2.5
-- 1.3.6.1.4.1.37950.1.1.5.12.4.2.5
-- 1.3.6.1.4.1.37950.1.1.5.12.4.2.5
-- 1.3.6.1.4.1.37950.1.1.5.12.4.2.5
-- 1.3.6.1.4.1.37950.1.1.5.12.4.2.5
-- 1.3.6.1.4.1.37950.1.1.5.12.4.2.5
-- 1.3.6.1.4.1.37950.1.1.5.12.4.2.5
-- 1.3.6.1.4.1.37950.1.1.5.12.4.2.5
		-- 1.3.6.1.4.1.37950.1.1.5.12.4.2.5
		priPotsParameterTable OBJECT-TYPE
			SYNTAX SEQUENCE OF PriPotsParameterEntry
			MAX-ACCESS not-accessible
			STATUS current
			DESCRIPTION
				"Description."
			::= { onuPriPortInfo 5 }

		
--          1.3.6.1.4.1.37950.1.1.5.12.4.2.5.1
-- 1.3.6.1.4.1.37950.1.1.5.12.4.2.5.1
-- 1.3.6.1.4.1.37950.1.1.5.12.4.2.5.1
-- 1.3.6.1.4.1.37950.1.1.5.12.4.2.5.1
-- 1.3.6.1.4.1.37950.1.1.5.12.4.2.5.1
-- 1.3.6.1.4.1.37950.1.1.5.12.4.2.5.1
-- 1.3.6.1.4.1.37950.1.1.5.12.4.2.5.1
-- 1.3.6.1.4.1.37950.1.1.5.12.4.2.5.1
-- 1.3.6.1.4.1.37950.1.1.5.12.4.2.5.1
		-- 1.3.6.1.4.1.37950.1.1.5.12.4.2.5.1
		priPotsParameterEntry OBJECT-TYPE
			SYNTAX PriPotsParameterEntry
			MAX-ACCESS not-accessible
			STATUS current
			DESCRIPTION
				"Description."
			INDEX { priPortPtPonS, priPortPtOnuS, priPortPtPotsNoS }
			::= { priPotsParameterTable 1 }

		
		PriPotsParameterEntry ::=
			SEQUENCE { 
				priPortPtPonS
					Integer32,
				priPortPtOnuS
					Integer32,
				priPortPtPotsNoS
					Integer32,
				priPortPtVarS
					INTEGER,
				priPortPtEchoCancleS
					INTEGER,
				priPotsPtInputGainS
					Integer32,
				priPotsPtOutputGainS
					Integer32,
				priPotsPtDtmfModeS
					INTEGER
			 }

--          1.3.6.1.4.1.37950.1.1.5.12.4.2.5.1.1
-- 1.3.6.1.4.1.37950.1.1.5.12.4.2.5.1.1
-- 1.3.6.1.4.1.37950.1.1.5.12.4.2.5.1.1
-- 1.3.6.1.4.1.37950.1.1.5.12.4.2.5.1.1
-- 1.3.6.1.4.1.37950.1.1.5.12.4.2.5.1.1
-- 1.3.6.1.4.1.37950.1.1.5.12.4.2.5.1.1
-- 1.3.6.1.4.1.37950.1.1.5.12.4.2.5.1.1
-- 1.3.6.1.4.1.37950.1.1.5.12.4.2.5.1.1
-- 1.3.6.1.4.1.37950.1.1.5.12.4.2.5.1.1
		-- 1.3.6.1.4.1.37950.1.1.5.12.4.2.5.1.1
		priPortPtPonS OBJECT-TYPE
			SYNTAX Integer32 (1..16)
			MAX-ACCESS read-write
			STATUS current
			DESCRIPTION
				"Description."
			::= { priPotsParameterEntry 1 }

		
--          1.3.6.1.4.1.37950.1.1.5.12.4.2.5.1.2
-- 1.3.6.1.4.1.37950.1.1.5.12.4.2.5.1.2
-- 1.3.6.1.4.1.37950.1.1.5.12.4.2.5.1.2
-- 1.3.6.1.4.1.37950.1.1.5.12.4.2.5.1.2
-- 1.3.6.1.4.1.37950.1.1.5.12.4.2.5.1.2
-- 1.3.6.1.4.1.37950.1.1.5.12.4.2.5.1.2
-- 1.3.6.1.4.1.37950.1.1.5.12.4.2.5.1.2
-- 1.3.6.1.4.1.37950.1.1.5.12.4.2.5.1.2
-- 1.3.6.1.4.1.37950.1.1.5.12.4.2.5.1.2
		-- 1.3.6.1.4.1.37950.1.1.5.12.4.2.5.1.2
		priPortPtOnuS OBJECT-TYPE
			SYNTAX Integer32 (1..65535)
			MAX-ACCESS read-write
			STATUS current
			DESCRIPTION
				"Description."
			::= { priPotsParameterEntry 2 }

		
--          1.3.6.1.4.1.37950.1.1.5.12.4.2.5.1.3
-- 1.3.6.1.4.1.37950.1.1.5.12.4.2.5.1.3
-- 1.3.6.1.4.1.37950.1.1.5.12.4.2.5.1.3
-- 1.3.6.1.4.1.37950.1.1.5.12.4.2.5.1.3
-- 1.3.6.1.4.1.37950.1.1.5.12.4.2.5.1.3
-- 1.3.6.1.4.1.37950.1.1.5.12.4.2.5.1.3
-- 1.3.6.1.4.1.37950.1.1.5.12.4.2.5.1.3
-- 1.3.6.1.4.1.37950.1.1.5.12.4.2.5.1.3
-- 1.3.6.1.4.1.37950.1.1.5.12.4.2.5.1.3
		-- 1.3.6.1.4.1.37950.1.1.5.12.4.2.5.1.3
		priPortPtPotsNoS OBJECT-TYPE
			SYNTAX Integer32 (1..255)
			MAX-ACCESS read-write
			STATUS current
			DESCRIPTION
				"Description."
			::= { priPotsParameterEntry 3 }

		
--          1.3.6.1.4.1.37950.1.1.5.12.4.2.5.1.4
-- 1.3.6.1.4.1.37950.1.1.5.12.4.2.5.1.4
-- 1.3.6.1.4.1.37950.1.1.5.12.4.2.5.1.4
-- 1.3.6.1.4.1.37950.1.1.5.12.4.2.5.1.4
-- 1.3.6.1.4.1.37950.1.1.5.12.4.2.5.1.4
-- 1.3.6.1.4.1.37950.1.1.5.12.4.2.5.1.4
-- 1.3.6.1.4.1.37950.1.1.5.12.4.2.5.1.4
-- 1.3.6.1.4.1.37950.1.1.5.12.4.2.5.1.4
-- 1.3.6.1.4.1.37950.1.1.5.12.4.2.5.1.4
		-- 1.3.6.1.4.1.37950.1.1.5.12.4.2.5.1.4
		priPortPtVarS OBJECT-TYPE
			SYNTAX INTEGER
				{
				disable(0),
				enable(1)
				}
			MAX-ACCESS read-write
			STATUS current
			DESCRIPTION
				"Description."
			::= { priPotsParameterEntry 4 }

		
--          1.3.6.1.4.1.37950.1.1.5.12.4.2.5.1.5
-- 1.3.6.1.4.1.37950.1.1.5.12.4.2.5.1.5
-- 1.3.6.1.4.1.37950.1.1.5.12.4.2.5.1.5
-- 1.3.6.1.4.1.37950.1.1.5.12.4.2.5.1.5
-- 1.3.6.1.4.1.37950.1.1.5.12.4.2.5.1.5
-- 1.3.6.1.4.1.37950.1.1.5.12.4.2.5.1.5
-- 1.3.6.1.4.1.37950.1.1.5.12.4.2.5.1.5
-- 1.3.6.1.4.1.37950.1.1.5.12.4.2.5.1.5
-- 1.3.6.1.4.1.37950.1.1.5.12.4.2.5.1.5
		-- 1.3.6.1.4.1.37950.1.1.5.12.4.2.5.1.5
		priPortPtEchoCancleS OBJECT-TYPE
			SYNTAX INTEGER
				{
				disable(0),
				enable(1)
				}
			MAX-ACCESS read-write
			STATUS current
			DESCRIPTION
				"Description."
			::= { priPotsParameterEntry 5 }

		
--          1.3.6.1.4.1.37950.1.1.5.12.4.2.5.1.6
-- 1.3.6.1.4.1.37950.1.1.5.12.4.2.5.1.6
-- 1.3.6.1.4.1.37950.1.1.5.12.4.2.5.1.6
-- 1.3.6.1.4.1.37950.1.1.5.12.4.2.5.1.6
-- 1.3.6.1.4.1.37950.1.1.5.12.4.2.5.1.6
-- 1.3.6.1.4.1.37950.1.1.5.12.4.2.5.1.6
-- 1.3.6.1.4.1.37950.1.1.5.12.4.2.5.1.6
-- 1.3.6.1.4.1.37950.1.1.5.12.4.2.5.1.6
-- 1.3.6.1.4.1.37950.1.1.5.12.4.2.5.1.6
		-- 1.3.6.1.4.1.37950.1.1.5.12.4.2.5.1.6
		priPotsPtInputGainS OBJECT-TYPE
			SYNTAX Integer32 (-32..32)
			MAX-ACCESS read-write
			STATUS current
			DESCRIPTION
				"Description."
			::= { priPotsParameterEntry 6 }

		
--          1.3.6.1.4.1.37950.1.1.5.12.4.2.5.1.7
-- 1.3.6.1.4.1.37950.1.1.5.12.4.2.5.1.7
-- 1.3.6.1.4.1.37950.1.1.5.12.4.2.5.1.7
-- 1.3.6.1.4.1.37950.1.1.5.12.4.2.5.1.7
-- 1.3.6.1.4.1.37950.1.1.5.12.4.2.5.1.7
-- 1.3.6.1.4.1.37950.1.1.5.12.4.2.5.1.7
-- 1.3.6.1.4.1.37950.1.1.5.12.4.2.5.1.7
-- 1.3.6.1.4.1.37950.1.1.5.12.4.2.5.1.7
-- 1.3.6.1.4.1.37950.1.1.5.12.4.2.5.1.7
		-- 1.3.6.1.4.1.37950.1.1.5.12.4.2.5.1.7
		priPotsPtOutputGainS OBJECT-TYPE
			SYNTAX Integer32 (-32..32)
			MAX-ACCESS read-write
			STATUS current
			DESCRIPTION
				"Description."
			::= { priPotsParameterEntry 7 }

		
--          1.3.6.1.4.1.37950.1.1.5.12.4.2.5.1.8
-- 1.3.6.1.4.1.37950.1.1.5.12.4.2.5.1.8
-- 1.3.6.1.4.1.37950.1.1.5.12.4.2.5.1.8
-- 1.3.6.1.4.1.37950.1.1.5.12.4.2.5.1.8
-- 1.3.6.1.4.1.37950.1.1.5.12.4.2.5.1.8
-- 1.3.6.1.4.1.37950.1.1.5.12.4.2.5.1.8
-- 1.3.6.1.4.1.37950.1.1.5.12.4.2.5.1.8
-- 1.3.6.1.4.1.37950.1.1.5.12.4.2.5.1.8
-- 1.3.6.1.4.1.37950.1.1.5.12.4.2.5.1.8
		-- 1.3.6.1.4.1.37950.1.1.5.12.4.2.5.1.8
		priPotsPtDtmfModeS OBJECT-TYPE
			SYNTAX INTEGER
				{
				transparent(0),
				rfc2833(1),
				rfc2833-redundancy(2),
				outband(3)
				}
			MAX-ACCESS read-write
			STATUS current
			DESCRIPTION
				"Description."
			::= { priPotsParameterEntry 8 }

		
--         1.3.6.1.4.1.37950.1.1.5.12.4.2.6
-- 1.3.6.1.4.1.37950.1.1.5.12.4.2.6
-- 1.3.6.1.4.1.37950.1.1.5.12.4.2.6
-- 1.3.6.1.4.1.37950.1.1.5.12.4.2.6
-- 1.3.6.1.4.1.37950.1.1.5.12.4.2.6
-- 1.3.6.1.4.1.37950.1.1.5.12.4.2.6
-- 1.3.6.1.4.1.37950.1.1.5.12.4.2.6
-- 1.3.6.1.4.1.37950.1.1.5.12.4.2.6
		-- 1.3.6.1.4.1.37950.1.1.5.12.4.2.6
		priPortMacTable OBJECT-TYPE
			SYNTAX SEQUENCE OF PriPortMacEntry
			MAX-ACCESS not-accessible
			STATUS current
			DESCRIPTION
				"Description."
			::= { onuPriPortInfo 6 }

		
--         1.3.6.1.4.1.37950.1.1.5.12.4.2.6.1
-- 1.3.6.1.4.1.37950.1.1.5.12.4.2.6.1
-- 1.3.6.1.4.1.37950.1.1.5.12.4.2.6.1
-- 1.3.6.1.4.1.37950.1.1.5.12.4.2.6.1
-- 1.3.6.1.4.1.37950.1.1.5.12.4.2.6.1
-- 1.3.6.1.4.1.37950.1.1.5.12.4.2.6.1
-- 1.3.6.1.4.1.37950.1.1.5.12.4.2.6.1
-- 1.3.6.1.4.1.37950.1.1.5.12.4.2.6.1
		-- 1.3.6.1.4.1.37950.1.1.5.12.4.2.6.1
		priPortMacEntry OBJECT-TYPE
			SYNTAX PriPortMacEntry
			MAX-ACCESS not-accessible
			STATUS current
			DESCRIPTION
				"Description."
			INDEX { priPortMacPonS, priPortMacOnuS, priPortMacEthNoS, priPortMacIndex }
			::= { priPortMacTable 1 }

		
		PriPortMacEntry ::=
			SEQUENCE { 
				priPortMacPonS
					INTEGER,
				priPortMacOnuS
					INTEGER,
				priPortMacEthNoS
					INTEGER,
				priPortMacIndex
					INTEGER,
				learningMacNumber
					INTEGER,
				reportMacNumber
					INTEGER,
				priPortMacAddr
					OCTET STRING,
				priPortMacVlan
					INTEGER
			 }

--         1.3.6.1.4.1.37950.1.1.5.12.4.2.6.1.1
-- 1.3.6.1.4.1.37950.1.1.5.12.4.2.6.1.1
-- 1.3.6.1.4.1.37950.1.1.5.12.4.2.6.1.1
-- 1.3.6.1.4.1.37950.1.1.5.12.4.2.6.1.1
-- 1.3.6.1.4.1.37950.1.1.5.12.4.2.6.1.1
-- 1.3.6.1.4.1.37950.1.1.5.12.4.2.6.1.1
-- 1.3.6.1.4.1.37950.1.1.5.12.4.2.6.1.1
-- 1.3.6.1.4.1.37950.1.1.5.12.4.2.6.1.1
		-- 1.3.6.1.4.1.37950.1.1.5.12.4.2.6.1.1
		priPortMacPonS OBJECT-TYPE
			SYNTAX INTEGER
			MAX-ACCESS read-write
			STATUS current
			DESCRIPTION
				"Description."
			::= { priPortMacEntry 1 }

		
--         1.3.6.1.4.1.37950.1.1.5.12.4.2.6.1.2
-- 1.3.6.1.4.1.37950.1.1.5.12.4.2.6.1.2
-- 1.3.6.1.4.1.37950.1.1.5.12.4.2.6.1.2
-- 1.3.6.1.4.1.37950.1.1.5.12.4.2.6.1.2
-- 1.3.6.1.4.1.37950.1.1.5.12.4.2.6.1.2
-- 1.3.6.1.4.1.37950.1.1.5.12.4.2.6.1.2
-- 1.3.6.1.4.1.37950.1.1.5.12.4.2.6.1.2
-- 1.3.6.1.4.1.37950.1.1.5.12.4.2.6.1.2
		-- 1.3.6.1.4.1.37950.1.1.5.12.4.2.6.1.2
		priPortMacOnuS OBJECT-TYPE
			SYNTAX INTEGER
			MAX-ACCESS read-write
			STATUS current
			DESCRIPTION
				"Description."
			::= { priPortMacEntry 2 }

		
--         1.3.6.1.4.1.37950.1.1.5.12.4.2.6.1.3
-- 1.3.6.1.4.1.37950.1.1.5.12.4.2.6.1.3
-- 1.3.6.1.4.1.37950.1.1.5.12.4.2.6.1.3
-- 1.3.6.1.4.1.37950.1.1.5.12.4.2.6.1.3
-- 1.3.6.1.4.1.37950.1.1.5.12.4.2.6.1.3
-- 1.3.6.1.4.1.37950.1.1.5.12.4.2.6.1.3
-- 1.3.6.1.4.1.37950.1.1.5.12.4.2.6.1.3
-- 1.3.6.1.4.1.37950.1.1.5.12.4.2.6.1.3
		-- 1.3.6.1.4.1.37950.1.1.5.12.4.2.6.1.3
		priPortMacEthNoS OBJECT-TYPE
			SYNTAX INTEGER
			MAX-ACCESS read-write
			STATUS current
			DESCRIPTION
				"Description."
			::= { priPortMacEntry 3 }

		
--         1.3.6.1.4.1.37950.1.1.5.12.4.2.6.1.4
-- 1.3.6.1.4.1.37950.1.1.5.12.4.2.6.1.4
-- 1.3.6.1.4.1.37950.1.1.5.12.4.2.6.1.4
-- 1.3.6.1.4.1.37950.1.1.5.12.4.2.6.1.4
-- 1.3.6.1.4.1.37950.1.1.5.12.4.2.6.1.4
-- 1.3.6.1.4.1.37950.1.1.5.12.4.2.6.1.4
-- 1.3.6.1.4.1.37950.1.1.5.12.4.2.6.1.4
-- 1.3.6.1.4.1.37950.1.1.5.12.4.2.6.1.4
		-- 1.3.6.1.4.1.37950.1.1.5.12.4.2.6.1.4
		priPortMacIndex OBJECT-TYPE
			SYNTAX INTEGER
			MAX-ACCESS read-write
			STATUS current
			DESCRIPTION
				"Description."
			::= { priPortMacEntry 4 }

		
--         1.3.6.1.4.1.37950.1.1.5.12.4.2.6.1.5
-- 1.3.6.1.4.1.37950.1.1.5.12.4.2.6.1.5
-- 1.3.6.1.4.1.37950.1.1.5.12.4.2.6.1.5
-- 1.3.6.1.4.1.37950.1.1.5.12.4.2.6.1.5
-- 1.3.6.1.4.1.37950.1.1.5.12.4.2.6.1.5
-- 1.3.6.1.4.1.37950.1.1.5.12.4.2.6.1.5
-- 1.3.6.1.4.1.37950.1.1.5.12.4.2.6.1.5
-- 1.3.6.1.4.1.37950.1.1.5.12.4.2.6.1.5
		-- 1.3.6.1.4.1.37950.1.1.5.12.4.2.6.1.5
		learningMacNumber OBJECT-TYPE
			SYNTAX INTEGER
			MAX-ACCESS read-write
			STATUS current
			DESCRIPTION
				"Description."
			::= { priPortMacEntry 5 }

		
--         1.3.6.1.4.1.37950.1.1.5.12.4.2.6.1.6
-- 1.3.6.1.4.1.37950.1.1.5.12.4.2.6.1.6
-- 1.3.6.1.4.1.37950.1.1.5.12.4.2.6.1.6
-- 1.3.6.1.4.1.37950.1.1.5.12.4.2.6.1.6
-- 1.3.6.1.4.1.37950.1.1.5.12.4.2.6.1.6
-- 1.3.6.1.4.1.37950.1.1.5.12.4.2.6.1.6
-- 1.3.6.1.4.1.37950.1.1.5.12.4.2.6.1.6
-- 1.3.6.1.4.1.37950.1.1.5.12.4.2.6.1.6
		-- 1.3.6.1.4.1.37950.1.1.5.12.4.2.6.1.6
		reportMacNumber OBJECT-TYPE
			SYNTAX INTEGER
			MAX-ACCESS read-write
			STATUS current
			DESCRIPTION
				"Description."
			::= { priPortMacEntry 6 }

		
--         1.3.6.1.4.1.37950.1.1.5.12.4.2.6.1.7
-- 1.3.6.1.4.1.37950.1.1.5.12.4.2.6.1.7
-- 1.3.6.1.4.1.37950.1.1.5.12.4.2.6.1.7
-- 1.3.6.1.4.1.37950.1.1.5.12.4.2.6.1.7
-- 1.3.6.1.4.1.37950.1.1.5.12.4.2.6.1.7
-- 1.3.6.1.4.1.37950.1.1.5.12.4.2.6.1.7
-- 1.3.6.1.4.1.37950.1.1.5.12.4.2.6.1.7
-- 1.3.6.1.4.1.37950.1.1.5.12.4.2.6.1.7
		-- 1.3.6.1.4.1.37950.1.1.5.12.4.2.6.1.7
		priPortMacAddr OBJECT-TYPE
			SYNTAX OCTET STRING
			MAX-ACCESS read-write
			STATUS current
			DESCRIPTION
				"Description."
			::= { priPortMacEntry 7 }

		
--         1.3.6.1.4.1.37950.1.1.5.12.4.2.6.1.8
-- 1.3.6.1.4.1.37950.1.1.5.12.4.2.6.1.8
-- 1.3.6.1.4.1.37950.1.1.5.12.4.2.6.1.8
-- 1.3.6.1.4.1.37950.1.1.5.12.4.2.6.1.8
-- 1.3.6.1.4.1.37950.1.1.5.12.4.2.6.1.8
-- 1.3.6.1.4.1.37950.1.1.5.12.4.2.6.1.8
-- 1.3.6.1.4.1.37950.1.1.5.12.4.2.6.1.8
-- 1.3.6.1.4.1.37950.1.1.5.12.4.2.6.1.8
		-- 1.3.6.1.4.1.37950.1.1.5.12.4.2.6.1.8
		priPortMacVlan OBJECT-TYPE
			SYNTAX INTEGER
			MAX-ACCESS read-write
			STATUS current
			DESCRIPTION
				"Description."
			::= { priPortMacEntry 8 }

		
--          1.3.6.1.4.1.37950.1.1.5.12.5
-- 1.3.6.1.4.1.37950.1.1.5.12.5
-- 1.3.6.1.4.1.37950.1.1.5.12.5
-- 1.3.6.1.4.1.37950.1.1.5.12.5
-- 1.3.6.1.4.1.37950.1.1.5.12.5
-- 1.3.6.1.4.1.37950.1.1.5.12.5
-- 1.3.6.1.4.1.37950.1.1.5.12.5
-- 1.3.6.1.4.1.37950.1.1.5.12.5
-- 1.3.6.1.4.1.37950.1.1.5.12.5
		-- 1.3.6.1.4.1.37950.1.1.5.12.5
		onuPort OBJECT IDENTIFIER ::= { v1600dOnuMgmt 5 }

		
--          1.3.6.1.4.1.37950.1.1.5.12.5.1
-- 1.3.6.1.4.1.37950.1.1.5.12.5.1
-- 1.3.6.1.4.1.37950.1.1.5.12.5.1
-- 1.3.6.1.4.1.37950.1.1.5.12.5.1
-- 1.3.6.1.4.1.37950.1.1.5.12.5.1
-- 1.3.6.1.4.1.37950.1.1.5.12.5.1
-- 1.3.6.1.4.1.37950.1.1.5.12.5.1
-- 1.3.6.1.4.1.37950.1.1.5.12.5.1
-- 1.3.6.1.4.1.37950.1.1.5.12.5.1
		-- 1.3.6.1.4.1.37950.1.1.5.12.5.1
		onuPortInfo OBJECT IDENTIFIER ::= { onuPort 1 }

		
--          1.3.6.1.4.1.37950.1.1.5.12.5.1.1
-- 1.3.6.1.4.1.37950.1.1.5.12.5.1.1
-- 1.3.6.1.4.1.37950.1.1.5.12.5.1.1
-- 1.3.6.1.4.1.37950.1.1.5.12.5.1.1
-- 1.3.6.1.4.1.37950.1.1.5.12.5.1.1
-- 1.3.6.1.4.1.37950.1.1.5.12.5.1.1
-- 1.3.6.1.4.1.37950.1.1.5.12.5.1.1
-- 1.3.6.1.4.1.37950.1.1.5.12.5.1.1
-- 1.3.6.1.4.1.37950.1.1.5.12.5.1.1
		-- 1.3.6.1.4.1.37950.1.1.5.12.5.1.1
		onuPortInfoCfg OBJECT IDENTIFIER ::= { onuPortInfo 1 }

		
--          1.3.6.1.4.1.37950.1.1.5.12.5.1.1.1
-- 1.3.6.1.4.1.37950.1.1.5.12.5.1.1.1
-- 1.3.6.1.4.1.37950.1.1.5.12.5.1.1.1
-- 1.3.6.1.4.1.37950.1.1.5.12.5.1.1.1
-- 1.3.6.1.4.1.37950.1.1.5.12.5.1.1.1
-- 1.3.6.1.4.1.37950.1.1.5.12.5.1.1.1
-- 1.3.6.1.4.1.37950.1.1.5.12.5.1.1.1
-- 1.3.6.1.4.1.37950.1.1.5.12.5.1.1.1
-- 1.3.6.1.4.1.37950.1.1.5.12.5.1.1.1
		-- 1.3.6.1.4.1.37950.1.1.5.12.5.1.1.1
		infoPonNo OBJECT-TYPE
			SYNTAX INTEGER (1..16)
			MAX-ACCESS read-write
			STATUS current
			DESCRIPTION
				"Description."
			::= { onuPortInfoCfg 1 }

		
--          1.3.6.1.4.1.37950.1.1.5.12.5.1.1.2
-- 1.3.6.1.4.1.37950.1.1.5.12.5.1.1.2
-- 1.3.6.1.4.1.37950.1.1.5.12.5.1.1.2
-- 1.3.6.1.4.1.37950.1.1.5.12.5.1.1.2
-- 1.3.6.1.4.1.37950.1.1.5.12.5.1.1.2
-- 1.3.6.1.4.1.37950.1.1.5.12.5.1.1.2
-- 1.3.6.1.4.1.37950.1.1.5.12.5.1.1.2
-- 1.3.6.1.4.1.37950.1.1.5.12.5.1.1.2
-- 1.3.6.1.4.1.37950.1.1.5.12.5.1.1.2
		-- 1.3.6.1.4.1.37950.1.1.5.12.5.1.1.2
		infoOnuNo OBJECT-TYPE
			SYNTAX INTEGER (1..65535)
			MAX-ACCESS read-write
			STATUS current
			DESCRIPTION
				"Description."
			::= { onuPortInfoCfg 2 }

		
--          1.3.6.1.4.1.37950.1.1.5.12.5.1.1.3
-- 1.3.6.1.4.1.37950.1.1.5.12.5.1.1.3
-- 1.3.6.1.4.1.37950.1.1.5.12.5.1.1.3
-- 1.3.6.1.4.1.37950.1.1.5.12.5.1.1.3
-- 1.3.6.1.4.1.37950.1.1.5.12.5.1.1.3
-- 1.3.6.1.4.1.37950.1.1.5.12.5.1.1.3
-- 1.3.6.1.4.1.37950.1.1.5.12.5.1.1.3
-- 1.3.6.1.4.1.37950.1.1.5.12.5.1.1.3
-- 1.3.6.1.4.1.37950.1.1.5.12.5.1.1.3
		-- 1.3.6.1.4.1.37950.1.1.5.12.5.1.1.3
		infoPortNo OBJECT-TYPE
			SYNTAX INTEGER (1..255)
			MAX-ACCESS read-write
			STATUS current
			DESCRIPTION
				"Description."
			::= { onuPortInfoCfg 3 }

		
--          1.3.6.1.4.1.37950.1.1.5.12.5.1.1.4
-- 1.3.6.1.4.1.37950.1.1.5.12.5.1.1.4
-- 1.3.6.1.4.1.37950.1.1.5.12.5.1.1.4
-- 1.3.6.1.4.1.37950.1.1.5.12.5.1.1.4
-- 1.3.6.1.4.1.37950.1.1.5.12.5.1.1.4
-- 1.3.6.1.4.1.37950.1.1.5.12.5.1.1.4
-- 1.3.6.1.4.1.37950.1.1.5.12.5.1.1.4
-- 1.3.6.1.4.1.37950.1.1.5.12.5.1.1.4
-- 1.3.6.1.4.1.37950.1.1.5.12.5.1.1.4
		-- 1.3.6.1.4.1.37950.1.1.5.12.5.1.1.4
		infoAction OBJECT-TYPE
			SYNTAX INTEGER { commit(1) }
			MAX-ACCESS read-write
			STATUS current
			DESCRIPTION
				"Description."
			::= { onuPortInfoCfg 4 }

		
--          1.3.6.1.4.1.37950.1.1.5.12.5.1.2
-- 1.3.6.1.4.1.37950.1.1.5.12.5.1.2
-- 1.3.6.1.4.1.37950.1.1.5.12.5.1.2
-- 1.3.6.1.4.1.37950.1.1.5.12.5.1.2
-- 1.3.6.1.4.1.37950.1.1.5.12.5.1.2
-- 1.3.6.1.4.1.37950.1.1.5.12.5.1.2
-- 1.3.6.1.4.1.37950.1.1.5.12.5.1.2
-- 1.3.6.1.4.1.37950.1.1.5.12.5.1.2
-- 1.3.6.1.4.1.37950.1.1.5.12.5.1.2
		-- 1.3.6.1.4.1.37950.1.1.5.12.5.1.2
		onuPortInfoDisplay OBJECT IDENTIFIER ::= { onuPortInfo 2 }

		
--          1.3.6.1.4.1.37950.1.1.5.12.5.1.2.1
-- 1.3.6.1.4.1.37950.1.1.5.12.5.1.2.1
-- 1.3.6.1.4.1.37950.1.1.5.12.5.1.2.1
-- 1.3.6.1.4.1.37950.1.1.5.12.5.1.2.1
-- 1.3.6.1.4.1.37950.1.1.5.12.5.1.2.1
-- 1.3.6.1.4.1.37950.1.1.5.12.5.1.2.1
-- 1.3.6.1.4.1.37950.1.1.5.12.5.1.2.1
-- 1.3.6.1.4.1.37950.1.1.5.12.5.1.2.1
-- 1.3.6.1.4.1.37950.1.1.5.12.5.1.2.1
		-- 1.3.6.1.4.1.37950.1.1.5.12.5.1.2.1
		displayPortNo OBJECT-TYPE
			SYNTAX Integer32
			MAX-ACCESS read-only
			STATUS current
			DESCRIPTION
				"Description."
			::= { onuPortInfoDisplay 1 }

		
--          1.3.6.1.4.1.37950.1.1.5.12.5.1.2.2
-- 1.3.6.1.4.1.37950.1.1.5.12.5.1.2.2
-- 1.3.6.1.4.1.37950.1.1.5.12.5.1.2.2
-- 1.3.6.1.4.1.37950.1.1.5.12.5.1.2.2
-- 1.3.6.1.4.1.37950.1.1.5.12.5.1.2.2
-- 1.3.6.1.4.1.37950.1.1.5.12.5.1.2.2
-- 1.3.6.1.4.1.37950.1.1.5.12.5.1.2.2
-- 1.3.6.1.4.1.37950.1.1.5.12.5.1.2.2
-- 1.3.6.1.4.1.37950.1.1.5.12.5.1.2.2
		-- 1.3.6.1.4.1.37950.1.1.5.12.5.1.2.2
		linkState OBJECT-TYPE
			SYNTAX INTEGER
				{
				down(0),
				up(1)
				}
			MAX-ACCESS read-only
			STATUS current
			DESCRIPTION
				"Description."
			::= { onuPortInfoDisplay 2 }

		
--          1.3.6.1.4.1.37950.1.1.5.12.5.1.2.3
-- 1.3.6.1.4.1.37950.1.1.5.12.5.1.2.3
-- 1.3.6.1.4.1.37950.1.1.5.12.5.1.2.3
-- 1.3.6.1.4.1.37950.1.1.5.12.5.1.2.3
-- 1.3.6.1.4.1.37950.1.1.5.12.5.1.2.3
-- 1.3.6.1.4.1.37950.1.1.5.12.5.1.2.3
-- 1.3.6.1.4.1.37950.1.1.5.12.5.1.2.3
-- 1.3.6.1.4.1.37950.1.1.5.12.5.1.2.3
-- 1.3.6.1.4.1.37950.1.1.5.12.5.1.2.3
		-- 1.3.6.1.4.1.37950.1.1.5.12.5.1.2.3
		flowControl OBJECT-TYPE
			SYNTAX INTEGER
				{
				disable(0),
				enable(1)
				}
			MAX-ACCESS read-write
			STATUS current
			DESCRIPTION
				"Description."
			::= { onuPortInfoDisplay 3 }

		
--          1.3.6.1.4.1.37950.1.1.5.12.5.1.2.4
-- 1.3.6.1.4.1.37950.1.1.5.12.5.1.2.4
-- 1.3.6.1.4.1.37950.1.1.5.12.5.1.2.4
-- 1.3.6.1.4.1.37950.1.1.5.12.5.1.2.4
-- 1.3.6.1.4.1.37950.1.1.5.12.5.1.2.4
-- 1.3.6.1.4.1.37950.1.1.5.12.5.1.2.4
-- 1.3.6.1.4.1.37950.1.1.5.12.5.1.2.4
-- 1.3.6.1.4.1.37950.1.1.5.12.5.1.2.4
-- 1.3.6.1.4.1.37950.1.1.5.12.5.1.2.4
		-- 1.3.6.1.4.1.37950.1.1.5.12.5.1.2.4
		policyState OBJECT-TYPE
			SYNTAX INTEGER
				{
				disable(0),
				enable(1)
				}
			MAX-ACCESS read-only
			STATUS current
			DESCRIPTION
				"Description."
			::= { onuPortInfoDisplay 4 }

		
--          1.3.6.1.4.1.37950.1.1.5.12.5.1.2.5
-- 1.3.6.1.4.1.37950.1.1.5.12.5.1.2.5
-- 1.3.6.1.4.1.37950.1.1.5.12.5.1.2.5
-- 1.3.6.1.4.1.37950.1.1.5.12.5.1.2.5
-- 1.3.6.1.4.1.37950.1.1.5.12.5.1.2.5
-- 1.3.6.1.4.1.37950.1.1.5.12.5.1.2.5
-- 1.3.6.1.4.1.37950.1.1.5.12.5.1.2.5
-- 1.3.6.1.4.1.37950.1.1.5.12.5.1.2.5
-- 1.3.6.1.4.1.37950.1.1.5.12.5.1.2.5
		-- 1.3.6.1.4.1.37950.1.1.5.12.5.1.2.5
		policyCir OBJECT-TYPE
			SYNTAX INTEGER (0..1048576)
			MAX-ACCESS read-only
			STATUS current
			DESCRIPTION
				"Description."
			::= { onuPortInfoDisplay 5 }

		
--          1.3.6.1.4.1.37950.1.1.5.12.5.1.2.6
-- 1.3.6.1.4.1.37950.1.1.5.12.5.1.2.6
-- 1.3.6.1.4.1.37950.1.1.5.12.5.1.2.6
-- 1.3.6.1.4.1.37950.1.1.5.12.5.1.2.6
-- 1.3.6.1.4.1.37950.1.1.5.12.5.1.2.6
-- 1.3.6.1.4.1.37950.1.1.5.12.5.1.2.6
-- 1.3.6.1.4.1.37950.1.1.5.12.5.1.2.6
-- 1.3.6.1.4.1.37950.1.1.5.12.5.1.2.6
-- 1.3.6.1.4.1.37950.1.1.5.12.5.1.2.6
		-- 1.3.6.1.4.1.37950.1.1.5.12.5.1.2.6
		policyCbs OBJECT-TYPE
			SYNTAX INTEGER (0..10240)
			MAX-ACCESS read-only
			STATUS current
			DESCRIPTION
				"Description."
			::= { onuPortInfoDisplay 6 }

		
--          1.3.6.1.4.1.37950.1.1.5.12.5.1.2.7
-- 1.3.6.1.4.1.37950.1.1.5.12.5.1.2.7
-- 1.3.6.1.4.1.37950.1.1.5.12.5.1.2.7
-- 1.3.6.1.4.1.37950.1.1.5.12.5.1.2.7
-- 1.3.6.1.4.1.37950.1.1.5.12.5.1.2.7
-- 1.3.6.1.4.1.37950.1.1.5.12.5.1.2.7
-- 1.3.6.1.4.1.37950.1.1.5.12.5.1.2.7
-- 1.3.6.1.4.1.37950.1.1.5.12.5.1.2.7
-- 1.3.6.1.4.1.37950.1.1.5.12.5.1.2.7
		-- 1.3.6.1.4.1.37950.1.1.5.12.5.1.2.7
		policyEbs OBJECT-TYPE
			SYNTAX INTEGER (0..10240)
			MAX-ACCESS read-only
			STATUS current
			DESCRIPTION
				"Description."
			::= { onuPortInfoDisplay 7 }

		
--          1.3.6.1.4.1.37950.1.1.5.12.5.1.2.8
-- 1.3.6.1.4.1.37950.1.1.5.12.5.1.2.8
-- 1.3.6.1.4.1.37950.1.1.5.12.5.1.2.8
-- 1.3.6.1.4.1.37950.1.1.5.12.5.1.2.8
-- 1.3.6.1.4.1.37950.1.1.5.12.5.1.2.8
-- 1.3.6.1.4.1.37950.1.1.5.12.5.1.2.8
-- 1.3.6.1.4.1.37950.1.1.5.12.5.1.2.8
-- 1.3.6.1.4.1.37950.1.1.5.12.5.1.2.8
-- 1.3.6.1.4.1.37950.1.1.5.12.5.1.2.8
		-- 1.3.6.1.4.1.37950.1.1.5.12.5.1.2.8
		rateLimitState OBJECT-TYPE
			SYNTAX INTEGER
				{
				disable(0),
				enable(1)
				}
			MAX-ACCESS read-only
			STATUS current
			DESCRIPTION
				"Description."
			::= { onuPortInfoDisplay 8 }

		
--          1.3.6.1.4.1.37950.1.1.5.12.5.1.2.9
-- 1.3.6.1.4.1.37950.1.1.5.12.5.1.2.9
-- 1.3.6.1.4.1.37950.1.1.5.12.5.1.2.9
-- 1.3.6.1.4.1.37950.1.1.5.12.5.1.2.9
-- 1.3.6.1.4.1.37950.1.1.5.12.5.1.2.9
-- 1.3.6.1.4.1.37950.1.1.5.12.5.1.2.9
-- 1.3.6.1.4.1.37950.1.1.5.12.5.1.2.9
-- 1.3.6.1.4.1.37950.1.1.5.12.5.1.2.9
-- 1.3.6.1.4.1.37950.1.1.5.12.5.1.2.9
		-- 1.3.6.1.4.1.37950.1.1.5.12.5.1.2.9
		rateLimitCir OBJECT-TYPE
			SYNTAX INTEGER (0..1048576)
			MAX-ACCESS read-only
			STATUS current
			DESCRIPTION
				"Description."
			::= { onuPortInfoDisplay 9 }

		
--          1.3.6.1.4.1.37950.1.1.5.12.5.1.2.10
-- 1.3.6.1.4.1.37950.1.1.5.12.5.1.2.10
-- 1.3.6.1.4.1.37950.1.1.5.12.5.1.2.10
-- 1.3.6.1.4.1.37950.1.1.5.12.5.1.2.10
-- 1.3.6.1.4.1.37950.1.1.5.12.5.1.2.10
-- 1.3.6.1.4.1.37950.1.1.5.12.5.1.2.10
-- 1.3.6.1.4.1.37950.1.1.5.12.5.1.2.10
-- 1.3.6.1.4.1.37950.1.1.5.12.5.1.2.10
-- 1.3.6.1.4.1.37950.1.1.5.12.5.1.2.10
		-- 1.3.6.1.4.1.37950.1.1.5.12.5.1.2.10
		rateLimitPir OBJECT-TYPE
			SYNTAX INTEGER (0..1048576)
			MAX-ACCESS read-only
			STATUS current
			DESCRIPTION
				"Description."
			::= { onuPortInfoDisplay 10 }

		
--          1.3.6.1.4.1.37950.1.1.5.12.5.1.3
-- 1.3.6.1.4.1.37950.1.1.5.12.5.1.3
-- 1.3.6.1.4.1.37950.1.1.5.12.5.1.3
-- 1.3.6.1.4.1.37950.1.1.5.12.5.1.3
-- 1.3.6.1.4.1.37950.1.1.5.12.5.1.3
-- 1.3.6.1.4.1.37950.1.1.5.12.5.1.3
-- 1.3.6.1.4.1.37950.1.1.5.12.5.1.3
-- 1.3.6.1.4.1.37950.1.1.5.12.5.1.3
-- 1.3.6.1.4.1.37950.1.1.5.12.5.1.3
		-- 1.3.6.1.4.1.37950.1.1.5.12.5.1.3
		onuPortAdminTable OBJECT-TYPE
			SYNTAX SEQUENCE OF OnuPortAdminEntry
			MAX-ACCESS not-accessible
			STATUS current
			DESCRIPTION
				"Description."
			::= { onuPortInfo 3 }

		
--          1.3.6.1.4.1.37950.1.1.5.12.5.1.3.1
-- 1.3.6.1.4.1.37950.1.1.5.12.5.1.3.1
-- 1.3.6.1.4.1.37950.1.1.5.12.5.1.3.1
-- 1.3.6.1.4.1.37950.1.1.5.12.5.1.3.1
-- 1.3.6.1.4.1.37950.1.1.5.12.5.1.3.1
-- 1.3.6.1.4.1.37950.1.1.5.12.5.1.3.1
-- 1.3.6.1.4.1.37950.1.1.5.12.5.1.3.1
-- 1.3.6.1.4.1.37950.1.1.5.12.5.1.3.1
-- 1.3.6.1.4.1.37950.1.1.5.12.5.1.3.1
		-- 1.3.6.1.4.1.37950.1.1.5.12.5.1.3.1
		onuPortAdminEntry OBJECT-TYPE
			SYNTAX OnuPortAdminEntry
			MAX-ACCESS not-accessible
			STATUS current
			DESCRIPTION
				"Description."
			INDEX { onuPortAdminPonIndex, onuPortAdminOnuIndex, onuPortAdminPortIndex }
			::= { onuPortAdminTable 1 }

		
		OnuPortAdminEntry ::=
			SEQUENCE { 
				onuPortAdminPonIndex
					Integer32,
				onuPortAdminOnuIndex
					Integer32,
				onuPortAdminPortIndex
					Integer32,
				onuPortAdminVal
					INTEGER
			 }

--          1.3.6.1.4.1.37950.1.1.5.12.5.1.3.1.1
-- 1.3.6.1.4.1.37950.1.1.5.12.5.1.3.1.1
-- 1.3.6.1.4.1.37950.1.1.5.12.5.1.3.1.1
-- 1.3.6.1.4.1.37950.1.1.5.12.5.1.3.1.1
-- 1.3.6.1.4.1.37950.1.1.5.12.5.1.3.1.1
-- 1.3.6.1.4.1.37950.1.1.5.12.5.1.3.1.1
-- 1.3.6.1.4.1.37950.1.1.5.12.5.1.3.1.1
-- 1.3.6.1.4.1.37950.1.1.5.12.5.1.3.1.1
-- 1.3.6.1.4.1.37950.1.1.5.12.5.1.3.1.1
		-- 1.3.6.1.4.1.37950.1.1.5.12.5.1.3.1.1
		onuPortAdminPonIndex OBJECT-TYPE
			SYNTAX Integer32
			MAX-ACCESS read-only
			STATUS current
			DESCRIPTION
				"Description."
			::= { onuPortAdminEntry 1 }

		
--          1.3.6.1.4.1.37950.1.1.5.12.5.1.3.1.2
-- 1.3.6.1.4.1.37950.1.1.5.12.5.1.3.1.2
-- 1.3.6.1.4.1.37950.1.1.5.12.5.1.3.1.2
-- 1.3.6.1.4.1.37950.1.1.5.12.5.1.3.1.2
-- 1.3.6.1.4.1.37950.1.1.5.12.5.1.3.1.2
-- 1.3.6.1.4.1.37950.1.1.5.12.5.1.3.1.2
-- 1.3.6.1.4.1.37950.1.1.5.12.5.1.3.1.2
-- 1.3.6.1.4.1.37950.1.1.5.12.5.1.3.1.2
-- 1.3.6.1.4.1.37950.1.1.5.12.5.1.3.1.2
		-- 1.3.6.1.4.1.37950.1.1.5.12.5.1.3.1.2
		onuPortAdminOnuIndex OBJECT-TYPE
			SYNTAX Integer32
			MAX-ACCESS read-only
			STATUS current
			DESCRIPTION
				"Description."
			::= { onuPortAdminEntry 2 }

		
--          1.3.6.1.4.1.37950.1.1.5.12.5.1.3.1.3
-- 1.3.6.1.4.1.37950.1.1.5.12.5.1.3.1.3
-- 1.3.6.1.4.1.37950.1.1.5.12.5.1.3.1.3
-- 1.3.6.1.4.1.37950.1.1.5.12.5.1.3.1.3
-- 1.3.6.1.4.1.37950.1.1.5.12.5.1.3.1.3
-- 1.3.6.1.4.1.37950.1.1.5.12.5.1.3.1.3
-- 1.3.6.1.4.1.37950.1.1.5.12.5.1.3.1.3
-- 1.3.6.1.4.1.37950.1.1.5.12.5.1.3.1.3
-- 1.3.6.1.4.1.37950.1.1.5.12.5.1.3.1.3
		-- 1.3.6.1.4.1.37950.1.1.5.12.5.1.3.1.3
		onuPortAdminPortIndex OBJECT-TYPE
			SYNTAX Integer32
			MAX-ACCESS read-only
			STATUS current
			DESCRIPTION
				"Description."
			::= { onuPortAdminEntry 3 }

		
--          1.3.6.1.4.1.37950.1.1.5.12.5.1.3.1.4
-- 1.3.6.1.4.1.37950.1.1.5.12.5.1.3.1.4
-- 1.3.6.1.4.1.37950.1.1.5.12.5.1.3.1.4
-- 1.3.6.1.4.1.37950.1.1.5.12.5.1.3.1.4
-- 1.3.6.1.4.1.37950.1.1.5.12.5.1.3.1.4
-- 1.3.6.1.4.1.37950.1.1.5.12.5.1.3.1.4
-- 1.3.6.1.4.1.37950.1.1.5.12.5.1.3.1.4
-- 1.3.6.1.4.1.37950.1.1.5.12.5.1.3.1.4
-- 1.3.6.1.4.1.37950.1.1.5.12.5.1.3.1.4
		-- 1.3.6.1.4.1.37950.1.1.5.12.5.1.3.1.4
		onuPortAdminVal OBJECT-TYPE
			SYNTAX INTEGER
				{
				disable(0),
				enable(1)
				}
			MAX-ACCESS read-only
			STATUS current
			DESCRIPTION
				"Description."
			::= { onuPortAdminEntry 4 }

		
--          1.3.6.1.4.1.37950.1.1.5.12.5.1.4
-- 1.3.6.1.4.1.37950.1.1.5.12.5.1.4
-- 1.3.6.1.4.1.37950.1.1.5.12.5.1.4
-- 1.3.6.1.4.1.37950.1.1.5.12.5.1.4
-- 1.3.6.1.4.1.37950.1.1.5.12.5.1.4
-- 1.3.6.1.4.1.37950.1.1.5.12.5.1.4
-- 1.3.6.1.4.1.37950.1.1.5.12.5.1.4
-- 1.3.6.1.4.1.37950.1.1.5.12.5.1.4
-- 1.3.6.1.4.1.37950.1.1.5.12.5.1.4
		-- 1.3.6.1.4.1.37950.1.1.5.12.5.1.4
		onuPortAutoNegTable OBJECT-TYPE
			SYNTAX SEQUENCE OF OnuPortAutoNegEntry
			MAX-ACCESS not-accessible
			STATUS current
			DESCRIPTION
				"Description."
			::= { onuPortInfo 4 }

		
--          1.3.6.1.4.1.37950.1.1.5.12.5.1.4.1
-- 1.3.6.1.4.1.37950.1.1.5.12.5.1.4.1
-- 1.3.6.1.4.1.37950.1.1.5.12.5.1.4.1
-- 1.3.6.1.4.1.37950.1.1.5.12.5.1.4.1
-- 1.3.6.1.4.1.37950.1.1.5.12.5.1.4.1
-- 1.3.6.1.4.1.37950.1.1.5.12.5.1.4.1
-- 1.3.6.1.4.1.37950.1.1.5.12.5.1.4.1
-- 1.3.6.1.4.1.37950.1.1.5.12.5.1.4.1
-- 1.3.6.1.4.1.37950.1.1.5.12.5.1.4.1
		-- 1.3.6.1.4.1.37950.1.1.5.12.5.1.4.1
		onuPortAutoNegEntry OBJECT-TYPE
			SYNTAX OnuPortAutoNegEntry
			MAX-ACCESS not-accessible
			STATUS current
			DESCRIPTION
				"Description."
			INDEX { onuPortAutoNegPonIndex, onuPortAutoNegOnuIndex, onuPortAutoNegPortIndex }
			::= { onuPortAutoNegTable 1 }

		
		OnuPortAutoNegEntry ::=
			SEQUENCE { 
				onuPortAutoNegPonIndex
					Integer32,
				onuPortAutoNegOnuIndex
					Integer32,
				onuPortAutoNegPortIndex
					Integer32,
				onuPortAutoNegVal
					INTEGER
			 }

--          1.3.6.1.4.1.37950.1.1.5.12.5.1.4.1.1
-- 1.3.6.1.4.1.37950.1.1.5.12.5.1.4.1.1
-- 1.3.6.1.4.1.37950.1.1.5.12.5.1.4.1.1
-- 1.3.6.1.4.1.37950.1.1.5.12.5.1.4.1.1
-- 1.3.6.1.4.1.37950.1.1.5.12.5.1.4.1.1
-- 1.3.6.1.4.1.37950.1.1.5.12.5.1.4.1.1
-- 1.3.6.1.4.1.37950.1.1.5.12.5.1.4.1.1
-- 1.3.6.1.4.1.37950.1.1.5.12.5.1.4.1.1
-- 1.3.6.1.4.1.37950.1.1.5.12.5.1.4.1.1
		-- 1.3.6.1.4.1.37950.1.1.5.12.5.1.4.1.1
		onuPortAutoNegPonIndex OBJECT-TYPE
			SYNTAX Integer32
			MAX-ACCESS read-only
			STATUS current
			DESCRIPTION
				"Description."
			::= { onuPortAutoNegEntry 1 }

		
--          1.3.6.1.4.1.37950.1.1.5.12.5.1.4.1.2
-- 1.3.6.1.4.1.37950.1.1.5.12.5.1.4.1.2
-- 1.3.6.1.4.1.37950.1.1.5.12.5.1.4.1.2
-- 1.3.6.1.4.1.37950.1.1.5.12.5.1.4.1.2
-- 1.3.6.1.4.1.37950.1.1.5.12.5.1.4.1.2
-- 1.3.6.1.4.1.37950.1.1.5.12.5.1.4.1.2
-- 1.3.6.1.4.1.37950.1.1.5.12.5.1.4.1.2
-- 1.3.6.1.4.1.37950.1.1.5.12.5.1.4.1.2
-- 1.3.6.1.4.1.37950.1.1.5.12.5.1.4.1.2
		-- 1.3.6.1.4.1.37950.1.1.5.12.5.1.4.1.2
		onuPortAutoNegOnuIndex OBJECT-TYPE
			SYNTAX Integer32
			MAX-ACCESS read-only
			STATUS current
			DESCRIPTION
				"Description."
			::= { onuPortAutoNegEntry 2 }

		
--          1.3.6.1.4.1.37950.1.1.5.12.5.1.4.1.3
-- 1.3.6.1.4.1.37950.1.1.5.12.5.1.4.1.3
-- 1.3.6.1.4.1.37950.1.1.5.12.5.1.4.1.3
-- 1.3.6.1.4.1.37950.1.1.5.12.5.1.4.1.3
-- 1.3.6.1.4.1.37950.1.1.5.12.5.1.4.1.3
-- 1.3.6.1.4.1.37950.1.1.5.12.5.1.4.1.3
-- 1.3.6.1.4.1.37950.1.1.5.12.5.1.4.1.3
-- 1.3.6.1.4.1.37950.1.1.5.12.5.1.4.1.3
-- 1.3.6.1.4.1.37950.1.1.5.12.5.1.4.1.3
		-- 1.3.6.1.4.1.37950.1.1.5.12.5.1.4.1.3
		onuPortAutoNegPortIndex OBJECT-TYPE
			SYNTAX Integer32
			MAX-ACCESS read-only
			STATUS current
			DESCRIPTION
				"Description."
			::= { onuPortAutoNegEntry 3 }

		
--          1.3.6.1.4.1.37950.1.1.5.12.5.1.4.1.4
-- 1.3.6.1.4.1.37950.1.1.5.12.5.1.4.1.4
-- 1.3.6.1.4.1.37950.1.1.5.12.5.1.4.1.4
-- 1.3.6.1.4.1.37950.1.1.5.12.5.1.4.1.4
-- 1.3.6.1.4.1.37950.1.1.5.12.5.1.4.1.4
-- 1.3.6.1.4.1.37950.1.1.5.12.5.1.4.1.4
-- 1.3.6.1.4.1.37950.1.1.5.12.5.1.4.1.4
-- 1.3.6.1.4.1.37950.1.1.5.12.5.1.4.1.4
-- 1.3.6.1.4.1.37950.1.1.5.12.5.1.4.1.4
		-- 1.3.6.1.4.1.37950.1.1.5.12.5.1.4.1.4
		onuPortAutoNegVal OBJECT-TYPE
			SYNTAX INTEGER
				{
				disable(0),
				enable(1)
				}
			MAX-ACCESS read-only
			STATUS current
			DESCRIPTION
				"Description."
			::= { onuPortAutoNegEntry 4 }

		
--          1.3.6.1.4.1.37950.1.1.5.12.5.1.5
-- 1.3.6.1.4.1.37950.1.1.5.12.5.1.5
-- 1.3.6.1.4.1.37950.1.1.5.12.5.1.5
-- 1.3.6.1.4.1.37950.1.1.5.12.5.1.5
-- 1.3.6.1.4.1.37950.1.1.5.12.5.1.5
-- 1.3.6.1.4.1.37950.1.1.5.12.5.1.5
-- 1.3.6.1.4.1.37950.1.1.5.12.5.1.5
-- 1.3.6.1.4.1.37950.1.1.5.12.5.1.5
-- 1.3.6.1.4.1.37950.1.1.5.12.5.1.5
		-- 1.3.6.1.4.1.37950.1.1.5.12.5.1.5
		onuPortFcTable OBJECT-TYPE
			SYNTAX SEQUENCE OF OnuPortFcEntry
			MAX-ACCESS not-accessible
			STATUS current
			DESCRIPTION
				"Description."
			::= { onuPortInfo 5 }

		
--          1.3.6.1.4.1.37950.1.1.5.12.5.1.5.1
-- 1.3.6.1.4.1.37950.1.1.5.12.5.1.5.1
-- 1.3.6.1.4.1.37950.1.1.5.12.5.1.5.1
-- 1.3.6.1.4.1.37950.1.1.5.12.5.1.5.1
-- 1.3.6.1.4.1.37950.1.1.5.12.5.1.5.1
-- 1.3.6.1.4.1.37950.1.1.5.12.5.1.5.1
-- 1.3.6.1.4.1.37950.1.1.5.12.5.1.5.1
-- 1.3.6.1.4.1.37950.1.1.5.12.5.1.5.1
-- 1.3.6.1.4.1.37950.1.1.5.12.5.1.5.1
		-- 1.3.6.1.4.1.37950.1.1.5.12.5.1.5.1
		onuPortFcEntry OBJECT-TYPE
			SYNTAX OnuPortFcEntry
			MAX-ACCESS not-accessible
			STATUS current
			DESCRIPTION
				"Description."
			INDEX { onuPortFcPonIndex, onuPortFcOnuIndex, onuPortFcPortIndex }
			::= { onuPortFcTable 1 }

		
		OnuPortFcEntry ::=
			SEQUENCE { 
				onuPortFcPonIndex
					Integer32,
				onuPortFcOnuIndex
					Integer32,
				onuPortFcPortIndex
					Integer32,
				onuPortFcVal
					INTEGER
			 }

--          1.3.6.1.4.1.37950.1.1.5.12.5.1.5.1.1
-- 1.3.6.1.4.1.37950.1.1.5.12.5.1.5.1.1
-- 1.3.6.1.4.1.37950.1.1.5.12.5.1.5.1.1
-- 1.3.6.1.4.1.37950.1.1.5.12.5.1.5.1.1
-- 1.3.6.1.4.1.37950.1.1.5.12.5.1.5.1.1
-- 1.3.6.1.4.1.37950.1.1.5.12.5.1.5.1.1
-- 1.3.6.1.4.1.37950.1.1.5.12.5.1.5.1.1
-- 1.3.6.1.4.1.37950.1.1.5.12.5.1.5.1.1
-- 1.3.6.1.4.1.37950.1.1.5.12.5.1.5.1.1
		-- 1.3.6.1.4.1.37950.1.1.5.12.5.1.5.1.1
		onuPortFcPonIndex OBJECT-TYPE
			SYNTAX Integer32
			MAX-ACCESS read-only
			STATUS current
			DESCRIPTION
				"Description."
			::= { onuPortFcEntry 1 }

		
--          1.3.6.1.4.1.37950.1.1.5.12.5.1.5.1.2
-- 1.3.6.1.4.1.37950.1.1.5.12.5.1.5.1.2
-- 1.3.6.1.4.1.37950.1.1.5.12.5.1.5.1.2
-- 1.3.6.1.4.1.37950.1.1.5.12.5.1.5.1.2
-- 1.3.6.1.4.1.37950.1.1.5.12.5.1.5.1.2
-- 1.3.6.1.4.1.37950.1.1.5.12.5.1.5.1.2
-- 1.3.6.1.4.1.37950.1.1.5.12.5.1.5.1.2
-- 1.3.6.1.4.1.37950.1.1.5.12.5.1.5.1.2
-- 1.3.6.1.4.1.37950.1.1.5.12.5.1.5.1.2
		-- 1.3.6.1.4.1.37950.1.1.5.12.5.1.5.1.2
		onuPortFcOnuIndex OBJECT-TYPE
			SYNTAX Integer32
			MAX-ACCESS read-only
			STATUS current
			DESCRIPTION
				"Description."
			::= { onuPortFcEntry 2 }

		
--          1.3.6.1.4.1.37950.1.1.5.12.5.1.5.1.3
-- 1.3.6.1.4.1.37950.1.1.5.12.5.1.5.1.3
-- 1.3.6.1.4.1.37950.1.1.5.12.5.1.5.1.3
-- 1.3.6.1.4.1.37950.1.1.5.12.5.1.5.1.3
-- 1.3.6.1.4.1.37950.1.1.5.12.5.1.5.1.3
-- 1.3.6.1.4.1.37950.1.1.5.12.5.1.5.1.3
-- 1.3.6.1.4.1.37950.1.1.5.12.5.1.5.1.3
-- 1.3.6.1.4.1.37950.1.1.5.12.5.1.5.1.3
-- 1.3.6.1.4.1.37950.1.1.5.12.5.1.5.1.3
		-- 1.3.6.1.4.1.37950.1.1.5.12.5.1.5.1.3
		onuPortFcPortIndex OBJECT-TYPE
			SYNTAX Integer32
			MAX-ACCESS read-only
			STATUS current
			DESCRIPTION
				"Description."
			::= { onuPortFcEntry 3 }

		
--          1.3.6.1.4.1.37950.1.1.5.12.5.1.5.1.4
-- 1.3.6.1.4.1.37950.1.1.5.12.5.1.5.1.4
-- 1.3.6.1.4.1.37950.1.1.5.12.5.1.5.1.4
-- 1.3.6.1.4.1.37950.1.1.5.12.5.1.5.1.4
-- 1.3.6.1.4.1.37950.1.1.5.12.5.1.5.1.4
-- 1.3.6.1.4.1.37950.1.1.5.12.5.1.5.1.4
-- 1.3.6.1.4.1.37950.1.1.5.12.5.1.5.1.4
-- 1.3.6.1.4.1.37950.1.1.5.12.5.1.5.1.4
-- 1.3.6.1.4.1.37950.1.1.5.12.5.1.5.1.4
		-- 1.3.6.1.4.1.37950.1.1.5.12.5.1.5.1.4
		onuPortFcVal OBJECT-TYPE
			SYNTAX INTEGER
				{
				disable(0),
				enable(1)
				}
			MAX-ACCESS read-only
			STATUS current
			DESCRIPTION
				"Description."
			::= { onuPortFcEntry 4 }

		
--          1.3.6.1.4.1.37950.1.1.5.12.5.1.6
-- 1.3.6.1.4.1.37950.1.1.5.12.5.1.6
-- 1.3.6.1.4.1.37950.1.1.5.12.5.1.6
-- 1.3.6.1.4.1.37950.1.1.5.12.5.1.6
-- 1.3.6.1.4.1.37950.1.1.5.12.5.1.6
-- 1.3.6.1.4.1.37950.1.1.5.12.5.1.6
-- 1.3.6.1.4.1.37950.1.1.5.12.5.1.6
-- 1.3.6.1.4.1.37950.1.1.5.12.5.1.6
-- 1.3.6.1.4.1.37950.1.1.5.12.5.1.6
		-- 1.3.6.1.4.1.37950.1.1.5.12.5.1.6
		portLoopdetectTable OBJECT-TYPE
			SYNTAX SEQUENCE OF PortLoopdetectEntry
			MAX-ACCESS not-accessible
			STATUS current
			DESCRIPTION
				"Description."
			::= { onuPortInfo 6 }

		
--          1.3.6.1.4.1.37950.1.1.5.12.5.1.6.1
-- 1.3.6.1.4.1.37950.1.1.5.12.5.1.6.1
-- 1.3.6.1.4.1.37950.1.1.5.12.5.1.6.1
-- 1.3.6.1.4.1.37950.1.1.5.12.5.1.6.1
-- 1.3.6.1.4.1.37950.1.1.5.12.5.1.6.1
-- 1.3.6.1.4.1.37950.1.1.5.12.5.1.6.1
-- 1.3.6.1.4.1.37950.1.1.5.12.5.1.6.1
-- 1.3.6.1.4.1.37950.1.1.5.12.5.1.6.1
-- 1.3.6.1.4.1.37950.1.1.5.12.5.1.6.1
		-- 1.3.6.1.4.1.37950.1.1.5.12.5.1.6.1
		portLoopdetectEntry OBJECT-TYPE
			SYNTAX PortLoopdetectEntry
			MAX-ACCESS not-accessible
			STATUS current
			DESCRIPTION
				"Description."
			INDEX { portLoopdetectPonIndex, portLoopdetectOnuIndex, portLoopdetectPortIndex }
			::= { portLoopdetectTable 1 }

		
		PortLoopdetectEntry ::=
			SEQUENCE { 
				portLoopdetectPonIndex
					Integer32,
				portLoopdetectOnuIndex
					Integer32,
				portLoopdetectPortIndex
					Integer32,
				portLoopdetectVal
					INTEGER
			 }

--          1.3.6.1.4.1.37950.1.1.5.12.5.1.6.1.1
-- 1.3.6.1.4.1.37950.1.1.5.12.5.1.6.1.1
-- 1.3.6.1.4.1.37950.1.1.5.12.5.1.6.1.1
-- 1.3.6.1.4.1.37950.1.1.5.12.5.1.6.1.1
-- 1.3.6.1.4.1.37950.1.1.5.12.5.1.6.1.1
-- 1.3.6.1.4.1.37950.1.1.5.12.5.1.6.1.1
-- 1.3.6.1.4.1.37950.1.1.5.12.5.1.6.1.1
-- 1.3.6.1.4.1.37950.1.1.5.12.5.1.6.1.1
-- 1.3.6.1.4.1.37950.1.1.5.12.5.1.6.1.1
		-- 1.3.6.1.4.1.37950.1.1.5.12.5.1.6.1.1
		portLoopdetectPonIndex OBJECT-TYPE
			SYNTAX Integer32
			MAX-ACCESS read-only
			STATUS current
			DESCRIPTION
				"Description."
			::= { portLoopdetectEntry 1 }

		
--          1.3.6.1.4.1.37950.1.1.5.12.5.1.6.1.2
-- 1.3.6.1.4.1.37950.1.1.5.12.5.1.6.1.2
-- 1.3.6.1.4.1.37950.1.1.5.12.5.1.6.1.2
-- 1.3.6.1.4.1.37950.1.1.5.12.5.1.6.1.2
-- 1.3.6.1.4.1.37950.1.1.5.12.5.1.6.1.2
-- 1.3.6.1.4.1.37950.1.1.5.12.5.1.6.1.2
-- 1.3.6.1.4.1.37950.1.1.5.12.5.1.6.1.2
-- 1.3.6.1.4.1.37950.1.1.5.12.5.1.6.1.2
-- 1.3.6.1.4.1.37950.1.1.5.12.5.1.6.1.2
		-- 1.3.6.1.4.1.37950.1.1.5.12.5.1.6.1.2
		portLoopdetectOnuIndex OBJECT-TYPE
			SYNTAX Integer32
			MAX-ACCESS read-only
			STATUS current
			DESCRIPTION
				"Description."
			::= { portLoopdetectEntry 2 }

		
--          1.3.6.1.4.1.37950.1.1.5.12.5.1.6.1.3
-- 1.3.6.1.4.1.37950.1.1.5.12.5.1.6.1.3
-- 1.3.6.1.4.1.37950.1.1.5.12.5.1.6.1.3
-- 1.3.6.1.4.1.37950.1.1.5.12.5.1.6.1.3
-- 1.3.6.1.4.1.37950.1.1.5.12.5.1.6.1.3
-- 1.3.6.1.4.1.37950.1.1.5.12.5.1.6.1.3
-- 1.3.6.1.4.1.37950.1.1.5.12.5.1.6.1.3
-- 1.3.6.1.4.1.37950.1.1.5.12.5.1.6.1.3
-- 1.3.6.1.4.1.37950.1.1.5.12.5.1.6.1.3
		-- 1.3.6.1.4.1.37950.1.1.5.12.5.1.6.1.3
		portLoopdetectPortIndex OBJECT-TYPE
			SYNTAX Integer32
			MAX-ACCESS read-only
			STATUS current
			DESCRIPTION
				"Description."
			::= { portLoopdetectEntry 3 }

		
--          1.3.6.1.4.1.37950.1.1.5.12.5.1.6.1.4
-- 1.3.6.1.4.1.37950.1.1.5.12.5.1.6.1.4
-- 1.3.6.1.4.1.37950.1.1.5.12.5.1.6.1.4
-- 1.3.6.1.4.1.37950.1.1.5.12.5.1.6.1.4
-- 1.3.6.1.4.1.37950.1.1.5.12.5.1.6.1.4
-- 1.3.6.1.4.1.37950.1.1.5.12.5.1.6.1.4
-- 1.3.6.1.4.1.37950.1.1.5.12.5.1.6.1.4
-- 1.3.6.1.4.1.37950.1.1.5.12.5.1.6.1.4
-- 1.3.6.1.4.1.37950.1.1.5.12.5.1.6.1.4
		-- 1.3.6.1.4.1.37950.1.1.5.12.5.1.6.1.4
		portLoopdetectVal OBJECT-TYPE
			SYNTAX INTEGER
				{
				disable(0),
				enable(1)
				}
			MAX-ACCESS read-only
			STATUS current
			DESCRIPTION
				"Description."
			::= { portLoopdetectEntry 4 }

		
--          1.3.6.1.4.1.37950.1.1.5.12.5.1.7
-- 1.3.6.1.4.1.37950.1.1.5.12.5.1.7
-- 1.3.6.1.4.1.37950.1.1.5.12.5.1.7
-- 1.3.6.1.4.1.37950.1.1.5.12.5.1.7
-- 1.3.6.1.4.1.37950.1.1.5.12.5.1.7
-- 1.3.6.1.4.1.37950.1.1.5.12.5.1.7
-- 1.3.6.1.4.1.37950.1.1.5.12.5.1.7
-- 1.3.6.1.4.1.37950.1.1.5.12.5.1.7
-- 1.3.6.1.4.1.37950.1.1.5.12.5.1.7
		-- 1.3.6.1.4.1.37950.1.1.5.12.5.1.7
		onuPortUpstreamLimitTable OBJECT-TYPE
			SYNTAX SEQUENCE OF OnuPortUpstreamLimitEntry
			MAX-ACCESS not-accessible
			STATUS current
			DESCRIPTION
				"Description."
			::= { onuPortInfo 7 }

		
--          1.3.6.1.4.1.37950.1.1.5.12.5.1.7.1
-- 1.3.6.1.4.1.37950.1.1.5.12.5.1.7.1
-- 1.3.6.1.4.1.37950.1.1.5.12.5.1.7.1
-- 1.3.6.1.4.1.37950.1.1.5.12.5.1.7.1
-- 1.3.6.1.4.1.37950.1.1.5.12.5.1.7.1
-- 1.3.6.1.4.1.37950.1.1.5.12.5.1.7.1
-- 1.3.6.1.4.1.37950.1.1.5.12.5.1.7.1
-- 1.3.6.1.4.1.37950.1.1.5.12.5.1.7.1
-- 1.3.6.1.4.1.37950.1.1.5.12.5.1.7.1
		-- 1.3.6.1.4.1.37950.1.1.5.12.5.1.7.1
		onuPortUpstreamLimitEntry OBJECT-TYPE
			SYNTAX OnuPortUpstreamLimitEntry
			MAX-ACCESS not-accessible
			STATUS current
			DESCRIPTION
				"Description."
			INDEX { onuPortUpstreamLimitPonIndex, onuPortUpstreamLimitOnuIndex, onuPortUpstreamLimitPortIndex }
			::= { onuPortUpstreamLimitTable 1 }

		
		OnuPortUpstreamLimitEntry ::=
			SEQUENCE { 
				onuPortUpstreamLimitPonIndex
					Integer32,
				onuPortUpstreamLimitOnuIndex
					Integer32,
				onuPortUpstreamLimitPortIndex
					Integer32,
				onuPortUpstreamLimitCir
					Integer32,
				onuPortUpstreamLimitCbs
					Integer32,
				onuPortUpstreamLimitEbs
					Integer32
			 }

--          1.3.6.1.4.1.37950.1.1.5.12.5.1.7.1.1
-- 1.3.6.1.4.1.37950.1.1.5.12.5.1.7.1.1
-- 1.3.6.1.4.1.37950.1.1.5.12.5.1.7.1.1
-- 1.3.6.1.4.1.37950.1.1.5.12.5.1.7.1.1
-- 1.3.6.1.4.1.37950.1.1.5.12.5.1.7.1.1
-- 1.3.6.1.4.1.37950.1.1.5.12.5.1.7.1.1
-- 1.3.6.1.4.1.37950.1.1.5.12.5.1.7.1.1
-- 1.3.6.1.4.1.37950.1.1.5.12.5.1.7.1.1
-- 1.3.6.1.4.1.37950.1.1.5.12.5.1.7.1.1
		-- 1.3.6.1.4.1.37950.1.1.5.12.5.1.7.1.1
		onuPortUpstreamLimitPonIndex OBJECT-TYPE
			SYNTAX Integer32
			MAX-ACCESS read-only
			STATUS current
			DESCRIPTION
				"Description."
			::= { onuPortUpstreamLimitEntry 1 }

		
--          1.3.6.1.4.1.37950.1.1.5.12.5.1.7.1.2
-- 1.3.6.1.4.1.37950.1.1.5.12.5.1.7.1.2
-- 1.3.6.1.4.1.37950.1.1.5.12.5.1.7.1.2
-- 1.3.6.1.4.1.37950.1.1.5.12.5.1.7.1.2
-- 1.3.6.1.4.1.37950.1.1.5.12.5.1.7.1.2
-- 1.3.6.1.4.1.37950.1.1.5.12.5.1.7.1.2
-- 1.3.6.1.4.1.37950.1.1.5.12.5.1.7.1.2
-- 1.3.6.1.4.1.37950.1.1.5.12.5.1.7.1.2
-- 1.3.6.1.4.1.37950.1.1.5.12.5.1.7.1.2
		-- 1.3.6.1.4.1.37950.1.1.5.12.5.1.7.1.2
		onuPortUpstreamLimitOnuIndex OBJECT-TYPE
			SYNTAX Integer32
			MAX-ACCESS read-only
			STATUS current
			DESCRIPTION
				"Description."
			::= { onuPortUpstreamLimitEntry 2 }

		
--          1.3.6.1.4.1.37950.1.1.5.12.5.1.7.1.3
-- 1.3.6.1.4.1.37950.1.1.5.12.5.1.7.1.3
-- 1.3.6.1.4.1.37950.1.1.5.12.5.1.7.1.3
-- 1.3.6.1.4.1.37950.1.1.5.12.5.1.7.1.3
-- 1.3.6.1.4.1.37950.1.1.5.12.5.1.7.1.3
-- 1.3.6.1.4.1.37950.1.1.5.12.5.1.7.1.3
-- 1.3.6.1.4.1.37950.1.1.5.12.5.1.7.1.3
-- 1.3.6.1.4.1.37950.1.1.5.12.5.1.7.1.3
-- 1.3.6.1.4.1.37950.1.1.5.12.5.1.7.1.3
		-- 1.3.6.1.4.1.37950.1.1.5.12.5.1.7.1.3
		onuPortUpstreamLimitPortIndex OBJECT-TYPE
			SYNTAX Integer32
			MAX-ACCESS read-only
			STATUS current
			DESCRIPTION
				"Description."
			::= { onuPortUpstreamLimitEntry 3 }

		
--          1.3.6.1.4.1.37950.1.1.5.12.5.1.7.1.4
-- 1.3.6.1.4.1.37950.1.1.5.12.5.1.7.1.4
-- 1.3.6.1.4.1.37950.1.1.5.12.5.1.7.1.4
-- 1.3.6.1.4.1.37950.1.1.5.12.5.1.7.1.4
-- 1.3.6.1.4.1.37950.1.1.5.12.5.1.7.1.4
-- 1.3.6.1.4.1.37950.1.1.5.12.5.1.7.1.4
-- 1.3.6.1.4.1.37950.1.1.5.12.5.1.7.1.4
-- 1.3.6.1.4.1.37950.1.1.5.12.5.1.7.1.4
-- 1.3.6.1.4.1.37950.1.1.5.12.5.1.7.1.4
		-- 1.3.6.1.4.1.37950.1.1.5.12.5.1.7.1.4
		onuPortUpstreamLimitCir OBJECT-TYPE
			SYNTAX Integer32
			MAX-ACCESS read-only
			STATUS current
			DESCRIPTION
				"Description."
			::= { onuPortUpstreamLimitEntry 4 }

		
--          1.3.6.1.4.1.37950.1.1.5.12.5.1.7.1.5
-- 1.3.6.1.4.1.37950.1.1.5.12.5.1.7.1.5
-- 1.3.6.1.4.1.37950.1.1.5.12.5.1.7.1.5
-- 1.3.6.1.4.1.37950.1.1.5.12.5.1.7.1.5
-- 1.3.6.1.4.1.37950.1.1.5.12.5.1.7.1.5
-- 1.3.6.1.4.1.37950.1.1.5.12.5.1.7.1.5
-- 1.3.6.1.4.1.37950.1.1.5.12.5.1.7.1.5
-- 1.3.6.1.4.1.37950.1.1.5.12.5.1.7.1.5
-- 1.3.6.1.4.1.37950.1.1.5.12.5.1.7.1.5
		-- 1.3.6.1.4.1.37950.1.1.5.12.5.1.7.1.5
		onuPortUpstreamLimitCbs OBJECT-TYPE
			SYNTAX Integer32
			MAX-ACCESS read-only
			STATUS current
			DESCRIPTION
				"Description."
			::= { onuPortUpstreamLimitEntry 5 }

		
--          1.3.6.1.4.1.37950.1.1.5.12.5.1.7.1.6
-- 1.3.6.1.4.1.37950.1.1.5.12.5.1.7.1.6
-- 1.3.6.1.4.1.37950.1.1.5.12.5.1.7.1.6
-- 1.3.6.1.4.1.37950.1.1.5.12.5.1.7.1.6
-- 1.3.6.1.4.1.37950.1.1.5.12.5.1.7.1.6
-- 1.3.6.1.4.1.37950.1.1.5.12.5.1.7.1.6
-- 1.3.6.1.4.1.37950.1.1.5.12.5.1.7.1.6
-- 1.3.6.1.4.1.37950.1.1.5.12.5.1.7.1.6
-- 1.3.6.1.4.1.37950.1.1.5.12.5.1.7.1.6
		-- 1.3.6.1.4.1.37950.1.1.5.12.5.1.7.1.6
		onuPortUpstreamLimitEbs OBJECT-TYPE
			SYNTAX Integer32
			MAX-ACCESS read-only
			STATUS current
			DESCRIPTION
				"Description."
			::= { onuPortUpstreamLimitEntry 6 }

		
--          1.3.6.1.4.1.37950.1.1.5.12.5.1.8
-- 1.3.6.1.4.1.37950.1.1.5.12.5.1.8
-- 1.3.6.1.4.1.37950.1.1.5.12.5.1.8
-- 1.3.6.1.4.1.37950.1.1.5.12.5.1.8
-- 1.3.6.1.4.1.37950.1.1.5.12.5.1.8
-- 1.3.6.1.4.1.37950.1.1.5.12.5.1.8
-- 1.3.6.1.4.1.37950.1.1.5.12.5.1.8
-- 1.3.6.1.4.1.37950.1.1.5.12.5.1.8
-- 1.3.6.1.4.1.37950.1.1.5.12.5.1.8
		-- 1.3.6.1.4.1.37950.1.1.5.12.5.1.8
		onuPortDownstreamLimitTable OBJECT-TYPE
			SYNTAX SEQUENCE OF OnuPortDownstreamLimitEntry
			MAX-ACCESS not-accessible
			STATUS current
			DESCRIPTION
				"Description."
			::= { onuPortInfo 8 }

		
--          1.3.6.1.4.1.37950.1.1.5.12.5.1.8.1
-- 1.3.6.1.4.1.37950.1.1.5.12.5.1.8.1
-- 1.3.6.1.4.1.37950.1.1.5.12.5.1.8.1
-- 1.3.6.1.4.1.37950.1.1.5.12.5.1.8.1
-- 1.3.6.1.4.1.37950.1.1.5.12.5.1.8.1
-- 1.3.6.1.4.1.37950.1.1.5.12.5.1.8.1
-- 1.3.6.1.4.1.37950.1.1.5.12.5.1.8.1
-- 1.3.6.1.4.1.37950.1.1.5.12.5.1.8.1
-- 1.3.6.1.4.1.37950.1.1.5.12.5.1.8.1
		-- 1.3.6.1.4.1.37950.1.1.5.12.5.1.8.1
		onuPortDownstreamLimitEntry OBJECT-TYPE
			SYNTAX OnuPortDownstreamLimitEntry
			MAX-ACCESS not-accessible
			STATUS current
			DESCRIPTION
				"Description."
			INDEX { onuPortDownstreamLimitPonIndex, onuPortDownstreamLimitOnuIndex, onuPortDownstreamLimitPortIndex }
			::= { onuPortDownstreamLimitTable 1 }

		
		OnuPortDownstreamLimitEntry ::=
			SEQUENCE { 
				onuPortDownstreamLimitPonIndex
					Integer32,
				onuPortDownstreamLimitOnuIndex
					Integer32,
				onuPortDownstreamLimitPortIndex
					Integer32,
				onuPortDownstreamLimitCir
					Integer32,
				onuPortDownstreamLimitPir
					Integer32
			 }

--          1.3.6.1.4.1.37950.1.1.5.12.5.1.8.1.1
-- 1.3.6.1.4.1.37950.1.1.5.12.5.1.8.1.1
-- 1.3.6.1.4.1.37950.1.1.5.12.5.1.8.1.1
-- 1.3.6.1.4.1.37950.1.1.5.12.5.1.8.1.1
-- 1.3.6.1.4.1.37950.1.1.5.12.5.1.8.1.1
-- 1.3.6.1.4.1.37950.1.1.5.12.5.1.8.1.1
-- 1.3.6.1.4.1.37950.1.1.5.12.5.1.8.1.1
-- 1.3.6.1.4.1.37950.1.1.5.12.5.1.8.1.1
-- 1.3.6.1.4.1.37950.1.1.5.12.5.1.8.1.1
		-- 1.3.6.1.4.1.37950.1.1.5.12.5.1.8.1.1
		onuPortDownstreamLimitPonIndex OBJECT-TYPE
			SYNTAX Integer32
			MAX-ACCESS read-only
			STATUS current
			DESCRIPTION
				"Description."
			::= { onuPortDownstreamLimitEntry 1 }

		
--          1.3.6.1.4.1.37950.1.1.5.12.5.1.8.1.2
-- 1.3.6.1.4.1.37950.1.1.5.12.5.1.8.1.2
-- 1.3.6.1.4.1.37950.1.1.5.12.5.1.8.1.2
-- 1.3.6.1.4.1.37950.1.1.5.12.5.1.8.1.2
-- 1.3.6.1.4.1.37950.1.1.5.12.5.1.8.1.2
-- 1.3.6.1.4.1.37950.1.1.5.12.5.1.8.1.2
-- 1.3.6.1.4.1.37950.1.1.5.12.5.1.8.1.2
-- 1.3.6.1.4.1.37950.1.1.5.12.5.1.8.1.2
-- 1.3.6.1.4.1.37950.1.1.5.12.5.1.8.1.2
		-- 1.3.6.1.4.1.37950.1.1.5.12.5.1.8.1.2
		onuPortDownstreamLimitOnuIndex OBJECT-TYPE
			SYNTAX Integer32
			MAX-ACCESS read-only
			STATUS current
			DESCRIPTION
				"Description."
			::= { onuPortDownstreamLimitEntry 2 }

		
--          1.3.6.1.4.1.37950.1.1.5.12.5.1.8.1.3
-- 1.3.6.1.4.1.37950.1.1.5.12.5.1.8.1.3
-- 1.3.6.1.4.1.37950.1.1.5.12.5.1.8.1.3
-- 1.3.6.1.4.1.37950.1.1.5.12.5.1.8.1.3
-- 1.3.6.1.4.1.37950.1.1.5.12.5.1.8.1.3
-- 1.3.6.1.4.1.37950.1.1.5.12.5.1.8.1.3
-- 1.3.6.1.4.1.37950.1.1.5.12.5.1.8.1.3
-- 1.3.6.1.4.1.37950.1.1.5.12.5.1.8.1.3
-- 1.3.6.1.4.1.37950.1.1.5.12.5.1.8.1.3
		-- 1.3.6.1.4.1.37950.1.1.5.12.5.1.8.1.3
		onuPortDownstreamLimitPortIndex OBJECT-TYPE
			SYNTAX Integer32
			MAX-ACCESS read-only
			STATUS current
			DESCRIPTION
				"Description."
			::= { onuPortDownstreamLimitEntry 3 }

		
--          1.3.6.1.4.1.37950.1.1.5.12.5.1.8.1.4
-- 1.3.6.1.4.1.37950.1.1.5.12.5.1.8.1.4
-- 1.3.6.1.4.1.37950.1.1.5.12.5.1.8.1.4
-- 1.3.6.1.4.1.37950.1.1.5.12.5.1.8.1.4
-- 1.3.6.1.4.1.37950.1.1.5.12.5.1.8.1.4
-- 1.3.6.1.4.1.37950.1.1.5.12.5.1.8.1.4
-- 1.3.6.1.4.1.37950.1.1.5.12.5.1.8.1.4
-- 1.3.6.1.4.1.37950.1.1.5.12.5.1.8.1.4
-- 1.3.6.1.4.1.37950.1.1.5.12.5.1.8.1.4
		-- 1.3.6.1.4.1.37950.1.1.5.12.5.1.8.1.4
		onuPortDownstreamLimitCir OBJECT-TYPE
			SYNTAX Integer32
			MAX-ACCESS read-only
			STATUS current
			DESCRIPTION
				"Description."
			::= { onuPortDownstreamLimitEntry 4 }

		
--          1.3.6.1.4.1.37950.1.1.5.12.5.1.8.1.5
-- 1.3.6.1.4.1.37950.1.1.5.12.5.1.8.1.5
-- 1.3.6.1.4.1.37950.1.1.5.12.5.1.8.1.5
-- 1.3.6.1.4.1.37950.1.1.5.12.5.1.8.1.5
-- 1.3.6.1.4.1.37950.1.1.5.12.5.1.8.1.5
-- 1.3.6.1.4.1.37950.1.1.5.12.5.1.8.1.5
-- 1.3.6.1.4.1.37950.1.1.5.12.5.1.8.1.5
-- 1.3.6.1.4.1.37950.1.1.5.12.5.1.8.1.5
-- 1.3.6.1.4.1.37950.1.1.5.12.5.1.8.1.5
		-- 1.3.6.1.4.1.37950.1.1.5.12.5.1.8.1.5
		onuPortDownstreamLimitPir OBJECT-TYPE
			SYNTAX Integer32
			MAX-ACCESS read-only
			STATUS current
			DESCRIPTION
				"Description."
			::= { onuPortDownstreamLimitEntry 5 }

		
--          1.3.6.1.4.1.37950.1.1.5.12.5.1.9
-- 1.3.6.1.4.1.37950.1.1.5.12.5.1.9
-- 1.3.6.1.4.1.37950.1.1.5.12.5.1.9
-- 1.3.6.1.4.1.37950.1.1.5.12.5.1.9
-- 1.3.6.1.4.1.37950.1.1.5.12.5.1.9
-- 1.3.6.1.4.1.37950.1.1.5.12.5.1.9
-- 1.3.6.1.4.1.37950.1.1.5.12.5.1.9
-- 1.3.6.1.4.1.37950.1.1.5.12.5.1.9
-- 1.3.6.1.4.1.37950.1.1.5.12.5.1.9
		-- 1.3.6.1.4.1.37950.1.1.5.12.5.1.9
		onuPortLinkstateTable OBJECT-TYPE
			SYNTAX SEQUENCE OF OnuPortLinkstateEntry
			MAX-ACCESS not-accessible
			STATUS current
			DESCRIPTION
				"Description."
			::= { onuPortInfo 9 }

		
--          1.3.6.1.4.1.37950.1.1.5.12.5.1.9.1
-- 1.3.6.1.4.1.37950.1.1.5.12.5.1.9.1
-- 1.3.6.1.4.1.37950.1.1.5.12.5.1.9.1
-- 1.3.6.1.4.1.37950.1.1.5.12.5.1.9.1
-- 1.3.6.1.4.1.37950.1.1.5.12.5.1.9.1
-- 1.3.6.1.4.1.37950.1.1.5.12.5.1.9.1
-- 1.3.6.1.4.1.37950.1.1.5.12.5.1.9.1
-- 1.3.6.1.4.1.37950.1.1.5.12.5.1.9.1
-- 1.3.6.1.4.1.37950.1.1.5.12.5.1.9.1
		-- 1.3.6.1.4.1.37950.1.1.5.12.5.1.9.1
		onuPortLinkstateEntry OBJECT-TYPE
			SYNTAX OnuPortLinkstateEntry
			MAX-ACCESS not-accessible
			STATUS current
			DESCRIPTION
				"Description."
			INDEX { onuPortLinkstatePonIndex, onuPortLinkstateOnuIndex, onuPortLinkstatePortIndex }
			::= { onuPortLinkstateTable 1 }

		
		OnuPortLinkstateEntry ::=
			SEQUENCE { 
				onuPortLinkstatePonIndex
					Integer32,
				onuPortLinkstateOnuIndex
					Integer32,
				onuPortLinkstatePortIndex
					Integer32,
				onuPortLinkstateVal
					INTEGER
			 }

--          1.3.6.1.4.1.37950.1.1.5.12.5.1.9.1.1
-- 1.3.6.1.4.1.37950.1.1.5.12.5.1.9.1.1
-- 1.3.6.1.4.1.37950.1.1.5.12.5.1.9.1.1
-- 1.3.6.1.4.1.37950.1.1.5.12.5.1.9.1.1
-- 1.3.6.1.4.1.37950.1.1.5.12.5.1.9.1.1
-- 1.3.6.1.4.1.37950.1.1.5.12.5.1.9.1.1
-- 1.3.6.1.4.1.37950.1.1.5.12.5.1.9.1.1
-- 1.3.6.1.4.1.37950.1.1.5.12.5.1.9.1.1
-- 1.3.6.1.4.1.37950.1.1.5.12.5.1.9.1.1
		-- 1.3.6.1.4.1.37950.1.1.5.12.5.1.9.1.1
		onuPortLinkstatePonIndex OBJECT-TYPE
			SYNTAX Integer32
			MAX-ACCESS read-only
			STATUS current
			DESCRIPTION
				"Description."
			::= { onuPortLinkstateEntry 1 }

		
--          1.3.6.1.4.1.37950.1.1.5.12.5.1.9.1.2
-- 1.3.6.1.4.1.37950.1.1.5.12.5.1.9.1.2
-- 1.3.6.1.4.1.37950.1.1.5.12.5.1.9.1.2
-- 1.3.6.1.4.1.37950.1.1.5.12.5.1.9.1.2
-- 1.3.6.1.4.1.37950.1.1.5.12.5.1.9.1.2
-- 1.3.6.1.4.1.37950.1.1.5.12.5.1.9.1.2
-- 1.3.6.1.4.1.37950.1.1.5.12.5.1.9.1.2
-- 1.3.6.1.4.1.37950.1.1.5.12.5.1.9.1.2
-- 1.3.6.1.4.1.37950.1.1.5.12.5.1.9.1.2
		-- 1.3.6.1.4.1.37950.1.1.5.12.5.1.9.1.2
		onuPortLinkstateOnuIndex OBJECT-TYPE
			SYNTAX Integer32
			MAX-ACCESS read-only
			STATUS current
			DESCRIPTION
				"Description."
			::= { onuPortLinkstateEntry 2 }

		
--          1.3.6.1.4.1.37950.1.1.5.12.5.1.9.1.3
-- 1.3.6.1.4.1.37950.1.1.5.12.5.1.9.1.3
-- 1.3.6.1.4.1.37950.1.1.5.12.5.1.9.1.3
-- 1.3.6.1.4.1.37950.1.1.5.12.5.1.9.1.3
-- 1.3.6.1.4.1.37950.1.1.5.12.5.1.9.1.3
-- 1.3.6.1.4.1.37950.1.1.5.12.5.1.9.1.3
-- 1.3.6.1.4.1.37950.1.1.5.12.5.1.9.1.3
-- 1.3.6.1.4.1.37950.1.1.5.12.5.1.9.1.3
-- 1.3.6.1.4.1.37950.1.1.5.12.5.1.9.1.3
		-- 1.3.6.1.4.1.37950.1.1.5.12.5.1.9.1.3
		onuPortLinkstatePortIndex OBJECT-TYPE
			SYNTAX Integer32
			MAX-ACCESS read-only
			STATUS current
			DESCRIPTION
				"Description."
			::= { onuPortLinkstateEntry 3 }

		
--          1.3.6.1.4.1.37950.1.1.5.12.5.1.9.1.4
-- 1.3.6.1.4.1.37950.1.1.5.12.5.1.9.1.4
-- 1.3.6.1.4.1.37950.1.1.5.12.5.1.9.1.4
-- 1.3.6.1.4.1.37950.1.1.5.12.5.1.9.1.4
-- 1.3.6.1.4.1.37950.1.1.5.12.5.1.9.1.4
-- 1.3.6.1.4.1.37950.1.1.5.12.5.1.9.1.4
-- 1.3.6.1.4.1.37950.1.1.5.12.5.1.9.1.4
-- 1.3.6.1.4.1.37950.1.1.5.12.5.1.9.1.4
-- 1.3.6.1.4.1.37950.1.1.5.12.5.1.9.1.4
		-- 1.3.6.1.4.1.37950.1.1.5.12.5.1.9.1.4
		onuPortLinkstateVal OBJECT-TYPE
			SYNTAX INTEGER
				{
				down(0),
				up(1)
				}
			MAX-ACCESS read-only
			STATUS current
			DESCRIPTION
				"Description."
			::= { onuPortLinkstateEntry 4 }

		
--          1.3.6.1.4.1.37950.1.1.5.12.5.1.10
-- 1.3.6.1.4.1.37950.1.1.5.12.5.1.10
-- 1.3.6.1.4.1.37950.1.1.5.12.5.1.10
-- 1.3.6.1.4.1.37950.1.1.5.12.5.1.10
-- 1.3.6.1.4.1.37950.1.1.5.12.5.1.10
-- 1.3.6.1.4.1.37950.1.1.5.12.5.1.10
-- 1.3.6.1.4.1.37950.1.1.5.12.5.1.10
-- 1.3.6.1.4.1.37950.1.1.5.12.5.1.10
-- 1.3.6.1.4.1.37950.1.1.5.12.5.1.10
		-- 1.3.6.1.4.1.37950.1.1.5.12.5.1.10
		onuVlanPortTable OBJECT-TYPE
			SYNTAX SEQUENCE OF OnuVlanPortEntry
			MAX-ACCESS not-accessible
			STATUS current
			DESCRIPTION
				"Description."
			::= { onuPortInfo 10 }

		
--          1.3.6.1.4.1.37950.1.1.5.12.5.1.10.1
-- 1.3.6.1.4.1.37950.1.1.5.12.5.1.10.1
-- 1.3.6.1.4.1.37950.1.1.5.12.5.1.10.1
-- 1.3.6.1.4.1.37950.1.1.5.12.5.1.10.1
-- 1.3.6.1.4.1.37950.1.1.5.12.5.1.10.1
-- 1.3.6.1.4.1.37950.1.1.5.12.5.1.10.1
-- 1.3.6.1.4.1.37950.1.1.5.12.5.1.10.1
-- 1.3.6.1.4.1.37950.1.1.5.12.5.1.10.1
-- 1.3.6.1.4.1.37950.1.1.5.12.5.1.10.1
		-- 1.3.6.1.4.1.37950.1.1.5.12.5.1.10.1
		onuVlanPortEntry OBJECT-TYPE
			SYNTAX OnuVlanPortEntry
			MAX-ACCESS not-accessible
			STATUS current
			DESCRIPTION
				"Description."
			INDEX { onuVlanPonIndex, onuVlanOnuIndex, onuVlanPortIndex }
			::= { onuVlanPortTable 1 }

		
		OnuVlanPortEntry ::=
			SEQUENCE { 
				onuVlanPonIndex
					Integer32,
				onuVlanOnuIndex
					Integer32,
				onuVlanPortIndex
					Integer32,
				onuVlanPortMode
					INTEGER,
				onuVlanPortPvid
					INTEGER,
				onuVlanPortVlan
					OCTET STRING,
				onuVlanPortPri
					Integer32
			 }

--          1.3.6.1.4.1.37950.1.1.5.12.5.1.10.1.1
-- 1.3.6.1.4.1.37950.1.1.5.12.5.1.10.1.1
-- 1.3.6.1.4.1.37950.1.1.5.12.5.1.10.1.1
-- 1.3.6.1.4.1.37950.1.1.5.12.5.1.10.1.1
-- 1.3.6.1.4.1.37950.1.1.5.12.5.1.10.1.1
-- 1.3.6.1.4.1.37950.1.1.5.12.5.1.10.1.1
-- 1.3.6.1.4.1.37950.1.1.5.12.5.1.10.1.1
-- 1.3.6.1.4.1.37950.1.1.5.12.5.1.10.1.1
-- 1.3.6.1.4.1.37950.1.1.5.12.5.1.10.1.1
		-- 1.3.6.1.4.1.37950.1.1.5.12.5.1.10.1.1
		onuVlanPonIndex OBJECT-TYPE
			SYNTAX Integer32
			MAX-ACCESS read-only
			STATUS current
			DESCRIPTION
				"Description."
			::= { onuVlanPortEntry 1 }

		
--          1.3.6.1.4.1.37950.1.1.5.12.5.1.10.1.2
-- 1.3.6.1.4.1.37950.1.1.5.12.5.1.10.1.2
-- 1.3.6.1.4.1.37950.1.1.5.12.5.1.10.1.2
-- 1.3.6.1.4.1.37950.1.1.5.12.5.1.10.1.2
-- 1.3.6.1.4.1.37950.1.1.5.12.5.1.10.1.2
-- 1.3.6.1.4.1.37950.1.1.5.12.5.1.10.1.2
-- 1.3.6.1.4.1.37950.1.1.5.12.5.1.10.1.2
-- 1.3.6.1.4.1.37950.1.1.5.12.5.1.10.1.2
-- 1.3.6.1.4.1.37950.1.1.5.12.5.1.10.1.2
		-- 1.3.6.1.4.1.37950.1.1.5.12.5.1.10.1.2
		onuVlanOnuIndex OBJECT-TYPE
			SYNTAX Integer32
			MAX-ACCESS read-only
			STATUS current
			DESCRIPTION
				"Description."
			::= { onuVlanPortEntry 2 }

		
--          1.3.6.1.4.1.37950.1.1.5.12.5.1.10.1.3
-- 1.3.6.1.4.1.37950.1.1.5.12.5.1.10.1.3
-- 1.3.6.1.4.1.37950.1.1.5.12.5.1.10.1.3
-- 1.3.6.1.4.1.37950.1.1.5.12.5.1.10.1.3
-- 1.3.6.1.4.1.37950.1.1.5.12.5.1.10.1.3
-- 1.3.6.1.4.1.37950.1.1.5.12.5.1.10.1.3
-- 1.3.6.1.4.1.37950.1.1.5.12.5.1.10.1.3
-- 1.3.6.1.4.1.37950.1.1.5.12.5.1.10.1.3
-- 1.3.6.1.4.1.37950.1.1.5.12.5.1.10.1.3
		-- 1.3.6.1.4.1.37950.1.1.5.12.5.1.10.1.3
		onuVlanPortIndex OBJECT-TYPE
			SYNTAX Integer32
			MAX-ACCESS read-only
			STATUS current
			DESCRIPTION
				"Description."
			::= { onuVlanPortEntry 3 }

		
--          1.3.6.1.4.1.37950.1.1.5.12.5.1.10.1.4
-- 1.3.6.1.4.1.37950.1.1.5.12.5.1.10.1.4
-- 1.3.6.1.4.1.37950.1.1.5.12.5.1.10.1.4
-- 1.3.6.1.4.1.37950.1.1.5.12.5.1.10.1.4
-- 1.3.6.1.4.1.37950.1.1.5.12.5.1.10.1.4
-- 1.3.6.1.4.1.37950.1.1.5.12.5.1.10.1.4
-- 1.3.6.1.4.1.37950.1.1.5.12.5.1.10.1.4
-- 1.3.6.1.4.1.37950.1.1.5.12.5.1.10.1.4
-- 1.3.6.1.4.1.37950.1.1.5.12.5.1.10.1.4
		-- 1.3.6.1.4.1.37950.1.1.5.12.5.1.10.1.4
		onuVlanPortMode OBJECT-TYPE
			SYNTAX INTEGER
				{
				transparent(0),
				tag(1),
				translation(2),
				aggregation(3),
				trunk(4)
				}
			MAX-ACCESS read-only
			STATUS current
			DESCRIPTION
				"Description."
			::= { onuVlanPortEntry 4 }

		
--          1.3.6.1.4.1.37950.1.1.5.12.5.1.10.1.5
-- 1.3.6.1.4.1.37950.1.1.5.12.5.1.10.1.5
-- 1.3.6.1.4.1.37950.1.1.5.12.5.1.10.1.5
-- 1.3.6.1.4.1.37950.1.1.5.12.5.1.10.1.5
-- 1.3.6.1.4.1.37950.1.1.5.12.5.1.10.1.5
-- 1.3.6.1.4.1.37950.1.1.5.12.5.1.10.1.5
-- 1.3.6.1.4.1.37950.1.1.5.12.5.1.10.1.5
-- 1.3.6.1.4.1.37950.1.1.5.12.5.1.10.1.5
-- 1.3.6.1.4.1.37950.1.1.5.12.5.1.10.1.5
		-- 1.3.6.1.4.1.37950.1.1.5.12.5.1.10.1.5
		onuVlanPortPvid OBJECT-TYPE
			SYNTAX INTEGER
			MAX-ACCESS read-only
			STATUS current
			DESCRIPTION
				"Description."
			::= { onuVlanPortEntry 5 }

		
--          1.3.6.1.4.1.37950.1.1.5.12.5.1.10.1.6
-- 1.3.6.1.4.1.37950.1.1.5.12.5.1.10.1.6
-- 1.3.6.1.4.1.37950.1.1.5.12.5.1.10.1.6
-- 1.3.6.1.4.1.37950.1.1.5.12.5.1.10.1.6
-- 1.3.6.1.4.1.37950.1.1.5.12.5.1.10.1.6
-- 1.3.6.1.4.1.37950.1.1.5.12.5.1.10.1.6
-- 1.3.6.1.4.1.37950.1.1.5.12.5.1.10.1.6
-- 1.3.6.1.4.1.37950.1.1.5.12.5.1.10.1.6
-- 1.3.6.1.4.1.37950.1.1.5.12.5.1.10.1.6
		-- 1.3.6.1.4.1.37950.1.1.5.12.5.1.10.1.6
		onuVlanPortVlan OBJECT-TYPE
			SYNTAX OCTET STRING
			MAX-ACCESS read-only
			STATUS current
			DESCRIPTION
				"Description."
			::= { onuVlanPortEntry 6 }

		
--         1.3.6.1.4.1.37950.1.1.5.12.5.1.10.1.7
-- 1.3.6.1.4.1.37950.1.1.5.12.5.1.10.1.7
-- 1.3.6.1.4.1.37950.1.1.5.12.5.1.10.1.7
-- 1.3.6.1.4.1.37950.1.1.5.12.5.1.10.1.7
-- 1.3.6.1.4.1.37950.1.1.5.12.5.1.10.1.7
-- 1.3.6.1.4.1.37950.1.1.5.12.5.1.10.1.7
-- 1.3.6.1.4.1.37950.1.1.5.12.5.1.10.1.7
-- 1.3.6.1.4.1.37950.1.1.5.12.5.1.10.1.7
		-- 1.3.6.1.4.1.37950.1.1.5.12.5.1.10.1.7
		onuVlanPortPri OBJECT-TYPE
			SYNTAX Integer32
			MAX-ACCESS read-only
			STATUS current
			DESCRIPTION
				"Description."
			::= { onuVlanPortEntry 7 }

		
--          1.3.6.1.4.1.37950.1.1.5.12.5.1.11
-- 1.3.6.1.4.1.37950.1.1.5.12.5.1.11
-- 1.3.6.1.4.1.37950.1.1.5.12.5.1.11
-- 1.3.6.1.4.1.37950.1.1.5.12.5.1.11
-- 1.3.6.1.4.1.37950.1.1.5.12.5.1.11
-- 1.3.6.1.4.1.37950.1.1.5.12.5.1.11
-- 1.3.6.1.4.1.37950.1.1.5.12.5.1.11
-- 1.3.6.1.4.1.37950.1.1.5.12.5.1.11
-- 1.3.6.1.4.1.37950.1.1.5.12.5.1.11
		-- 1.3.6.1.4.1.37950.1.1.5.12.5.1.11
		onuPortStatEnTable OBJECT-TYPE
			SYNTAX SEQUENCE OF OnuPortStatEnEntry
			MAX-ACCESS not-accessible
			STATUS current
			DESCRIPTION
				"Description."
			::= { onuPortInfo 11 }

		
--          1.3.6.1.4.1.37950.1.1.5.12.5.1.11.1
-- 1.3.6.1.4.1.37950.1.1.5.12.5.1.11.1
-- 1.3.6.1.4.1.37950.1.1.5.12.5.1.11.1
-- 1.3.6.1.4.1.37950.1.1.5.12.5.1.11.1
-- 1.3.6.1.4.1.37950.1.1.5.12.5.1.11.1
-- 1.3.6.1.4.1.37950.1.1.5.12.5.1.11.1
-- 1.3.6.1.4.1.37950.1.1.5.12.5.1.11.1
-- 1.3.6.1.4.1.37950.1.1.5.12.5.1.11.1
-- 1.3.6.1.4.1.37950.1.1.5.12.5.1.11.1
		-- 1.3.6.1.4.1.37950.1.1.5.12.5.1.11.1
		onuPortStatEnEntry OBJECT-TYPE
			SYNTAX OnuPortStatEnEntry
			MAX-ACCESS not-accessible
			STATUS current
			DESCRIPTION
				"Description."
			INDEX { onuPortStatEnPonIndex, onuPortStatEnOnuIndex, onuPortStatEnPortIndex }
			::= { onuPortStatEnTable 1 }

		
		OnuPortStatEnEntry ::=
			SEQUENCE { 
				onuPortStatEnPonIndex
					Integer32,
				onuPortStatEnOnuIndex
					Integer32,
				onuPortStatEnPortIndex
					Integer32,
				onuPortStatEn
					INTEGER,
				onuPortStatEnPeriod
					INTEGER
			 }

--          1.3.6.1.4.1.37950.1.1.5.12.5.1.11.1.1
-- 1.3.6.1.4.1.37950.1.1.5.12.5.1.11.1.1
-- 1.3.6.1.4.1.37950.1.1.5.12.5.1.11.1.1
-- 1.3.6.1.4.1.37950.1.1.5.12.5.1.11.1.1
-- 1.3.6.1.4.1.37950.1.1.5.12.5.1.11.1.1
-- 1.3.6.1.4.1.37950.1.1.5.12.5.1.11.1.1
-- 1.3.6.1.4.1.37950.1.1.5.12.5.1.11.1.1
-- 1.3.6.1.4.1.37950.1.1.5.12.5.1.11.1.1
-- 1.3.6.1.4.1.37950.1.1.5.12.5.1.11.1.1
		-- 1.3.6.1.4.1.37950.1.1.5.12.5.1.11.1.1
		onuPortStatEnPonIndex OBJECT-TYPE
			SYNTAX Integer32
			MAX-ACCESS read-only
			STATUS current
			DESCRIPTION
				"Description."
			::= { onuPortStatEnEntry 1 }

		
--          1.3.6.1.4.1.37950.1.1.5.12.5.1.11.1.2
-- 1.3.6.1.4.1.37950.1.1.5.12.5.1.11.1.2
-- 1.3.6.1.4.1.37950.1.1.5.12.5.1.11.1.2
-- 1.3.6.1.4.1.37950.1.1.5.12.5.1.11.1.2
-- 1.3.6.1.4.1.37950.1.1.5.12.5.1.11.1.2
-- 1.3.6.1.4.1.37950.1.1.5.12.5.1.11.1.2
-- 1.3.6.1.4.1.37950.1.1.5.12.5.1.11.1.2
-- 1.3.6.1.4.1.37950.1.1.5.12.5.1.11.1.2
-- 1.3.6.1.4.1.37950.1.1.5.12.5.1.11.1.2
		-- 1.3.6.1.4.1.37950.1.1.5.12.5.1.11.1.2
		onuPortStatEnOnuIndex OBJECT-TYPE
			SYNTAX Integer32
			MAX-ACCESS read-only
			STATUS current
			DESCRIPTION
				"Description."
			::= { onuPortStatEnEntry 2 }

		
--          1.3.6.1.4.1.37950.1.1.5.12.5.1.11.1.3
-- 1.3.6.1.4.1.37950.1.1.5.12.5.1.11.1.3
-- 1.3.6.1.4.1.37950.1.1.5.12.5.1.11.1.3
-- 1.3.6.1.4.1.37950.1.1.5.12.5.1.11.1.3
-- 1.3.6.1.4.1.37950.1.1.5.12.5.1.11.1.3
-- 1.3.6.1.4.1.37950.1.1.5.12.5.1.11.1.3
-- 1.3.6.1.4.1.37950.1.1.5.12.5.1.11.1.3
-- 1.3.6.1.4.1.37950.1.1.5.12.5.1.11.1.3
-- 1.3.6.1.4.1.37950.1.1.5.12.5.1.11.1.3
		-- 1.3.6.1.4.1.37950.1.1.5.12.5.1.11.1.3
		onuPortStatEnPortIndex OBJECT-TYPE
			SYNTAX Integer32
			MAX-ACCESS read-only
			STATUS current
			DESCRIPTION
				"Description."
			::= { onuPortStatEnEntry 3 }

		
--          1.3.6.1.4.1.37950.1.1.5.12.5.1.11.1.4
-- 1.3.6.1.4.1.37950.1.1.5.12.5.1.11.1.4
-- 1.3.6.1.4.1.37950.1.1.5.12.5.1.11.1.4
-- 1.3.6.1.4.1.37950.1.1.5.12.5.1.11.1.4
-- 1.3.6.1.4.1.37950.1.1.5.12.5.1.11.1.4
-- 1.3.6.1.4.1.37950.1.1.5.12.5.1.11.1.4
-- 1.3.6.1.4.1.37950.1.1.5.12.5.1.11.1.4
-- 1.3.6.1.4.1.37950.1.1.5.12.5.1.11.1.4
-- 1.3.6.1.4.1.37950.1.1.5.12.5.1.11.1.4
		-- 1.3.6.1.4.1.37950.1.1.5.12.5.1.11.1.4
		onuPortStatEn OBJECT-TYPE
			SYNTAX INTEGER
				{
				disable(0),
				enable(1)
				}
			MAX-ACCESS read-only
			STATUS current
			DESCRIPTION
				"Description."
			::= { onuPortStatEnEntry 4 }

		
--          1.3.6.1.4.1.37950.1.1.5.12.5.1.11.1.5
-- 1.3.6.1.4.1.37950.1.1.5.12.5.1.11.1.5
-- 1.3.6.1.4.1.37950.1.1.5.12.5.1.11.1.5
-- 1.3.6.1.4.1.37950.1.1.5.12.5.1.11.1.5
-- 1.3.6.1.4.1.37950.1.1.5.12.5.1.11.1.5
-- 1.3.6.1.4.1.37950.1.1.5.12.5.1.11.1.5
-- 1.3.6.1.4.1.37950.1.1.5.12.5.1.11.1.5
-- 1.3.6.1.4.1.37950.1.1.5.12.5.1.11.1.5
-- 1.3.6.1.4.1.37950.1.1.5.12.5.1.11.1.5
		-- 1.3.6.1.4.1.37950.1.1.5.12.5.1.11.1.5
		onuPortStatEnPeriod OBJECT-TYPE
			SYNTAX INTEGER
			MAX-ACCESS read-only
			STATUS current
			DESCRIPTION
				"Description."
			::= { onuPortStatEnEntry 5 }

		
--          1.3.6.1.4.1.37950.1.1.5.12.5.1.12
-- 1.3.6.1.4.1.37950.1.1.5.12.5.1.12
-- 1.3.6.1.4.1.37950.1.1.5.12.5.1.12
-- 1.3.6.1.4.1.37950.1.1.5.12.5.1.12
-- 1.3.6.1.4.1.37950.1.1.5.12.5.1.12
-- 1.3.6.1.4.1.37950.1.1.5.12.5.1.12
-- 1.3.6.1.4.1.37950.1.1.5.12.5.1.12
-- 1.3.6.1.4.1.37950.1.1.5.12.5.1.12
-- 1.3.6.1.4.1.37950.1.1.5.12.5.1.12
		-- 1.3.6.1.4.1.37950.1.1.5.12.5.1.12
		onuPortStatTable OBJECT-TYPE
			SYNTAX SEQUENCE OF OnuPortStatEntry
			MAX-ACCESS not-accessible
			STATUS current
			DESCRIPTION
				"Description."
			::= { onuPortInfo 12 }

		
--          1.3.6.1.4.1.37950.1.1.5.12.5.1.12.1
-- 1.3.6.1.4.1.37950.1.1.5.12.5.1.12.1
-- 1.3.6.1.4.1.37950.1.1.5.12.5.1.12.1
-- 1.3.6.1.4.1.37950.1.1.5.12.5.1.12.1
-- 1.3.6.1.4.1.37950.1.1.5.12.5.1.12.1
-- 1.3.6.1.4.1.37950.1.1.5.12.5.1.12.1
-- 1.3.6.1.4.1.37950.1.1.5.12.5.1.12.1
-- 1.3.6.1.4.1.37950.1.1.5.12.5.1.12.1
-- 1.3.6.1.4.1.37950.1.1.5.12.5.1.12.1
		-- 1.3.6.1.4.1.37950.1.1.5.12.5.1.12.1
		onuPortStatEntry OBJECT-TYPE
			SYNTAX OnuPortStatEntry
			MAX-ACCESS not-accessible
			STATUS current
			DESCRIPTION
				"Description."
			INDEX { onuPortStatPonIndex, onuPortStatOnuIndex, onuPortStatPortIndex }
			::= { onuPortStatTable 1 }

		
		OnuPortStatEntry ::=
			SEQUENCE { 
				onuPortStatPonIndex
					Integer32,
				onuPortStatOnuIndex
					Integer32,
				onuPortStatPortIndex
					Integer32,
				statDnDropEvents
					Counter32,
				statUpDropEvents
					Counter32,
				statDnOctets
					Counter32,
				statUpOctets
					Counter32,
				statDnFrames
					Counter32,
				statUpFrames
					Counter32,
				statDnBcFrames
					Counter32,
				statUpBcFrames
					Counter32,
				statDnMcFrames
					Counter32,
				statUpMcFrames
					Counter32,
				statDnCrcErrFrames
					Counter32,
				statUpCrcErrFrames
					Counter32,
				statDnUndersizeFrames
					Counter32,
				statUpUndersizeFrames
					Counter32,
				statDnOversizeFrames
					Counter32,
				statUpOversizeFrames
					Counter32,
				statDnFragments
					Counter32,
				statUpFragments
					Counter32,
				statDnJabbers
					Counter32,
				statUpJabbers
					Counter32,
				statDn64OctetsFrames
					Counter32,
				statDn65to127OctetsFrames
					Counter32,
				statDn128to255OctetsFrames
					Counter32,
				statDn256to511OctetsFrames
					Counter32,
				statDn512to1023OctetsFrames
					Counter32,
				statDn1024to1518OctetsFrames
					Counter32,
				statUp64OctetsFrames
					Counter32,
				statUp65to127OctetsFrames
					Counter32,
				statUp128to255OctetsFrames
					Counter32,
				statUp256to511OctetsFrames
					Counter32,
				statUp512to1023OctetsFrames
					Counter32,
				statUp1024to1518OctetsFrames
					Counter32,
				statDnDiscardFrames
					Counter32,
				statUpDiscardFrames
					Counter32,
				statDnErrFrames
					Counter32,
				statUpErrFrames
					Counter32,
				statStatusChangeTimes
					Counter32
			 }

--          1.3.6.1.4.1.37950.1.1.5.12.5.1.12.1.1
-- 1.3.6.1.4.1.37950.1.1.5.12.5.1.12.1.1
-- 1.3.6.1.4.1.37950.1.1.5.12.5.1.12.1.1
-- 1.3.6.1.4.1.37950.1.1.5.12.5.1.12.1.1
-- 1.3.6.1.4.1.37950.1.1.5.12.5.1.12.1.1
-- 1.3.6.1.4.1.37950.1.1.5.12.5.1.12.1.1
-- 1.3.6.1.4.1.37950.1.1.5.12.5.1.12.1.1
-- 1.3.6.1.4.1.37950.1.1.5.12.5.1.12.1.1
-- 1.3.6.1.4.1.37950.1.1.5.12.5.1.12.1.1
		-- 1.3.6.1.4.1.37950.1.1.5.12.5.1.12.1.1
		onuPortStatPonIndex OBJECT-TYPE
			SYNTAX Integer32
			MAX-ACCESS read-only
			STATUS current
			DESCRIPTION
				"Description."
			::= { onuPortStatEntry 1 }

		
--          1.3.6.1.4.1.37950.1.1.5.12.5.1.12.1.2
-- 1.3.6.1.4.1.37950.1.1.5.12.5.1.12.1.2
-- 1.3.6.1.4.1.37950.1.1.5.12.5.1.12.1.2
-- 1.3.6.1.4.1.37950.1.1.5.12.5.1.12.1.2
-- 1.3.6.1.4.1.37950.1.1.5.12.5.1.12.1.2
-- 1.3.6.1.4.1.37950.1.1.5.12.5.1.12.1.2
-- 1.3.6.1.4.1.37950.1.1.5.12.5.1.12.1.2
-- 1.3.6.1.4.1.37950.1.1.5.12.5.1.12.1.2
-- 1.3.6.1.4.1.37950.1.1.5.12.5.1.12.1.2
		-- 1.3.6.1.4.1.37950.1.1.5.12.5.1.12.1.2
		onuPortStatOnuIndex OBJECT-TYPE
			SYNTAX Integer32
			MAX-ACCESS read-only
			STATUS current
			DESCRIPTION
				"Description."
			::= { onuPortStatEntry 2 }

		
--          1.3.6.1.4.1.37950.1.1.5.12.5.1.12.1.3
-- 1.3.6.1.4.1.37950.1.1.5.12.5.1.12.1.3
-- 1.3.6.1.4.1.37950.1.1.5.12.5.1.12.1.3
-- 1.3.6.1.4.1.37950.1.1.5.12.5.1.12.1.3
-- 1.3.6.1.4.1.37950.1.1.5.12.5.1.12.1.3
-- 1.3.6.1.4.1.37950.1.1.5.12.5.1.12.1.3
-- 1.3.6.1.4.1.37950.1.1.5.12.5.1.12.1.3
-- 1.3.6.1.4.1.37950.1.1.5.12.5.1.12.1.3
-- 1.3.6.1.4.1.37950.1.1.5.12.5.1.12.1.3
		-- 1.3.6.1.4.1.37950.1.1.5.12.5.1.12.1.3
		onuPortStatPortIndex OBJECT-TYPE
			SYNTAX Integer32
			MAX-ACCESS read-only
			STATUS current
			DESCRIPTION
				"Description."
			::= { onuPortStatEntry 3 }

		
--          1.3.6.1.4.1.37950.1.1.5.12.5.1.12.1.4
-- 1.3.6.1.4.1.37950.1.1.5.12.5.1.12.1.4
-- 1.3.6.1.4.1.37950.1.1.5.12.5.1.12.1.4
-- 1.3.6.1.4.1.37950.1.1.5.12.5.1.12.1.4
-- 1.3.6.1.4.1.37950.1.1.5.12.5.1.12.1.4
-- 1.3.6.1.4.1.37950.1.1.5.12.5.1.12.1.4
-- 1.3.6.1.4.1.37950.1.1.5.12.5.1.12.1.4
-- 1.3.6.1.4.1.37950.1.1.5.12.5.1.12.1.4
-- 1.3.6.1.4.1.37950.1.1.5.12.5.1.12.1.4
		-- 1.3.6.1.4.1.37950.1.1.5.12.5.1.12.1.4
		statDnDropEvents OBJECT-TYPE
			SYNTAX Counter32
			MAX-ACCESS read-only
			STATUS current
			DESCRIPTION
				"Description."
			::= { onuPortStatEntry 4 }

		
--          1.3.6.1.4.1.37950.1.1.5.12.5.1.12.1.5
-- 1.3.6.1.4.1.37950.1.1.5.12.5.1.12.1.5
-- 1.3.6.1.4.1.37950.1.1.5.12.5.1.12.1.5
-- 1.3.6.1.4.1.37950.1.1.5.12.5.1.12.1.5
-- 1.3.6.1.4.1.37950.1.1.5.12.5.1.12.1.5
-- 1.3.6.1.4.1.37950.1.1.5.12.5.1.12.1.5
-- 1.3.6.1.4.1.37950.1.1.5.12.5.1.12.1.5
-- 1.3.6.1.4.1.37950.1.1.5.12.5.1.12.1.5
-- 1.3.6.1.4.1.37950.1.1.5.12.5.1.12.1.5
		-- 1.3.6.1.4.1.37950.1.1.5.12.5.1.12.1.5
		statUpDropEvents OBJECT-TYPE
			SYNTAX Counter32
			MAX-ACCESS read-only
			STATUS current
			DESCRIPTION
				"Description."
			::= { onuPortStatEntry 5 }

		
--          1.3.6.1.4.1.37950.1.1.5.12.5.1.12.1.6
-- 1.3.6.1.4.1.37950.1.1.5.12.5.1.12.1.6
-- 1.3.6.1.4.1.37950.1.1.5.12.5.1.12.1.6
-- 1.3.6.1.4.1.37950.1.1.5.12.5.1.12.1.6
-- 1.3.6.1.4.1.37950.1.1.5.12.5.1.12.1.6
-- 1.3.6.1.4.1.37950.1.1.5.12.5.1.12.1.6
-- 1.3.6.1.4.1.37950.1.1.5.12.5.1.12.1.6
-- 1.3.6.1.4.1.37950.1.1.5.12.5.1.12.1.6
-- 1.3.6.1.4.1.37950.1.1.5.12.5.1.12.1.6
		-- 1.3.6.1.4.1.37950.1.1.5.12.5.1.12.1.6
		statDnOctets OBJECT-TYPE
			SYNTAX Counter32
			MAX-ACCESS read-only
			STATUS current
			DESCRIPTION
				"Description."
			::= { onuPortStatEntry 6 }

		
--          1.3.6.1.4.1.37950.1.1.5.12.5.1.12.1.7
-- 1.3.6.1.4.1.37950.1.1.5.12.5.1.12.1.7
-- 1.3.6.1.4.1.37950.1.1.5.12.5.1.12.1.7
-- 1.3.6.1.4.1.37950.1.1.5.12.5.1.12.1.7
-- 1.3.6.1.4.1.37950.1.1.5.12.5.1.12.1.7
-- 1.3.6.1.4.1.37950.1.1.5.12.5.1.12.1.7
-- 1.3.6.1.4.1.37950.1.1.5.12.5.1.12.1.7
-- 1.3.6.1.4.1.37950.1.1.5.12.5.1.12.1.7
-- 1.3.6.1.4.1.37950.1.1.5.12.5.1.12.1.7
		-- 1.3.6.1.4.1.37950.1.1.5.12.5.1.12.1.7
		statUpOctets OBJECT-TYPE
			SYNTAX Counter32
			MAX-ACCESS read-only
			STATUS current
			DESCRIPTION
				"Description."
			::= { onuPortStatEntry 7 }

		
--          1.3.6.1.4.1.37950.1.1.5.12.5.1.12.1.8
-- 1.3.6.1.4.1.37950.1.1.5.12.5.1.12.1.8
-- 1.3.6.1.4.1.37950.1.1.5.12.5.1.12.1.8
-- 1.3.6.1.4.1.37950.1.1.5.12.5.1.12.1.8
-- 1.3.6.1.4.1.37950.1.1.5.12.5.1.12.1.8
-- 1.3.6.1.4.1.37950.1.1.5.12.5.1.12.1.8
-- 1.3.6.1.4.1.37950.1.1.5.12.5.1.12.1.8
-- 1.3.6.1.4.1.37950.1.1.5.12.5.1.12.1.8
-- 1.3.6.1.4.1.37950.1.1.5.12.5.1.12.1.8
		-- 1.3.6.1.4.1.37950.1.1.5.12.5.1.12.1.8
		statDnFrames OBJECT-TYPE
			SYNTAX Counter32
			MAX-ACCESS read-only
			STATUS current
			DESCRIPTION
				"Description."
			::= { onuPortStatEntry 8 }

		
--          1.3.6.1.4.1.37950.1.1.5.12.5.1.12.1.9
-- 1.3.6.1.4.1.37950.1.1.5.12.5.1.12.1.9
-- 1.3.6.1.4.1.37950.1.1.5.12.5.1.12.1.9
-- 1.3.6.1.4.1.37950.1.1.5.12.5.1.12.1.9
-- 1.3.6.1.4.1.37950.1.1.5.12.5.1.12.1.9
-- 1.3.6.1.4.1.37950.1.1.5.12.5.1.12.1.9
-- 1.3.6.1.4.1.37950.1.1.5.12.5.1.12.1.9
-- 1.3.6.1.4.1.37950.1.1.5.12.5.1.12.1.9
-- 1.3.6.1.4.1.37950.1.1.5.12.5.1.12.1.9
		-- 1.3.6.1.4.1.37950.1.1.5.12.5.1.12.1.9
		statUpFrames OBJECT-TYPE
			SYNTAX Counter32
			MAX-ACCESS read-only
			STATUS current
			DESCRIPTION
				"Description."
			::= { onuPortStatEntry 9 }

		
--          1.3.6.1.4.1.37950.1.1.5.12.5.1.12.1.10
-- 1.3.6.1.4.1.37950.1.1.5.12.5.1.12.1.10
-- 1.3.6.1.4.1.37950.1.1.5.12.5.1.12.1.10
-- 1.3.6.1.4.1.37950.1.1.5.12.5.1.12.1.10
-- 1.3.6.1.4.1.37950.1.1.5.12.5.1.12.1.10
-- 1.3.6.1.4.1.37950.1.1.5.12.5.1.12.1.10
-- 1.3.6.1.4.1.37950.1.1.5.12.5.1.12.1.10
-- 1.3.6.1.4.1.37950.1.1.5.12.5.1.12.1.10
-- 1.3.6.1.4.1.37950.1.1.5.12.5.1.12.1.10
		-- 1.3.6.1.4.1.37950.1.1.5.12.5.1.12.1.10
		statDnBcFrames OBJECT-TYPE
			SYNTAX Counter32
			MAX-ACCESS read-only
			STATUS current
			DESCRIPTION
				"Description."
			::= { onuPortStatEntry 10 }

		
--          1.3.6.1.4.1.37950.1.1.5.12.5.1.12.1.11
-- 1.3.6.1.4.1.37950.1.1.5.12.5.1.12.1.11
-- 1.3.6.1.4.1.37950.1.1.5.12.5.1.12.1.11
-- 1.3.6.1.4.1.37950.1.1.5.12.5.1.12.1.11
-- 1.3.6.1.4.1.37950.1.1.5.12.5.1.12.1.11
-- 1.3.6.1.4.1.37950.1.1.5.12.5.1.12.1.11
-- 1.3.6.1.4.1.37950.1.1.5.12.5.1.12.1.11
-- 1.3.6.1.4.1.37950.1.1.5.12.5.1.12.1.11
-- 1.3.6.1.4.1.37950.1.1.5.12.5.1.12.1.11
		-- 1.3.6.1.4.1.37950.1.1.5.12.5.1.12.1.11
		statUpBcFrames OBJECT-TYPE
			SYNTAX Counter32
			MAX-ACCESS read-only
			STATUS current
			DESCRIPTION
				"Description."
			::= { onuPortStatEntry 11 }

		
--          1.3.6.1.4.1.37950.1.1.5.12.5.1.12.1.12
-- 1.3.6.1.4.1.37950.1.1.5.12.5.1.12.1.12
-- 1.3.6.1.4.1.37950.1.1.5.12.5.1.12.1.12
-- 1.3.6.1.4.1.37950.1.1.5.12.5.1.12.1.12
-- 1.3.6.1.4.1.37950.1.1.5.12.5.1.12.1.12
-- 1.3.6.1.4.1.37950.1.1.5.12.5.1.12.1.12
-- 1.3.6.1.4.1.37950.1.1.5.12.5.1.12.1.12
-- 1.3.6.1.4.1.37950.1.1.5.12.5.1.12.1.12
-- 1.3.6.1.4.1.37950.1.1.5.12.5.1.12.1.12
		-- 1.3.6.1.4.1.37950.1.1.5.12.5.1.12.1.12
		statDnMcFrames OBJECT-TYPE
			SYNTAX Counter32
			MAX-ACCESS read-only
			STATUS current
			DESCRIPTION
				"Description."
			::= { onuPortStatEntry 12 }

		
--          1.3.6.1.4.1.37950.1.1.5.12.5.1.12.1.13
-- 1.3.6.1.4.1.37950.1.1.5.12.5.1.12.1.13
-- 1.3.6.1.4.1.37950.1.1.5.12.5.1.12.1.13
-- 1.3.6.1.4.1.37950.1.1.5.12.5.1.12.1.13
-- 1.3.6.1.4.1.37950.1.1.5.12.5.1.12.1.13
-- 1.3.6.1.4.1.37950.1.1.5.12.5.1.12.1.13
-- 1.3.6.1.4.1.37950.1.1.5.12.5.1.12.1.13
-- 1.3.6.1.4.1.37950.1.1.5.12.5.1.12.1.13
-- 1.3.6.1.4.1.37950.1.1.5.12.5.1.12.1.13
		-- 1.3.6.1.4.1.37950.1.1.5.12.5.1.12.1.13
		statUpMcFrames OBJECT-TYPE
			SYNTAX Counter32
			MAX-ACCESS read-only
			STATUS current
			DESCRIPTION
				"Description."
			::= { onuPortStatEntry 13 }

		
--          1.3.6.1.4.1.37950.1.1.5.12.5.1.12.1.14
-- 1.3.6.1.4.1.37950.1.1.5.12.5.1.12.1.14
-- 1.3.6.1.4.1.37950.1.1.5.12.5.1.12.1.14
-- 1.3.6.1.4.1.37950.1.1.5.12.5.1.12.1.14
-- 1.3.6.1.4.1.37950.1.1.5.12.5.1.12.1.14
-- 1.3.6.1.4.1.37950.1.1.5.12.5.1.12.1.14
-- 1.3.6.1.4.1.37950.1.1.5.12.5.1.12.1.14
-- 1.3.6.1.4.1.37950.1.1.5.12.5.1.12.1.14
-- 1.3.6.1.4.1.37950.1.1.5.12.5.1.12.1.14
		-- 1.3.6.1.4.1.37950.1.1.5.12.5.1.12.1.14
		statDnCrcErrFrames OBJECT-TYPE
			SYNTAX Counter32
			MAX-ACCESS read-only
			STATUS current
			DESCRIPTION
				"Description."
			::= { onuPortStatEntry 14 }

		
--          1.3.6.1.4.1.37950.1.1.5.12.5.1.12.1.15
-- 1.3.6.1.4.1.37950.1.1.5.12.5.1.12.1.15
-- 1.3.6.1.4.1.37950.1.1.5.12.5.1.12.1.15
-- 1.3.6.1.4.1.37950.1.1.5.12.5.1.12.1.15
-- 1.3.6.1.4.1.37950.1.1.5.12.5.1.12.1.15
-- 1.3.6.1.4.1.37950.1.1.5.12.5.1.12.1.15
-- 1.3.6.1.4.1.37950.1.1.5.12.5.1.12.1.15
-- 1.3.6.1.4.1.37950.1.1.5.12.5.1.12.1.15
-- 1.3.6.1.4.1.37950.1.1.5.12.5.1.12.1.15
		-- 1.3.6.1.4.1.37950.1.1.5.12.5.1.12.1.15
		statUpCrcErrFrames OBJECT-TYPE
			SYNTAX Counter32
			MAX-ACCESS read-only
			STATUS current
			DESCRIPTION
				"Description."
			::= { onuPortStatEntry 15 }

		
--          1.3.6.1.4.1.37950.1.1.5.12.5.1.12.1.16
-- 1.3.6.1.4.1.37950.1.1.5.12.5.1.12.1.16
-- 1.3.6.1.4.1.37950.1.1.5.12.5.1.12.1.16
-- 1.3.6.1.4.1.37950.1.1.5.12.5.1.12.1.16
-- 1.3.6.1.4.1.37950.1.1.5.12.5.1.12.1.16
-- 1.3.6.1.4.1.37950.1.1.5.12.5.1.12.1.16
-- 1.3.6.1.4.1.37950.1.1.5.12.5.1.12.1.16
-- 1.3.6.1.4.1.37950.1.1.5.12.5.1.12.1.16
-- 1.3.6.1.4.1.37950.1.1.5.12.5.1.12.1.16
		-- 1.3.6.1.4.1.37950.1.1.5.12.5.1.12.1.16
		statDnUndersizeFrames OBJECT-TYPE
			SYNTAX Counter32
			MAX-ACCESS read-only
			STATUS current
			DESCRIPTION
				"Description."
			::= { onuPortStatEntry 16 }

		
--          1.3.6.1.4.1.37950.1.1.5.12.5.1.12.1.17
-- 1.3.6.1.4.1.37950.1.1.5.12.5.1.12.1.17
-- 1.3.6.1.4.1.37950.1.1.5.12.5.1.12.1.17
-- 1.3.6.1.4.1.37950.1.1.5.12.5.1.12.1.17
-- 1.3.6.1.4.1.37950.1.1.5.12.5.1.12.1.17
-- 1.3.6.1.4.1.37950.1.1.5.12.5.1.12.1.17
-- 1.3.6.1.4.1.37950.1.1.5.12.5.1.12.1.17
-- 1.3.6.1.4.1.37950.1.1.5.12.5.1.12.1.17
-- 1.3.6.1.4.1.37950.1.1.5.12.5.1.12.1.17
		-- 1.3.6.1.4.1.37950.1.1.5.12.5.1.12.1.17
		statUpUndersizeFrames OBJECT-TYPE
			SYNTAX Counter32
			MAX-ACCESS read-only
			STATUS current
			DESCRIPTION
				"Description."
			::= { onuPortStatEntry 17 }

		
--          1.3.6.1.4.1.37950.1.1.5.12.5.1.12.1.18
-- 1.3.6.1.4.1.37950.1.1.5.12.5.1.12.1.18
-- 1.3.6.1.4.1.37950.1.1.5.12.5.1.12.1.18
-- 1.3.6.1.4.1.37950.1.1.5.12.5.1.12.1.18
-- 1.3.6.1.4.1.37950.1.1.5.12.5.1.12.1.18
-- 1.3.6.1.4.1.37950.1.1.5.12.5.1.12.1.18
-- 1.3.6.1.4.1.37950.1.1.5.12.5.1.12.1.18
-- 1.3.6.1.4.1.37950.1.1.5.12.5.1.12.1.18
-- 1.3.6.1.4.1.37950.1.1.5.12.5.1.12.1.18
		-- 1.3.6.1.4.1.37950.1.1.5.12.5.1.12.1.18
		statDnOversizeFrames OBJECT-TYPE
			SYNTAX Counter32
			MAX-ACCESS read-only
			STATUS current
			DESCRIPTION
				"Description."
			::= { onuPortStatEntry 18 }

		
--          1.3.6.1.4.1.37950.1.1.5.12.5.1.12.1.19
-- 1.3.6.1.4.1.37950.1.1.5.12.5.1.12.1.19
-- 1.3.6.1.4.1.37950.1.1.5.12.5.1.12.1.19
-- 1.3.6.1.4.1.37950.1.1.5.12.5.1.12.1.19
-- 1.3.6.1.4.1.37950.1.1.5.12.5.1.12.1.19
-- 1.3.6.1.4.1.37950.1.1.5.12.5.1.12.1.19
-- 1.3.6.1.4.1.37950.1.1.5.12.5.1.12.1.19
-- 1.3.6.1.4.1.37950.1.1.5.12.5.1.12.1.19
-- 1.3.6.1.4.1.37950.1.1.5.12.5.1.12.1.19
		-- 1.3.6.1.4.1.37950.1.1.5.12.5.1.12.1.19
		statUpOversizeFrames OBJECT-TYPE
			SYNTAX Counter32
			MAX-ACCESS read-only
			STATUS current
			DESCRIPTION
				"Description."
			::= { onuPortStatEntry 19 }

		
--          1.3.6.1.4.1.37950.1.1.5.12.5.1.12.1.20
-- 1.3.6.1.4.1.37950.1.1.5.12.5.1.12.1.20
-- 1.3.6.1.4.1.37950.1.1.5.12.5.1.12.1.20
-- 1.3.6.1.4.1.37950.1.1.5.12.5.1.12.1.20
-- 1.3.6.1.4.1.37950.1.1.5.12.5.1.12.1.20
-- 1.3.6.1.4.1.37950.1.1.5.12.5.1.12.1.20
-- 1.3.6.1.4.1.37950.1.1.5.12.5.1.12.1.20
-- 1.3.6.1.4.1.37950.1.1.5.12.5.1.12.1.20
-- 1.3.6.1.4.1.37950.1.1.5.12.5.1.12.1.20
		-- 1.3.6.1.4.1.37950.1.1.5.12.5.1.12.1.20
		statDnFragments OBJECT-TYPE
			SYNTAX Counter32
			MAX-ACCESS read-only
			STATUS current
			DESCRIPTION
				"Description."
			::= { onuPortStatEntry 20 }

		
--          1.3.6.1.4.1.37950.1.1.5.12.5.1.12.1.21
-- 1.3.6.1.4.1.37950.1.1.5.12.5.1.12.1.21
-- 1.3.6.1.4.1.37950.1.1.5.12.5.1.12.1.21
-- 1.3.6.1.4.1.37950.1.1.5.12.5.1.12.1.21
-- 1.3.6.1.4.1.37950.1.1.5.12.5.1.12.1.21
-- 1.3.6.1.4.1.37950.1.1.5.12.5.1.12.1.21
-- 1.3.6.1.4.1.37950.1.1.5.12.5.1.12.1.21
-- 1.3.6.1.4.1.37950.1.1.5.12.5.1.12.1.21
-- 1.3.6.1.4.1.37950.1.1.5.12.5.1.12.1.21
		-- 1.3.6.1.4.1.37950.1.1.5.12.5.1.12.1.21
		statUpFragments OBJECT-TYPE
			SYNTAX Counter32
			MAX-ACCESS read-only
			STATUS current
			DESCRIPTION
				"Description."
			::= { onuPortStatEntry 21 }

		
--          1.3.6.1.4.1.37950.1.1.5.12.5.1.12.1.22
-- 1.3.6.1.4.1.37950.1.1.5.12.5.1.12.1.22
-- 1.3.6.1.4.1.37950.1.1.5.12.5.1.12.1.22
-- 1.3.6.1.4.1.37950.1.1.5.12.5.1.12.1.22
-- 1.3.6.1.4.1.37950.1.1.5.12.5.1.12.1.22
-- 1.3.6.1.4.1.37950.1.1.5.12.5.1.12.1.22
-- 1.3.6.1.4.1.37950.1.1.5.12.5.1.12.1.22
-- 1.3.6.1.4.1.37950.1.1.5.12.5.1.12.1.22
-- 1.3.6.1.4.1.37950.1.1.5.12.5.1.12.1.22
		-- 1.3.6.1.4.1.37950.1.1.5.12.5.1.12.1.22
		statDnJabbers OBJECT-TYPE
			SYNTAX Counter32
			MAX-ACCESS read-only
			STATUS current
			DESCRIPTION
				"Description."
			::= { onuPortStatEntry 22 }

		
--          1.3.6.1.4.1.37950.1.1.5.12.5.1.12.1.23
-- 1.3.6.1.4.1.37950.1.1.5.12.5.1.12.1.23
-- 1.3.6.1.4.1.37950.1.1.5.12.5.1.12.1.23
-- 1.3.6.1.4.1.37950.1.1.5.12.5.1.12.1.23
-- 1.3.6.1.4.1.37950.1.1.5.12.5.1.12.1.23
-- 1.3.6.1.4.1.37950.1.1.5.12.5.1.12.1.23
-- 1.3.6.1.4.1.37950.1.1.5.12.5.1.12.1.23
-- 1.3.6.1.4.1.37950.1.1.5.12.5.1.12.1.23
-- 1.3.6.1.4.1.37950.1.1.5.12.5.1.12.1.23
		-- 1.3.6.1.4.1.37950.1.1.5.12.5.1.12.1.23
		statUpJabbers OBJECT-TYPE
			SYNTAX Counter32
			MAX-ACCESS read-only
			STATUS current
			DESCRIPTION
				"Description."
			::= { onuPortStatEntry 23 }

		
--          1.3.6.1.4.1.37950.1.1.5.12.5.1.12.1.24
-- 1.3.6.1.4.1.37950.1.1.5.12.5.1.12.1.24
-- 1.3.6.1.4.1.37950.1.1.5.12.5.1.12.1.24
-- 1.3.6.1.4.1.37950.1.1.5.12.5.1.12.1.24
-- 1.3.6.1.4.1.37950.1.1.5.12.5.1.12.1.24
-- 1.3.6.1.4.1.37950.1.1.5.12.5.1.12.1.24
-- 1.3.6.1.4.1.37950.1.1.5.12.5.1.12.1.24
-- 1.3.6.1.4.1.37950.1.1.5.12.5.1.12.1.24
-- 1.3.6.1.4.1.37950.1.1.5.12.5.1.12.1.24
		-- 1.3.6.1.4.1.37950.1.1.5.12.5.1.12.1.24
		statDn64OctetsFrames OBJECT-TYPE
			SYNTAX Counter32
			MAX-ACCESS read-only
			STATUS current
			DESCRIPTION
				"Description."
			::= { onuPortStatEntry 24 }

		
--          1.3.6.1.4.1.37950.1.1.5.12.5.1.12.1.25
-- 1.3.6.1.4.1.37950.1.1.5.12.5.1.12.1.25
-- 1.3.6.1.4.1.37950.1.1.5.12.5.1.12.1.25
-- 1.3.6.1.4.1.37950.1.1.5.12.5.1.12.1.25
-- 1.3.6.1.4.1.37950.1.1.5.12.5.1.12.1.25
-- 1.3.6.1.4.1.37950.1.1.5.12.5.1.12.1.25
-- 1.3.6.1.4.1.37950.1.1.5.12.5.1.12.1.25
-- 1.3.6.1.4.1.37950.1.1.5.12.5.1.12.1.25
-- 1.3.6.1.4.1.37950.1.1.5.12.5.1.12.1.25
		-- 1.3.6.1.4.1.37950.1.1.5.12.5.1.12.1.25
		statDn65to127OctetsFrames OBJECT-TYPE
			SYNTAX Counter32
			MAX-ACCESS read-only
			STATUS current
			DESCRIPTION
				"Description."
			::= { onuPortStatEntry 25 }

		
--          1.3.6.1.4.1.37950.1.1.5.12.5.1.12.1.26
-- 1.3.6.1.4.1.37950.1.1.5.12.5.1.12.1.26
-- 1.3.6.1.4.1.37950.1.1.5.12.5.1.12.1.26
-- 1.3.6.1.4.1.37950.1.1.5.12.5.1.12.1.26
-- 1.3.6.1.4.1.37950.1.1.5.12.5.1.12.1.26
-- 1.3.6.1.4.1.37950.1.1.5.12.5.1.12.1.26
-- 1.3.6.1.4.1.37950.1.1.5.12.5.1.12.1.26
-- 1.3.6.1.4.1.37950.1.1.5.12.5.1.12.1.26
-- 1.3.6.1.4.1.37950.1.1.5.12.5.1.12.1.26
		-- 1.3.6.1.4.1.37950.1.1.5.12.5.1.12.1.26
		statDn128to255OctetsFrames OBJECT-TYPE
			SYNTAX Counter32
			MAX-ACCESS read-only
			STATUS current
			DESCRIPTION
				"Description."
			::= { onuPortStatEntry 26 }

		
--          1.3.6.1.4.1.37950.1.1.5.12.5.1.12.1.27
-- 1.3.6.1.4.1.37950.1.1.5.12.5.1.12.1.27
-- 1.3.6.1.4.1.37950.1.1.5.12.5.1.12.1.27
-- 1.3.6.1.4.1.37950.1.1.5.12.5.1.12.1.27
-- 1.3.6.1.4.1.37950.1.1.5.12.5.1.12.1.27
-- 1.3.6.1.4.1.37950.1.1.5.12.5.1.12.1.27
-- 1.3.6.1.4.1.37950.1.1.5.12.5.1.12.1.27
-- 1.3.6.1.4.1.37950.1.1.5.12.5.1.12.1.27
-- 1.3.6.1.4.1.37950.1.1.5.12.5.1.12.1.27
		-- 1.3.6.1.4.1.37950.1.1.5.12.5.1.12.1.27
		statDn256to511OctetsFrames OBJECT-TYPE
			SYNTAX Counter32
			MAX-ACCESS read-only
			STATUS current
			DESCRIPTION
				"Description."
			::= { onuPortStatEntry 27 }

		
--          1.3.6.1.4.1.37950.1.1.5.12.5.1.12.1.28
-- 1.3.6.1.4.1.37950.1.1.5.12.5.1.12.1.28
-- 1.3.6.1.4.1.37950.1.1.5.12.5.1.12.1.28
-- 1.3.6.1.4.1.37950.1.1.5.12.5.1.12.1.28
-- 1.3.6.1.4.1.37950.1.1.5.12.5.1.12.1.28
-- 1.3.6.1.4.1.37950.1.1.5.12.5.1.12.1.28
-- 1.3.6.1.4.1.37950.1.1.5.12.5.1.12.1.28
-- 1.3.6.1.4.1.37950.1.1.5.12.5.1.12.1.28
-- 1.3.6.1.4.1.37950.1.1.5.12.5.1.12.1.28
		-- 1.3.6.1.4.1.37950.1.1.5.12.5.1.12.1.28
		statDn512to1023OctetsFrames OBJECT-TYPE
			SYNTAX Counter32
			MAX-ACCESS read-only
			STATUS current
			DESCRIPTION
				"Description."
			::= { onuPortStatEntry 28 }

		
--          1.3.6.1.4.1.37950.1.1.5.12.5.1.12.1.29
-- 1.3.6.1.4.1.37950.1.1.5.12.5.1.12.1.29
-- 1.3.6.1.4.1.37950.1.1.5.12.5.1.12.1.29
-- 1.3.6.1.4.1.37950.1.1.5.12.5.1.12.1.29
-- 1.3.6.1.4.1.37950.1.1.5.12.5.1.12.1.29
-- 1.3.6.1.4.1.37950.1.1.5.12.5.1.12.1.29
-- 1.3.6.1.4.1.37950.1.1.5.12.5.1.12.1.29
-- 1.3.6.1.4.1.37950.1.1.5.12.5.1.12.1.29
-- 1.3.6.1.4.1.37950.1.1.5.12.5.1.12.1.29
		-- 1.3.6.1.4.1.37950.1.1.5.12.5.1.12.1.29
		statDn1024to1518OctetsFrames OBJECT-TYPE
			SYNTAX Counter32
			MAX-ACCESS read-only
			STATUS current
			DESCRIPTION
				"Description."
			::= { onuPortStatEntry 29 }

		
--          1.3.6.1.4.1.37950.1.1.5.12.5.1.12.1.30
-- 1.3.6.1.4.1.37950.1.1.5.12.5.1.12.1.30
-- 1.3.6.1.4.1.37950.1.1.5.12.5.1.12.1.30
-- 1.3.6.1.4.1.37950.1.1.5.12.5.1.12.1.30
-- 1.3.6.1.4.1.37950.1.1.5.12.5.1.12.1.30
-- 1.3.6.1.4.1.37950.1.1.5.12.5.1.12.1.30
-- 1.3.6.1.4.1.37950.1.1.5.12.5.1.12.1.30
-- 1.3.6.1.4.1.37950.1.1.5.12.5.1.12.1.30
-- 1.3.6.1.4.1.37950.1.1.5.12.5.1.12.1.30
		-- 1.3.6.1.4.1.37950.1.1.5.12.5.1.12.1.30
		statUp64OctetsFrames OBJECT-TYPE
			SYNTAX Counter32
			MAX-ACCESS read-only
			STATUS current
			DESCRIPTION
				"Description."
			::= { onuPortStatEntry 30 }

		
--          1.3.6.1.4.1.37950.1.1.5.12.5.1.12.1.31
-- 1.3.6.1.4.1.37950.1.1.5.12.5.1.12.1.31
-- 1.3.6.1.4.1.37950.1.1.5.12.5.1.12.1.31
-- 1.3.6.1.4.1.37950.1.1.5.12.5.1.12.1.31
-- 1.3.6.1.4.1.37950.1.1.5.12.5.1.12.1.31
-- 1.3.6.1.4.1.37950.1.1.5.12.5.1.12.1.31
-- 1.3.6.1.4.1.37950.1.1.5.12.5.1.12.1.31
-- 1.3.6.1.4.1.37950.1.1.5.12.5.1.12.1.31
-- 1.3.6.1.4.1.37950.1.1.5.12.5.1.12.1.31
		-- 1.3.6.1.4.1.37950.1.1.5.12.5.1.12.1.31
		statUp65to127OctetsFrames OBJECT-TYPE
			SYNTAX Counter32
			MAX-ACCESS read-only
			STATUS current
			DESCRIPTION
				"Description."
			::= { onuPortStatEntry 31 }

		
--          1.3.6.1.4.1.37950.1.1.5.12.5.1.12.1.32
-- 1.3.6.1.4.1.37950.1.1.5.12.5.1.12.1.32
-- 1.3.6.1.4.1.37950.1.1.5.12.5.1.12.1.32
-- 1.3.6.1.4.1.37950.1.1.5.12.5.1.12.1.32
-- 1.3.6.1.4.1.37950.1.1.5.12.5.1.12.1.32
-- 1.3.6.1.4.1.37950.1.1.5.12.5.1.12.1.32
-- 1.3.6.1.4.1.37950.1.1.5.12.5.1.12.1.32
-- 1.3.6.1.4.1.37950.1.1.5.12.5.1.12.1.32
-- 1.3.6.1.4.1.37950.1.1.5.12.5.1.12.1.32
		-- 1.3.6.1.4.1.37950.1.1.5.12.5.1.12.1.32
		statUp128to255OctetsFrames OBJECT-TYPE
			SYNTAX Counter32
			MAX-ACCESS read-only
			STATUS current
			DESCRIPTION
				"Description."
			::= { onuPortStatEntry 32 }

		
--          1.3.6.1.4.1.37950.1.1.5.12.5.1.12.1.33
-- 1.3.6.1.4.1.37950.1.1.5.12.5.1.12.1.33
-- 1.3.6.1.4.1.37950.1.1.5.12.5.1.12.1.33
-- 1.3.6.1.4.1.37950.1.1.5.12.5.1.12.1.33
-- 1.3.6.1.4.1.37950.1.1.5.12.5.1.12.1.33
-- 1.3.6.1.4.1.37950.1.1.5.12.5.1.12.1.33
-- 1.3.6.1.4.1.37950.1.1.5.12.5.1.12.1.33
-- 1.3.6.1.4.1.37950.1.1.5.12.5.1.12.1.33
-- 1.3.6.1.4.1.37950.1.1.5.12.5.1.12.1.33
		-- 1.3.6.1.4.1.37950.1.1.5.12.5.1.12.1.33
		statUp256to511OctetsFrames OBJECT-TYPE
			SYNTAX Counter32
			MAX-ACCESS read-only
			STATUS current
			DESCRIPTION
				"Description."
			::= { onuPortStatEntry 33 }

		
--          1.3.6.1.4.1.37950.1.1.5.12.5.1.12.1.34
-- 1.3.6.1.4.1.37950.1.1.5.12.5.1.12.1.34
-- 1.3.6.1.4.1.37950.1.1.5.12.5.1.12.1.34
-- 1.3.6.1.4.1.37950.1.1.5.12.5.1.12.1.34
-- 1.3.6.1.4.1.37950.1.1.5.12.5.1.12.1.34
-- 1.3.6.1.4.1.37950.1.1.5.12.5.1.12.1.34
-- 1.3.6.1.4.1.37950.1.1.5.12.5.1.12.1.34
-- 1.3.6.1.4.1.37950.1.1.5.12.5.1.12.1.34
-- 1.3.6.1.4.1.37950.1.1.5.12.5.1.12.1.34
		-- 1.3.6.1.4.1.37950.1.1.5.12.5.1.12.1.34
		statUp512to1023OctetsFrames OBJECT-TYPE
			SYNTAX Counter32
			MAX-ACCESS read-only
			STATUS current
			DESCRIPTION
				"Description."
			::= { onuPortStatEntry 34 }

		
--          1.3.6.1.4.1.37950.1.1.5.12.5.1.12.1.35
-- 1.3.6.1.4.1.37950.1.1.5.12.5.1.12.1.35
-- 1.3.6.1.4.1.37950.1.1.5.12.5.1.12.1.35
-- 1.3.6.1.4.1.37950.1.1.5.12.5.1.12.1.35
-- 1.3.6.1.4.1.37950.1.1.5.12.5.1.12.1.35
-- 1.3.6.1.4.1.37950.1.1.5.12.5.1.12.1.35
-- 1.3.6.1.4.1.37950.1.1.5.12.5.1.12.1.35
-- 1.3.6.1.4.1.37950.1.1.5.12.5.1.12.1.35
-- 1.3.6.1.4.1.37950.1.1.5.12.5.1.12.1.35
		-- 1.3.6.1.4.1.37950.1.1.5.12.5.1.12.1.35
		statUp1024to1518OctetsFrames OBJECT-TYPE
			SYNTAX Counter32
			MAX-ACCESS read-only
			STATUS current
			DESCRIPTION
				"Description."
			::= { onuPortStatEntry 35 }

		
--          1.3.6.1.4.1.37950.1.1.5.12.5.1.12.1.36
-- 1.3.6.1.4.1.37950.1.1.5.12.5.1.12.1.36
-- 1.3.6.1.4.1.37950.1.1.5.12.5.1.12.1.36
-- 1.3.6.1.4.1.37950.1.1.5.12.5.1.12.1.36
-- 1.3.6.1.4.1.37950.1.1.5.12.5.1.12.1.36
-- 1.3.6.1.4.1.37950.1.1.5.12.5.1.12.1.36
-- 1.3.6.1.4.1.37950.1.1.5.12.5.1.12.1.36
-- 1.3.6.1.4.1.37950.1.1.5.12.5.1.12.1.36
-- 1.3.6.1.4.1.37950.1.1.5.12.5.1.12.1.36
		-- 1.3.6.1.4.1.37950.1.1.5.12.5.1.12.1.36
		statDnDiscardFrames OBJECT-TYPE
			SYNTAX Counter32
			MAX-ACCESS read-only
			STATUS current
			DESCRIPTION
				"Description."
			::= { onuPortStatEntry 36 }

		
--          1.3.6.1.4.1.37950.1.1.5.12.5.1.12.1.37
-- 1.3.6.1.4.1.37950.1.1.5.12.5.1.12.1.37
-- 1.3.6.1.4.1.37950.1.1.5.12.5.1.12.1.37
-- 1.3.6.1.4.1.37950.1.1.5.12.5.1.12.1.37
-- 1.3.6.1.4.1.37950.1.1.5.12.5.1.12.1.37
-- 1.3.6.1.4.1.37950.1.1.5.12.5.1.12.1.37
-- 1.3.6.1.4.1.37950.1.1.5.12.5.1.12.1.37
-- 1.3.6.1.4.1.37950.1.1.5.12.5.1.12.1.37
-- 1.3.6.1.4.1.37950.1.1.5.12.5.1.12.1.37
		-- 1.3.6.1.4.1.37950.1.1.5.12.5.1.12.1.37
		statUpDiscardFrames OBJECT-TYPE
			SYNTAX Counter32
			MAX-ACCESS read-only
			STATUS current
			DESCRIPTION
				"Description."
			::= { onuPortStatEntry 37 }

		
--          1.3.6.1.4.1.37950.1.1.5.12.5.1.12.1.38
-- 1.3.6.1.4.1.37950.1.1.5.12.5.1.12.1.38
-- 1.3.6.1.4.1.37950.1.1.5.12.5.1.12.1.38
-- 1.3.6.1.4.1.37950.1.1.5.12.5.1.12.1.38
-- 1.3.6.1.4.1.37950.1.1.5.12.5.1.12.1.38
-- 1.3.6.1.4.1.37950.1.1.5.12.5.1.12.1.38
-- 1.3.6.1.4.1.37950.1.1.5.12.5.1.12.1.38
-- 1.3.6.1.4.1.37950.1.1.5.12.5.1.12.1.38
-- 1.3.6.1.4.1.37950.1.1.5.12.5.1.12.1.38
		-- 1.3.6.1.4.1.37950.1.1.5.12.5.1.12.1.38
		statDnErrFrames OBJECT-TYPE
			SYNTAX Counter32
			MAX-ACCESS read-only
			STATUS current
			DESCRIPTION
				"Description."
			::= { onuPortStatEntry 38 }

		
--          1.3.6.1.4.1.37950.1.1.5.12.5.1.12.1.39
-- 1.3.6.1.4.1.37950.1.1.5.12.5.1.12.1.39
-- 1.3.6.1.4.1.37950.1.1.5.12.5.1.12.1.39
-- 1.3.6.1.4.1.37950.1.1.5.12.5.1.12.1.39
-- 1.3.6.1.4.1.37950.1.1.5.12.5.1.12.1.39
-- 1.3.6.1.4.1.37950.1.1.5.12.5.1.12.1.39
-- 1.3.6.1.4.1.37950.1.1.5.12.5.1.12.1.39
-- 1.3.6.1.4.1.37950.1.1.5.12.5.1.12.1.39
-- 1.3.6.1.4.1.37950.1.1.5.12.5.1.12.1.39
		-- 1.3.6.1.4.1.37950.1.1.5.12.5.1.12.1.39
		statUpErrFrames OBJECT-TYPE
			SYNTAX Counter32
			MAX-ACCESS read-only
			STATUS current
			DESCRIPTION
				"Description."
			::= { onuPortStatEntry 39 }

		
--          1.3.6.1.4.1.37950.1.1.5.12.5.1.12.1.40
-- 1.3.6.1.4.1.37950.1.1.5.12.5.1.12.1.40
-- 1.3.6.1.4.1.37950.1.1.5.12.5.1.12.1.40
-- 1.3.6.1.4.1.37950.1.1.5.12.5.1.12.1.40
-- 1.3.6.1.4.1.37950.1.1.5.12.5.1.12.1.40
-- 1.3.6.1.4.1.37950.1.1.5.12.5.1.12.1.40
-- 1.3.6.1.4.1.37950.1.1.5.12.5.1.12.1.40
-- 1.3.6.1.4.1.37950.1.1.5.12.5.1.12.1.40
-- 1.3.6.1.4.1.37950.1.1.5.12.5.1.12.1.40
		-- 1.3.6.1.4.1.37950.1.1.5.12.5.1.12.1.40
		statStatusChangeTimes OBJECT-TYPE
			SYNTAX Counter32
			MAX-ACCESS read-only
			STATUS current
			DESCRIPTION
				"Description."
			::= { onuPortStatEntry 40 }

		
--          1.3.6.1.4.1.37950.1.1.5.12.5.1.13
-- 1.3.6.1.4.1.37950.1.1.5.12.5.1.13
-- 1.3.6.1.4.1.37950.1.1.5.12.5.1.13
-- 1.3.6.1.4.1.37950.1.1.5.12.5.1.13
-- 1.3.6.1.4.1.37950.1.1.5.12.5.1.13
-- 1.3.6.1.4.1.37950.1.1.5.12.5.1.13
-- 1.3.6.1.4.1.37950.1.1.5.12.5.1.13
-- 1.3.6.1.4.1.37950.1.1.5.12.5.1.13
-- 1.3.6.1.4.1.37950.1.1.5.12.5.1.13
		-- 1.3.6.1.4.1.37950.1.1.5.12.5.1.13
		onuPortBasicTable OBJECT-TYPE
			SYNTAX SEQUENCE OF OnuPortBasicEntry
			MAX-ACCESS not-accessible
			STATUS current
			DESCRIPTION
				"Description."
			::= { onuPortInfo 13 }

		
--          1.3.6.1.4.1.37950.1.1.5.12.5.1.13.1
-- 1.3.6.1.4.1.37950.1.1.5.12.5.1.13.1
-- 1.3.6.1.4.1.37950.1.1.5.12.5.1.13.1
-- 1.3.6.1.4.1.37950.1.1.5.12.5.1.13.1
-- 1.3.6.1.4.1.37950.1.1.5.12.5.1.13.1
-- 1.3.6.1.4.1.37950.1.1.5.12.5.1.13.1
-- 1.3.6.1.4.1.37950.1.1.5.12.5.1.13.1
-- 1.3.6.1.4.1.37950.1.1.5.12.5.1.13.1
-- 1.3.6.1.4.1.37950.1.1.5.12.5.1.13.1
		-- 1.3.6.1.4.1.37950.1.1.5.12.5.1.13.1
		onuPortBasicEntry OBJECT-TYPE
			SYNTAX OnuPortBasicEntry
			MAX-ACCESS not-accessible
			STATUS current
			DESCRIPTION
				"Description."
			INDEX { onuPortBasicPonIndex, onuPortBasicOnuIndex, onuPortBasicPortIndex }
			::= { onuPortBasicTable 1 }

		
		OnuPortBasicEntry ::=
			SEQUENCE { 
				onuPortBasicPonIndex
					Integer32,
				onuPortBasicOnuIndex
					Integer32,
				onuPortBasicPortIndex
					Integer32,
				onuPortBasicLinkStatus
					INTEGER,
				onuPortBasicAdminStatus
					INTEGER,
				onuPortBasicAutoNgt
					INTEGER,
				onuPortBasicFlowCtl
					INTEGER,
				onuPortBasicLoopback
					INTEGER,
				onuPortBasicPolicyState
					INTEGER,
				onuPortBasicPolicyCir
					Integer32,
				onuPortBasicPolicyCbs
					Integer32,
				onuPortBasicPolicyEbs
					Integer32,
				onuPortBasicRateState
					INTEGER,
				onuPortBasicRateCir
					Integer32,
				onuPortBasicRatePir
					Integer32
			 }

--          1.3.6.1.4.1.37950.1.1.5.12.5.1.13.1.1
-- 1.3.6.1.4.1.37950.1.1.5.12.5.1.13.1.1
-- 1.3.6.1.4.1.37950.1.1.5.12.5.1.13.1.1
-- 1.3.6.1.4.1.37950.1.1.5.12.5.1.13.1.1
-- 1.3.6.1.4.1.37950.1.1.5.12.5.1.13.1.1
-- 1.3.6.1.4.1.37950.1.1.5.12.5.1.13.1.1
-- 1.3.6.1.4.1.37950.1.1.5.12.5.1.13.1.1
-- 1.3.6.1.4.1.37950.1.1.5.12.5.1.13.1.1
-- 1.3.6.1.4.1.37950.1.1.5.12.5.1.13.1.1
		-- 1.3.6.1.4.1.37950.1.1.5.12.5.1.13.1.1
		onuPortBasicPonIndex OBJECT-TYPE
			SYNTAX Integer32
			MAX-ACCESS read-only
			STATUS current
			DESCRIPTION
				"Description."
			::= { onuPortBasicEntry 1 }

		
--          1.3.6.1.4.1.37950.1.1.5.12.5.1.13.1.2
-- 1.3.6.1.4.1.37950.1.1.5.12.5.1.13.1.2
-- 1.3.6.1.4.1.37950.1.1.5.12.5.1.13.1.2
-- 1.3.6.1.4.1.37950.1.1.5.12.5.1.13.1.2
-- 1.3.6.1.4.1.37950.1.1.5.12.5.1.13.1.2
-- 1.3.6.1.4.1.37950.1.1.5.12.5.1.13.1.2
-- 1.3.6.1.4.1.37950.1.1.5.12.5.1.13.1.2
-- 1.3.6.1.4.1.37950.1.1.5.12.5.1.13.1.2
-- 1.3.6.1.4.1.37950.1.1.5.12.5.1.13.1.2
		-- 1.3.6.1.4.1.37950.1.1.5.12.5.1.13.1.2
		onuPortBasicOnuIndex OBJECT-TYPE
			SYNTAX Integer32
			MAX-ACCESS read-only
			STATUS current
			DESCRIPTION
				"Description."
			::= { onuPortBasicEntry 2 }

		
--          1.3.6.1.4.1.37950.1.1.5.12.5.1.13.1.3
-- 1.3.6.1.4.1.37950.1.1.5.12.5.1.13.1.3
-- 1.3.6.1.4.1.37950.1.1.5.12.5.1.13.1.3
-- 1.3.6.1.4.1.37950.1.1.5.12.5.1.13.1.3
-- 1.3.6.1.4.1.37950.1.1.5.12.5.1.13.1.3
-- 1.3.6.1.4.1.37950.1.1.5.12.5.1.13.1.3
-- 1.3.6.1.4.1.37950.1.1.5.12.5.1.13.1.3
-- 1.3.6.1.4.1.37950.1.1.5.12.5.1.13.1.3
-- 1.3.6.1.4.1.37950.1.1.5.12.5.1.13.1.3
		-- 1.3.6.1.4.1.37950.1.1.5.12.5.1.13.1.3
		onuPortBasicPortIndex OBJECT-TYPE
			SYNTAX Integer32
			MAX-ACCESS read-only
			STATUS current
			DESCRIPTION
				"Description."
			::= { onuPortBasicEntry 3 }

		
--          1.3.6.1.4.1.37950.1.1.5.12.5.1.13.1.4
-- 1.3.6.1.4.1.37950.1.1.5.12.5.1.13.1.4
-- 1.3.6.1.4.1.37950.1.1.5.12.5.1.13.1.4
-- 1.3.6.1.4.1.37950.1.1.5.12.5.1.13.1.4
-- 1.3.6.1.4.1.37950.1.1.5.12.5.1.13.1.4
-- 1.3.6.1.4.1.37950.1.1.5.12.5.1.13.1.4
-- 1.3.6.1.4.1.37950.1.1.5.12.5.1.13.1.4
-- 1.3.6.1.4.1.37950.1.1.5.12.5.1.13.1.4
-- 1.3.6.1.4.1.37950.1.1.5.12.5.1.13.1.4
		-- 1.3.6.1.4.1.37950.1.1.5.12.5.1.13.1.4
		onuPortBasicLinkStatus OBJECT-TYPE
			SYNTAX INTEGER
				{
				down(0),
				up(1)
				}
			MAX-ACCESS read-only
			STATUS current
			DESCRIPTION
				"Description."
			::= { onuPortBasicEntry 4 }

		
--          1.3.6.1.4.1.37950.1.1.5.12.5.1.13.1.5
-- 1.3.6.1.4.1.37950.1.1.5.12.5.1.13.1.5
-- 1.3.6.1.4.1.37950.1.1.5.12.5.1.13.1.5
-- 1.3.6.1.4.1.37950.1.1.5.12.5.1.13.1.5
-- 1.3.6.1.4.1.37950.1.1.5.12.5.1.13.1.5
-- 1.3.6.1.4.1.37950.1.1.5.12.5.1.13.1.5
-- 1.3.6.1.4.1.37950.1.1.5.12.5.1.13.1.5
-- 1.3.6.1.4.1.37950.1.1.5.12.5.1.13.1.5
-- 1.3.6.1.4.1.37950.1.1.5.12.5.1.13.1.5
		-- 1.3.6.1.4.1.37950.1.1.5.12.5.1.13.1.5
		onuPortBasicAdminStatus OBJECT-TYPE
			SYNTAX INTEGER
				{
				disable(0),
				enable(1)
				}
			MAX-ACCESS read-only
			STATUS current
			DESCRIPTION
				"Description."
			::= { onuPortBasicEntry 5 }

		
--          1.3.6.1.4.1.37950.1.1.5.12.5.1.13.1.6
-- 1.3.6.1.4.1.37950.1.1.5.12.5.1.13.1.6
-- 1.3.6.1.4.1.37950.1.1.5.12.5.1.13.1.6
-- 1.3.6.1.4.1.37950.1.1.5.12.5.1.13.1.6
-- 1.3.6.1.4.1.37950.1.1.5.12.5.1.13.1.6
-- 1.3.6.1.4.1.37950.1.1.5.12.5.1.13.1.6
-- 1.3.6.1.4.1.37950.1.1.5.12.5.1.13.1.6
-- 1.3.6.1.4.1.37950.1.1.5.12.5.1.13.1.6
-- 1.3.6.1.4.1.37950.1.1.5.12.5.1.13.1.6
		-- 1.3.6.1.4.1.37950.1.1.5.12.5.1.13.1.6
		onuPortBasicAutoNgt OBJECT-TYPE
			SYNTAX INTEGER
				{
				disable(0),
				enable(1)
				}
			MAX-ACCESS read-only
			STATUS current
			DESCRIPTION
				"Description."
			::= { onuPortBasicEntry 6 }

		
--          1.3.6.1.4.1.37950.1.1.5.12.5.1.13.1.7
-- 1.3.6.1.4.1.37950.1.1.5.12.5.1.13.1.7
-- 1.3.6.1.4.1.37950.1.1.5.12.5.1.13.1.7
-- 1.3.6.1.4.1.37950.1.1.5.12.5.1.13.1.7
-- 1.3.6.1.4.1.37950.1.1.5.12.5.1.13.1.7
-- 1.3.6.1.4.1.37950.1.1.5.12.5.1.13.1.7
-- 1.3.6.1.4.1.37950.1.1.5.12.5.1.13.1.7
-- 1.3.6.1.4.1.37950.1.1.5.12.5.1.13.1.7
-- 1.3.6.1.4.1.37950.1.1.5.12.5.1.13.1.7
		-- 1.3.6.1.4.1.37950.1.1.5.12.5.1.13.1.7
		onuPortBasicFlowCtl OBJECT-TYPE
			SYNTAX INTEGER
				{
				disable(0),
				enable(1)
				}
			MAX-ACCESS read-only
			STATUS current
			DESCRIPTION
				"Description."
			::= { onuPortBasicEntry 7 }

		
--          1.3.6.1.4.1.37950.1.1.5.12.5.1.13.1.8
-- 1.3.6.1.4.1.37950.1.1.5.12.5.1.13.1.8
-- 1.3.6.1.4.1.37950.1.1.5.12.5.1.13.1.8
-- 1.3.6.1.4.1.37950.1.1.5.12.5.1.13.1.8
-- 1.3.6.1.4.1.37950.1.1.5.12.5.1.13.1.8
-- 1.3.6.1.4.1.37950.1.1.5.12.5.1.13.1.8
-- 1.3.6.1.4.1.37950.1.1.5.12.5.1.13.1.8
-- 1.3.6.1.4.1.37950.1.1.5.12.5.1.13.1.8
-- 1.3.6.1.4.1.37950.1.1.5.12.5.1.13.1.8
		-- 1.3.6.1.4.1.37950.1.1.5.12.5.1.13.1.8
		onuPortBasicLoopback OBJECT-TYPE
			SYNTAX INTEGER
				{
				disable(0),
				enable(1)
				}
			MAX-ACCESS read-only
			STATUS current
			DESCRIPTION
				"Description."
			::= { onuPortBasicEntry 8 }

		
--          1.3.6.1.4.1.37950.1.1.5.12.5.1.13.1.9
-- 1.3.6.1.4.1.37950.1.1.5.12.5.1.13.1.9
-- 1.3.6.1.4.1.37950.1.1.5.12.5.1.13.1.9
-- 1.3.6.1.4.1.37950.1.1.5.12.5.1.13.1.9
-- 1.3.6.1.4.1.37950.1.1.5.12.5.1.13.1.9
-- 1.3.6.1.4.1.37950.1.1.5.12.5.1.13.1.9
-- 1.3.6.1.4.1.37950.1.1.5.12.5.1.13.1.9
-- 1.3.6.1.4.1.37950.1.1.5.12.5.1.13.1.9
-- 1.3.6.1.4.1.37950.1.1.5.12.5.1.13.1.9
		-- 1.3.6.1.4.1.37950.1.1.5.12.5.1.13.1.9
		onuPortBasicPolicyState OBJECT-TYPE
			SYNTAX INTEGER
				{
				disable(0),
				enable(1)
				}
			MAX-ACCESS read-only
			STATUS current
			DESCRIPTION
				"Description."
			::= { onuPortBasicEntry 9 }

		
--          1.3.6.1.4.1.37950.1.1.5.12.5.1.13.1.10
-- 1.3.6.1.4.1.37950.1.1.5.12.5.1.13.1.10
-- 1.3.6.1.4.1.37950.1.1.5.12.5.1.13.1.10
-- 1.3.6.1.4.1.37950.1.1.5.12.5.1.13.1.10
-- 1.3.6.1.4.1.37950.1.1.5.12.5.1.13.1.10
-- 1.3.6.1.4.1.37950.1.1.5.12.5.1.13.1.10
-- 1.3.6.1.4.1.37950.1.1.5.12.5.1.13.1.10
-- 1.3.6.1.4.1.37950.1.1.5.12.5.1.13.1.10
-- 1.3.6.1.4.1.37950.1.1.5.12.5.1.13.1.10
		-- 1.3.6.1.4.1.37950.1.1.5.12.5.1.13.1.10
		onuPortBasicPolicyCir OBJECT-TYPE
			SYNTAX Integer32
			MAX-ACCESS read-only
			STATUS current
			DESCRIPTION
				"Description."
			::= { onuPortBasicEntry 10 }

		
--          1.3.6.1.4.1.37950.1.1.5.12.5.1.13.1.11
-- 1.3.6.1.4.1.37950.1.1.5.12.5.1.13.1.11
-- 1.3.6.1.4.1.37950.1.1.5.12.5.1.13.1.11
-- 1.3.6.1.4.1.37950.1.1.5.12.5.1.13.1.11
-- 1.3.6.1.4.1.37950.1.1.5.12.5.1.13.1.11
-- 1.3.6.1.4.1.37950.1.1.5.12.5.1.13.1.11
-- 1.3.6.1.4.1.37950.1.1.5.12.5.1.13.1.11
-- 1.3.6.1.4.1.37950.1.1.5.12.5.1.13.1.11
-- 1.3.6.1.4.1.37950.1.1.5.12.5.1.13.1.11
		-- 1.3.6.1.4.1.37950.1.1.5.12.5.1.13.1.11
		onuPortBasicPolicyCbs OBJECT-TYPE
			SYNTAX Integer32
			MAX-ACCESS read-only
			STATUS current
			DESCRIPTION
				"Description."
			::= { onuPortBasicEntry 11 }

		
--          1.3.6.1.4.1.37950.1.1.5.12.5.1.13.1.12
-- 1.3.6.1.4.1.37950.1.1.5.12.5.1.13.1.12
-- 1.3.6.1.4.1.37950.1.1.5.12.5.1.13.1.12
-- 1.3.6.1.4.1.37950.1.1.5.12.5.1.13.1.12
-- 1.3.6.1.4.1.37950.1.1.5.12.5.1.13.1.12
-- 1.3.6.1.4.1.37950.1.1.5.12.5.1.13.1.12
-- 1.3.6.1.4.1.37950.1.1.5.12.5.1.13.1.12
-- 1.3.6.1.4.1.37950.1.1.5.12.5.1.13.1.12
-- 1.3.6.1.4.1.37950.1.1.5.12.5.1.13.1.12
		-- 1.3.6.1.4.1.37950.1.1.5.12.5.1.13.1.12
		onuPortBasicPolicyEbs OBJECT-TYPE
			SYNTAX Integer32
			MAX-ACCESS read-only
			STATUS current
			DESCRIPTION
				"Description."
			::= { onuPortBasicEntry 12 }

		
--          1.3.6.1.4.1.37950.1.1.5.12.5.1.13.1.13
-- 1.3.6.1.4.1.37950.1.1.5.12.5.1.13.1.13
-- 1.3.6.1.4.1.37950.1.1.5.12.5.1.13.1.13
-- 1.3.6.1.4.1.37950.1.1.5.12.5.1.13.1.13
-- 1.3.6.1.4.1.37950.1.1.5.12.5.1.13.1.13
-- 1.3.6.1.4.1.37950.1.1.5.12.5.1.13.1.13
-- 1.3.6.1.4.1.37950.1.1.5.12.5.1.13.1.13
-- 1.3.6.1.4.1.37950.1.1.5.12.5.1.13.1.13
-- 1.3.6.1.4.1.37950.1.1.5.12.5.1.13.1.13
		-- 1.3.6.1.4.1.37950.1.1.5.12.5.1.13.1.13
		onuPortBasicRateState OBJECT-TYPE
			SYNTAX INTEGER
				{
				disable(0),
				enable(1)
				}
			MAX-ACCESS read-only
			STATUS current
			DESCRIPTION
				"Description."
			::= { onuPortBasicEntry 13 }

		
--          1.3.6.1.4.1.37950.1.1.5.12.5.1.13.1.14
-- 1.3.6.1.4.1.37950.1.1.5.12.5.1.13.1.14
-- 1.3.6.1.4.1.37950.1.1.5.12.5.1.13.1.14
-- 1.3.6.1.4.1.37950.1.1.5.12.5.1.13.1.14
-- 1.3.6.1.4.1.37950.1.1.5.12.5.1.13.1.14
-- 1.3.6.1.4.1.37950.1.1.5.12.5.1.13.1.14
-- 1.3.6.1.4.1.37950.1.1.5.12.5.1.13.1.14
-- 1.3.6.1.4.1.37950.1.1.5.12.5.1.13.1.14
-- 1.3.6.1.4.1.37950.1.1.5.12.5.1.13.1.14
		-- 1.3.6.1.4.1.37950.1.1.5.12.5.1.13.1.14
		onuPortBasicRateCir OBJECT-TYPE
			SYNTAX Integer32
			MAX-ACCESS read-only
			STATUS current
			DESCRIPTION
				"Description."
			::= { onuPortBasicEntry 14 }

		
--          1.3.6.1.4.1.37950.1.1.5.12.5.1.13.1.15
-- 1.3.6.1.4.1.37950.1.1.5.12.5.1.13.1.15
-- 1.3.6.1.4.1.37950.1.1.5.12.5.1.13.1.15
-- 1.3.6.1.4.1.37950.1.1.5.12.5.1.13.1.15
-- 1.3.6.1.4.1.37950.1.1.5.12.5.1.13.1.15
-- 1.3.6.1.4.1.37950.1.1.5.12.5.1.13.1.15
-- 1.3.6.1.4.1.37950.1.1.5.12.5.1.13.1.15
-- 1.3.6.1.4.1.37950.1.1.5.12.5.1.13.1.15
-- 1.3.6.1.4.1.37950.1.1.5.12.5.1.13.1.15
		-- 1.3.6.1.4.1.37950.1.1.5.12.5.1.13.1.15
		onuPortBasicRatePir OBJECT-TYPE
			SYNTAX Integer32
			MAX-ACCESS read-only
			STATUS current
			DESCRIPTION
				"Description."
			::= { onuPortBasicEntry 15 }

		
--         1.3.6.1.4.1.37950.1.1.5.12.5.1.14
-- 1.3.6.1.4.1.37950.1.1.5.12.5.1.14
-- 1.3.6.1.4.1.37950.1.1.5.12.5.1.14
-- 1.3.6.1.4.1.37950.1.1.5.12.5.1.14
-- 1.3.6.1.4.1.37950.1.1.5.12.5.1.14
-- 1.3.6.1.4.1.37950.1.1.5.12.5.1.14
-- 1.3.6.1.4.1.37950.1.1.5.12.5.1.14
-- 1.3.6.1.4.1.37950.1.1.5.12.5.1.14
		-- 1.3.6.1.4.1.37950.1.1.5.12.5.1.14
		onuPortDisLoopTable OBJECT-TYPE
			SYNTAX SEQUENCE OF OnuPortDisLoopEntry
			MAX-ACCESS not-accessible
			STATUS current
			DESCRIPTION
				"Description."
			::= { onuPortInfo 14 }

		
--         1.3.6.1.4.1.37950.1.1.5.12.5.1.14.1
-- 1.3.6.1.4.1.37950.1.1.5.12.5.1.14.1
-- 1.3.6.1.4.1.37950.1.1.5.12.5.1.14.1
-- 1.3.6.1.4.1.37950.1.1.5.12.5.1.14.1
-- 1.3.6.1.4.1.37950.1.1.5.12.5.1.14.1
-- 1.3.6.1.4.1.37950.1.1.5.12.5.1.14.1
-- 1.3.6.1.4.1.37950.1.1.5.12.5.1.14.1
-- 1.3.6.1.4.1.37950.1.1.5.12.5.1.14.1
		-- 1.3.6.1.4.1.37950.1.1.5.12.5.1.14.1
		onuPortDisLoopEntry OBJECT-TYPE
			SYNTAX OnuPortDisLoopEntry
			MAX-ACCESS not-accessible
			STATUS current
			DESCRIPTION
				"Description."
			INDEX { onuPortDisLoopPon, onuPortDisLoopOnu, onuPortDisLoopPort }
			::= { onuPortDisLoopTable 1 }

		
		OnuPortDisLoopEntry ::=
			SEQUENCE { 
				onuPortDisLoopPon
					INTEGER,
				onuPortDisLoopOnu
					INTEGER,
				onuPortDisLoopPort
					Integer32,
				onuPortDisLoopEn
					INTEGER
			 }

--         1.3.6.1.4.1.37950.1.1.5.12.5.1.14.1.1
-- 1.3.6.1.4.1.37950.1.1.5.12.5.1.14.1.1
-- 1.3.6.1.4.1.37950.1.1.5.12.5.1.14.1.1
-- 1.3.6.1.4.1.37950.1.1.5.12.5.1.14.1.1
-- 1.3.6.1.4.1.37950.1.1.5.12.5.1.14.1.1
-- 1.3.6.1.4.1.37950.1.1.5.12.5.1.14.1.1
-- 1.3.6.1.4.1.37950.1.1.5.12.5.1.14.1.1
-- 1.3.6.1.4.1.37950.1.1.5.12.5.1.14.1.1
		-- 1.3.6.1.4.1.37950.1.1.5.12.5.1.14.1.1
		onuPortDisLoopPon OBJECT-TYPE
			SYNTAX INTEGER (1..16)
			MAX-ACCESS read-write
			STATUS current
			DESCRIPTION
				"Description."
			::= { onuPortDisLoopEntry 1 }

		
--         1.3.6.1.4.1.37950.1.1.5.12.5.1.14.1.2
-- 1.3.6.1.4.1.37950.1.1.5.12.5.1.14.1.2
-- 1.3.6.1.4.1.37950.1.1.5.12.5.1.14.1.2
-- 1.3.6.1.4.1.37950.1.1.5.12.5.1.14.1.2
-- 1.3.6.1.4.1.37950.1.1.5.12.5.1.14.1.2
-- 1.3.6.1.4.1.37950.1.1.5.12.5.1.14.1.2
-- 1.3.6.1.4.1.37950.1.1.5.12.5.1.14.1.2
-- 1.3.6.1.4.1.37950.1.1.5.12.5.1.14.1.2
		-- 1.3.6.1.4.1.37950.1.1.5.12.5.1.14.1.2
		onuPortDisLoopOnu OBJECT-TYPE
			SYNTAX INTEGER (1..65535)
			MAX-ACCESS read-write
			STATUS current
			DESCRIPTION
				"Description."
			::= { onuPortDisLoopEntry 2 }

		
--         1.3.6.1.4.1.37950.1.1.5.12.5.1.14.1.3
-- 1.3.6.1.4.1.37950.1.1.5.12.5.1.14.1.3
-- 1.3.6.1.4.1.37950.1.1.5.12.5.1.14.1.3
-- 1.3.6.1.4.1.37950.1.1.5.12.5.1.14.1.3
-- 1.3.6.1.4.1.37950.1.1.5.12.5.1.14.1.3
-- 1.3.6.1.4.1.37950.1.1.5.12.5.1.14.1.3
-- 1.3.6.1.4.1.37950.1.1.5.12.5.1.14.1.3
-- 1.3.6.1.4.1.37950.1.1.5.12.5.1.14.1.3
		-- 1.3.6.1.4.1.37950.1.1.5.12.5.1.14.1.3
		onuPortDisLoopPort OBJECT-TYPE
			SYNTAX Integer32
			MAX-ACCESS read-write
			STATUS current
			DESCRIPTION
				"Description."
			::= { onuPortDisLoopEntry 3 }

		
--         1.3.6.1.4.1.37950.1.1.5.12.5.1.14.1.4
-- 1.3.6.1.4.1.37950.1.1.5.12.5.1.14.1.4
-- 1.3.6.1.4.1.37950.1.1.5.12.5.1.14.1.4
-- 1.3.6.1.4.1.37950.1.1.5.12.5.1.14.1.4
-- 1.3.6.1.4.1.37950.1.1.5.12.5.1.14.1.4
-- 1.3.6.1.4.1.37950.1.1.5.12.5.1.14.1.4
-- 1.3.6.1.4.1.37950.1.1.5.12.5.1.14.1.4
-- 1.3.6.1.4.1.37950.1.1.5.12.5.1.14.1.4
		-- 1.3.6.1.4.1.37950.1.1.5.12.5.1.14.1.4
		onuPortDisLoopEn OBJECT-TYPE
			SYNTAX INTEGER
				{
				disable(0),
				enable(1)
				}
			MAX-ACCESS read-only
			STATUS current
			DESCRIPTION
				"Description."
			::= { onuPortDisLoopEntry 4 }

		
--          1.3.6.1.4.1.37950.1.1.5.12.5.2
-- 1.3.6.1.4.1.37950.1.1.5.12.5.2
-- 1.3.6.1.4.1.37950.1.1.5.12.5.2
-- 1.3.6.1.4.1.37950.1.1.5.12.5.2
-- 1.3.6.1.4.1.37950.1.1.5.12.5.2
-- 1.3.6.1.4.1.37950.1.1.5.12.5.2
-- 1.3.6.1.4.1.37950.1.1.5.12.5.2
-- 1.3.6.1.4.1.37950.1.1.5.12.5.2
-- 1.3.6.1.4.1.37950.1.1.5.12.5.2
		-- 1.3.6.1.4.1.37950.1.1.5.12.5.2
		onuPortCfg OBJECT IDENTIFIER ::= { onuPort 2 }

		
--          1.3.6.1.4.1.37950.1.1.5.12.5.2.1
-- 1.3.6.1.4.1.37950.1.1.5.12.5.2.1
-- 1.3.6.1.4.1.37950.1.1.5.12.5.2.1
-- 1.3.6.1.4.1.37950.1.1.5.12.5.2.1
-- 1.3.6.1.4.1.37950.1.1.5.12.5.2.1
-- 1.3.6.1.4.1.37950.1.1.5.12.5.2.1
-- 1.3.6.1.4.1.37950.1.1.5.12.5.2.1
-- 1.3.6.1.4.1.37950.1.1.5.12.5.2.1
-- 1.3.6.1.4.1.37950.1.1.5.12.5.2.1
		-- 1.3.6.1.4.1.37950.1.1.5.12.5.2.1
		onuPortAdminCfg OBJECT IDENTIFIER ::= { onuPortCfg 1 }

		
--          1.3.6.1.4.1.37950.1.1.5.12.5.2.1.1
-- 1.3.6.1.4.1.37950.1.1.5.12.5.2.1.1
-- 1.3.6.1.4.1.37950.1.1.5.12.5.2.1.1
-- 1.3.6.1.4.1.37950.1.1.5.12.5.2.1.1
-- 1.3.6.1.4.1.37950.1.1.5.12.5.2.1.1
-- 1.3.6.1.4.1.37950.1.1.5.12.5.2.1.1
-- 1.3.6.1.4.1.37950.1.1.5.12.5.2.1.1
-- 1.3.6.1.4.1.37950.1.1.5.12.5.2.1.1
-- 1.3.6.1.4.1.37950.1.1.5.12.5.2.1.1
		-- 1.3.6.1.4.1.37950.1.1.5.12.5.2.1.1
		portAdminPonNo OBJECT-TYPE
			SYNTAX INTEGER (1..16)
			MAX-ACCESS read-write
			STATUS current
			DESCRIPTION
				"Description."
			::= { onuPortAdminCfg 1 }

		
--          1.3.6.1.4.1.37950.1.1.5.12.5.2.1.2
-- 1.3.6.1.4.1.37950.1.1.5.12.5.2.1.2
-- 1.3.6.1.4.1.37950.1.1.5.12.5.2.1.2
-- 1.3.6.1.4.1.37950.1.1.5.12.5.2.1.2
-- 1.3.6.1.4.1.37950.1.1.5.12.5.2.1.2
-- 1.3.6.1.4.1.37950.1.1.5.12.5.2.1.2
-- 1.3.6.1.4.1.37950.1.1.5.12.5.2.1.2
-- 1.3.6.1.4.1.37950.1.1.5.12.5.2.1.2
-- 1.3.6.1.4.1.37950.1.1.5.12.5.2.1.2
		-- 1.3.6.1.4.1.37950.1.1.5.12.5.2.1.2
		portAdminOnuNo OBJECT-TYPE
			SYNTAX INTEGER (1..65535)
			MAX-ACCESS read-write
			STATUS current
			DESCRIPTION
				"Description."
			::= { onuPortAdminCfg 2 }

		
--          1.3.6.1.4.1.37950.1.1.5.12.5.2.1.3
-- 1.3.6.1.4.1.37950.1.1.5.12.5.2.1.3
-- 1.3.6.1.4.1.37950.1.1.5.12.5.2.1.3
-- 1.3.6.1.4.1.37950.1.1.5.12.5.2.1.3
-- 1.3.6.1.4.1.37950.1.1.5.12.5.2.1.3
-- 1.3.6.1.4.1.37950.1.1.5.12.5.2.1.3
-- 1.3.6.1.4.1.37950.1.1.5.12.5.2.1.3
-- 1.3.6.1.4.1.37950.1.1.5.12.5.2.1.3
-- 1.3.6.1.4.1.37950.1.1.5.12.5.2.1.3
		-- 1.3.6.1.4.1.37950.1.1.5.12.5.2.1.3
		portAdminPortNo OBJECT-TYPE
			SYNTAX INTEGER (1..255)
			MAX-ACCESS read-write
			STATUS current
			DESCRIPTION
				"Description."
			::= { onuPortAdminCfg 3 }

		
--          1.3.6.1.4.1.37950.1.1.5.12.5.2.1.4
-- 1.3.6.1.4.1.37950.1.1.5.12.5.2.1.4
-- 1.3.6.1.4.1.37950.1.1.5.12.5.2.1.4
-- 1.3.6.1.4.1.37950.1.1.5.12.5.2.1.4
-- 1.3.6.1.4.1.37950.1.1.5.12.5.2.1.4
-- 1.3.6.1.4.1.37950.1.1.5.12.5.2.1.4
-- 1.3.6.1.4.1.37950.1.1.5.12.5.2.1.4
-- 1.3.6.1.4.1.37950.1.1.5.12.5.2.1.4
-- 1.3.6.1.4.1.37950.1.1.5.12.5.2.1.4
		-- 1.3.6.1.4.1.37950.1.1.5.12.5.2.1.4
		portAdmin OBJECT-TYPE
			SYNTAX INTEGER
				{
				disable(0),
				enable(1)
				}
			MAX-ACCESS read-write
			STATUS current
			DESCRIPTION
				"Description."
			::= { onuPortAdminCfg 4 }

		
--          1.3.6.1.4.1.37950.1.1.5.12.5.2.2
-- 1.3.6.1.4.1.37950.1.1.5.12.5.2.2
-- 1.3.6.1.4.1.37950.1.1.5.12.5.2.2
-- 1.3.6.1.4.1.37950.1.1.5.12.5.2.2
-- 1.3.6.1.4.1.37950.1.1.5.12.5.2.2
-- 1.3.6.1.4.1.37950.1.1.5.12.5.2.2
-- 1.3.6.1.4.1.37950.1.1.5.12.5.2.2
-- 1.3.6.1.4.1.37950.1.1.5.12.5.2.2
-- 1.3.6.1.4.1.37950.1.1.5.12.5.2.2
		-- 1.3.6.1.4.1.37950.1.1.5.12.5.2.2
		onuPortAutoNegCfg OBJECT IDENTIFIER ::= { onuPortCfg 2 }

		
--          1.3.6.1.4.1.37950.1.1.5.12.5.2.2.1
-- 1.3.6.1.4.1.37950.1.1.5.12.5.2.2.1
-- 1.3.6.1.4.1.37950.1.1.5.12.5.2.2.1
-- 1.3.6.1.4.1.37950.1.1.5.12.5.2.2.1
-- 1.3.6.1.4.1.37950.1.1.5.12.5.2.2.1
-- 1.3.6.1.4.1.37950.1.1.5.12.5.2.2.1
-- 1.3.6.1.4.1.37950.1.1.5.12.5.2.2.1
-- 1.3.6.1.4.1.37950.1.1.5.12.5.2.2.1
-- 1.3.6.1.4.1.37950.1.1.5.12.5.2.2.1
		-- 1.3.6.1.4.1.37950.1.1.5.12.5.2.2.1
		autoNegPonNo OBJECT-TYPE
			SYNTAX INTEGER (1..16)
			MAX-ACCESS read-write
			STATUS current
			DESCRIPTION
				"Description."
			::= { onuPortAutoNegCfg 1 }

		
--          1.3.6.1.4.1.37950.1.1.5.12.5.2.2.2
-- 1.3.6.1.4.1.37950.1.1.5.12.5.2.2.2
-- 1.3.6.1.4.1.37950.1.1.5.12.5.2.2.2
-- 1.3.6.1.4.1.37950.1.1.5.12.5.2.2.2
-- 1.3.6.1.4.1.37950.1.1.5.12.5.2.2.2
-- 1.3.6.1.4.1.37950.1.1.5.12.5.2.2.2
-- 1.3.6.1.4.1.37950.1.1.5.12.5.2.2.2
-- 1.3.6.1.4.1.37950.1.1.5.12.5.2.2.2
-- 1.3.6.1.4.1.37950.1.1.5.12.5.2.2.2
		-- 1.3.6.1.4.1.37950.1.1.5.12.5.2.2.2
		autoNegOnuNo OBJECT-TYPE
			SYNTAX INTEGER (1..65535)
			MAX-ACCESS read-write
			STATUS current
			DESCRIPTION
				"Description."
			::= { onuPortAutoNegCfg 2 }

		
--          1.3.6.1.4.1.37950.1.1.5.12.5.2.2.3
-- 1.3.6.1.4.1.37950.1.1.5.12.5.2.2.3
-- 1.3.6.1.4.1.37950.1.1.5.12.5.2.2.3
-- 1.3.6.1.4.1.37950.1.1.5.12.5.2.2.3
-- 1.3.6.1.4.1.37950.1.1.5.12.5.2.2.3
-- 1.3.6.1.4.1.37950.1.1.5.12.5.2.2.3
-- 1.3.6.1.4.1.37950.1.1.5.12.5.2.2.3
-- 1.3.6.1.4.1.37950.1.1.5.12.5.2.2.3
-- 1.3.6.1.4.1.37950.1.1.5.12.5.2.2.3
		-- 1.3.6.1.4.1.37950.1.1.5.12.5.2.2.3
		autoNegPortNo OBJECT-TYPE
			SYNTAX INTEGER (1..255)
			MAX-ACCESS read-write
			STATUS current
			DESCRIPTION
				"Description."
			::= { onuPortAutoNegCfg 3 }

		
--          1.3.6.1.4.1.37950.1.1.5.12.5.2.2.4
-- 1.3.6.1.4.1.37950.1.1.5.12.5.2.2.4
-- 1.3.6.1.4.1.37950.1.1.5.12.5.2.2.4
-- 1.3.6.1.4.1.37950.1.1.5.12.5.2.2.4
-- 1.3.6.1.4.1.37950.1.1.5.12.5.2.2.4
-- 1.3.6.1.4.1.37950.1.1.5.12.5.2.2.4
-- 1.3.6.1.4.1.37950.1.1.5.12.5.2.2.4
-- 1.3.6.1.4.1.37950.1.1.5.12.5.2.2.4
-- 1.3.6.1.4.1.37950.1.1.5.12.5.2.2.4
		-- 1.3.6.1.4.1.37950.1.1.5.12.5.2.2.4
		portAutoNeg OBJECT-TYPE
			SYNTAX INTEGER
				{
				disable(0),
				enable(1)
				}
			MAX-ACCESS read-write
			STATUS current
			DESCRIPTION
				"Description."
			::= { onuPortAutoNegCfg 4 }

		
--          1.3.6.1.4.1.37950.1.1.5.12.5.2.3
-- 1.3.6.1.4.1.37950.1.1.5.12.5.2.3
-- 1.3.6.1.4.1.37950.1.1.5.12.5.2.3
-- 1.3.6.1.4.1.37950.1.1.5.12.5.2.3
-- 1.3.6.1.4.1.37950.1.1.5.12.5.2.3
-- 1.3.6.1.4.1.37950.1.1.5.12.5.2.3
-- 1.3.6.1.4.1.37950.1.1.5.12.5.2.3
-- 1.3.6.1.4.1.37950.1.1.5.12.5.2.3
-- 1.3.6.1.4.1.37950.1.1.5.12.5.2.3
		-- 1.3.6.1.4.1.37950.1.1.5.12.5.2.3
		onuPortAutoNegRstCfg OBJECT IDENTIFIER ::= { onuPortCfg 3 }

		
--          1.3.6.1.4.1.37950.1.1.5.12.5.2.3.1
-- 1.3.6.1.4.1.37950.1.1.5.12.5.2.3.1
-- 1.3.6.1.4.1.37950.1.1.5.12.5.2.3.1
-- 1.3.6.1.4.1.37950.1.1.5.12.5.2.3.1
-- 1.3.6.1.4.1.37950.1.1.5.12.5.2.3.1
-- 1.3.6.1.4.1.37950.1.1.5.12.5.2.3.1
-- 1.3.6.1.4.1.37950.1.1.5.12.5.2.3.1
-- 1.3.6.1.4.1.37950.1.1.5.12.5.2.3.1
-- 1.3.6.1.4.1.37950.1.1.5.12.5.2.3.1
		-- 1.3.6.1.4.1.37950.1.1.5.12.5.2.3.1
		autoNegRstPonNo OBJECT-TYPE
			SYNTAX INTEGER (1..16)
			MAX-ACCESS read-write
			STATUS current
			DESCRIPTION
				"Description."
			::= { onuPortAutoNegRstCfg 1 }

		
--          1.3.6.1.4.1.37950.1.1.5.12.5.2.3.2
-- 1.3.6.1.4.1.37950.1.1.5.12.5.2.3.2
-- 1.3.6.1.4.1.37950.1.1.5.12.5.2.3.2
-- 1.3.6.1.4.1.37950.1.1.5.12.5.2.3.2
-- 1.3.6.1.4.1.37950.1.1.5.12.5.2.3.2
-- 1.3.6.1.4.1.37950.1.1.5.12.5.2.3.2
-- 1.3.6.1.4.1.37950.1.1.5.12.5.2.3.2
-- 1.3.6.1.4.1.37950.1.1.5.12.5.2.3.2
-- 1.3.6.1.4.1.37950.1.1.5.12.5.2.3.2
		-- 1.3.6.1.4.1.37950.1.1.5.12.5.2.3.2
		autoNegRstOnuNo OBJECT-TYPE
			SYNTAX INTEGER (1..65535)
			MAX-ACCESS read-write
			STATUS current
			DESCRIPTION
				"Description."
			::= { onuPortAutoNegRstCfg 2 }

		
--          1.3.6.1.4.1.37950.1.1.5.12.5.2.3.3
-- 1.3.6.1.4.1.37950.1.1.5.12.5.2.3.3
-- 1.3.6.1.4.1.37950.1.1.5.12.5.2.3.3
-- 1.3.6.1.4.1.37950.1.1.5.12.5.2.3.3
-- 1.3.6.1.4.1.37950.1.1.5.12.5.2.3.3
-- 1.3.6.1.4.1.37950.1.1.5.12.5.2.3.3
-- 1.3.6.1.4.1.37950.1.1.5.12.5.2.3.3
-- 1.3.6.1.4.1.37950.1.1.5.12.5.2.3.3
-- 1.3.6.1.4.1.37950.1.1.5.12.5.2.3.3
		-- 1.3.6.1.4.1.37950.1.1.5.12.5.2.3.3
		autoNegRstPortNo OBJECT-TYPE
			SYNTAX INTEGER (1..255)
			MAX-ACCESS read-write
			STATUS current
			DESCRIPTION
				"Description."
			::= { onuPortAutoNegRstCfg 3 }

		
--          1.3.6.1.4.1.37950.1.1.5.12.5.2.3.4
-- 1.3.6.1.4.1.37950.1.1.5.12.5.2.3.4
-- 1.3.6.1.4.1.37950.1.1.5.12.5.2.3.4
-- 1.3.6.1.4.1.37950.1.1.5.12.5.2.3.4
-- 1.3.6.1.4.1.37950.1.1.5.12.5.2.3.4
-- 1.3.6.1.4.1.37950.1.1.5.12.5.2.3.4
-- 1.3.6.1.4.1.37950.1.1.5.12.5.2.3.4
-- 1.3.6.1.4.1.37950.1.1.5.12.5.2.3.4
-- 1.3.6.1.4.1.37950.1.1.5.12.5.2.3.4
		-- 1.3.6.1.4.1.37950.1.1.5.12.5.2.3.4
		portAutoNegRestart OBJECT-TYPE
			SYNTAX INTEGER { enable(1) }
			MAX-ACCESS read-write
			STATUS current
			DESCRIPTION
				"Description."
			::= { onuPortAutoNegRstCfg 4 }

		
--          1.3.6.1.4.1.37950.1.1.5.12.5.2.4
-- 1.3.6.1.4.1.37950.1.1.5.12.5.2.4
-- 1.3.6.1.4.1.37950.1.1.5.12.5.2.4
-- 1.3.6.1.4.1.37950.1.1.5.12.5.2.4
-- 1.3.6.1.4.1.37950.1.1.5.12.5.2.4
-- 1.3.6.1.4.1.37950.1.1.5.12.5.2.4
-- 1.3.6.1.4.1.37950.1.1.5.12.5.2.4
-- 1.3.6.1.4.1.37950.1.1.5.12.5.2.4
-- 1.3.6.1.4.1.37950.1.1.5.12.5.2.4
		-- 1.3.6.1.4.1.37950.1.1.5.12.5.2.4
		onuPortFcCfg OBJECT IDENTIFIER ::= { onuPortCfg 4 }

		
--          1.3.6.1.4.1.37950.1.1.5.12.5.2.4.1
-- 1.3.6.1.4.1.37950.1.1.5.12.5.2.4.1
-- 1.3.6.1.4.1.37950.1.1.5.12.5.2.4.1
-- 1.3.6.1.4.1.37950.1.1.5.12.5.2.4.1
-- 1.3.6.1.4.1.37950.1.1.5.12.5.2.4.1
-- 1.3.6.1.4.1.37950.1.1.5.12.5.2.4.1
-- 1.3.6.1.4.1.37950.1.1.5.12.5.2.4.1
-- 1.3.6.1.4.1.37950.1.1.5.12.5.2.4.1
-- 1.3.6.1.4.1.37950.1.1.5.12.5.2.4.1
		-- 1.3.6.1.4.1.37950.1.1.5.12.5.2.4.1
		fcPonNo OBJECT-TYPE
			SYNTAX INTEGER (1..16)
			MAX-ACCESS read-write
			STATUS current
			DESCRIPTION
				"Description."
			::= { onuPortFcCfg 1 }

		
--          1.3.6.1.4.1.37950.1.1.5.12.5.2.4.2
-- 1.3.6.1.4.1.37950.1.1.5.12.5.2.4.2
-- 1.3.6.1.4.1.37950.1.1.5.12.5.2.4.2
-- 1.3.6.1.4.1.37950.1.1.5.12.5.2.4.2
-- 1.3.6.1.4.1.37950.1.1.5.12.5.2.4.2
-- 1.3.6.1.4.1.37950.1.1.5.12.5.2.4.2
-- 1.3.6.1.4.1.37950.1.1.5.12.5.2.4.2
-- 1.3.6.1.4.1.37950.1.1.5.12.5.2.4.2
-- 1.3.6.1.4.1.37950.1.1.5.12.5.2.4.2
		-- 1.3.6.1.4.1.37950.1.1.5.12.5.2.4.2
		fcOnuNo OBJECT-TYPE
			SYNTAX INTEGER (1..65535)
			MAX-ACCESS read-write
			STATUS current
			DESCRIPTION
				"Description."
			::= { onuPortFcCfg 2 }

		
--          1.3.6.1.4.1.37950.1.1.5.12.5.2.4.3
-- 1.3.6.1.4.1.37950.1.1.5.12.5.2.4.3
-- 1.3.6.1.4.1.37950.1.1.5.12.5.2.4.3
-- 1.3.6.1.4.1.37950.1.1.5.12.5.2.4.3
-- 1.3.6.1.4.1.37950.1.1.5.12.5.2.4.3
-- 1.3.6.1.4.1.37950.1.1.5.12.5.2.4.3
-- 1.3.6.1.4.1.37950.1.1.5.12.5.2.4.3
-- 1.3.6.1.4.1.37950.1.1.5.12.5.2.4.3
-- 1.3.6.1.4.1.37950.1.1.5.12.5.2.4.3
		-- 1.3.6.1.4.1.37950.1.1.5.12.5.2.4.3
		fcPortNo OBJECT-TYPE
			SYNTAX INTEGER (1..255)
			MAX-ACCESS read-write
			STATUS current
			DESCRIPTION
				"Description."
			::= { onuPortFcCfg 3 }

		
--          1.3.6.1.4.1.37950.1.1.5.12.5.2.4.4
-- 1.3.6.1.4.1.37950.1.1.5.12.5.2.4.4
-- 1.3.6.1.4.1.37950.1.1.5.12.5.2.4.4
-- 1.3.6.1.4.1.37950.1.1.5.12.5.2.4.4
-- 1.3.6.1.4.1.37950.1.1.5.12.5.2.4.4
-- 1.3.6.1.4.1.37950.1.1.5.12.5.2.4.4
-- 1.3.6.1.4.1.37950.1.1.5.12.5.2.4.4
-- 1.3.6.1.4.1.37950.1.1.5.12.5.2.4.4
-- 1.3.6.1.4.1.37950.1.1.5.12.5.2.4.4
		-- 1.3.6.1.4.1.37950.1.1.5.12.5.2.4.4
		portFlowControl OBJECT-TYPE
			SYNTAX INTEGER
				{
				disable(0),
				enable(1)
				}
			MAX-ACCESS read-write
			STATUS current
			DESCRIPTION
				"Description."
			::= { onuPortFcCfg 4 }

		
--          1.3.6.1.4.1.37950.1.1.5.12.5.2.5
-- 1.3.6.1.4.1.37950.1.1.5.12.5.2.5
-- 1.3.6.1.4.1.37950.1.1.5.12.5.2.5
-- 1.3.6.1.4.1.37950.1.1.5.12.5.2.5
-- 1.3.6.1.4.1.37950.1.1.5.12.5.2.5
-- 1.3.6.1.4.1.37950.1.1.5.12.5.2.5
-- 1.3.6.1.4.1.37950.1.1.5.12.5.2.5
-- 1.3.6.1.4.1.37950.1.1.5.12.5.2.5
-- 1.3.6.1.4.1.37950.1.1.5.12.5.2.5
		-- 1.3.6.1.4.1.37950.1.1.5.12.5.2.5
		portLoopdetectCfg OBJECT IDENTIFIER ::= { onuPortCfg 5 }

		
--          1.3.6.1.4.1.37950.1.1.5.12.5.2.5.1
-- 1.3.6.1.4.1.37950.1.1.5.12.5.2.5.1
-- 1.3.6.1.4.1.37950.1.1.5.12.5.2.5.1
-- 1.3.6.1.4.1.37950.1.1.5.12.5.2.5.1
-- 1.3.6.1.4.1.37950.1.1.5.12.5.2.5.1
-- 1.3.6.1.4.1.37950.1.1.5.12.5.2.5.1
-- 1.3.6.1.4.1.37950.1.1.5.12.5.2.5.1
-- 1.3.6.1.4.1.37950.1.1.5.12.5.2.5.1
-- 1.3.6.1.4.1.37950.1.1.5.12.5.2.5.1
		-- 1.3.6.1.4.1.37950.1.1.5.12.5.2.5.1
		loopPonNo OBJECT-TYPE
			SYNTAX INTEGER (1..16)
			MAX-ACCESS read-write
			STATUS current
			DESCRIPTION
				"Description."
			::= { portLoopdetectCfg 1 }

		
--          1.3.6.1.4.1.37950.1.1.5.12.5.2.5.2
-- 1.3.6.1.4.1.37950.1.1.5.12.5.2.5.2
-- 1.3.6.1.4.1.37950.1.1.5.12.5.2.5.2
-- 1.3.6.1.4.1.37950.1.1.5.12.5.2.5.2
-- 1.3.6.1.4.1.37950.1.1.5.12.5.2.5.2
-- 1.3.6.1.4.1.37950.1.1.5.12.5.2.5.2
-- 1.3.6.1.4.1.37950.1.1.5.12.5.2.5.2
-- 1.3.6.1.4.1.37950.1.1.5.12.5.2.5.2
-- 1.3.6.1.4.1.37950.1.1.5.12.5.2.5.2
		-- 1.3.6.1.4.1.37950.1.1.5.12.5.2.5.2
		loopOnuNo OBJECT-TYPE
			SYNTAX INTEGER (1..65535)
			MAX-ACCESS read-write
			STATUS current
			DESCRIPTION
				"Description."
			::= { portLoopdetectCfg 2 }

		
--          1.3.6.1.4.1.37950.1.1.5.12.5.2.5.3
-- 1.3.6.1.4.1.37950.1.1.5.12.5.2.5.3
-- 1.3.6.1.4.1.37950.1.1.5.12.5.2.5.3
-- 1.3.6.1.4.1.37950.1.1.5.12.5.2.5.3
-- 1.3.6.1.4.1.37950.1.1.5.12.5.2.5.3
-- 1.3.6.1.4.1.37950.1.1.5.12.5.2.5.3
-- 1.3.6.1.4.1.37950.1.1.5.12.5.2.5.3
-- 1.3.6.1.4.1.37950.1.1.5.12.5.2.5.3
-- 1.3.6.1.4.1.37950.1.1.5.12.5.2.5.3
		-- 1.3.6.1.4.1.37950.1.1.5.12.5.2.5.3
		loopPortNo OBJECT-TYPE
			SYNTAX INTEGER (1..255)
			MAX-ACCESS read-write
			STATUS current
			DESCRIPTION
				"Description."
			::= { portLoopdetectCfg 3 }

		
--          1.3.6.1.4.1.37950.1.1.5.12.5.2.5.4
-- 1.3.6.1.4.1.37950.1.1.5.12.5.2.5.4
-- 1.3.6.1.4.1.37950.1.1.5.12.5.2.5.4
-- 1.3.6.1.4.1.37950.1.1.5.12.5.2.5.4
-- 1.3.6.1.4.1.37950.1.1.5.12.5.2.5.4
-- 1.3.6.1.4.1.37950.1.1.5.12.5.2.5.4
-- 1.3.6.1.4.1.37950.1.1.5.12.5.2.5.4
-- 1.3.6.1.4.1.37950.1.1.5.12.5.2.5.4
-- 1.3.6.1.4.1.37950.1.1.5.12.5.2.5.4
		-- 1.3.6.1.4.1.37950.1.1.5.12.5.2.5.4
		portLoopdetect OBJECT-TYPE
			SYNTAX INTEGER
				{
				disable(0),
				enable(1)
				}
			MAX-ACCESS read-write
			STATUS current
			DESCRIPTION
				"Description."
			::= { portLoopdetectCfg 4 }

		
--          1.3.6.1.4.1.37950.1.1.5.12.5.2.6
-- 1.3.6.1.4.1.37950.1.1.5.12.5.2.6
-- 1.3.6.1.4.1.37950.1.1.5.12.5.2.6
-- 1.3.6.1.4.1.37950.1.1.5.12.5.2.6
-- 1.3.6.1.4.1.37950.1.1.5.12.5.2.6
-- 1.3.6.1.4.1.37950.1.1.5.12.5.2.6
-- 1.3.6.1.4.1.37950.1.1.5.12.5.2.6
-- 1.3.6.1.4.1.37950.1.1.5.12.5.2.6
-- 1.3.6.1.4.1.37950.1.1.5.12.5.2.6
		-- 1.3.6.1.4.1.37950.1.1.5.12.5.2.6
		portDisLoopCfg OBJECT IDENTIFIER ::= { onuPortCfg 6 }

		
--          1.3.6.1.4.1.37950.1.1.5.12.5.2.6.1
-- 1.3.6.1.4.1.37950.1.1.5.12.5.2.6.1
-- 1.3.6.1.4.1.37950.1.1.5.12.5.2.6.1
-- 1.3.6.1.4.1.37950.1.1.5.12.5.2.6.1
-- 1.3.6.1.4.1.37950.1.1.5.12.5.2.6.1
-- 1.3.6.1.4.1.37950.1.1.5.12.5.2.6.1
-- 1.3.6.1.4.1.37950.1.1.5.12.5.2.6.1
-- 1.3.6.1.4.1.37950.1.1.5.12.5.2.6.1
-- 1.3.6.1.4.1.37950.1.1.5.12.5.2.6.1
		-- 1.3.6.1.4.1.37950.1.1.5.12.5.2.6.1
		disLoopPonNo OBJECT-TYPE
			SYNTAX INTEGER (1..16)
			MAX-ACCESS read-write
			STATUS current
			DESCRIPTION
				"Description."
			::= { portDisLoopCfg 1 }

		
--          1.3.6.1.4.1.37950.1.1.5.12.5.2.6.2
-- 1.3.6.1.4.1.37950.1.1.5.12.5.2.6.2
-- 1.3.6.1.4.1.37950.1.1.5.12.5.2.6.2
-- 1.3.6.1.4.1.37950.1.1.5.12.5.2.6.2
-- 1.3.6.1.4.1.37950.1.1.5.12.5.2.6.2
-- 1.3.6.1.4.1.37950.1.1.5.12.5.2.6.2
-- 1.3.6.1.4.1.37950.1.1.5.12.5.2.6.2
-- 1.3.6.1.4.1.37950.1.1.5.12.5.2.6.2
-- 1.3.6.1.4.1.37950.1.1.5.12.5.2.6.2
		-- 1.3.6.1.4.1.37950.1.1.5.12.5.2.6.2
		disLoopOnuNo OBJECT-TYPE
			SYNTAX INTEGER (1..65535)
			MAX-ACCESS read-write
			STATUS current
			DESCRIPTION
				"Description."
			::= { portDisLoopCfg 2 }

		
--          1.3.6.1.4.1.37950.1.1.5.12.5.2.6.3
-- 1.3.6.1.4.1.37950.1.1.5.12.5.2.6.3
-- 1.3.6.1.4.1.37950.1.1.5.12.5.2.6.3
-- 1.3.6.1.4.1.37950.1.1.5.12.5.2.6.3
-- 1.3.6.1.4.1.37950.1.1.5.12.5.2.6.3
-- 1.3.6.1.4.1.37950.1.1.5.12.5.2.6.3
-- 1.3.6.1.4.1.37950.1.1.5.12.5.2.6.3
-- 1.3.6.1.4.1.37950.1.1.5.12.5.2.6.3
-- 1.3.6.1.4.1.37950.1.1.5.12.5.2.6.3
		-- 1.3.6.1.4.1.37950.1.1.5.12.5.2.6.3
		disLoopPortNo OBJECT-TYPE
			SYNTAX INTEGER (1..255)
			MAX-ACCESS read-write
			STATUS current
			DESCRIPTION
				"Description."
			::= { portDisLoopCfg 3 }

		
--          1.3.6.1.4.1.37950.1.1.5.12.5.2.6.4
-- 1.3.6.1.4.1.37950.1.1.5.12.5.2.6.4
-- 1.3.6.1.4.1.37950.1.1.5.12.5.2.6.4
-- 1.3.6.1.4.1.37950.1.1.5.12.5.2.6.4
-- 1.3.6.1.4.1.37950.1.1.5.12.5.2.6.4
-- 1.3.6.1.4.1.37950.1.1.5.12.5.2.6.4
-- 1.3.6.1.4.1.37950.1.1.5.12.5.2.6.4
-- 1.3.6.1.4.1.37950.1.1.5.12.5.2.6.4
-- 1.3.6.1.4.1.37950.1.1.5.12.5.2.6.4
		-- 1.3.6.1.4.1.37950.1.1.5.12.5.2.6.4
		portDisableLoopEn OBJECT-TYPE
			SYNTAX INTEGER
				{
				disable(0),
				enable(1)
				}
			MAX-ACCESS read-write
			STATUS current
			DESCRIPTION
				"Description."
			::= { portDisLoopCfg 4 }

		
--          1.3.6.1.4.1.37950.1.1.5.12.5.2.8
-- 1.3.6.1.4.1.37950.1.1.5.12.5.2.8
-- 1.3.6.1.4.1.37950.1.1.5.12.5.2.8
-- 1.3.6.1.4.1.37950.1.1.5.12.5.2.8
-- 1.3.6.1.4.1.37950.1.1.5.12.5.2.8
-- 1.3.6.1.4.1.37950.1.1.5.12.5.2.8
-- 1.3.6.1.4.1.37950.1.1.5.12.5.2.8
-- 1.3.6.1.4.1.37950.1.1.5.12.5.2.8
-- 1.3.6.1.4.1.37950.1.1.5.12.5.2.8
		-- 1.3.6.1.4.1.37950.1.1.5.12.5.2.8
		onuPortUpstreamLimit OBJECT IDENTIFIER ::= { onuPortCfg 8 }

		
--          1.3.6.1.4.1.37950.1.1.5.12.5.2.8.1
-- 1.3.6.1.4.1.37950.1.1.5.12.5.2.8.1
-- 1.3.6.1.4.1.37950.1.1.5.12.5.2.8.1
-- 1.3.6.1.4.1.37950.1.1.5.12.5.2.8.1
-- 1.3.6.1.4.1.37950.1.1.5.12.5.2.8.1
-- 1.3.6.1.4.1.37950.1.1.5.12.5.2.8.1
-- 1.3.6.1.4.1.37950.1.1.5.12.5.2.8.1
-- 1.3.6.1.4.1.37950.1.1.5.12.5.2.8.1
-- 1.3.6.1.4.1.37950.1.1.5.12.5.2.8.1
		-- 1.3.6.1.4.1.37950.1.1.5.12.5.2.8.1
		upLimitPonNo OBJECT-TYPE
			SYNTAX INTEGER (1..16)
			MAX-ACCESS read-write
			STATUS current
			DESCRIPTION
				"Description."
			::= { onuPortUpstreamLimit 1 }

		
--          1.3.6.1.4.1.37950.1.1.5.12.5.2.8.2
-- 1.3.6.1.4.1.37950.1.1.5.12.5.2.8.2
-- 1.3.6.1.4.1.37950.1.1.5.12.5.2.8.2
-- 1.3.6.1.4.1.37950.1.1.5.12.5.2.8.2
-- 1.3.6.1.4.1.37950.1.1.5.12.5.2.8.2
-- 1.3.6.1.4.1.37950.1.1.5.12.5.2.8.2
-- 1.3.6.1.4.1.37950.1.1.5.12.5.2.8.2
-- 1.3.6.1.4.1.37950.1.1.5.12.5.2.8.2
-- 1.3.6.1.4.1.37950.1.1.5.12.5.2.8.2
		-- 1.3.6.1.4.1.37950.1.1.5.12.5.2.8.2
		upLimitOnuNo OBJECT-TYPE
			SYNTAX INTEGER (1..65535)
			MAX-ACCESS read-write
			STATUS current
			DESCRIPTION
				"Description."
			::= { onuPortUpstreamLimit 2 }

		
--          1.3.6.1.4.1.37950.1.1.5.12.5.2.8.3
-- 1.3.6.1.4.1.37950.1.1.5.12.5.2.8.3
-- 1.3.6.1.4.1.37950.1.1.5.12.5.2.8.3
-- 1.3.6.1.4.1.37950.1.1.5.12.5.2.8.3
-- 1.3.6.1.4.1.37950.1.1.5.12.5.2.8.3
-- 1.3.6.1.4.1.37950.1.1.5.12.5.2.8.3
-- 1.3.6.1.4.1.37950.1.1.5.12.5.2.8.3
-- 1.3.6.1.4.1.37950.1.1.5.12.5.2.8.3
-- 1.3.6.1.4.1.37950.1.1.5.12.5.2.8.3
		-- 1.3.6.1.4.1.37950.1.1.5.12.5.2.8.3
		upLimitPortNo OBJECT-TYPE
			SYNTAX INTEGER (1..255)
			MAX-ACCESS read-write
			STATUS current
			DESCRIPTION
				"Description."
			::= { onuPortUpstreamLimit 3 }

		
--          1.3.6.1.4.1.37950.1.1.5.12.5.2.8.4
-- 1.3.6.1.4.1.37950.1.1.5.12.5.2.8.4
-- 1.3.6.1.4.1.37950.1.1.5.12.5.2.8.4
-- 1.3.6.1.4.1.37950.1.1.5.12.5.2.8.4
-- 1.3.6.1.4.1.37950.1.1.5.12.5.2.8.4
-- 1.3.6.1.4.1.37950.1.1.5.12.5.2.8.4
-- 1.3.6.1.4.1.37950.1.1.5.12.5.2.8.4
-- 1.3.6.1.4.1.37950.1.1.5.12.5.2.8.4
-- 1.3.6.1.4.1.37950.1.1.5.12.5.2.8.4
		-- 1.3.6.1.4.1.37950.1.1.5.12.5.2.8.4
		upLimitCir OBJECT-TYPE
			SYNTAX INTEGER (0..1048576)
			MAX-ACCESS read-write
			STATUS current
			DESCRIPTION
				"Description."
			::= { onuPortUpstreamLimit 4 }

		
--          1.3.6.1.4.1.37950.1.1.5.12.5.2.8.5
-- 1.3.6.1.4.1.37950.1.1.5.12.5.2.8.5
-- 1.3.6.1.4.1.37950.1.1.5.12.5.2.8.5
-- 1.3.6.1.4.1.37950.1.1.5.12.5.2.8.5
-- 1.3.6.1.4.1.37950.1.1.5.12.5.2.8.5
-- 1.3.6.1.4.1.37950.1.1.5.12.5.2.8.5
-- 1.3.6.1.4.1.37950.1.1.5.12.5.2.8.5
-- 1.3.6.1.4.1.37950.1.1.5.12.5.2.8.5
-- 1.3.6.1.4.1.37950.1.1.5.12.5.2.8.5
		-- 1.3.6.1.4.1.37950.1.1.5.12.5.2.8.5
		upLimitCbs OBJECT-TYPE
			SYNTAX INTEGER (0..10240)
			MAX-ACCESS read-write
			STATUS current
			DESCRIPTION
				"Description."
			::= { onuPortUpstreamLimit 5 }

		
--          1.3.6.1.4.1.37950.1.1.5.12.5.2.8.6
-- 1.3.6.1.4.1.37950.1.1.5.12.5.2.8.6
-- 1.3.6.1.4.1.37950.1.1.5.12.5.2.8.6
-- 1.3.6.1.4.1.37950.1.1.5.12.5.2.8.6
-- 1.3.6.1.4.1.37950.1.1.5.12.5.2.8.6
-- 1.3.6.1.4.1.37950.1.1.5.12.5.2.8.6
-- 1.3.6.1.4.1.37950.1.1.5.12.5.2.8.6
-- 1.3.6.1.4.1.37950.1.1.5.12.5.2.8.6
-- 1.3.6.1.4.1.37950.1.1.5.12.5.2.8.6
		-- 1.3.6.1.4.1.37950.1.1.5.12.5.2.8.6
		upLimitEbs OBJECT-TYPE
			SYNTAX INTEGER (0..10240)
			MAX-ACCESS read-write
			STATUS current
			DESCRIPTION
				"Description."
			::= { onuPortUpstreamLimit 6 }

		
--          1.3.6.1.4.1.37950.1.1.5.12.5.2.8.7
-- 1.3.6.1.4.1.37950.1.1.5.12.5.2.8.7
-- 1.3.6.1.4.1.37950.1.1.5.12.5.2.8.7
-- 1.3.6.1.4.1.37950.1.1.5.12.5.2.8.7
-- 1.3.6.1.4.1.37950.1.1.5.12.5.2.8.7
-- 1.3.6.1.4.1.37950.1.1.5.12.5.2.8.7
-- 1.3.6.1.4.1.37950.1.1.5.12.5.2.8.7
-- 1.3.6.1.4.1.37950.1.1.5.12.5.2.8.7
-- 1.3.6.1.4.1.37950.1.1.5.12.5.2.8.7
		-- 1.3.6.1.4.1.37950.1.1.5.12.5.2.8.7
		upLimitAction OBJECT-TYPE
			SYNTAX INTEGER
				{
				add(1),
				delete(2)
				}
			MAX-ACCESS read-write
			STATUS current
			DESCRIPTION
				"Description."
			::= { onuPortUpstreamLimit 7 }

		
--          1.3.6.1.4.1.37950.1.1.5.12.5.2.9
-- 1.3.6.1.4.1.37950.1.1.5.12.5.2.9
-- 1.3.6.1.4.1.37950.1.1.5.12.5.2.9
-- 1.3.6.1.4.1.37950.1.1.5.12.5.2.9
-- 1.3.6.1.4.1.37950.1.1.5.12.5.2.9
-- 1.3.6.1.4.1.37950.1.1.5.12.5.2.9
-- 1.3.6.1.4.1.37950.1.1.5.12.5.2.9
-- 1.3.6.1.4.1.37950.1.1.5.12.5.2.9
-- 1.3.6.1.4.1.37950.1.1.5.12.5.2.9
		-- 1.3.6.1.4.1.37950.1.1.5.12.5.2.9
		onuPortDownstreamLimit OBJECT IDENTIFIER ::= { onuPortCfg 9 }

		
--          1.3.6.1.4.1.37950.1.1.5.12.5.2.9.1
-- 1.3.6.1.4.1.37950.1.1.5.12.5.2.9.1
-- 1.3.6.1.4.1.37950.1.1.5.12.5.2.9.1
-- 1.3.6.1.4.1.37950.1.1.5.12.5.2.9.1
-- 1.3.6.1.4.1.37950.1.1.5.12.5.2.9.1
-- 1.3.6.1.4.1.37950.1.1.5.12.5.2.9.1
-- 1.3.6.1.4.1.37950.1.1.5.12.5.2.9.1
-- 1.3.6.1.4.1.37950.1.1.5.12.5.2.9.1
-- 1.3.6.1.4.1.37950.1.1.5.12.5.2.9.1
		-- 1.3.6.1.4.1.37950.1.1.5.12.5.2.9.1
		downLimitPonNo OBJECT-TYPE
			SYNTAX INTEGER (1..16)
			MAX-ACCESS read-write
			STATUS current
			DESCRIPTION
				"Description."
			::= { onuPortDownstreamLimit 1 }

		
--          1.3.6.1.4.1.37950.1.1.5.12.5.2.9.2
-- 1.3.6.1.4.1.37950.1.1.5.12.5.2.9.2
-- 1.3.6.1.4.1.37950.1.1.5.12.5.2.9.2
-- 1.3.6.1.4.1.37950.1.1.5.12.5.2.9.2
-- 1.3.6.1.4.1.37950.1.1.5.12.5.2.9.2
-- 1.3.6.1.4.1.37950.1.1.5.12.5.2.9.2
-- 1.3.6.1.4.1.37950.1.1.5.12.5.2.9.2
-- 1.3.6.1.4.1.37950.1.1.5.12.5.2.9.2
-- 1.3.6.1.4.1.37950.1.1.5.12.5.2.9.2
		-- 1.3.6.1.4.1.37950.1.1.5.12.5.2.9.2
		downLimitOnuNo OBJECT-TYPE
			SYNTAX INTEGER (1..65535)
			MAX-ACCESS read-write
			STATUS current
			DESCRIPTION
				"Description."
			::= { onuPortDownstreamLimit 2 }

		
--          1.3.6.1.4.1.37950.1.1.5.12.5.2.9.3
-- 1.3.6.1.4.1.37950.1.1.5.12.5.2.9.3
-- 1.3.6.1.4.1.37950.1.1.5.12.5.2.9.3
-- 1.3.6.1.4.1.37950.1.1.5.12.5.2.9.3
-- 1.3.6.1.4.1.37950.1.1.5.12.5.2.9.3
-- 1.3.6.1.4.1.37950.1.1.5.12.5.2.9.3
-- 1.3.6.1.4.1.37950.1.1.5.12.5.2.9.3
-- 1.3.6.1.4.1.37950.1.1.5.12.5.2.9.3
-- 1.3.6.1.4.1.37950.1.1.5.12.5.2.9.3
		-- 1.3.6.1.4.1.37950.1.1.5.12.5.2.9.3
		downLimitPortNo OBJECT-TYPE
			SYNTAX INTEGER (1..65535)
			MAX-ACCESS read-write
			STATUS current
			DESCRIPTION
				"Description."
			::= { onuPortDownstreamLimit 3 }

		
--          1.3.6.1.4.1.37950.1.1.5.12.5.2.9.4
-- 1.3.6.1.4.1.37950.1.1.5.12.5.2.9.4
-- 1.3.6.1.4.1.37950.1.1.5.12.5.2.9.4
-- 1.3.6.1.4.1.37950.1.1.5.12.5.2.9.4
-- 1.3.6.1.4.1.37950.1.1.5.12.5.2.9.4
-- 1.3.6.1.4.1.37950.1.1.5.12.5.2.9.4
-- 1.3.6.1.4.1.37950.1.1.5.12.5.2.9.4
-- 1.3.6.1.4.1.37950.1.1.5.12.5.2.9.4
-- 1.3.6.1.4.1.37950.1.1.5.12.5.2.9.4
		-- 1.3.6.1.4.1.37950.1.1.5.12.5.2.9.4
		downLimitCir OBJECT-TYPE
			SYNTAX INTEGER (0..1048576)
			MAX-ACCESS read-write
			STATUS current
			DESCRIPTION
				"Description."
			::= { onuPortDownstreamLimit 4 }

		
--          1.3.6.1.4.1.37950.1.1.5.12.5.2.9.5
-- 1.3.6.1.4.1.37950.1.1.5.12.5.2.9.5
-- 1.3.6.1.4.1.37950.1.1.5.12.5.2.9.5
-- 1.3.6.1.4.1.37950.1.1.5.12.5.2.9.5
-- 1.3.6.1.4.1.37950.1.1.5.12.5.2.9.5
-- 1.3.6.1.4.1.37950.1.1.5.12.5.2.9.5
-- 1.3.6.1.4.1.37950.1.1.5.12.5.2.9.5
-- 1.3.6.1.4.1.37950.1.1.5.12.5.2.9.5
-- 1.3.6.1.4.1.37950.1.1.5.12.5.2.9.5
		-- 1.3.6.1.4.1.37950.1.1.5.12.5.2.9.5
		downLimitPir OBJECT-TYPE
			SYNTAX INTEGER (0..1048576)
			MAX-ACCESS read-write
			STATUS current
			DESCRIPTION
				"Description."
			::= { onuPortDownstreamLimit 5 }

		
--          1.3.6.1.4.1.37950.1.1.5.12.5.2.9.6
-- 1.3.6.1.4.1.37950.1.1.5.12.5.2.9.6
-- 1.3.6.1.4.1.37950.1.1.5.12.5.2.9.6
-- 1.3.6.1.4.1.37950.1.1.5.12.5.2.9.6
-- 1.3.6.1.4.1.37950.1.1.5.12.5.2.9.6
-- 1.3.6.1.4.1.37950.1.1.5.12.5.2.9.6
-- 1.3.6.1.4.1.37950.1.1.5.12.5.2.9.6
-- 1.3.6.1.4.1.37950.1.1.5.12.5.2.9.6
-- 1.3.6.1.4.1.37950.1.1.5.12.5.2.9.6
		-- 1.3.6.1.4.1.37950.1.1.5.12.5.2.9.6
		downLimitAction OBJECT-TYPE
			SYNTAX INTEGER
				{
				add(1),
				delete(2)
				}
			MAX-ACCESS read-write
			STATUS current
			DESCRIPTION
				"Description."
			::= { onuPortDownstreamLimit 6 }

		
--          1.3.6.1.4.1.37950.1.1.5.12.5.2.10
-- 1.3.6.1.4.1.37950.1.1.5.12.5.2.10
-- 1.3.6.1.4.1.37950.1.1.5.12.5.2.10
-- 1.3.6.1.4.1.37950.1.1.5.12.5.2.10
-- 1.3.6.1.4.1.37950.1.1.5.12.5.2.10
-- 1.3.6.1.4.1.37950.1.1.5.12.5.2.10
-- 1.3.6.1.4.1.37950.1.1.5.12.5.2.10
-- 1.3.6.1.4.1.37950.1.1.5.12.5.2.10
-- 1.3.6.1.4.1.37950.1.1.5.12.5.2.10
		-- 1.3.6.1.4.1.37950.1.1.5.12.5.2.10
		onuPortVlan OBJECT IDENTIFIER ::= { onuPortCfg 10 }

		
--          1.3.6.1.4.1.37950.1.1.5.12.5.2.10.1
-- 1.3.6.1.4.1.37950.1.1.5.12.5.2.10.1
-- 1.3.6.1.4.1.37950.1.1.5.12.5.2.10.1
-- 1.3.6.1.4.1.37950.1.1.5.12.5.2.10.1
-- 1.3.6.1.4.1.37950.1.1.5.12.5.2.10.1
-- 1.3.6.1.4.1.37950.1.1.5.12.5.2.10.1
-- 1.3.6.1.4.1.37950.1.1.5.12.5.2.10.1
-- 1.3.6.1.4.1.37950.1.1.5.12.5.2.10.1
-- 1.3.6.1.4.1.37950.1.1.5.12.5.2.10.1
		-- 1.3.6.1.4.1.37950.1.1.5.12.5.2.10.1
		onuPortVlanMode OBJECT IDENTIFIER ::= { onuPortVlan 1 }

		
--          1.3.6.1.4.1.37950.1.1.5.12.5.2.10.1.1
-- 1.3.6.1.4.1.37950.1.1.5.12.5.2.10.1.1
-- 1.3.6.1.4.1.37950.1.1.5.12.5.2.10.1.1
-- 1.3.6.1.4.1.37950.1.1.5.12.5.2.10.1.1
-- 1.3.6.1.4.1.37950.1.1.5.12.5.2.10.1.1
-- 1.3.6.1.4.1.37950.1.1.5.12.5.2.10.1.1
-- 1.3.6.1.4.1.37950.1.1.5.12.5.2.10.1.1
-- 1.3.6.1.4.1.37950.1.1.5.12.5.2.10.1.1
-- 1.3.6.1.4.1.37950.1.1.5.12.5.2.10.1.1
		-- 1.3.6.1.4.1.37950.1.1.5.12.5.2.10.1.1
		vlanModePonNo OBJECT-TYPE
			SYNTAX INTEGER (1..16)
			MAX-ACCESS read-write
			STATUS current
			DESCRIPTION
				"Description."
			::= { onuPortVlanMode 1 }

		
--          1.3.6.1.4.1.37950.1.1.5.12.5.2.10.1.2
-- 1.3.6.1.4.1.37950.1.1.5.12.5.2.10.1.2
-- 1.3.6.1.4.1.37950.1.1.5.12.5.2.10.1.2
-- 1.3.6.1.4.1.37950.1.1.5.12.5.2.10.1.2
-- 1.3.6.1.4.1.37950.1.1.5.12.5.2.10.1.2
-- 1.3.6.1.4.1.37950.1.1.5.12.5.2.10.1.2
-- 1.3.6.1.4.1.37950.1.1.5.12.5.2.10.1.2
-- 1.3.6.1.4.1.37950.1.1.5.12.5.2.10.1.2
-- 1.3.6.1.4.1.37950.1.1.5.12.5.2.10.1.2
		-- 1.3.6.1.4.1.37950.1.1.5.12.5.2.10.1.2
		vlanModeOnuNo OBJECT-TYPE
			SYNTAX INTEGER (1..65535)
			MAX-ACCESS read-write
			STATUS current
			DESCRIPTION
				"Description."
			::= { onuPortVlanMode 2 }

		
--          1.3.6.1.4.1.37950.1.1.5.12.5.2.10.1.3
-- 1.3.6.1.4.1.37950.1.1.5.12.5.2.10.1.3
-- 1.3.6.1.4.1.37950.1.1.5.12.5.2.10.1.3
-- 1.3.6.1.4.1.37950.1.1.5.12.5.2.10.1.3
-- 1.3.6.1.4.1.37950.1.1.5.12.5.2.10.1.3
-- 1.3.6.1.4.1.37950.1.1.5.12.5.2.10.1.3
-- 1.3.6.1.4.1.37950.1.1.5.12.5.2.10.1.3
-- 1.3.6.1.4.1.37950.1.1.5.12.5.2.10.1.3
-- 1.3.6.1.4.1.37950.1.1.5.12.5.2.10.1.3
		-- 1.3.6.1.4.1.37950.1.1.5.12.5.2.10.1.3
		vlanModePortNo OBJECT-TYPE
			SYNTAX INTEGER (1..255)
			MAX-ACCESS read-write
			STATUS current
			DESCRIPTION
				"Description."
			::= { onuPortVlanMode 3 }

		
--          1.3.6.1.4.1.37950.1.1.5.12.5.2.10.1.4
-- 1.3.6.1.4.1.37950.1.1.5.12.5.2.10.1.4
-- 1.3.6.1.4.1.37950.1.1.5.12.5.2.10.1.4
-- 1.3.6.1.4.1.37950.1.1.5.12.5.2.10.1.4
-- 1.3.6.1.4.1.37950.1.1.5.12.5.2.10.1.4
-- 1.3.6.1.4.1.37950.1.1.5.12.5.2.10.1.4
-- 1.3.6.1.4.1.37950.1.1.5.12.5.2.10.1.4
-- 1.3.6.1.4.1.37950.1.1.5.12.5.2.10.1.4
-- 1.3.6.1.4.1.37950.1.1.5.12.5.2.10.1.4
		-- 1.3.6.1.4.1.37950.1.1.5.12.5.2.10.1.4
		vlanMode OBJECT-TYPE
			SYNTAX INTEGER
				{
				transparent(1),
				tag(2),
				translation(3),
				aggregation(4),
				trunk(5)
				}
			MAX-ACCESS read-write
			STATUS current
			DESCRIPTION
				"Description."
			::= { onuPortVlanMode 4 }

		
--          1.3.6.1.4.1.37950.1.1.5.12.5.2.10.2
-- 1.3.6.1.4.1.37950.1.1.5.12.5.2.10.2
-- 1.3.6.1.4.1.37950.1.1.5.12.5.2.10.2
-- 1.3.6.1.4.1.37950.1.1.5.12.5.2.10.2
-- 1.3.6.1.4.1.37950.1.1.5.12.5.2.10.2
-- 1.3.6.1.4.1.37950.1.1.5.12.5.2.10.2
-- 1.3.6.1.4.1.37950.1.1.5.12.5.2.10.2
-- 1.3.6.1.4.1.37950.1.1.5.12.5.2.10.2
-- 1.3.6.1.4.1.37950.1.1.5.12.5.2.10.2
		-- 1.3.6.1.4.1.37950.1.1.5.12.5.2.10.2
		onuPortVlanPvid OBJECT IDENTIFIER ::= { onuPortVlan 2 }

		
--          1.3.6.1.4.1.37950.1.1.5.12.5.2.10.2.1
-- 1.3.6.1.4.1.37950.1.1.5.12.5.2.10.2.1
-- 1.3.6.1.4.1.37950.1.1.5.12.5.2.10.2.1
-- 1.3.6.1.4.1.37950.1.1.5.12.5.2.10.2.1
-- 1.3.6.1.4.1.37950.1.1.5.12.5.2.10.2.1
-- 1.3.6.1.4.1.37950.1.1.5.12.5.2.10.2.1
-- 1.3.6.1.4.1.37950.1.1.5.12.5.2.10.2.1
-- 1.3.6.1.4.1.37950.1.1.5.12.5.2.10.2.1
-- 1.3.6.1.4.1.37950.1.1.5.12.5.2.10.2.1
		-- 1.3.6.1.4.1.37950.1.1.5.12.5.2.10.2.1
		portPvidPonNo OBJECT-TYPE
			SYNTAX INTEGER (1..16)
			MAX-ACCESS read-write
			STATUS current
			DESCRIPTION
				"Description."
			::= { onuPortVlanPvid 1 }

		
--          1.3.6.1.4.1.37950.1.1.5.12.5.2.10.2.2
-- 1.3.6.1.4.1.37950.1.1.5.12.5.2.10.2.2
-- 1.3.6.1.4.1.37950.1.1.5.12.5.2.10.2.2
-- 1.3.6.1.4.1.37950.1.1.5.12.5.2.10.2.2
-- 1.3.6.1.4.1.37950.1.1.5.12.5.2.10.2.2
-- 1.3.6.1.4.1.37950.1.1.5.12.5.2.10.2.2
-- 1.3.6.1.4.1.37950.1.1.5.12.5.2.10.2.2
-- 1.3.6.1.4.1.37950.1.1.5.12.5.2.10.2.2
-- 1.3.6.1.4.1.37950.1.1.5.12.5.2.10.2.2
		-- 1.3.6.1.4.1.37950.1.1.5.12.5.2.10.2.2
		portPvidOnuNo OBJECT-TYPE
			SYNTAX INTEGER (1..65535)
			MAX-ACCESS read-write
			STATUS current
			DESCRIPTION
				"Description."
			::= { onuPortVlanPvid 2 }

		
--          1.3.6.1.4.1.37950.1.1.5.12.5.2.10.2.3
-- 1.3.6.1.4.1.37950.1.1.5.12.5.2.10.2.3
-- 1.3.6.1.4.1.37950.1.1.5.12.5.2.10.2.3
-- 1.3.6.1.4.1.37950.1.1.5.12.5.2.10.2.3
-- 1.3.6.1.4.1.37950.1.1.5.12.5.2.10.2.3
-- 1.3.6.1.4.1.37950.1.1.5.12.5.2.10.2.3
-- 1.3.6.1.4.1.37950.1.1.5.12.5.2.10.2.3
-- 1.3.6.1.4.1.37950.1.1.5.12.5.2.10.2.3
-- 1.3.6.1.4.1.37950.1.1.5.12.5.2.10.2.3
		-- 1.3.6.1.4.1.37950.1.1.5.12.5.2.10.2.3
		portPvidPortNo OBJECT-TYPE
			SYNTAX INTEGER (1..255)
			MAX-ACCESS read-write
			STATUS current
			DESCRIPTION
				"Description."
			::= { onuPortVlanPvid 3 }

		
--          1.3.6.1.4.1.37950.1.1.5.12.5.2.10.2.4
-- 1.3.6.1.4.1.37950.1.1.5.12.5.2.10.2.4
-- 1.3.6.1.4.1.37950.1.1.5.12.5.2.10.2.4
-- 1.3.6.1.4.1.37950.1.1.5.12.5.2.10.2.4
-- 1.3.6.1.4.1.37950.1.1.5.12.5.2.10.2.4
-- 1.3.6.1.4.1.37950.1.1.5.12.5.2.10.2.4
-- 1.3.6.1.4.1.37950.1.1.5.12.5.2.10.2.4
-- 1.3.6.1.4.1.37950.1.1.5.12.5.2.10.2.4
-- 1.3.6.1.4.1.37950.1.1.5.12.5.2.10.2.4
		-- 1.3.6.1.4.1.37950.1.1.5.12.5.2.10.2.4
		portPvidValue OBJECT-TYPE
			SYNTAX INTEGER (1..4095)
			MAX-ACCESS read-write
			STATUS current
			DESCRIPTION
				"Description."
			::= { onuPortVlanPvid 4 }

		
--          1.3.6.1.4.1.37950.1.1.5.12.5.2.10.2.5
-- 1.3.6.1.4.1.37950.1.1.5.12.5.2.10.2.5
-- 1.3.6.1.4.1.37950.1.1.5.12.5.2.10.2.5
-- 1.3.6.1.4.1.37950.1.1.5.12.5.2.10.2.5
-- 1.3.6.1.4.1.37950.1.1.5.12.5.2.10.2.5
-- 1.3.6.1.4.1.37950.1.1.5.12.5.2.10.2.5
-- 1.3.6.1.4.1.37950.1.1.5.12.5.2.10.2.5
-- 1.3.6.1.4.1.37950.1.1.5.12.5.2.10.2.5
-- 1.3.6.1.4.1.37950.1.1.5.12.5.2.10.2.5
		-- 1.3.6.1.4.1.37950.1.1.5.12.5.2.10.2.5
		portPriValue OBJECT-TYPE
			SYNTAX INTEGER (0..7)
			MAX-ACCESS read-write
			STATUS current
			DESCRIPTION
				"Description."
			::= { onuPortVlanPvid 5 }

		
--          1.3.6.1.4.1.37950.1.1.5.12.5.2.10.2.6
-- 1.3.6.1.4.1.37950.1.1.5.12.5.2.10.2.6
-- 1.3.6.1.4.1.37950.1.1.5.12.5.2.10.2.6
-- 1.3.6.1.4.1.37950.1.1.5.12.5.2.10.2.6
-- 1.3.6.1.4.1.37950.1.1.5.12.5.2.10.2.6
-- 1.3.6.1.4.1.37950.1.1.5.12.5.2.10.2.6
-- 1.3.6.1.4.1.37950.1.1.5.12.5.2.10.2.6
-- 1.3.6.1.4.1.37950.1.1.5.12.5.2.10.2.6
-- 1.3.6.1.4.1.37950.1.1.5.12.5.2.10.2.6
		-- 1.3.6.1.4.1.37950.1.1.5.12.5.2.10.2.6
		pvidAction OBJECT-TYPE
			SYNTAX INTEGER { commit(1) }
			MAX-ACCESS read-write
			STATUS current
			DESCRIPTION
				"Description."
			::= { onuPortVlanPvid 6 }

		
--          1.3.6.1.4.1.37950.1.1.5.12.5.2.10.3
-- 1.3.6.1.4.1.37950.1.1.5.12.5.2.10.3
-- 1.3.6.1.4.1.37950.1.1.5.12.5.2.10.3
-- 1.3.6.1.4.1.37950.1.1.5.12.5.2.10.3
-- 1.3.6.1.4.1.37950.1.1.5.12.5.2.10.3
-- 1.3.6.1.4.1.37950.1.1.5.12.5.2.10.3
-- 1.3.6.1.4.1.37950.1.1.5.12.5.2.10.3
-- 1.3.6.1.4.1.37950.1.1.5.12.5.2.10.3
-- 1.3.6.1.4.1.37950.1.1.5.12.5.2.10.3
		-- 1.3.6.1.4.1.37950.1.1.5.12.5.2.10.3
		onuPortVlanTranslate OBJECT IDENTIFIER ::= { onuPortVlan 3 }

		
--          1.3.6.1.4.1.37950.1.1.5.12.5.2.10.3.1
-- 1.3.6.1.4.1.37950.1.1.5.12.5.2.10.3.1
-- 1.3.6.1.4.1.37950.1.1.5.12.5.2.10.3.1
-- 1.3.6.1.4.1.37950.1.1.5.12.5.2.10.3.1
-- 1.3.6.1.4.1.37950.1.1.5.12.5.2.10.3.1
-- 1.3.6.1.4.1.37950.1.1.5.12.5.2.10.3.1
-- 1.3.6.1.4.1.37950.1.1.5.12.5.2.10.3.1
-- 1.3.6.1.4.1.37950.1.1.5.12.5.2.10.3.1
-- 1.3.6.1.4.1.37950.1.1.5.12.5.2.10.3.1
		-- 1.3.6.1.4.1.37950.1.1.5.12.5.2.10.3.1
		translatePonNo OBJECT-TYPE
			SYNTAX INTEGER (1..16)
			MAX-ACCESS read-write
			STATUS current
			DESCRIPTION
				"Description."
			::= { onuPortVlanTranslate 1 }

		
--          1.3.6.1.4.1.37950.1.1.5.12.5.2.10.3.2
-- 1.3.6.1.4.1.37950.1.1.5.12.5.2.10.3.2
-- 1.3.6.1.4.1.37950.1.1.5.12.5.2.10.3.2
-- 1.3.6.1.4.1.37950.1.1.5.12.5.2.10.3.2
-- 1.3.6.1.4.1.37950.1.1.5.12.5.2.10.3.2
-- 1.3.6.1.4.1.37950.1.1.5.12.5.2.10.3.2
-- 1.3.6.1.4.1.37950.1.1.5.12.5.2.10.3.2
-- 1.3.6.1.4.1.37950.1.1.5.12.5.2.10.3.2
-- 1.3.6.1.4.1.37950.1.1.5.12.5.2.10.3.2
		-- 1.3.6.1.4.1.37950.1.1.5.12.5.2.10.3.2
		translateOnuNo OBJECT-TYPE
			SYNTAX INTEGER (1..65535)
			MAX-ACCESS read-write
			STATUS current
			DESCRIPTION
				"Description."
			::= { onuPortVlanTranslate 2 }

		
--          1.3.6.1.4.1.37950.1.1.5.12.5.2.10.3.3
-- 1.3.6.1.4.1.37950.1.1.5.12.5.2.10.3.3
-- 1.3.6.1.4.1.37950.1.1.5.12.5.2.10.3.3
-- 1.3.6.1.4.1.37950.1.1.5.12.5.2.10.3.3
-- 1.3.6.1.4.1.37950.1.1.5.12.5.2.10.3.3
-- 1.3.6.1.4.1.37950.1.1.5.12.5.2.10.3.3
-- 1.3.6.1.4.1.37950.1.1.5.12.5.2.10.3.3
-- 1.3.6.1.4.1.37950.1.1.5.12.5.2.10.3.3
-- 1.3.6.1.4.1.37950.1.1.5.12.5.2.10.3.3
		-- 1.3.6.1.4.1.37950.1.1.5.12.5.2.10.3.3
		translatePortNo OBJECT-TYPE
			SYNTAX INTEGER (1..255)
			MAX-ACCESS read-write
			STATUS current
			DESCRIPTION
				"Description."
			::= { onuPortVlanTranslate 3 }

		
--          1.3.6.1.4.1.37950.1.1.5.12.5.2.10.3.4
-- 1.3.6.1.4.1.37950.1.1.5.12.5.2.10.3.4
-- 1.3.6.1.4.1.37950.1.1.5.12.5.2.10.3.4
-- 1.3.6.1.4.1.37950.1.1.5.12.5.2.10.3.4
-- 1.3.6.1.4.1.37950.1.1.5.12.5.2.10.3.4
-- 1.3.6.1.4.1.37950.1.1.5.12.5.2.10.3.4
-- 1.3.6.1.4.1.37950.1.1.5.12.5.2.10.3.4
-- 1.3.6.1.4.1.37950.1.1.5.12.5.2.10.3.4
-- 1.3.6.1.4.1.37950.1.1.5.12.5.2.10.3.4
		-- 1.3.6.1.4.1.37950.1.1.5.12.5.2.10.3.4
		translateOldVlan OBJECT-TYPE
			SYNTAX INTEGER (1..4095)
			MAX-ACCESS read-write
			STATUS current
			DESCRIPTION
				"Description."
			::= { onuPortVlanTranslate 4 }

		
--          1.3.6.1.4.1.37950.1.1.5.12.5.2.10.3.5
-- 1.3.6.1.4.1.37950.1.1.5.12.5.2.10.3.5
-- 1.3.6.1.4.1.37950.1.1.5.12.5.2.10.3.5
-- 1.3.6.1.4.1.37950.1.1.5.12.5.2.10.3.5
-- 1.3.6.1.4.1.37950.1.1.5.12.5.2.10.3.5
-- 1.3.6.1.4.1.37950.1.1.5.12.5.2.10.3.5
-- 1.3.6.1.4.1.37950.1.1.5.12.5.2.10.3.5
-- 1.3.6.1.4.1.37950.1.1.5.12.5.2.10.3.5
-- 1.3.6.1.4.1.37950.1.1.5.12.5.2.10.3.5
		-- 1.3.6.1.4.1.37950.1.1.5.12.5.2.10.3.5
		translateNewVlan OBJECT-TYPE
			SYNTAX INTEGER (1..4095)
			MAX-ACCESS read-write
			STATUS current
			DESCRIPTION
				"Description."
			::= { onuPortVlanTranslate 5 }

		
--          1.3.6.1.4.1.37950.1.1.5.12.5.2.10.3.6
-- 1.3.6.1.4.1.37950.1.1.5.12.5.2.10.3.6
-- 1.3.6.1.4.1.37950.1.1.5.12.5.2.10.3.6
-- 1.3.6.1.4.1.37950.1.1.5.12.5.2.10.3.6
-- 1.3.6.1.4.1.37950.1.1.5.12.5.2.10.3.6
-- 1.3.6.1.4.1.37950.1.1.5.12.5.2.10.3.6
-- 1.3.6.1.4.1.37950.1.1.5.12.5.2.10.3.6
-- 1.3.6.1.4.1.37950.1.1.5.12.5.2.10.3.6
-- 1.3.6.1.4.1.37950.1.1.5.12.5.2.10.3.6
		-- 1.3.6.1.4.1.37950.1.1.5.12.5.2.10.3.6
		translateAction OBJECT-TYPE
			SYNTAX INTEGER
				{
				set(1),
				add(2),
				delete(3)
				}
			MAX-ACCESS read-write
			STATUS current
			DESCRIPTION
				"Description."
			::= { onuPortVlanTranslate 6 }

		
--          1.3.6.1.4.1.37950.1.1.5.12.5.2.10.4
-- 1.3.6.1.4.1.37950.1.1.5.12.5.2.10.4
-- 1.3.6.1.4.1.37950.1.1.5.12.5.2.10.4
-- 1.3.6.1.4.1.37950.1.1.5.12.5.2.10.4
-- 1.3.6.1.4.1.37950.1.1.5.12.5.2.10.4
-- 1.3.6.1.4.1.37950.1.1.5.12.5.2.10.4
-- 1.3.6.1.4.1.37950.1.1.5.12.5.2.10.4
-- 1.3.6.1.4.1.37950.1.1.5.12.5.2.10.4
-- 1.3.6.1.4.1.37950.1.1.5.12.5.2.10.4
		-- 1.3.6.1.4.1.37950.1.1.5.12.5.2.10.4
		onuPortVlanTransTable OBJECT-TYPE
			SYNTAX SEQUENCE OF OnuPortVlanTransEntry
			MAX-ACCESS not-accessible
			STATUS current
			DESCRIPTION
				"Description."
			::= { onuPortVlan 4 }

		
--          1.3.6.1.4.1.37950.1.1.5.12.5.2.10.4.1
-- 1.3.6.1.4.1.37950.1.1.5.12.5.2.10.4.1
-- 1.3.6.1.4.1.37950.1.1.5.12.5.2.10.4.1
-- 1.3.6.1.4.1.37950.1.1.5.12.5.2.10.4.1
-- 1.3.6.1.4.1.37950.1.1.5.12.5.2.10.4.1
-- 1.3.6.1.4.1.37950.1.1.5.12.5.2.10.4.1
-- 1.3.6.1.4.1.37950.1.1.5.12.5.2.10.4.1
-- 1.3.6.1.4.1.37950.1.1.5.12.5.2.10.4.1
-- 1.3.6.1.4.1.37950.1.1.5.12.5.2.10.4.1
		-- 1.3.6.1.4.1.37950.1.1.5.12.5.2.10.4.1
		onuPortVlanTransEntry OBJECT-TYPE
			SYNTAX OnuPortVlanTransEntry
			MAX-ACCESS not-accessible
			STATUS current
			DESCRIPTION
				"Description."
			INDEX { vlanTransItem }
			::= { onuPortVlanTransTable 1 }

		
		OnuPortVlanTransEntry ::=
			SEQUENCE { 
				vlanTransItem
					Integer32,
				vlanTransPonNo
					INTEGER,
				vlanTransOnuNo
					INTEGER,
				vlanTransPortNo
					INTEGER,
				vlanTransOldVlan
					INTEGER,
				vlanTransNewVlan
					INTEGER
			 }

--          1.3.6.1.4.1.37950.1.1.5.12.5.2.10.4.1.1
-- 1.3.6.1.4.1.37950.1.1.5.12.5.2.10.4.1.1
-- 1.3.6.1.4.1.37950.1.1.5.12.5.2.10.4.1.1
-- 1.3.6.1.4.1.37950.1.1.5.12.5.2.10.4.1.1
-- 1.3.6.1.4.1.37950.1.1.5.12.5.2.10.4.1.1
-- 1.3.6.1.4.1.37950.1.1.5.12.5.2.10.4.1.1
-- 1.3.6.1.4.1.37950.1.1.5.12.5.2.10.4.1.1
-- 1.3.6.1.4.1.37950.1.1.5.12.5.2.10.4.1.1
-- 1.3.6.1.4.1.37950.1.1.5.12.5.2.10.4.1.1
		-- 1.3.6.1.4.1.37950.1.1.5.12.5.2.10.4.1.1
		vlanTransItem OBJECT-TYPE
			SYNTAX Integer32
			MAX-ACCESS read-write
			STATUS current
			DESCRIPTION
				"Description."
			::= { onuPortVlanTransEntry 1 }

		
--          1.3.6.1.4.1.37950.1.1.5.12.5.2.10.4.1.2
-- 1.3.6.1.4.1.37950.1.1.5.12.5.2.10.4.1.2
-- 1.3.6.1.4.1.37950.1.1.5.12.5.2.10.4.1.2
-- 1.3.6.1.4.1.37950.1.1.5.12.5.2.10.4.1.2
-- 1.3.6.1.4.1.37950.1.1.5.12.5.2.10.4.1.2
-- 1.3.6.1.4.1.37950.1.1.5.12.5.2.10.4.1.2
-- 1.3.6.1.4.1.37950.1.1.5.12.5.2.10.4.1.2
-- 1.3.6.1.4.1.37950.1.1.5.12.5.2.10.4.1.2
-- 1.3.6.1.4.1.37950.1.1.5.12.5.2.10.4.1.2
		-- 1.3.6.1.4.1.37950.1.1.5.12.5.2.10.4.1.2
		vlanTransPonNo OBJECT-TYPE
			SYNTAX INTEGER (1..16)
			MAX-ACCESS read-write
			STATUS current
			DESCRIPTION
				"Description."
			::= { onuPortVlanTransEntry 2 }

		
--          1.3.6.1.4.1.37950.1.1.5.12.5.2.10.4.1.3
-- 1.3.6.1.4.1.37950.1.1.5.12.5.2.10.4.1.3
-- 1.3.6.1.4.1.37950.1.1.5.12.5.2.10.4.1.3
-- 1.3.6.1.4.1.37950.1.1.5.12.5.2.10.4.1.3
-- 1.3.6.1.4.1.37950.1.1.5.12.5.2.10.4.1.3
-- 1.3.6.1.4.1.37950.1.1.5.12.5.2.10.4.1.3
-- 1.3.6.1.4.1.37950.1.1.5.12.5.2.10.4.1.3
-- 1.3.6.1.4.1.37950.1.1.5.12.5.2.10.4.1.3
-- 1.3.6.1.4.1.37950.1.1.5.12.5.2.10.4.1.3
		-- 1.3.6.1.4.1.37950.1.1.5.12.5.2.10.4.1.3
		vlanTransOnuNo OBJECT-TYPE
			SYNTAX INTEGER (1..65535)
			MAX-ACCESS read-write
			STATUS current
			DESCRIPTION
				"Description."
			::= { onuPortVlanTransEntry 3 }

		
--          1.3.6.1.4.1.37950.1.1.5.12.5.2.10.4.1.4
-- 1.3.6.1.4.1.37950.1.1.5.12.5.2.10.4.1.4
-- 1.3.6.1.4.1.37950.1.1.5.12.5.2.10.4.1.4
-- 1.3.6.1.4.1.37950.1.1.5.12.5.2.10.4.1.4
-- 1.3.6.1.4.1.37950.1.1.5.12.5.2.10.4.1.4
-- 1.3.6.1.4.1.37950.1.1.5.12.5.2.10.4.1.4
-- 1.3.6.1.4.1.37950.1.1.5.12.5.2.10.4.1.4
-- 1.3.6.1.4.1.37950.1.1.5.12.5.2.10.4.1.4
-- 1.3.6.1.4.1.37950.1.1.5.12.5.2.10.4.1.4
		-- 1.3.6.1.4.1.37950.1.1.5.12.5.2.10.4.1.4
		vlanTransPortNo OBJECT-TYPE
			SYNTAX INTEGER (1..65535)
			MAX-ACCESS read-write
			STATUS current
			DESCRIPTION
				"Description."
			::= { onuPortVlanTransEntry 4 }

		
--          1.3.6.1.4.1.37950.1.1.5.12.5.2.10.4.1.5
-- 1.3.6.1.4.1.37950.1.1.5.12.5.2.10.4.1.5
-- 1.3.6.1.4.1.37950.1.1.5.12.5.2.10.4.1.5
-- 1.3.6.1.4.1.37950.1.1.5.12.5.2.10.4.1.5
-- 1.3.6.1.4.1.37950.1.1.5.12.5.2.10.4.1.5
-- 1.3.6.1.4.1.37950.1.1.5.12.5.2.10.4.1.5
-- 1.3.6.1.4.1.37950.1.1.5.12.5.2.10.4.1.5
-- 1.3.6.1.4.1.37950.1.1.5.12.5.2.10.4.1.5
-- 1.3.6.1.4.1.37950.1.1.5.12.5.2.10.4.1.5
		-- 1.3.6.1.4.1.37950.1.1.5.12.5.2.10.4.1.5
		vlanTransOldVlan OBJECT-TYPE
			SYNTAX INTEGER (1..4095)
			MAX-ACCESS read-write
			STATUS current
			DESCRIPTION
				"Description."
			::= { onuPortVlanTransEntry 5 }

		
--          1.3.6.1.4.1.37950.1.1.5.12.5.2.10.4.1.6
-- 1.3.6.1.4.1.37950.1.1.5.12.5.2.10.4.1.6
-- 1.3.6.1.4.1.37950.1.1.5.12.5.2.10.4.1.6
-- 1.3.6.1.4.1.37950.1.1.5.12.5.2.10.4.1.6
-- 1.3.6.1.4.1.37950.1.1.5.12.5.2.10.4.1.6
-- 1.3.6.1.4.1.37950.1.1.5.12.5.2.10.4.1.6
-- 1.3.6.1.4.1.37950.1.1.5.12.5.2.10.4.1.6
-- 1.3.6.1.4.1.37950.1.1.5.12.5.2.10.4.1.6
-- 1.3.6.1.4.1.37950.1.1.5.12.5.2.10.4.1.6
		-- 1.3.6.1.4.1.37950.1.1.5.12.5.2.10.4.1.6
		vlanTransNewVlan OBJECT-TYPE
			SYNTAX INTEGER (1..4095)
			MAX-ACCESS read-write
			STATUS current
			DESCRIPTION
				"Description."
			::= { onuPortVlanTransEntry 6 }

		
--          1.3.6.1.4.1.37950.1.1.5.12.5.2.10.5
-- 1.3.6.1.4.1.37950.1.1.5.12.5.2.10.5
-- 1.3.6.1.4.1.37950.1.1.5.12.5.2.10.5
-- 1.3.6.1.4.1.37950.1.1.5.12.5.2.10.5
-- 1.3.6.1.4.1.37950.1.1.5.12.5.2.10.5
-- 1.3.6.1.4.1.37950.1.1.5.12.5.2.10.5
-- 1.3.6.1.4.1.37950.1.1.5.12.5.2.10.5
-- 1.3.6.1.4.1.37950.1.1.5.12.5.2.10.5
-- 1.3.6.1.4.1.37950.1.1.5.12.5.2.10.5
		-- 1.3.6.1.4.1.37950.1.1.5.12.5.2.10.5
		onuPortVlanTrunk OBJECT IDENTIFIER ::= { onuPortVlan 5 }

		
--          1.3.6.1.4.1.37950.1.1.5.12.5.2.10.5.1
-- 1.3.6.1.4.1.37950.1.1.5.12.5.2.10.5.1
-- 1.3.6.1.4.1.37950.1.1.5.12.5.2.10.5.1
-- 1.3.6.1.4.1.37950.1.1.5.12.5.2.10.5.1
-- 1.3.6.1.4.1.37950.1.1.5.12.5.2.10.5.1
-- 1.3.6.1.4.1.37950.1.1.5.12.5.2.10.5.1
-- 1.3.6.1.4.1.37950.1.1.5.12.5.2.10.5.1
-- 1.3.6.1.4.1.37950.1.1.5.12.5.2.10.5.1
-- 1.3.6.1.4.1.37950.1.1.5.12.5.2.10.5.1
		-- 1.3.6.1.4.1.37950.1.1.5.12.5.2.10.5.1
		trunkPonNo OBJECT-TYPE
			SYNTAX INTEGER (1..16)
			MAX-ACCESS read-write
			STATUS current
			DESCRIPTION
				"Description."
			::= { onuPortVlanTrunk 1 }

		
--          1.3.6.1.4.1.37950.1.1.5.12.5.2.10.5.2
-- 1.3.6.1.4.1.37950.1.1.5.12.5.2.10.5.2
-- 1.3.6.1.4.1.37950.1.1.5.12.5.2.10.5.2
-- 1.3.6.1.4.1.37950.1.1.5.12.5.2.10.5.2
-- 1.3.6.1.4.1.37950.1.1.5.12.5.2.10.5.2
-- 1.3.6.1.4.1.37950.1.1.5.12.5.2.10.5.2
-- 1.3.6.1.4.1.37950.1.1.5.12.5.2.10.5.2
-- 1.3.6.1.4.1.37950.1.1.5.12.5.2.10.5.2
-- 1.3.6.1.4.1.37950.1.1.5.12.5.2.10.5.2
		-- 1.3.6.1.4.1.37950.1.1.5.12.5.2.10.5.2
		trunkOnuNo OBJECT-TYPE
			SYNTAX INTEGER (1..65535)
			MAX-ACCESS read-write
			STATUS current
			DESCRIPTION
				"Description."
			::= { onuPortVlanTrunk 2 }

		
--          1.3.6.1.4.1.37950.1.1.5.12.5.2.10.5.3
-- 1.3.6.1.4.1.37950.1.1.5.12.5.2.10.5.3
-- 1.3.6.1.4.1.37950.1.1.5.12.5.2.10.5.3
-- 1.3.6.1.4.1.37950.1.1.5.12.5.2.10.5.3
-- 1.3.6.1.4.1.37950.1.1.5.12.5.2.10.5.3
-- 1.3.6.1.4.1.37950.1.1.5.12.5.2.10.5.3
-- 1.3.6.1.4.1.37950.1.1.5.12.5.2.10.5.3
-- 1.3.6.1.4.1.37950.1.1.5.12.5.2.10.5.3
-- 1.3.6.1.4.1.37950.1.1.5.12.5.2.10.5.3
		-- 1.3.6.1.4.1.37950.1.1.5.12.5.2.10.5.3
		trunkPortNo OBJECT-TYPE
			SYNTAX INTEGER (1..255)
			MAX-ACCESS read-write
			STATUS current
			DESCRIPTION
				"Description."
			::= { onuPortVlanTrunk 3 }

		
--          1.3.6.1.4.1.37950.1.1.5.12.5.2.10.5.4
-- 1.3.6.1.4.1.37950.1.1.5.12.5.2.10.5.4
-- 1.3.6.1.4.1.37950.1.1.5.12.5.2.10.5.4
-- 1.3.6.1.4.1.37950.1.1.5.12.5.2.10.5.4
-- 1.3.6.1.4.1.37950.1.1.5.12.5.2.10.5.4
-- 1.3.6.1.4.1.37950.1.1.5.12.5.2.10.5.4
-- 1.3.6.1.4.1.37950.1.1.5.12.5.2.10.5.4
-- 1.3.6.1.4.1.37950.1.1.5.12.5.2.10.5.4
-- 1.3.6.1.4.1.37950.1.1.5.12.5.2.10.5.4
		-- 1.3.6.1.4.1.37950.1.1.5.12.5.2.10.5.4
		trunkPortVid OBJECT-TYPE
			SYNTAX INTEGER (1..4095)
			MAX-ACCESS read-write
			STATUS current
			DESCRIPTION
				"Description."
			::= { onuPortVlanTrunk 4 }

		
--          1.3.6.1.4.1.37950.1.1.5.12.5.2.10.5.5
-- 1.3.6.1.4.1.37950.1.1.5.12.5.2.10.5.5
-- 1.3.6.1.4.1.37950.1.1.5.12.5.2.10.5.5
-- 1.3.6.1.4.1.37950.1.1.5.12.5.2.10.5.5
-- 1.3.6.1.4.1.37950.1.1.5.12.5.2.10.5.5
-- 1.3.6.1.4.1.37950.1.1.5.12.5.2.10.5.5
-- 1.3.6.1.4.1.37950.1.1.5.12.5.2.10.5.5
-- 1.3.6.1.4.1.37950.1.1.5.12.5.2.10.5.5
-- 1.3.6.1.4.1.37950.1.1.5.12.5.2.10.5.5
		-- 1.3.6.1.4.1.37950.1.1.5.12.5.2.10.5.5
		trunkPortVidAction OBJECT-TYPE
			SYNTAX INTEGER
				{
				set(1),
				add(2),
				delete(3)
				}
			MAX-ACCESS read-write
			STATUS current
			DESCRIPTION
				"Description."
			::= { onuPortVlanTrunk 5 }

		
--          1.3.6.1.4.1.37950.1.1.5.12.5.2.10.6
-- 1.3.6.1.4.1.37950.1.1.5.12.5.2.10.6
-- 1.3.6.1.4.1.37950.1.1.5.12.5.2.10.6
-- 1.3.6.1.4.1.37950.1.1.5.12.5.2.10.6
-- 1.3.6.1.4.1.37950.1.1.5.12.5.2.10.6
-- 1.3.6.1.4.1.37950.1.1.5.12.5.2.10.6
-- 1.3.6.1.4.1.37950.1.1.5.12.5.2.10.6
-- 1.3.6.1.4.1.37950.1.1.5.12.5.2.10.6
-- 1.3.6.1.4.1.37950.1.1.5.12.5.2.10.6
		-- 1.3.6.1.4.1.37950.1.1.5.12.5.2.10.6
		onuPortVlanTrunkTable OBJECT-TYPE
			SYNTAX SEQUENCE OF OnuPortVlanTrunkEntry
			MAX-ACCESS not-accessible
			STATUS current
			DESCRIPTION
				"Description."
			::= { onuPortVlan 6 }

		
--          1.3.6.1.4.1.37950.1.1.5.12.5.2.10.6.1
-- 1.3.6.1.4.1.37950.1.1.5.12.5.2.10.6.1
-- 1.3.6.1.4.1.37950.1.1.5.12.5.2.10.6.1
-- 1.3.6.1.4.1.37950.1.1.5.12.5.2.10.6.1
-- 1.3.6.1.4.1.37950.1.1.5.12.5.2.10.6.1
-- 1.3.6.1.4.1.37950.1.1.5.12.5.2.10.6.1
-- 1.3.6.1.4.1.37950.1.1.5.12.5.2.10.6.1
-- 1.3.6.1.4.1.37950.1.1.5.12.5.2.10.6.1
-- 1.3.6.1.4.1.37950.1.1.5.12.5.2.10.6.1
		-- 1.3.6.1.4.1.37950.1.1.5.12.5.2.10.6.1
		onuPortVlanTrunkEntry OBJECT-TYPE
			SYNTAX OnuPortVlanTrunkEntry
			MAX-ACCESS not-accessible
			STATUS current
			DESCRIPTION
				"Description."
			INDEX { vlanTrunkItem }
			::= { onuPortVlanTrunkTable 1 }

		
		OnuPortVlanTrunkEntry ::=
			SEQUENCE { 
				vlanTrunkItem
					Integer32,
				vlanTrunkPonNo
					INTEGER,
				vlanTrunkOnuNo
					INTEGER,
				vlanTrunkPortNo
					INTEGER,
				vlanTrunkVid
					INTEGER
			 }

--          1.3.6.1.4.1.37950.1.1.5.12.5.2.10.6.1.1
-- 1.3.6.1.4.1.37950.1.1.5.12.5.2.10.6.1.1
-- 1.3.6.1.4.1.37950.1.1.5.12.5.2.10.6.1.1
-- 1.3.6.1.4.1.37950.1.1.5.12.5.2.10.6.1.1
-- 1.3.6.1.4.1.37950.1.1.5.12.5.2.10.6.1.1
-- 1.3.6.1.4.1.37950.1.1.5.12.5.2.10.6.1.1
-- 1.3.6.1.4.1.37950.1.1.5.12.5.2.10.6.1.1
-- 1.3.6.1.4.1.37950.1.1.5.12.5.2.10.6.1.1
-- 1.3.6.1.4.1.37950.1.1.5.12.5.2.10.6.1.1
		-- 1.3.6.1.4.1.37950.1.1.5.12.5.2.10.6.1.1
		vlanTrunkItem OBJECT-TYPE
			SYNTAX Integer32
			MAX-ACCESS read-write
			STATUS current
			DESCRIPTION
				"Description."
			::= { onuPortVlanTrunkEntry 1 }

		
--          1.3.6.1.4.1.37950.1.1.5.12.5.2.10.6.1.2
-- 1.3.6.1.4.1.37950.1.1.5.12.5.2.10.6.1.2
-- 1.3.6.1.4.1.37950.1.1.5.12.5.2.10.6.1.2
-- 1.3.6.1.4.1.37950.1.1.5.12.5.2.10.6.1.2
-- 1.3.6.1.4.1.37950.1.1.5.12.5.2.10.6.1.2
-- 1.3.6.1.4.1.37950.1.1.5.12.5.2.10.6.1.2
-- 1.3.6.1.4.1.37950.1.1.5.12.5.2.10.6.1.2
-- 1.3.6.1.4.1.37950.1.1.5.12.5.2.10.6.1.2
-- 1.3.6.1.4.1.37950.1.1.5.12.5.2.10.6.1.2
		-- 1.3.6.1.4.1.37950.1.1.5.12.5.2.10.6.1.2
		vlanTrunkPonNo OBJECT-TYPE
			SYNTAX INTEGER (1..16)
			MAX-ACCESS read-write
			STATUS current
			DESCRIPTION
				"Description."
			::= { onuPortVlanTrunkEntry 2 }

		
--          1.3.6.1.4.1.37950.1.1.5.12.5.2.10.6.1.3
-- 1.3.6.1.4.1.37950.1.1.5.12.5.2.10.6.1.3
-- 1.3.6.1.4.1.37950.1.1.5.12.5.2.10.6.1.3
-- 1.3.6.1.4.1.37950.1.1.5.12.5.2.10.6.1.3
-- 1.3.6.1.4.1.37950.1.1.5.12.5.2.10.6.1.3
-- 1.3.6.1.4.1.37950.1.1.5.12.5.2.10.6.1.3
-- 1.3.6.1.4.1.37950.1.1.5.12.5.2.10.6.1.3
-- 1.3.6.1.4.1.37950.1.1.5.12.5.2.10.6.1.3
-- 1.3.6.1.4.1.37950.1.1.5.12.5.2.10.6.1.3
		-- 1.3.6.1.4.1.37950.1.1.5.12.5.2.10.6.1.3
		vlanTrunkOnuNo OBJECT-TYPE
			SYNTAX INTEGER (1..65535)
			MAX-ACCESS read-write
			STATUS current
			DESCRIPTION
				"Description."
			::= { onuPortVlanTrunkEntry 3 }

		
--          1.3.6.1.4.1.37950.1.1.5.12.5.2.10.6.1.4
-- 1.3.6.1.4.1.37950.1.1.5.12.5.2.10.6.1.4
-- 1.3.6.1.4.1.37950.1.1.5.12.5.2.10.6.1.4
-- 1.3.6.1.4.1.37950.1.1.5.12.5.2.10.6.1.4
-- 1.3.6.1.4.1.37950.1.1.5.12.5.2.10.6.1.4
-- 1.3.6.1.4.1.37950.1.1.5.12.5.2.10.6.1.4
-- 1.3.6.1.4.1.37950.1.1.5.12.5.2.10.6.1.4
-- 1.3.6.1.4.1.37950.1.1.5.12.5.2.10.6.1.4
-- 1.3.6.1.4.1.37950.1.1.5.12.5.2.10.6.1.4
		-- 1.3.6.1.4.1.37950.1.1.5.12.5.2.10.6.1.4
		vlanTrunkPortNo OBJECT-TYPE
			SYNTAX INTEGER (1..255)
			MAX-ACCESS read-write
			STATUS current
			DESCRIPTION
				"Description."
			::= { onuPortVlanTrunkEntry 4 }

		
--          1.3.6.1.4.1.37950.1.1.5.12.5.2.10.6.1.5
-- 1.3.6.1.4.1.37950.1.1.5.12.5.2.10.6.1.5
-- 1.3.6.1.4.1.37950.1.1.5.12.5.2.10.6.1.5
-- 1.3.6.1.4.1.37950.1.1.5.12.5.2.10.6.1.5
-- 1.3.6.1.4.1.37950.1.1.5.12.5.2.10.6.1.5
-- 1.3.6.1.4.1.37950.1.1.5.12.5.2.10.6.1.5
-- 1.3.6.1.4.1.37950.1.1.5.12.5.2.10.6.1.5
-- 1.3.6.1.4.1.37950.1.1.5.12.5.2.10.6.1.5
-- 1.3.6.1.4.1.37950.1.1.5.12.5.2.10.6.1.5
		-- 1.3.6.1.4.1.37950.1.1.5.12.5.2.10.6.1.5
		vlanTrunkVid OBJECT-TYPE
			SYNTAX INTEGER (1..4095)
			MAX-ACCESS read-write
			STATUS current
			DESCRIPTION
				"Description."
			::= { onuPortVlanTrunkEntry 5 }

		
--          1.3.6.1.4.1.37950.1.1.5.12.5.2.10.7
-- 1.3.6.1.4.1.37950.1.1.5.12.5.2.10.7
-- 1.3.6.1.4.1.37950.1.1.5.12.5.2.10.7
-- 1.3.6.1.4.1.37950.1.1.5.12.5.2.10.7
-- 1.3.6.1.4.1.37950.1.1.5.12.5.2.10.7
-- 1.3.6.1.4.1.37950.1.1.5.12.5.2.10.7
-- 1.3.6.1.4.1.37950.1.1.5.12.5.2.10.7
-- 1.3.6.1.4.1.37950.1.1.5.12.5.2.10.7
-- 1.3.6.1.4.1.37950.1.1.5.12.5.2.10.7
		-- 1.3.6.1.4.1.37950.1.1.5.12.5.2.10.7
		onuPortVlanAgg OBJECT IDENTIFIER ::= { onuPortVlan 7 }

		
--          1.3.6.1.4.1.37950.1.1.5.12.5.2.10.7.1
-- 1.3.6.1.4.1.37950.1.1.5.12.5.2.10.7.1
-- 1.3.6.1.4.1.37950.1.1.5.12.5.2.10.7.1
-- 1.3.6.1.4.1.37950.1.1.5.12.5.2.10.7.1
-- 1.3.6.1.4.1.37950.1.1.5.12.5.2.10.7.1
-- 1.3.6.1.4.1.37950.1.1.5.12.5.2.10.7.1
-- 1.3.6.1.4.1.37950.1.1.5.12.5.2.10.7.1
-- 1.3.6.1.4.1.37950.1.1.5.12.5.2.10.7.1
-- 1.3.6.1.4.1.37950.1.1.5.12.5.2.10.7.1
		-- 1.3.6.1.4.1.37950.1.1.5.12.5.2.10.7.1
		onuVlanAggPonNo OBJECT-TYPE
			SYNTAX INTEGER (1..16)
			MAX-ACCESS read-write
			STATUS current
			DESCRIPTION
				"Description."
			::= { onuPortVlanAgg 1 }

		
--          1.3.6.1.4.1.37950.1.1.5.12.5.2.10.7.2
-- 1.3.6.1.4.1.37950.1.1.5.12.5.2.10.7.2
-- 1.3.6.1.4.1.37950.1.1.5.12.5.2.10.7.2
-- 1.3.6.1.4.1.37950.1.1.5.12.5.2.10.7.2
-- 1.3.6.1.4.1.37950.1.1.5.12.5.2.10.7.2
-- 1.3.6.1.4.1.37950.1.1.5.12.5.2.10.7.2
-- 1.3.6.1.4.1.37950.1.1.5.12.5.2.10.7.2
-- 1.3.6.1.4.1.37950.1.1.5.12.5.2.10.7.2
-- 1.3.6.1.4.1.37950.1.1.5.12.5.2.10.7.2
		-- 1.3.6.1.4.1.37950.1.1.5.12.5.2.10.7.2
		onuVlanAggOnuNo OBJECT-TYPE
			SYNTAX INTEGER (1..65535)
			MAX-ACCESS read-write
			STATUS current
			DESCRIPTION
				"Description."
			::= { onuPortVlanAgg 2 }

		
--          1.3.6.1.4.1.37950.1.1.5.12.5.2.10.7.3
-- 1.3.6.1.4.1.37950.1.1.5.12.5.2.10.7.3
-- 1.3.6.1.4.1.37950.1.1.5.12.5.2.10.7.3
-- 1.3.6.1.4.1.37950.1.1.5.12.5.2.10.7.3
-- 1.3.6.1.4.1.37950.1.1.5.12.5.2.10.7.3
-- 1.3.6.1.4.1.37950.1.1.5.12.5.2.10.7.3
-- 1.3.6.1.4.1.37950.1.1.5.12.5.2.10.7.3
-- 1.3.6.1.4.1.37950.1.1.5.12.5.2.10.7.3
-- 1.3.6.1.4.1.37950.1.1.5.12.5.2.10.7.3
		-- 1.3.6.1.4.1.37950.1.1.5.12.5.2.10.7.3
		onuVlanAggPortNo OBJECT-TYPE
			SYNTAX INTEGER (1..255)
			MAX-ACCESS read-write
			STATUS current
			DESCRIPTION
				"Description."
			::= { onuPortVlanAgg 3 }

		
--          1.3.6.1.4.1.37950.1.1.5.12.5.2.10.7.4
-- 1.3.6.1.4.1.37950.1.1.5.12.5.2.10.7.4
-- 1.3.6.1.4.1.37950.1.1.5.12.5.2.10.7.4
-- 1.3.6.1.4.1.37950.1.1.5.12.5.2.10.7.4
-- 1.3.6.1.4.1.37950.1.1.5.12.5.2.10.7.4
-- 1.3.6.1.4.1.37950.1.1.5.12.5.2.10.7.4
-- 1.3.6.1.4.1.37950.1.1.5.12.5.2.10.7.4
-- 1.3.6.1.4.1.37950.1.1.5.12.5.2.10.7.4
-- 1.3.6.1.4.1.37950.1.1.5.12.5.2.10.7.4
		-- 1.3.6.1.4.1.37950.1.1.5.12.5.2.10.7.4
		onuAggNewVlan OBJECT-TYPE
			SYNTAX INTEGER (1..4095)
			MAX-ACCESS read-write
			STATUS current
			DESCRIPTION
				"Description."
			::= { onuPortVlanAgg 4 }

		
--          1.3.6.1.4.1.37950.1.1.5.12.5.2.10.7.5
-- 1.3.6.1.4.1.37950.1.1.5.12.5.2.10.7.5
-- 1.3.6.1.4.1.37950.1.1.5.12.5.2.10.7.5
-- 1.3.6.1.4.1.37950.1.1.5.12.5.2.10.7.5
-- 1.3.6.1.4.1.37950.1.1.5.12.5.2.10.7.5
-- 1.3.6.1.4.1.37950.1.1.5.12.5.2.10.7.5
-- 1.3.6.1.4.1.37950.1.1.5.12.5.2.10.7.5
-- 1.3.6.1.4.1.37950.1.1.5.12.5.2.10.7.5
-- 1.3.6.1.4.1.37950.1.1.5.12.5.2.10.7.5
		-- 1.3.6.1.4.1.37950.1.1.5.12.5.2.10.7.5
		onuAggOldVlan1 OBJECT-TYPE
			SYNTAX INTEGER (0..4095)
			MAX-ACCESS read-write
			STATUS current
			DESCRIPTION
				"Description."
			::= { onuPortVlanAgg 5 }

		
--          1.3.6.1.4.1.37950.1.1.5.12.5.2.10.7.6
-- 1.3.6.1.4.1.37950.1.1.5.12.5.2.10.7.6
-- 1.3.6.1.4.1.37950.1.1.5.12.5.2.10.7.6
-- 1.3.6.1.4.1.37950.1.1.5.12.5.2.10.7.6
-- 1.3.6.1.4.1.37950.1.1.5.12.5.2.10.7.6
-- 1.3.6.1.4.1.37950.1.1.5.12.5.2.10.7.6
-- 1.3.6.1.4.1.37950.1.1.5.12.5.2.10.7.6
-- 1.3.6.1.4.1.37950.1.1.5.12.5.2.10.7.6
-- 1.3.6.1.4.1.37950.1.1.5.12.5.2.10.7.6
		-- 1.3.6.1.4.1.37950.1.1.5.12.5.2.10.7.6
		onuAggOldVlan2 OBJECT-TYPE
			SYNTAX INTEGER (0..4095)
			MAX-ACCESS read-write
			STATUS current
			DESCRIPTION
				"Description."
			::= { onuPortVlanAgg 6 }

		
--          1.3.6.1.4.1.37950.1.1.5.12.5.2.10.7.7
-- 1.3.6.1.4.1.37950.1.1.5.12.5.2.10.7.7
-- 1.3.6.1.4.1.37950.1.1.5.12.5.2.10.7.7
-- 1.3.6.1.4.1.37950.1.1.5.12.5.2.10.7.7
-- 1.3.6.1.4.1.37950.1.1.5.12.5.2.10.7.7
-- 1.3.6.1.4.1.37950.1.1.5.12.5.2.10.7.7
-- 1.3.6.1.4.1.37950.1.1.5.12.5.2.10.7.7
-- 1.3.6.1.4.1.37950.1.1.5.12.5.2.10.7.7
-- 1.3.6.1.4.1.37950.1.1.5.12.5.2.10.7.7
		-- 1.3.6.1.4.1.37950.1.1.5.12.5.2.10.7.7
		onuAggOldVlan3 OBJECT-TYPE
			SYNTAX INTEGER (0..4095)
			MAX-ACCESS read-write
			STATUS current
			DESCRIPTION
				"Description."
			::= { onuPortVlanAgg 7 }

		
--          1.3.6.1.4.1.37950.1.1.5.12.5.2.10.7.8
-- 1.3.6.1.4.1.37950.1.1.5.12.5.2.10.7.8
-- 1.3.6.1.4.1.37950.1.1.5.12.5.2.10.7.8
-- 1.3.6.1.4.1.37950.1.1.5.12.5.2.10.7.8
-- 1.3.6.1.4.1.37950.1.1.5.12.5.2.10.7.8
-- 1.3.6.1.4.1.37950.1.1.5.12.5.2.10.7.8
-- 1.3.6.1.4.1.37950.1.1.5.12.5.2.10.7.8
-- 1.3.6.1.4.1.37950.1.1.5.12.5.2.10.7.8
-- 1.3.6.1.4.1.37950.1.1.5.12.5.2.10.7.8
		-- 1.3.6.1.4.1.37950.1.1.5.12.5.2.10.7.8
		onuAggOldVlan4 OBJECT-TYPE
			SYNTAX INTEGER (0..4095)
			MAX-ACCESS read-write
			STATUS current
			DESCRIPTION
				"Description."
			::= { onuPortVlanAgg 8 }

		
--          1.3.6.1.4.1.37950.1.1.5.12.5.2.10.7.9
-- 1.3.6.1.4.1.37950.1.1.5.12.5.2.10.7.9
-- 1.3.6.1.4.1.37950.1.1.5.12.5.2.10.7.9
-- 1.3.6.1.4.1.37950.1.1.5.12.5.2.10.7.9
-- 1.3.6.1.4.1.37950.1.1.5.12.5.2.10.7.9
-- 1.3.6.1.4.1.37950.1.1.5.12.5.2.10.7.9
-- 1.3.6.1.4.1.37950.1.1.5.12.5.2.10.7.9
-- 1.3.6.1.4.1.37950.1.1.5.12.5.2.10.7.9
-- 1.3.6.1.4.1.37950.1.1.5.12.5.2.10.7.9
		-- 1.3.6.1.4.1.37950.1.1.5.12.5.2.10.7.9
		onuAggOldVlan5 OBJECT-TYPE
			SYNTAX INTEGER (0..4095)
			MAX-ACCESS read-write
			STATUS current
			DESCRIPTION
				"Description."
			::= { onuPortVlanAgg 9 }

		
--          1.3.6.1.4.1.37950.1.1.5.12.5.2.10.7.10
-- 1.3.6.1.4.1.37950.1.1.5.12.5.2.10.7.10
-- 1.3.6.1.4.1.37950.1.1.5.12.5.2.10.7.10
-- 1.3.6.1.4.1.37950.1.1.5.12.5.2.10.7.10
-- 1.3.6.1.4.1.37950.1.1.5.12.5.2.10.7.10
-- 1.3.6.1.4.1.37950.1.1.5.12.5.2.10.7.10
-- 1.3.6.1.4.1.37950.1.1.5.12.5.2.10.7.10
-- 1.3.6.1.4.1.37950.1.1.5.12.5.2.10.7.10
-- 1.3.6.1.4.1.37950.1.1.5.12.5.2.10.7.10
		-- 1.3.6.1.4.1.37950.1.1.5.12.5.2.10.7.10
		onuAggOldVlan6 OBJECT-TYPE
			SYNTAX INTEGER (0..4095)
			MAX-ACCESS read-write
			STATUS current
			DESCRIPTION
				"Description."
			::= { onuPortVlanAgg 10 }

		
--          1.3.6.1.4.1.37950.1.1.5.12.5.2.10.7.11
-- 1.3.6.1.4.1.37950.1.1.5.12.5.2.10.7.11
-- 1.3.6.1.4.1.37950.1.1.5.12.5.2.10.7.11
-- 1.3.6.1.4.1.37950.1.1.5.12.5.2.10.7.11
-- 1.3.6.1.4.1.37950.1.1.5.12.5.2.10.7.11
-- 1.3.6.1.4.1.37950.1.1.5.12.5.2.10.7.11
-- 1.3.6.1.4.1.37950.1.1.5.12.5.2.10.7.11
-- 1.3.6.1.4.1.37950.1.1.5.12.5.2.10.7.11
-- 1.3.6.1.4.1.37950.1.1.5.12.5.2.10.7.11
		-- 1.3.6.1.4.1.37950.1.1.5.12.5.2.10.7.11
		onuAggOldVlan7 OBJECT-TYPE
			SYNTAX INTEGER (0..4095)
			MAX-ACCESS read-write
			STATUS current
			DESCRIPTION
				"Description."
			::= { onuPortVlanAgg 11 }

		
--          1.3.6.1.4.1.37950.1.1.5.12.5.2.10.7.12
-- 1.3.6.1.4.1.37950.1.1.5.12.5.2.10.7.12
-- 1.3.6.1.4.1.37950.1.1.5.12.5.2.10.7.12
-- 1.3.6.1.4.1.37950.1.1.5.12.5.2.10.7.12
-- 1.3.6.1.4.1.37950.1.1.5.12.5.2.10.7.12
-- 1.3.6.1.4.1.37950.1.1.5.12.5.2.10.7.12
-- 1.3.6.1.4.1.37950.1.1.5.12.5.2.10.7.12
-- 1.3.6.1.4.1.37950.1.1.5.12.5.2.10.7.12
-- 1.3.6.1.4.1.37950.1.1.5.12.5.2.10.7.12
		-- 1.3.6.1.4.1.37950.1.1.5.12.5.2.10.7.12
		onuAggOldVlan8 OBJECT-TYPE
			SYNTAX INTEGER (0..4095)
			MAX-ACCESS read-write
			STATUS current
			DESCRIPTION
				"Description."
			::= { onuPortVlanAgg 12 }

		
--          1.3.6.1.4.1.37950.1.1.5.12.5.2.10.7.13
-- 1.3.6.1.4.1.37950.1.1.5.12.5.2.10.7.13
-- 1.3.6.1.4.1.37950.1.1.5.12.5.2.10.7.13
-- 1.3.6.1.4.1.37950.1.1.5.12.5.2.10.7.13
-- 1.3.6.1.4.1.37950.1.1.5.12.5.2.10.7.13
-- 1.3.6.1.4.1.37950.1.1.5.12.5.2.10.7.13
-- 1.3.6.1.4.1.37950.1.1.5.12.5.2.10.7.13
-- 1.3.6.1.4.1.37950.1.1.5.12.5.2.10.7.13
-- 1.3.6.1.4.1.37950.1.1.5.12.5.2.10.7.13
		-- 1.3.6.1.4.1.37950.1.1.5.12.5.2.10.7.13
		onuAggAction OBJECT-TYPE
			SYNTAX INTEGER
				{
				set(1),
				add(2),
				del(3)
				}
			MAX-ACCESS read-write
			STATUS current
			DESCRIPTION
				"Description."
			::= { onuPortVlanAgg 13 }

		
--          1.3.6.1.4.1.37950.1.1.5.12.5.2.11
-- 1.3.6.1.4.1.37950.1.1.5.12.5.2.11
-- 1.3.6.1.4.1.37950.1.1.5.12.5.2.11
-- 1.3.6.1.4.1.37950.1.1.5.12.5.2.11
-- 1.3.6.1.4.1.37950.1.1.5.12.5.2.11
-- 1.3.6.1.4.1.37950.1.1.5.12.5.2.11
-- 1.3.6.1.4.1.37950.1.1.5.12.5.2.11
-- 1.3.6.1.4.1.37950.1.1.5.12.5.2.11
-- 1.3.6.1.4.1.37950.1.1.5.12.5.2.11
		-- 1.3.6.1.4.1.37950.1.1.5.12.5.2.11
		onuPortClassifyCfg OBJECT IDENTIFIER ::= { onuPortCfg 11 }

		
--          1.3.6.1.4.1.37950.1.1.5.12.5.2.11.1
-- 1.3.6.1.4.1.37950.1.1.5.12.5.2.11.1
-- 1.3.6.1.4.1.37950.1.1.5.12.5.2.11.1
-- 1.3.6.1.4.1.37950.1.1.5.12.5.2.11.1
-- 1.3.6.1.4.1.37950.1.1.5.12.5.2.11.1
-- 1.3.6.1.4.1.37950.1.1.5.12.5.2.11.1
-- 1.3.6.1.4.1.37950.1.1.5.12.5.2.11.1
-- 1.3.6.1.4.1.37950.1.1.5.12.5.2.11.1
-- 1.3.6.1.4.1.37950.1.1.5.12.5.2.11.1
		-- 1.3.6.1.4.1.37950.1.1.5.12.5.2.11.1
		classPonNo OBJECT-TYPE
			SYNTAX INTEGER (1..16)
			MAX-ACCESS read-write
			STATUS current
			DESCRIPTION
				"Description."
			::= { onuPortClassifyCfg 1 }

		
--          1.3.6.1.4.1.37950.1.1.5.12.5.2.11.2
-- 1.3.6.1.4.1.37950.1.1.5.12.5.2.11.2
-- 1.3.6.1.4.1.37950.1.1.5.12.5.2.11.2
-- 1.3.6.1.4.1.37950.1.1.5.12.5.2.11.2
-- 1.3.6.1.4.1.37950.1.1.5.12.5.2.11.2
-- 1.3.6.1.4.1.37950.1.1.5.12.5.2.11.2
-- 1.3.6.1.4.1.37950.1.1.5.12.5.2.11.2
-- 1.3.6.1.4.1.37950.1.1.5.12.5.2.11.2
-- 1.3.6.1.4.1.37950.1.1.5.12.5.2.11.2
		-- 1.3.6.1.4.1.37950.1.1.5.12.5.2.11.2
		classOnuNo OBJECT-TYPE
			SYNTAX INTEGER (1..65535)
			MAX-ACCESS read-write
			STATUS current
			DESCRIPTION
				"Description."
			::= { onuPortClassifyCfg 2 }

		
--          1.3.6.1.4.1.37950.1.1.5.12.5.2.11.3
-- 1.3.6.1.4.1.37950.1.1.5.12.5.2.11.3
-- 1.3.6.1.4.1.37950.1.1.5.12.5.2.11.3
-- 1.3.6.1.4.1.37950.1.1.5.12.5.2.11.3
-- 1.3.6.1.4.1.37950.1.1.5.12.5.2.11.3
-- 1.3.6.1.4.1.37950.1.1.5.12.5.2.11.3
-- 1.3.6.1.4.1.37950.1.1.5.12.5.2.11.3
-- 1.3.6.1.4.1.37950.1.1.5.12.5.2.11.3
-- 1.3.6.1.4.1.37950.1.1.5.12.5.2.11.3
		-- 1.3.6.1.4.1.37950.1.1.5.12.5.2.11.3
		classPortNo OBJECT-TYPE
			SYNTAX INTEGER (1..255)
			MAX-ACCESS read-write
			STATUS current
			DESCRIPTION
				"Description."
			::= { onuPortClassifyCfg 3 }

		
--          1.3.6.1.4.1.37950.1.1.5.12.5.2.11.4
-- 1.3.6.1.4.1.37950.1.1.5.12.5.2.11.4
-- 1.3.6.1.4.1.37950.1.1.5.12.5.2.11.4
-- 1.3.6.1.4.1.37950.1.1.5.12.5.2.11.4
-- 1.3.6.1.4.1.37950.1.1.5.12.5.2.11.4
-- 1.3.6.1.4.1.37950.1.1.5.12.5.2.11.4
-- 1.3.6.1.4.1.37950.1.1.5.12.5.2.11.4
-- 1.3.6.1.4.1.37950.1.1.5.12.5.2.11.4
-- 1.3.6.1.4.1.37950.1.1.5.12.5.2.11.4
		-- 1.3.6.1.4.1.37950.1.1.5.12.5.2.11.4
		classPrecedence OBJECT-TYPE
			SYNTAX INTEGER (1..8)
			MAX-ACCESS read-write
			STATUS current
			DESCRIPTION
				"Description."
			::= { onuPortClassifyCfg 4 }

		
--          1.3.6.1.4.1.37950.1.1.5.12.5.2.11.5
-- 1.3.6.1.4.1.37950.1.1.5.12.5.2.11.5
-- 1.3.6.1.4.1.37950.1.1.5.12.5.2.11.5
-- 1.3.6.1.4.1.37950.1.1.5.12.5.2.11.5
-- 1.3.6.1.4.1.37950.1.1.5.12.5.2.11.5
-- 1.3.6.1.4.1.37950.1.1.5.12.5.2.11.5
-- 1.3.6.1.4.1.37950.1.1.5.12.5.2.11.5
-- 1.3.6.1.4.1.37950.1.1.5.12.5.2.11.5
-- 1.3.6.1.4.1.37950.1.1.5.12.5.2.11.5
		-- 1.3.6.1.4.1.37950.1.1.5.12.5.2.11.5
		classPri OBJECT-TYPE
			SYNTAX INTEGER (0..7)
			MAX-ACCESS read-write
			STATUS current
			DESCRIPTION
				"Description."
			::= { onuPortClassifyCfg 5 }

		
--          1.3.6.1.4.1.37950.1.1.5.12.5.2.11.6
-- 1.3.6.1.4.1.37950.1.1.5.12.5.2.11.6
-- 1.3.6.1.4.1.37950.1.1.5.12.5.2.11.6
-- 1.3.6.1.4.1.37950.1.1.5.12.5.2.11.6
-- 1.3.6.1.4.1.37950.1.1.5.12.5.2.11.6
-- 1.3.6.1.4.1.37950.1.1.5.12.5.2.11.6
-- 1.3.6.1.4.1.37950.1.1.5.12.5.2.11.6
-- 1.3.6.1.4.1.37950.1.1.5.12.5.2.11.6
-- 1.3.6.1.4.1.37950.1.1.5.12.5.2.11.6
		-- 1.3.6.1.4.1.37950.1.1.5.12.5.2.11.6
		dstMacEqualSel OBJECT-TYPE
			SYNTAX INTEGER
				{
				invalid(0),
				equal(1),
				unequal(2)
				}
			MAX-ACCESS read-write
			STATUS current
			DESCRIPTION
				"Description."
			::= { onuPortClassifyCfg 6 }

		
--          1.3.6.1.4.1.37950.1.1.5.12.5.2.11.7
-- 1.3.6.1.4.1.37950.1.1.5.12.5.2.11.7
-- 1.3.6.1.4.1.37950.1.1.5.12.5.2.11.7
-- 1.3.6.1.4.1.37950.1.1.5.12.5.2.11.7
-- 1.3.6.1.4.1.37950.1.1.5.12.5.2.11.7
-- 1.3.6.1.4.1.37950.1.1.5.12.5.2.11.7
-- 1.3.6.1.4.1.37950.1.1.5.12.5.2.11.7
-- 1.3.6.1.4.1.37950.1.1.5.12.5.2.11.7
-- 1.3.6.1.4.1.37950.1.1.5.12.5.2.11.7
		-- 1.3.6.1.4.1.37950.1.1.5.12.5.2.11.7
		dstMacValue OBJECT-TYPE
			SYNTAX OCTET STRING
			MAX-ACCESS read-write
			STATUS current
			DESCRIPTION
				"Description."
			::= { onuPortClassifyCfg 7 }

		
--          1.3.6.1.4.1.37950.1.1.5.12.5.2.11.8
-- 1.3.6.1.4.1.37950.1.1.5.12.5.2.11.8
-- 1.3.6.1.4.1.37950.1.1.5.12.5.2.11.8
-- 1.3.6.1.4.1.37950.1.1.5.12.5.2.11.8
-- 1.3.6.1.4.1.37950.1.1.5.12.5.2.11.8
-- 1.3.6.1.4.1.37950.1.1.5.12.5.2.11.8
-- 1.3.6.1.4.1.37950.1.1.5.12.5.2.11.8
-- 1.3.6.1.4.1.37950.1.1.5.12.5.2.11.8
-- 1.3.6.1.4.1.37950.1.1.5.12.5.2.11.8
		-- 1.3.6.1.4.1.37950.1.1.5.12.5.2.11.8
		srcMacEqualSel OBJECT-TYPE
			SYNTAX INTEGER
				{
				invalid(0),
				equal(1),
				unequal(2)
				}
			MAX-ACCESS read-write
			STATUS current
			DESCRIPTION
				"Description."
			::= { onuPortClassifyCfg 8 }

		
--          1.3.6.1.4.1.37950.1.1.5.12.5.2.11.9
-- 1.3.6.1.4.1.37950.1.1.5.12.5.2.11.9
-- 1.3.6.1.4.1.37950.1.1.5.12.5.2.11.9
-- 1.3.6.1.4.1.37950.1.1.5.12.5.2.11.9
-- 1.3.6.1.4.1.37950.1.1.5.12.5.2.11.9
-- 1.3.6.1.4.1.37950.1.1.5.12.5.2.11.9
-- 1.3.6.1.4.1.37950.1.1.5.12.5.2.11.9
-- 1.3.6.1.4.1.37950.1.1.5.12.5.2.11.9
-- 1.3.6.1.4.1.37950.1.1.5.12.5.2.11.9
		-- 1.3.6.1.4.1.37950.1.1.5.12.5.2.11.9
		srcMacValue OBJECT-TYPE
			SYNTAX OCTET STRING
			MAX-ACCESS read-write
			STATUS current
			DESCRIPTION
				"Description."
			::= { onuPortClassifyCfg 9 }

		
--          1.3.6.1.4.1.37950.1.1.5.12.5.2.11.10
-- 1.3.6.1.4.1.37950.1.1.5.12.5.2.11.10
-- 1.3.6.1.4.1.37950.1.1.5.12.5.2.11.10
-- 1.3.6.1.4.1.37950.1.1.5.12.5.2.11.10
-- 1.3.6.1.4.1.37950.1.1.5.12.5.2.11.10
-- 1.3.6.1.4.1.37950.1.1.5.12.5.2.11.10
-- 1.3.6.1.4.1.37950.1.1.5.12.5.2.11.10
-- 1.3.6.1.4.1.37950.1.1.5.12.5.2.11.10
-- 1.3.6.1.4.1.37950.1.1.5.12.5.2.11.10
		-- 1.3.6.1.4.1.37950.1.1.5.12.5.2.11.10
		vlanEqualSel OBJECT-TYPE
			SYNTAX INTEGER
				{
				invalid(0),
				equal(1),
				unequal(2)
				}
			MAX-ACCESS read-write
			STATUS current
			DESCRIPTION
				"Description."
			::= { onuPortClassifyCfg 10 }

		
--          1.3.6.1.4.1.37950.1.1.5.12.5.2.11.11
-- 1.3.6.1.4.1.37950.1.1.5.12.5.2.11.11
-- 1.3.6.1.4.1.37950.1.1.5.12.5.2.11.11
-- 1.3.6.1.4.1.37950.1.1.5.12.5.2.11.11
-- 1.3.6.1.4.1.37950.1.1.5.12.5.2.11.11
-- 1.3.6.1.4.1.37950.1.1.5.12.5.2.11.11
-- 1.3.6.1.4.1.37950.1.1.5.12.5.2.11.11
-- 1.3.6.1.4.1.37950.1.1.5.12.5.2.11.11
-- 1.3.6.1.4.1.37950.1.1.5.12.5.2.11.11
		-- 1.3.6.1.4.1.37950.1.1.5.12.5.2.11.11
		vlanValue OBJECT-TYPE
			SYNTAX INTEGER (1..4094)
			MAX-ACCESS read-write
			STATUS current
			DESCRIPTION
				"Description."
			::= { onuPortClassifyCfg 11 }

		
--          1.3.6.1.4.1.37950.1.1.5.12.5.2.11.12
-- 1.3.6.1.4.1.37950.1.1.5.12.5.2.11.12
-- 1.3.6.1.4.1.37950.1.1.5.12.5.2.11.12
-- 1.3.6.1.4.1.37950.1.1.5.12.5.2.11.12
-- 1.3.6.1.4.1.37950.1.1.5.12.5.2.11.12
-- 1.3.6.1.4.1.37950.1.1.5.12.5.2.11.12
-- 1.3.6.1.4.1.37950.1.1.5.12.5.2.11.12
-- 1.3.6.1.4.1.37950.1.1.5.12.5.2.11.12
-- 1.3.6.1.4.1.37950.1.1.5.12.5.2.11.12
		-- 1.3.6.1.4.1.37950.1.1.5.12.5.2.11.12
		cosEqualSel OBJECT-TYPE
			SYNTAX INTEGER
				{
				invalid(0),
				equal(1),
				unequal(2)
				}
			MAX-ACCESS read-write
			STATUS current
			DESCRIPTION
				"Description."
			::= { onuPortClassifyCfg 12 }

		
--          1.3.6.1.4.1.37950.1.1.5.12.5.2.11.13
-- 1.3.6.1.4.1.37950.1.1.5.12.5.2.11.13
-- 1.3.6.1.4.1.37950.1.1.5.12.5.2.11.13
-- 1.3.6.1.4.1.37950.1.1.5.12.5.2.11.13
-- 1.3.6.1.4.1.37950.1.1.5.12.5.2.11.13
-- 1.3.6.1.4.1.37950.1.1.5.12.5.2.11.13
-- 1.3.6.1.4.1.37950.1.1.5.12.5.2.11.13
-- 1.3.6.1.4.1.37950.1.1.5.12.5.2.11.13
-- 1.3.6.1.4.1.37950.1.1.5.12.5.2.11.13
		-- 1.3.6.1.4.1.37950.1.1.5.12.5.2.11.13
		cosValue OBJECT-TYPE
			SYNTAX INTEGER (0..7)
			MAX-ACCESS read-write
			STATUS current
			DESCRIPTION
				"Description."
			::= { onuPortClassifyCfg 13 }

		
--          1.3.6.1.4.1.37950.1.1.5.12.5.2.11.14
-- 1.3.6.1.4.1.37950.1.1.5.12.5.2.11.14
-- 1.3.6.1.4.1.37950.1.1.5.12.5.2.11.14
-- 1.3.6.1.4.1.37950.1.1.5.12.5.2.11.14
-- 1.3.6.1.4.1.37950.1.1.5.12.5.2.11.14
-- 1.3.6.1.4.1.37950.1.1.5.12.5.2.11.14
-- 1.3.6.1.4.1.37950.1.1.5.12.5.2.11.14
-- 1.3.6.1.4.1.37950.1.1.5.12.5.2.11.14
-- 1.3.6.1.4.1.37950.1.1.5.12.5.2.11.14
		-- 1.3.6.1.4.1.37950.1.1.5.12.5.2.11.14
		ethTypeEqualSel OBJECT-TYPE
			SYNTAX INTEGER
				{
				invalid(0),
				equal(1),
				unequal(2)
				}
			MAX-ACCESS read-write
			STATUS current
			DESCRIPTION
				"Description."
			::= { onuPortClassifyCfg 14 }

		
--          1.3.6.1.4.1.37950.1.1.5.12.5.2.11.15
-- 1.3.6.1.4.1.37950.1.1.5.12.5.2.11.15
-- 1.3.6.1.4.1.37950.1.1.5.12.5.2.11.15
-- 1.3.6.1.4.1.37950.1.1.5.12.5.2.11.15
-- 1.3.6.1.4.1.37950.1.1.5.12.5.2.11.15
-- 1.3.6.1.4.1.37950.1.1.5.12.5.2.11.15
-- 1.3.6.1.4.1.37950.1.1.5.12.5.2.11.15
-- 1.3.6.1.4.1.37950.1.1.5.12.5.2.11.15
-- 1.3.6.1.4.1.37950.1.1.5.12.5.2.11.15
		-- 1.3.6.1.4.1.37950.1.1.5.12.5.2.11.15
		ethTypeValue OBJECT-TYPE
			SYNTAX OCTET STRING
			MAX-ACCESS read-write
			STATUS current
			DESCRIPTION
				"Description."
			::= { onuPortClassifyCfg 15 }

		
--          1.3.6.1.4.1.37950.1.1.5.12.5.2.11.16
-- 1.3.6.1.4.1.37950.1.1.5.12.5.2.11.16
-- 1.3.6.1.4.1.37950.1.1.5.12.5.2.11.16
-- 1.3.6.1.4.1.37950.1.1.5.12.5.2.11.16
-- 1.3.6.1.4.1.37950.1.1.5.12.5.2.11.16
-- 1.3.6.1.4.1.37950.1.1.5.12.5.2.11.16
-- 1.3.6.1.4.1.37950.1.1.5.12.5.2.11.16
-- 1.3.6.1.4.1.37950.1.1.5.12.5.2.11.16
-- 1.3.6.1.4.1.37950.1.1.5.12.5.2.11.16
		-- 1.3.6.1.4.1.37950.1.1.5.12.5.2.11.16
		srcIpEqualSel OBJECT-TYPE
			SYNTAX INTEGER
				{
				invalid(0),
				equal(1),
				unequal(2)
				}
			MAX-ACCESS read-write
			STATUS current
			DESCRIPTION
				"Description."
			::= { onuPortClassifyCfg 16 }

		
--          1.3.6.1.4.1.37950.1.1.5.12.5.2.11.17
-- 1.3.6.1.4.1.37950.1.1.5.12.5.2.11.17
-- 1.3.6.1.4.1.37950.1.1.5.12.5.2.11.17
-- 1.3.6.1.4.1.37950.1.1.5.12.5.2.11.17
-- 1.3.6.1.4.1.37950.1.1.5.12.5.2.11.17
-- 1.3.6.1.4.1.37950.1.1.5.12.5.2.11.17
-- 1.3.6.1.4.1.37950.1.1.5.12.5.2.11.17
-- 1.3.6.1.4.1.37950.1.1.5.12.5.2.11.17
-- 1.3.6.1.4.1.37950.1.1.5.12.5.2.11.17
		-- 1.3.6.1.4.1.37950.1.1.5.12.5.2.11.17
		srcIpValue OBJECT-TYPE
			SYNTAX IpAddress
			MAX-ACCESS read-write
			STATUS current
			DESCRIPTION
				"Description."
			::= { onuPortClassifyCfg 17 }

		
--          1.3.6.1.4.1.37950.1.1.5.12.5.2.11.18
-- 1.3.6.1.4.1.37950.1.1.5.12.5.2.11.18
-- 1.3.6.1.4.1.37950.1.1.5.12.5.2.11.18
-- 1.3.6.1.4.1.37950.1.1.5.12.5.2.11.18
-- 1.3.6.1.4.1.37950.1.1.5.12.5.2.11.18
-- 1.3.6.1.4.1.37950.1.1.5.12.5.2.11.18
-- 1.3.6.1.4.1.37950.1.1.5.12.5.2.11.18
-- 1.3.6.1.4.1.37950.1.1.5.12.5.2.11.18
-- 1.3.6.1.4.1.37950.1.1.5.12.5.2.11.18
		-- 1.3.6.1.4.1.37950.1.1.5.12.5.2.11.18
		destIpEqualSel OBJECT-TYPE
			SYNTAX INTEGER
				{
				invalid(0),
				equal(1),
				unequal(2)
				}
			MAX-ACCESS read-write
			STATUS current
			DESCRIPTION
				"Description."
			::= { onuPortClassifyCfg 18 }

		
--          1.3.6.1.4.1.37950.1.1.5.12.5.2.11.19
-- 1.3.6.1.4.1.37950.1.1.5.12.5.2.11.19
-- 1.3.6.1.4.1.37950.1.1.5.12.5.2.11.19
-- 1.3.6.1.4.1.37950.1.1.5.12.5.2.11.19
-- 1.3.6.1.4.1.37950.1.1.5.12.5.2.11.19
-- 1.3.6.1.4.1.37950.1.1.5.12.5.2.11.19
-- 1.3.6.1.4.1.37950.1.1.5.12.5.2.11.19
-- 1.3.6.1.4.1.37950.1.1.5.12.5.2.11.19
-- 1.3.6.1.4.1.37950.1.1.5.12.5.2.11.19
		-- 1.3.6.1.4.1.37950.1.1.5.12.5.2.11.19
		destIpValue OBJECT-TYPE
			SYNTAX IpAddress
			MAX-ACCESS read-write
			STATUS current
			DESCRIPTION
				"Description."
			::= { onuPortClassifyCfg 19 }

		
--          1.3.6.1.4.1.37950.1.1.5.12.5.2.11.20
-- 1.3.6.1.4.1.37950.1.1.5.12.5.2.11.20
-- 1.3.6.1.4.1.37950.1.1.5.12.5.2.11.20
-- 1.3.6.1.4.1.37950.1.1.5.12.5.2.11.20
-- 1.3.6.1.4.1.37950.1.1.5.12.5.2.11.20
-- 1.3.6.1.4.1.37950.1.1.5.12.5.2.11.20
-- 1.3.6.1.4.1.37950.1.1.5.12.5.2.11.20
-- 1.3.6.1.4.1.37950.1.1.5.12.5.2.11.20
-- 1.3.6.1.4.1.37950.1.1.5.12.5.2.11.20
		-- 1.3.6.1.4.1.37950.1.1.5.12.5.2.11.20
		protocolEqualSel OBJECT-TYPE
			SYNTAX INTEGER
				{
				invalid(0),
				equal(1),
				unequal(2)
				}
			MAX-ACCESS read-write
			STATUS current
			DESCRIPTION
				"Description."
			::= { onuPortClassifyCfg 20 }

		
--          1.3.6.1.4.1.37950.1.1.5.12.5.2.11.21
-- 1.3.6.1.4.1.37950.1.1.5.12.5.2.11.21
-- 1.3.6.1.4.1.37950.1.1.5.12.5.2.11.21
-- 1.3.6.1.4.1.37950.1.1.5.12.5.2.11.21
-- 1.3.6.1.4.1.37950.1.1.5.12.5.2.11.21
-- 1.3.6.1.4.1.37950.1.1.5.12.5.2.11.21
-- 1.3.6.1.4.1.37950.1.1.5.12.5.2.11.21
-- 1.3.6.1.4.1.37950.1.1.5.12.5.2.11.21
-- 1.3.6.1.4.1.37950.1.1.5.12.5.2.11.21
		-- 1.3.6.1.4.1.37950.1.1.5.12.5.2.11.21
		protocolValue OBJECT-TYPE
			SYNTAX INTEGER (0..255)
			MAX-ACCESS read-write
			STATUS current
			DESCRIPTION
				"Description."
			::= { onuPortClassifyCfg 21 }

		
--          1.3.6.1.4.1.37950.1.1.5.12.5.2.11.22
-- 1.3.6.1.4.1.37950.1.1.5.12.5.2.11.22
-- 1.3.6.1.4.1.37950.1.1.5.12.5.2.11.22
-- 1.3.6.1.4.1.37950.1.1.5.12.5.2.11.22
-- 1.3.6.1.4.1.37950.1.1.5.12.5.2.11.22
-- 1.3.6.1.4.1.37950.1.1.5.12.5.2.11.22
-- 1.3.6.1.4.1.37950.1.1.5.12.5.2.11.22
-- 1.3.6.1.4.1.37950.1.1.5.12.5.2.11.22
-- 1.3.6.1.4.1.37950.1.1.5.12.5.2.11.22
		-- 1.3.6.1.4.1.37950.1.1.5.12.5.2.11.22
		tosDscpEuqalSel OBJECT-TYPE
			SYNTAX INTEGER
				{
				invalid(0),
				equal(1),
				unequal(2)
				}
			MAX-ACCESS read-write
			STATUS current
			DESCRIPTION
				"Description."
			::= { onuPortClassifyCfg 22 }

		
--          1.3.6.1.4.1.37950.1.1.5.12.5.2.11.23
-- 1.3.6.1.4.1.37950.1.1.5.12.5.2.11.23
-- 1.3.6.1.4.1.37950.1.1.5.12.5.2.11.23
-- 1.3.6.1.4.1.37950.1.1.5.12.5.2.11.23
-- 1.3.6.1.4.1.37950.1.1.5.12.5.2.11.23
-- 1.3.6.1.4.1.37950.1.1.5.12.5.2.11.23
-- 1.3.6.1.4.1.37950.1.1.5.12.5.2.11.23
-- 1.3.6.1.4.1.37950.1.1.5.12.5.2.11.23
-- 1.3.6.1.4.1.37950.1.1.5.12.5.2.11.23
		-- 1.3.6.1.4.1.37950.1.1.5.12.5.2.11.23
		tosDscpValue OBJECT-TYPE
			SYNTAX INTEGER (0..255)
			MAX-ACCESS read-write
			STATUS current
			DESCRIPTION
				"Description."
			::= { onuPortClassifyCfg 23 }

		
--          1.3.6.1.4.1.37950.1.1.5.12.5.2.11.24
-- 1.3.6.1.4.1.37950.1.1.5.12.5.2.11.24
-- 1.3.6.1.4.1.37950.1.1.5.12.5.2.11.24
-- 1.3.6.1.4.1.37950.1.1.5.12.5.2.11.24
-- 1.3.6.1.4.1.37950.1.1.5.12.5.2.11.24
-- 1.3.6.1.4.1.37950.1.1.5.12.5.2.11.24
-- 1.3.6.1.4.1.37950.1.1.5.12.5.2.11.24
-- 1.3.6.1.4.1.37950.1.1.5.12.5.2.11.24
-- 1.3.6.1.4.1.37950.1.1.5.12.5.2.11.24
		-- 1.3.6.1.4.1.37950.1.1.5.12.5.2.11.24
		srcPortEqualSel OBJECT-TYPE
			SYNTAX INTEGER
				{
				invalid(0),
				equal(1),
				unequal(2)
				}
			MAX-ACCESS read-write
			STATUS current
			DESCRIPTION
				"Description."
			::= { onuPortClassifyCfg 24 }

		
--          1.3.6.1.4.1.37950.1.1.5.12.5.2.11.25
-- 1.3.6.1.4.1.37950.1.1.5.12.5.2.11.25
-- 1.3.6.1.4.1.37950.1.1.5.12.5.2.11.25
-- 1.3.6.1.4.1.37950.1.1.5.12.5.2.11.25
-- 1.3.6.1.4.1.37950.1.1.5.12.5.2.11.25
-- 1.3.6.1.4.1.37950.1.1.5.12.5.2.11.25
-- 1.3.6.1.4.1.37950.1.1.5.12.5.2.11.25
-- 1.3.6.1.4.1.37950.1.1.5.12.5.2.11.25
-- 1.3.6.1.4.1.37950.1.1.5.12.5.2.11.25
		-- 1.3.6.1.4.1.37950.1.1.5.12.5.2.11.25
		srcPortValue OBJECT-TYPE
			SYNTAX INTEGER (0..65535)
			MAX-ACCESS read-write
			STATUS current
			DESCRIPTION
				"Description."
			::= { onuPortClassifyCfg 25 }

		
--          1.3.6.1.4.1.37950.1.1.5.12.5.2.11.26
-- 1.3.6.1.4.1.37950.1.1.5.12.5.2.11.26
-- 1.3.6.1.4.1.37950.1.1.5.12.5.2.11.26
-- 1.3.6.1.4.1.37950.1.1.5.12.5.2.11.26
-- 1.3.6.1.4.1.37950.1.1.5.12.5.2.11.26
-- 1.3.6.1.4.1.37950.1.1.5.12.5.2.11.26
-- 1.3.6.1.4.1.37950.1.1.5.12.5.2.11.26
-- 1.3.6.1.4.1.37950.1.1.5.12.5.2.11.26
-- 1.3.6.1.4.1.37950.1.1.5.12.5.2.11.26
		-- 1.3.6.1.4.1.37950.1.1.5.12.5.2.11.26
		destPortEqualSel OBJECT-TYPE
			SYNTAX INTEGER
				{
				invalid(0),
				equal(1),
				unequal(2)
				}
			MAX-ACCESS read-write
			STATUS current
			DESCRIPTION
				"Description."
			::= { onuPortClassifyCfg 26 }

		
--          1.3.6.1.4.1.37950.1.1.5.12.5.2.11.27
-- 1.3.6.1.4.1.37950.1.1.5.12.5.2.11.27
-- 1.3.6.1.4.1.37950.1.1.5.12.5.2.11.27
-- 1.3.6.1.4.1.37950.1.1.5.12.5.2.11.27
-- 1.3.6.1.4.1.37950.1.1.5.12.5.2.11.27
-- 1.3.6.1.4.1.37950.1.1.5.12.5.2.11.27
-- 1.3.6.1.4.1.37950.1.1.5.12.5.2.11.27
-- 1.3.6.1.4.1.37950.1.1.5.12.5.2.11.27
-- 1.3.6.1.4.1.37950.1.1.5.12.5.2.11.27
		-- 1.3.6.1.4.1.37950.1.1.5.12.5.2.11.27
		destPortValue OBJECT-TYPE
			SYNTAX INTEGER (0..65535)
			MAX-ACCESS read-write
			STATUS current
			DESCRIPTION
				"Description."
			::= { onuPortClassifyCfg 27 }

		
--          1.3.6.1.4.1.37950.1.1.5.12.5.2.11.28
-- 1.3.6.1.4.1.37950.1.1.5.12.5.2.11.28
-- 1.3.6.1.4.1.37950.1.1.5.12.5.2.11.28
-- 1.3.6.1.4.1.37950.1.1.5.12.5.2.11.28
-- 1.3.6.1.4.1.37950.1.1.5.12.5.2.11.28
-- 1.3.6.1.4.1.37950.1.1.5.12.5.2.11.28
-- 1.3.6.1.4.1.37950.1.1.5.12.5.2.11.28
-- 1.3.6.1.4.1.37950.1.1.5.12.5.2.11.28
-- 1.3.6.1.4.1.37950.1.1.5.12.5.2.11.28
		-- 1.3.6.1.4.1.37950.1.1.5.12.5.2.11.28
		classAction OBJECT-TYPE
			SYNTAX INTEGER { add(1) }
			MAX-ACCESS read-write
			STATUS current
			DESCRIPTION
				"Description."
			::= { onuPortClassifyCfg 28 }

		
--          1.3.6.1.4.1.37950.1.1.5.12.5.2.11.29
-- 1.3.6.1.4.1.37950.1.1.5.12.5.2.11.29
-- 1.3.6.1.4.1.37950.1.1.5.12.5.2.11.29
-- 1.3.6.1.4.1.37950.1.1.5.12.5.2.11.29
-- 1.3.6.1.4.1.37950.1.1.5.12.5.2.11.29
-- 1.3.6.1.4.1.37950.1.1.5.12.5.2.11.29
-- 1.3.6.1.4.1.37950.1.1.5.12.5.2.11.29
-- 1.3.6.1.4.1.37950.1.1.5.12.5.2.11.29
-- 1.3.6.1.4.1.37950.1.1.5.12.5.2.11.29
		-- 1.3.6.1.4.1.37950.1.1.5.12.5.2.11.29
		classQueue OBJECT-TYPE
			SYNTAX Integer32 (0..7)
			MAX-ACCESS read-write
			STATUS current
			DESCRIPTION
				"Description."
			::= { onuPortClassifyCfg 29 }

		
--          1.3.6.1.4.1.37950.1.1.5.12.5.2.12
-- 1.3.6.1.4.1.37950.1.1.5.12.5.2.12
-- 1.3.6.1.4.1.37950.1.1.5.12.5.2.12
-- 1.3.6.1.4.1.37950.1.1.5.12.5.2.12
-- 1.3.6.1.4.1.37950.1.1.5.12.5.2.12
-- 1.3.6.1.4.1.37950.1.1.5.12.5.2.12
-- 1.3.6.1.4.1.37950.1.1.5.12.5.2.12
-- 1.3.6.1.4.1.37950.1.1.5.12.5.2.12
-- 1.3.6.1.4.1.37950.1.1.5.12.5.2.12
		-- 1.3.6.1.4.1.37950.1.1.5.12.5.2.12
		onuPortClassifyDel OBJECT IDENTIFIER ::= { onuPortCfg 12 }

		
--          1.3.6.1.4.1.37950.1.1.5.12.5.2.12.1
-- 1.3.6.1.4.1.37950.1.1.5.12.5.2.12.1
-- 1.3.6.1.4.1.37950.1.1.5.12.5.2.12.1
-- 1.3.6.1.4.1.37950.1.1.5.12.5.2.12.1
-- 1.3.6.1.4.1.37950.1.1.5.12.5.2.12.1
-- 1.3.6.1.4.1.37950.1.1.5.12.5.2.12.1
-- 1.3.6.1.4.1.37950.1.1.5.12.5.2.12.1
-- 1.3.6.1.4.1.37950.1.1.5.12.5.2.12.1
-- 1.3.6.1.4.1.37950.1.1.5.12.5.2.12.1
		-- 1.3.6.1.4.1.37950.1.1.5.12.5.2.12.1
		classDelPonNo OBJECT-TYPE
			SYNTAX INTEGER (1..16)
			MAX-ACCESS read-write
			STATUS current
			DESCRIPTION
				"Description."
			::= { onuPortClassifyDel 1 }

		
--          1.3.6.1.4.1.37950.1.1.5.12.5.2.12.2
-- 1.3.6.1.4.1.37950.1.1.5.12.5.2.12.2
-- 1.3.6.1.4.1.37950.1.1.5.12.5.2.12.2
-- 1.3.6.1.4.1.37950.1.1.5.12.5.2.12.2
-- 1.3.6.1.4.1.37950.1.1.5.12.5.2.12.2
-- 1.3.6.1.4.1.37950.1.1.5.12.5.2.12.2
-- 1.3.6.1.4.1.37950.1.1.5.12.5.2.12.2
-- 1.3.6.1.4.1.37950.1.1.5.12.5.2.12.2
-- 1.3.6.1.4.1.37950.1.1.5.12.5.2.12.2
		-- 1.3.6.1.4.1.37950.1.1.5.12.5.2.12.2
		classDelOnuNo OBJECT-TYPE
			SYNTAX INTEGER (1..65535)
			MAX-ACCESS read-write
			STATUS current
			DESCRIPTION
				"Description."
			::= { onuPortClassifyDel 2 }

		
--          1.3.6.1.4.1.37950.1.1.5.12.5.2.12.3
-- 1.3.6.1.4.1.37950.1.1.5.12.5.2.12.3
-- 1.3.6.1.4.1.37950.1.1.5.12.5.2.12.3
-- 1.3.6.1.4.1.37950.1.1.5.12.5.2.12.3
-- 1.3.6.1.4.1.37950.1.1.5.12.5.2.12.3
-- 1.3.6.1.4.1.37950.1.1.5.12.5.2.12.3
-- 1.3.6.1.4.1.37950.1.1.5.12.5.2.12.3
-- 1.3.6.1.4.1.37950.1.1.5.12.5.2.12.3
-- 1.3.6.1.4.1.37950.1.1.5.12.5.2.12.3
		-- 1.3.6.1.4.1.37950.1.1.5.12.5.2.12.3
		classDelPortNo OBJECT-TYPE
			SYNTAX INTEGER (1..255)
			MAX-ACCESS read-write
			STATUS current
			DESCRIPTION
				"Description."
			::= { onuPortClassifyDel 3 }

		
--          1.3.6.1.4.1.37950.1.1.5.12.5.2.12.4
-- 1.3.6.1.4.1.37950.1.1.5.12.5.2.12.4
-- 1.3.6.1.4.1.37950.1.1.5.12.5.2.12.4
-- 1.3.6.1.4.1.37950.1.1.5.12.5.2.12.4
-- 1.3.6.1.4.1.37950.1.1.5.12.5.2.12.4
-- 1.3.6.1.4.1.37950.1.1.5.12.5.2.12.4
-- 1.3.6.1.4.1.37950.1.1.5.12.5.2.12.4
-- 1.3.6.1.4.1.37950.1.1.5.12.5.2.12.4
-- 1.3.6.1.4.1.37950.1.1.5.12.5.2.12.4
		-- 1.3.6.1.4.1.37950.1.1.5.12.5.2.12.4
		classDelPrecedence OBJECT-TYPE
			SYNTAX INTEGER (1..8)
			MAX-ACCESS read-write
			STATUS current
			DESCRIPTION
				"Description."
			::= { onuPortClassifyDel 4 }

		
--          1.3.6.1.4.1.37950.1.1.5.12.5.2.12.5
-- 1.3.6.1.4.1.37950.1.1.5.12.5.2.12.5
-- 1.3.6.1.4.1.37950.1.1.5.12.5.2.12.5
-- 1.3.6.1.4.1.37950.1.1.5.12.5.2.12.5
-- 1.3.6.1.4.1.37950.1.1.5.12.5.2.12.5
-- 1.3.6.1.4.1.37950.1.1.5.12.5.2.12.5
-- 1.3.6.1.4.1.37950.1.1.5.12.5.2.12.5
-- 1.3.6.1.4.1.37950.1.1.5.12.5.2.12.5
-- 1.3.6.1.4.1.37950.1.1.5.12.5.2.12.5
		-- 1.3.6.1.4.1.37950.1.1.5.12.5.2.12.5
		classDelAction OBJECT-TYPE
			SYNTAX INTEGER
				{
				delete(1),
				cleanAll(2)
				}
			MAX-ACCESS read-write
			STATUS current
			DESCRIPTION
				"Description."
			::= { onuPortClassifyDel 5 }

		
--          1.3.6.1.4.1.37950.1.1.5.12.5.2.13
-- 1.3.6.1.4.1.37950.1.1.5.12.5.2.13
-- 1.3.6.1.4.1.37950.1.1.5.12.5.2.13
-- 1.3.6.1.4.1.37950.1.1.5.12.5.2.13
-- 1.3.6.1.4.1.37950.1.1.5.12.5.2.13
-- 1.3.6.1.4.1.37950.1.1.5.12.5.2.13
-- 1.3.6.1.4.1.37950.1.1.5.12.5.2.13
-- 1.3.6.1.4.1.37950.1.1.5.12.5.2.13
-- 1.3.6.1.4.1.37950.1.1.5.12.5.2.13
		-- 1.3.6.1.4.1.37950.1.1.5.12.5.2.13
		onuPortClassifyTable OBJECT-TYPE
			SYNTAX SEQUENCE OF OnuPortClassifyEntry
			MAX-ACCESS not-accessible
			STATUS current
			DESCRIPTION
				"Description."
			::= { onuPortCfg 13 }

		
--          1.3.6.1.4.1.37950.1.1.5.12.5.2.13.1
-- 1.3.6.1.4.1.37950.1.1.5.12.5.2.13.1
-- 1.3.6.1.4.1.37950.1.1.5.12.5.2.13.1
-- 1.3.6.1.4.1.37950.1.1.5.12.5.2.13.1
-- 1.3.6.1.4.1.37950.1.1.5.12.5.2.13.1
-- 1.3.6.1.4.1.37950.1.1.5.12.5.2.13.1
-- 1.3.6.1.4.1.37950.1.1.5.12.5.2.13.1
-- 1.3.6.1.4.1.37950.1.1.5.12.5.2.13.1
-- 1.3.6.1.4.1.37950.1.1.5.12.5.2.13.1
		-- 1.3.6.1.4.1.37950.1.1.5.12.5.2.13.1
		onuPortClassifyEntry OBJECT-TYPE
			SYNTAX OnuPortClassifyEntry
			MAX-ACCESS not-accessible
			STATUS current
			DESCRIPTION
				"Description."
			INDEX { classifyItem }
			::= { onuPortClassifyTable 1 }

		
		OnuPortClassifyEntry ::=
			SEQUENCE { 
				classifyItem
					Integer32,
				classifyPonNo
					INTEGER,
				classifyOnuNo
					INTEGER,
				classifyPortNo
					INTEGER,
				classifyPrecedence
					INTEGER,
				classifyPri
					INTEGER,
				dstMacEqual
					INTEGER,
				dstMacVal
					OCTET STRING,
				srcMacEqual
					INTEGER,
				srcMacVal
					OCTET STRING,
				vlanEqual
					INTEGER,
				vlanVal
					INTEGER,
				cosEqual
					INTEGER,
				cosVal
					INTEGER,
				ethTypeEqual
					INTEGER,
				ethTypeVal
					OCTET STRING,
				srcIpEqual
					INTEGER,
				srcIpVal
					IpAddress,
				destIpEqual
					INTEGER,
				destIpVal
					IpAddress,
				protocolEqual
					INTEGER,
				protocolVal
					INTEGER,
				tosDscpEuqal
					INTEGER,
				tosDscpVal
					INTEGER,
				srcPortEqual
					INTEGER,
				srcPortVal
					INTEGER,
				destPortEqual
					INTEGER,
				destPortVal
					INTEGER,
				classifyQueue
					Integer32
			 }

--          1.3.6.1.4.1.37950.1.1.5.12.5.2.13.1.1
-- 1.3.6.1.4.1.37950.1.1.5.12.5.2.13.1.1
-- 1.3.6.1.4.1.37950.1.1.5.12.5.2.13.1.1
-- 1.3.6.1.4.1.37950.1.1.5.12.5.2.13.1.1
-- 1.3.6.1.4.1.37950.1.1.5.12.5.2.13.1.1
-- 1.3.6.1.4.1.37950.1.1.5.12.5.2.13.1.1
-- 1.3.6.1.4.1.37950.1.1.5.12.5.2.13.1.1
-- 1.3.6.1.4.1.37950.1.1.5.12.5.2.13.1.1
-- 1.3.6.1.4.1.37950.1.1.5.12.5.2.13.1.1
		-- 1.3.6.1.4.1.37950.1.1.5.12.5.2.13.1.1
		classifyItem OBJECT-TYPE
			SYNTAX Integer32
			MAX-ACCESS read-only
			STATUS current
			DESCRIPTION
				"Description."
			::= { onuPortClassifyEntry 1 }

		
--          1.3.6.1.4.1.37950.1.1.5.12.5.2.13.1.2
-- 1.3.6.1.4.1.37950.1.1.5.12.5.2.13.1.2
-- 1.3.6.1.4.1.37950.1.1.5.12.5.2.13.1.2
-- 1.3.6.1.4.1.37950.1.1.5.12.5.2.13.1.2
-- 1.3.6.1.4.1.37950.1.1.5.12.5.2.13.1.2
-- 1.3.6.1.4.1.37950.1.1.5.12.5.2.13.1.2
-- 1.3.6.1.4.1.37950.1.1.5.12.5.2.13.1.2
-- 1.3.6.1.4.1.37950.1.1.5.12.5.2.13.1.2
-- 1.3.6.1.4.1.37950.1.1.5.12.5.2.13.1.2
		-- 1.3.6.1.4.1.37950.1.1.5.12.5.2.13.1.2
		classifyPonNo OBJECT-TYPE
			SYNTAX INTEGER (1..16)
			MAX-ACCESS read-only
			STATUS current
			DESCRIPTION
				"Description."
			::= { onuPortClassifyEntry 2 }

		
--          1.3.6.1.4.1.37950.1.1.5.12.5.2.13.1.3
-- 1.3.6.1.4.1.37950.1.1.5.12.5.2.13.1.3
-- 1.3.6.1.4.1.37950.1.1.5.12.5.2.13.1.3
-- 1.3.6.1.4.1.37950.1.1.5.12.5.2.13.1.3
-- 1.3.6.1.4.1.37950.1.1.5.12.5.2.13.1.3
-- 1.3.6.1.4.1.37950.1.1.5.12.5.2.13.1.3
-- 1.3.6.1.4.1.37950.1.1.5.12.5.2.13.1.3
-- 1.3.6.1.4.1.37950.1.1.5.12.5.2.13.1.3
-- 1.3.6.1.4.1.37950.1.1.5.12.5.2.13.1.3
		-- 1.3.6.1.4.1.37950.1.1.5.12.5.2.13.1.3
		classifyOnuNo OBJECT-TYPE
			SYNTAX INTEGER (1..65535)
			MAX-ACCESS read-only
			STATUS current
			DESCRIPTION
				"Description."
			::= { onuPortClassifyEntry 3 }

		
--          1.3.6.1.4.1.37950.1.1.5.12.5.2.13.1.4
-- 1.3.6.1.4.1.37950.1.1.5.12.5.2.13.1.4
-- 1.3.6.1.4.1.37950.1.1.5.12.5.2.13.1.4
-- 1.3.6.1.4.1.37950.1.1.5.12.5.2.13.1.4
-- 1.3.6.1.4.1.37950.1.1.5.12.5.2.13.1.4
-- 1.3.6.1.4.1.37950.1.1.5.12.5.2.13.1.4
-- 1.3.6.1.4.1.37950.1.1.5.12.5.2.13.1.4
-- 1.3.6.1.4.1.37950.1.1.5.12.5.2.13.1.4
-- 1.3.6.1.4.1.37950.1.1.5.12.5.2.13.1.4
		-- 1.3.6.1.4.1.37950.1.1.5.12.5.2.13.1.4
		classifyPortNo OBJECT-TYPE
			SYNTAX INTEGER (1..255)
			MAX-ACCESS read-only
			STATUS current
			DESCRIPTION
				"Description."
			::= { onuPortClassifyEntry 4 }

		
--          1.3.6.1.4.1.37950.1.1.5.12.5.2.13.1.5
-- 1.3.6.1.4.1.37950.1.1.5.12.5.2.13.1.5
-- 1.3.6.1.4.1.37950.1.1.5.12.5.2.13.1.5
-- 1.3.6.1.4.1.37950.1.1.5.12.5.2.13.1.5
-- 1.3.6.1.4.1.37950.1.1.5.12.5.2.13.1.5
-- 1.3.6.1.4.1.37950.1.1.5.12.5.2.13.1.5
-- 1.3.6.1.4.1.37950.1.1.5.12.5.2.13.1.5
-- 1.3.6.1.4.1.37950.1.1.5.12.5.2.13.1.5
-- 1.3.6.1.4.1.37950.1.1.5.12.5.2.13.1.5
		-- 1.3.6.1.4.1.37950.1.1.5.12.5.2.13.1.5
		classifyPrecedence OBJECT-TYPE
			SYNTAX INTEGER (1..8)
			MAX-ACCESS read-only
			STATUS current
			DESCRIPTION
				"Description."
			::= { onuPortClassifyEntry 5 }

		
--          1.3.6.1.4.1.37950.1.1.5.12.5.2.13.1.6
-- 1.3.6.1.4.1.37950.1.1.5.12.5.2.13.1.6
-- 1.3.6.1.4.1.37950.1.1.5.12.5.2.13.1.6
-- 1.3.6.1.4.1.37950.1.1.5.12.5.2.13.1.6
-- 1.3.6.1.4.1.37950.1.1.5.12.5.2.13.1.6
-- 1.3.6.1.4.1.37950.1.1.5.12.5.2.13.1.6
-- 1.3.6.1.4.1.37950.1.1.5.12.5.2.13.1.6
-- 1.3.6.1.4.1.37950.1.1.5.12.5.2.13.1.6
-- 1.3.6.1.4.1.37950.1.1.5.12.5.2.13.1.6
		-- 1.3.6.1.4.1.37950.1.1.5.12.5.2.13.1.6
		classifyPri OBJECT-TYPE
			SYNTAX INTEGER (0..7)
			MAX-ACCESS read-only
			STATUS current
			DESCRIPTION
				"Description."
			::= { onuPortClassifyEntry 6 }

		
--          1.3.6.1.4.1.37950.1.1.5.12.5.2.13.1.7
-- 1.3.6.1.4.1.37950.1.1.5.12.5.2.13.1.7
-- 1.3.6.1.4.1.37950.1.1.5.12.5.2.13.1.7
-- 1.3.6.1.4.1.37950.1.1.5.12.5.2.13.1.7
-- 1.3.6.1.4.1.37950.1.1.5.12.5.2.13.1.7
-- 1.3.6.1.4.1.37950.1.1.5.12.5.2.13.1.7
-- 1.3.6.1.4.1.37950.1.1.5.12.5.2.13.1.7
-- 1.3.6.1.4.1.37950.1.1.5.12.5.2.13.1.7
-- 1.3.6.1.4.1.37950.1.1.5.12.5.2.13.1.7
		-- 1.3.6.1.4.1.37950.1.1.5.12.5.2.13.1.7
		dstMacEqual OBJECT-TYPE
			SYNTAX INTEGER
				{
				invalid(0),
				equal(1),
				unequal(2)
				}
			MAX-ACCESS read-only
			STATUS current
			DESCRIPTION
				"Description."
			::= { onuPortClassifyEntry 7 }

		
--          1.3.6.1.4.1.37950.1.1.5.12.5.2.13.1.8
-- 1.3.6.1.4.1.37950.1.1.5.12.5.2.13.1.8
-- 1.3.6.1.4.1.37950.1.1.5.12.5.2.13.1.8
-- 1.3.6.1.4.1.37950.1.1.5.12.5.2.13.1.8
-- 1.3.6.1.4.1.37950.1.1.5.12.5.2.13.1.8
-- 1.3.6.1.4.1.37950.1.1.5.12.5.2.13.1.8
-- 1.3.6.1.4.1.37950.1.1.5.12.5.2.13.1.8
-- 1.3.6.1.4.1.37950.1.1.5.12.5.2.13.1.8
-- 1.3.6.1.4.1.37950.1.1.5.12.5.2.13.1.8
		-- 1.3.6.1.4.1.37950.1.1.5.12.5.2.13.1.8
		dstMacVal OBJECT-TYPE
			SYNTAX OCTET STRING
			MAX-ACCESS read-only
			STATUS current
			DESCRIPTION
				"Description."
			::= { onuPortClassifyEntry 8 }

		
--          1.3.6.1.4.1.37950.1.1.5.12.5.2.13.1.9
-- 1.3.6.1.4.1.37950.1.1.5.12.5.2.13.1.9
-- 1.3.6.1.4.1.37950.1.1.5.12.5.2.13.1.9
-- 1.3.6.1.4.1.37950.1.1.5.12.5.2.13.1.9
-- 1.3.6.1.4.1.37950.1.1.5.12.5.2.13.1.9
-- 1.3.6.1.4.1.37950.1.1.5.12.5.2.13.1.9
-- 1.3.6.1.4.1.37950.1.1.5.12.5.2.13.1.9
-- 1.3.6.1.4.1.37950.1.1.5.12.5.2.13.1.9
-- 1.3.6.1.4.1.37950.1.1.5.12.5.2.13.1.9
		-- 1.3.6.1.4.1.37950.1.1.5.12.5.2.13.1.9
		srcMacEqual OBJECT-TYPE
			SYNTAX INTEGER
				{
				invalid(0),
				equal(1),
				unequal(2)
				}
			MAX-ACCESS read-only
			STATUS current
			DESCRIPTION
				"Description."
			::= { onuPortClassifyEntry 9 }

		
--          1.3.6.1.4.1.37950.1.1.5.12.5.2.13.1.10
-- 1.3.6.1.4.1.37950.1.1.5.12.5.2.13.1.10
-- 1.3.6.1.4.1.37950.1.1.5.12.5.2.13.1.10
-- 1.3.6.1.4.1.37950.1.1.5.12.5.2.13.1.10
-- 1.3.6.1.4.1.37950.1.1.5.12.5.2.13.1.10
-- 1.3.6.1.4.1.37950.1.1.5.12.5.2.13.1.10
-- 1.3.6.1.4.1.37950.1.1.5.12.5.2.13.1.10
-- 1.3.6.1.4.1.37950.1.1.5.12.5.2.13.1.10
-- 1.3.6.1.4.1.37950.1.1.5.12.5.2.13.1.10
		-- 1.3.6.1.4.1.37950.1.1.5.12.5.2.13.1.10
		srcMacVal OBJECT-TYPE
			SYNTAX OCTET STRING
			MAX-ACCESS read-only
			STATUS current
			DESCRIPTION
				"Description."
			::= { onuPortClassifyEntry 10 }

		
--          1.3.6.1.4.1.37950.1.1.5.12.5.2.13.1.11
-- 1.3.6.1.4.1.37950.1.1.5.12.5.2.13.1.11
-- 1.3.6.1.4.1.37950.1.1.5.12.5.2.13.1.11
-- 1.3.6.1.4.1.37950.1.1.5.12.5.2.13.1.11
-- 1.3.6.1.4.1.37950.1.1.5.12.5.2.13.1.11
-- 1.3.6.1.4.1.37950.1.1.5.12.5.2.13.1.11
-- 1.3.6.1.4.1.37950.1.1.5.12.5.2.13.1.11
-- 1.3.6.1.4.1.37950.1.1.5.12.5.2.13.1.11
-- 1.3.6.1.4.1.37950.1.1.5.12.5.2.13.1.11
		-- 1.3.6.1.4.1.37950.1.1.5.12.5.2.13.1.11
		vlanEqual OBJECT-TYPE
			SYNTAX INTEGER
				{
				invalid(0),
				equal(1),
				unequal(2)
				}
			MAX-ACCESS read-only
			STATUS current
			DESCRIPTION
				"Description."
			::= { onuPortClassifyEntry 11 }

		
--          1.3.6.1.4.1.37950.1.1.5.12.5.2.13.1.12
-- 1.3.6.1.4.1.37950.1.1.5.12.5.2.13.1.12
-- 1.3.6.1.4.1.37950.1.1.5.12.5.2.13.1.12
-- 1.3.6.1.4.1.37950.1.1.5.12.5.2.13.1.12
-- 1.3.6.1.4.1.37950.1.1.5.12.5.2.13.1.12
-- 1.3.6.1.4.1.37950.1.1.5.12.5.2.13.1.12
-- 1.3.6.1.4.1.37950.1.1.5.12.5.2.13.1.12
-- 1.3.6.1.4.1.37950.1.1.5.12.5.2.13.1.12
-- 1.3.6.1.4.1.37950.1.1.5.12.5.2.13.1.12
		-- 1.3.6.1.4.1.37950.1.1.5.12.5.2.13.1.12
		vlanVal OBJECT-TYPE
			SYNTAX INTEGER (0..4094)
			MAX-ACCESS read-only
			STATUS current
			DESCRIPTION
				"Description."
			::= { onuPortClassifyEntry 12 }

		
--          1.3.6.1.4.1.37950.1.1.5.12.5.2.13.1.13
-- 1.3.6.1.4.1.37950.1.1.5.12.5.2.13.1.13
-- 1.3.6.1.4.1.37950.1.1.5.12.5.2.13.1.13
-- 1.3.6.1.4.1.37950.1.1.5.12.5.2.13.1.13
-- 1.3.6.1.4.1.37950.1.1.5.12.5.2.13.1.13
-- 1.3.6.1.4.1.37950.1.1.5.12.5.2.13.1.13
-- 1.3.6.1.4.1.37950.1.1.5.12.5.2.13.1.13
-- 1.3.6.1.4.1.37950.1.1.5.12.5.2.13.1.13
-- 1.3.6.1.4.1.37950.1.1.5.12.5.2.13.1.13
		-- 1.3.6.1.4.1.37950.1.1.5.12.5.2.13.1.13
		cosEqual OBJECT-TYPE
			SYNTAX INTEGER
				{
				invalid(0),
				equal(1),
				unequal(2)
				}
			MAX-ACCESS read-only
			STATUS current
			DESCRIPTION
				"Description."
			::= { onuPortClassifyEntry 13 }

		
--          1.3.6.1.4.1.37950.1.1.5.12.5.2.13.1.14
-- 1.3.6.1.4.1.37950.1.1.5.12.5.2.13.1.14
-- 1.3.6.1.4.1.37950.1.1.5.12.5.2.13.1.14
-- 1.3.6.1.4.1.37950.1.1.5.12.5.2.13.1.14
-- 1.3.6.1.4.1.37950.1.1.5.12.5.2.13.1.14
-- 1.3.6.1.4.1.37950.1.1.5.12.5.2.13.1.14
-- 1.3.6.1.4.1.37950.1.1.5.12.5.2.13.1.14
-- 1.3.6.1.4.1.37950.1.1.5.12.5.2.13.1.14
-- 1.3.6.1.4.1.37950.1.1.5.12.5.2.13.1.14
		-- 1.3.6.1.4.1.37950.1.1.5.12.5.2.13.1.14
		cosVal OBJECT-TYPE
			SYNTAX INTEGER (-1..7)
			MAX-ACCESS read-only
			STATUS current
			DESCRIPTION
				"Description."
			::= { onuPortClassifyEntry 14 }

		
--          1.3.6.1.4.1.37950.1.1.5.12.5.2.13.1.15
-- 1.3.6.1.4.1.37950.1.1.5.12.5.2.13.1.15
-- 1.3.6.1.4.1.37950.1.1.5.12.5.2.13.1.15
-- 1.3.6.1.4.1.37950.1.1.5.12.5.2.13.1.15
-- 1.3.6.1.4.1.37950.1.1.5.12.5.2.13.1.15
-- 1.3.6.1.4.1.37950.1.1.5.12.5.2.13.1.15
-- 1.3.6.1.4.1.37950.1.1.5.12.5.2.13.1.15
-- 1.3.6.1.4.1.37950.1.1.5.12.5.2.13.1.15
-- 1.3.6.1.4.1.37950.1.1.5.12.5.2.13.1.15
		-- 1.3.6.1.4.1.37950.1.1.5.12.5.2.13.1.15
		ethTypeEqual OBJECT-TYPE
			SYNTAX INTEGER
				{
				invalid(0),
				equal(1),
				unequal(2)
				}
			MAX-ACCESS read-only
			STATUS current
			DESCRIPTION
				"Description."
			::= { onuPortClassifyEntry 15 }

		
--          1.3.6.1.4.1.37950.1.1.5.12.5.2.13.1.16
-- 1.3.6.1.4.1.37950.1.1.5.12.5.2.13.1.16
-- 1.3.6.1.4.1.37950.1.1.5.12.5.2.13.1.16
-- 1.3.6.1.4.1.37950.1.1.5.12.5.2.13.1.16
-- 1.3.6.1.4.1.37950.1.1.5.12.5.2.13.1.16
-- 1.3.6.1.4.1.37950.1.1.5.12.5.2.13.1.16
-- 1.3.6.1.4.1.37950.1.1.5.12.5.2.13.1.16
-- 1.3.6.1.4.1.37950.1.1.5.12.5.2.13.1.16
-- 1.3.6.1.4.1.37950.1.1.5.12.5.2.13.1.16
		-- 1.3.6.1.4.1.37950.1.1.5.12.5.2.13.1.16
		ethTypeVal OBJECT-TYPE
			SYNTAX OCTET STRING
			MAX-ACCESS read-only
			STATUS current
			DESCRIPTION
				"Description."
			::= { onuPortClassifyEntry 16 }

		
--          1.3.6.1.4.1.37950.1.1.5.12.5.2.13.1.17
-- 1.3.6.1.4.1.37950.1.1.5.12.5.2.13.1.17
-- 1.3.6.1.4.1.37950.1.1.5.12.5.2.13.1.17
-- 1.3.6.1.4.1.37950.1.1.5.12.5.2.13.1.17
-- 1.3.6.1.4.1.37950.1.1.5.12.5.2.13.1.17
-- 1.3.6.1.4.1.37950.1.1.5.12.5.2.13.1.17
-- 1.3.6.1.4.1.37950.1.1.5.12.5.2.13.1.17
-- 1.3.6.1.4.1.37950.1.1.5.12.5.2.13.1.17
-- 1.3.6.1.4.1.37950.1.1.5.12.5.2.13.1.17
		-- 1.3.6.1.4.1.37950.1.1.5.12.5.2.13.1.17
		srcIpEqual OBJECT-TYPE
			SYNTAX INTEGER
				{
				invalid(0),
				equal(1),
				unequal(2)
				}
			MAX-ACCESS read-only
			STATUS current
			DESCRIPTION
				"Description."
			::= { onuPortClassifyEntry 17 }

		
--          1.3.6.1.4.1.37950.1.1.5.12.5.2.13.1.18
-- 1.3.6.1.4.1.37950.1.1.5.12.5.2.13.1.18
-- 1.3.6.1.4.1.37950.1.1.5.12.5.2.13.1.18
-- 1.3.6.1.4.1.37950.1.1.5.12.5.2.13.1.18
-- 1.3.6.1.4.1.37950.1.1.5.12.5.2.13.1.18
-- 1.3.6.1.4.1.37950.1.1.5.12.5.2.13.1.18
-- 1.3.6.1.4.1.37950.1.1.5.12.5.2.13.1.18
-- 1.3.6.1.4.1.37950.1.1.5.12.5.2.13.1.18
-- 1.3.6.1.4.1.37950.1.1.5.12.5.2.13.1.18
		-- 1.3.6.1.4.1.37950.1.1.5.12.5.2.13.1.18
		srcIpVal OBJECT-TYPE
			SYNTAX IpAddress
			MAX-ACCESS read-only
			STATUS current
			DESCRIPTION
				"Description."
			::= { onuPortClassifyEntry 18 }

		
--          1.3.6.1.4.1.37950.1.1.5.12.5.2.13.1.19
-- 1.3.6.1.4.1.37950.1.1.5.12.5.2.13.1.19
-- 1.3.6.1.4.1.37950.1.1.5.12.5.2.13.1.19
-- 1.3.6.1.4.1.37950.1.1.5.12.5.2.13.1.19
-- 1.3.6.1.4.1.37950.1.1.5.12.5.2.13.1.19
-- 1.3.6.1.4.1.37950.1.1.5.12.5.2.13.1.19
-- 1.3.6.1.4.1.37950.1.1.5.12.5.2.13.1.19
-- 1.3.6.1.4.1.37950.1.1.5.12.5.2.13.1.19
-- 1.3.6.1.4.1.37950.1.1.5.12.5.2.13.1.19
		-- 1.3.6.1.4.1.37950.1.1.5.12.5.2.13.1.19
		destIpEqual OBJECT-TYPE
			SYNTAX INTEGER
				{
				invalid(0),
				equal(1),
				unequal(2)
				}
			MAX-ACCESS read-only
			STATUS current
			DESCRIPTION
				"Description."
			::= { onuPortClassifyEntry 19 }

		
--          1.3.6.1.4.1.37950.1.1.5.12.5.2.13.1.20
-- 1.3.6.1.4.1.37950.1.1.5.12.5.2.13.1.20
-- 1.3.6.1.4.1.37950.1.1.5.12.5.2.13.1.20
-- 1.3.6.1.4.1.37950.1.1.5.12.5.2.13.1.20
-- 1.3.6.1.4.1.37950.1.1.5.12.5.2.13.1.20
-- 1.3.6.1.4.1.37950.1.1.5.12.5.2.13.1.20
-- 1.3.6.1.4.1.37950.1.1.5.12.5.2.13.1.20
-- 1.3.6.1.4.1.37950.1.1.5.12.5.2.13.1.20
-- 1.3.6.1.4.1.37950.1.1.5.12.5.2.13.1.20
		-- 1.3.6.1.4.1.37950.1.1.5.12.5.2.13.1.20
		destIpVal OBJECT-TYPE
			SYNTAX IpAddress
			MAX-ACCESS read-only
			STATUS current
			DESCRIPTION
				"Description."
			::= { onuPortClassifyEntry 20 }

		
--          1.3.6.1.4.1.37950.1.1.5.12.5.2.13.1.21
-- 1.3.6.1.4.1.37950.1.1.5.12.5.2.13.1.21
-- 1.3.6.1.4.1.37950.1.1.5.12.5.2.13.1.21
-- 1.3.6.1.4.1.37950.1.1.5.12.5.2.13.1.21
-- 1.3.6.1.4.1.37950.1.1.5.12.5.2.13.1.21
-- 1.3.6.1.4.1.37950.1.1.5.12.5.2.13.1.21
-- 1.3.6.1.4.1.37950.1.1.5.12.5.2.13.1.21
-- 1.3.6.1.4.1.37950.1.1.5.12.5.2.13.1.21
-- 1.3.6.1.4.1.37950.1.1.5.12.5.2.13.1.21
		-- 1.3.6.1.4.1.37950.1.1.5.12.5.2.13.1.21
		protocolEqual OBJECT-TYPE
			SYNTAX INTEGER
				{
				invalid(0),
				equal(1),
				unequal(2)
				}
			MAX-ACCESS read-only
			STATUS current
			DESCRIPTION
				"Description."
			::= { onuPortClassifyEntry 21 }

		
--          1.3.6.1.4.1.37950.1.1.5.12.5.2.13.1.22
-- 1.3.6.1.4.1.37950.1.1.5.12.5.2.13.1.22
-- 1.3.6.1.4.1.37950.1.1.5.12.5.2.13.1.22
-- 1.3.6.1.4.1.37950.1.1.5.12.5.2.13.1.22
-- 1.3.6.1.4.1.37950.1.1.5.12.5.2.13.1.22
-- 1.3.6.1.4.1.37950.1.1.5.12.5.2.13.1.22
-- 1.3.6.1.4.1.37950.1.1.5.12.5.2.13.1.22
-- 1.3.6.1.4.1.37950.1.1.5.12.5.2.13.1.22
-- 1.3.6.1.4.1.37950.1.1.5.12.5.2.13.1.22
		-- 1.3.6.1.4.1.37950.1.1.5.12.5.2.13.1.22
		protocolVal OBJECT-TYPE
			SYNTAX INTEGER (-1..255)
			MAX-ACCESS read-only
			STATUS current
			DESCRIPTION
				"Description."
			::= { onuPortClassifyEntry 22 }

		
--          1.3.6.1.4.1.37950.1.1.5.12.5.2.13.1.23
-- 1.3.6.1.4.1.37950.1.1.5.12.5.2.13.1.23
-- 1.3.6.1.4.1.37950.1.1.5.12.5.2.13.1.23
-- 1.3.6.1.4.1.37950.1.1.5.12.5.2.13.1.23
-- 1.3.6.1.4.1.37950.1.1.5.12.5.2.13.1.23
-- 1.3.6.1.4.1.37950.1.1.5.12.5.2.13.1.23
-- 1.3.6.1.4.1.37950.1.1.5.12.5.2.13.1.23
-- 1.3.6.1.4.1.37950.1.1.5.12.5.2.13.1.23
-- 1.3.6.1.4.1.37950.1.1.5.12.5.2.13.1.23
		-- 1.3.6.1.4.1.37950.1.1.5.12.5.2.13.1.23
		tosDscpEuqal OBJECT-TYPE
			SYNTAX INTEGER
				{
				invalid(0),
				equal(1),
				unequal(2)
				}
			MAX-ACCESS read-only
			STATUS current
			DESCRIPTION
				"Description."
			::= { onuPortClassifyEntry 23 }

		
--          1.3.6.1.4.1.37950.1.1.5.12.5.2.13.1.24
-- 1.3.6.1.4.1.37950.1.1.5.12.5.2.13.1.24
-- 1.3.6.1.4.1.37950.1.1.5.12.5.2.13.1.24
-- 1.3.6.1.4.1.37950.1.1.5.12.5.2.13.1.24
-- 1.3.6.1.4.1.37950.1.1.5.12.5.2.13.1.24
-- 1.3.6.1.4.1.37950.1.1.5.12.5.2.13.1.24
-- 1.3.6.1.4.1.37950.1.1.5.12.5.2.13.1.24
-- 1.3.6.1.4.1.37950.1.1.5.12.5.2.13.1.24
-- 1.3.6.1.4.1.37950.1.1.5.12.5.2.13.1.24
		-- 1.3.6.1.4.1.37950.1.1.5.12.5.2.13.1.24
		tosDscpVal OBJECT-TYPE
			SYNTAX INTEGER (-1..255)
			MAX-ACCESS read-only
			STATUS current
			DESCRIPTION
				"Description."
			::= { onuPortClassifyEntry 24 }

		
--          1.3.6.1.4.1.37950.1.1.5.12.5.2.13.1.25
-- 1.3.6.1.4.1.37950.1.1.5.12.5.2.13.1.25
-- 1.3.6.1.4.1.37950.1.1.5.12.5.2.13.1.25
-- 1.3.6.1.4.1.37950.1.1.5.12.5.2.13.1.25
-- 1.3.6.1.4.1.37950.1.1.5.12.5.2.13.1.25
-- 1.3.6.1.4.1.37950.1.1.5.12.5.2.13.1.25
-- 1.3.6.1.4.1.37950.1.1.5.12.5.2.13.1.25
-- 1.3.6.1.4.1.37950.1.1.5.12.5.2.13.1.25
-- 1.3.6.1.4.1.37950.1.1.5.12.5.2.13.1.25
		-- 1.3.6.1.4.1.37950.1.1.5.12.5.2.13.1.25
		srcPortEqual OBJECT-TYPE
			SYNTAX INTEGER
				{
				invalid(0),
				equal(1),
				unequal(2)
				}
			MAX-ACCESS read-only
			STATUS current
			DESCRIPTION
				"Description."
			::= { onuPortClassifyEntry 25 }

		
--          1.3.6.1.4.1.37950.1.1.5.12.5.2.13.1.26
-- 1.3.6.1.4.1.37950.1.1.5.12.5.2.13.1.26
-- 1.3.6.1.4.1.37950.1.1.5.12.5.2.13.1.26
-- 1.3.6.1.4.1.37950.1.1.5.12.5.2.13.1.26
-- 1.3.6.1.4.1.37950.1.1.5.12.5.2.13.1.26
-- 1.3.6.1.4.1.37950.1.1.5.12.5.2.13.1.26
-- 1.3.6.1.4.1.37950.1.1.5.12.5.2.13.1.26
-- 1.3.6.1.4.1.37950.1.1.5.12.5.2.13.1.26
-- 1.3.6.1.4.1.37950.1.1.5.12.5.2.13.1.26
		-- 1.3.6.1.4.1.37950.1.1.5.12.5.2.13.1.26
		srcPortVal OBJECT-TYPE
			SYNTAX INTEGER (-1..65535)
			MAX-ACCESS read-only
			STATUS current
			DESCRIPTION
				"Description."
			::= { onuPortClassifyEntry 26 }

		
--          1.3.6.1.4.1.37950.1.1.5.12.5.2.13.1.27
-- 1.3.6.1.4.1.37950.1.1.5.12.5.2.13.1.27
-- 1.3.6.1.4.1.37950.1.1.5.12.5.2.13.1.27
-- 1.3.6.1.4.1.37950.1.1.5.12.5.2.13.1.27
-- 1.3.6.1.4.1.37950.1.1.5.12.5.2.13.1.27
-- 1.3.6.1.4.1.37950.1.1.5.12.5.2.13.1.27
-- 1.3.6.1.4.1.37950.1.1.5.12.5.2.13.1.27
-- 1.3.6.1.4.1.37950.1.1.5.12.5.2.13.1.27
-- 1.3.6.1.4.1.37950.1.1.5.12.5.2.13.1.27
		-- 1.3.6.1.4.1.37950.1.1.5.12.5.2.13.1.27
		destPortEqual OBJECT-TYPE
			SYNTAX INTEGER
				{
				invalid(0),
				equal(1),
				unequal(2)
				}
			MAX-ACCESS read-only
			STATUS current
			DESCRIPTION
				"Description."
			::= { onuPortClassifyEntry 27 }

		
--          1.3.6.1.4.1.37950.1.1.5.12.5.2.13.1.28
-- 1.3.6.1.4.1.37950.1.1.5.12.5.2.13.1.28
-- 1.3.6.1.4.1.37950.1.1.5.12.5.2.13.1.28
-- 1.3.6.1.4.1.37950.1.1.5.12.5.2.13.1.28
-- 1.3.6.1.4.1.37950.1.1.5.12.5.2.13.1.28
-- 1.3.6.1.4.1.37950.1.1.5.12.5.2.13.1.28
-- 1.3.6.1.4.1.37950.1.1.5.12.5.2.13.1.28
-- 1.3.6.1.4.1.37950.1.1.5.12.5.2.13.1.28
-- 1.3.6.1.4.1.37950.1.1.5.12.5.2.13.1.28
		-- 1.3.6.1.4.1.37950.1.1.5.12.5.2.13.1.28
		destPortVal OBJECT-TYPE
			SYNTAX INTEGER (-1..65535)
			MAX-ACCESS read-only
			STATUS current
			DESCRIPTION
				"Description."
			::= { onuPortClassifyEntry 28 }

		
--          1.3.6.1.4.1.37950.1.1.5.12.5.2.13.1.29
-- 1.3.6.1.4.1.37950.1.1.5.12.5.2.13.1.29
-- 1.3.6.1.4.1.37950.1.1.5.12.5.2.13.1.29
-- 1.3.6.1.4.1.37950.1.1.5.12.5.2.13.1.29
-- 1.3.6.1.4.1.37950.1.1.5.12.5.2.13.1.29
-- 1.3.6.1.4.1.37950.1.1.5.12.5.2.13.1.29
-- 1.3.6.1.4.1.37950.1.1.5.12.5.2.13.1.29
-- 1.3.6.1.4.1.37950.1.1.5.12.5.2.13.1.29
-- 1.3.6.1.4.1.37950.1.1.5.12.5.2.13.1.29
		-- 1.3.6.1.4.1.37950.1.1.5.12.5.2.13.1.29
		classifyQueue OBJECT-TYPE
			SYNTAX Integer32 (0..7)
			MAX-ACCESS read-only
			STATUS current
			DESCRIPTION
				"Description."
			::= { onuPortClassifyEntry 29 }

		
--          1.3.6.1.4.1.37950.1.1.5.12.5.2.14
-- 1.3.6.1.4.1.37950.1.1.5.12.5.2.14
-- 1.3.6.1.4.1.37950.1.1.5.12.5.2.14
-- 1.3.6.1.4.1.37950.1.1.5.12.5.2.14
-- 1.3.6.1.4.1.37950.1.1.5.12.5.2.14
-- 1.3.6.1.4.1.37950.1.1.5.12.5.2.14
-- 1.3.6.1.4.1.37950.1.1.5.12.5.2.14
-- 1.3.6.1.4.1.37950.1.1.5.12.5.2.14
-- 1.3.6.1.4.1.37950.1.1.5.12.5.2.14
		-- 1.3.6.1.4.1.37950.1.1.5.12.5.2.14
		onuPortIgmpCfg OBJECT IDENTIFIER ::= { onuPortCfg 14 }

		
--          1.3.6.1.4.1.37950.1.1.5.12.5.2.14.1
-- 1.3.6.1.4.1.37950.1.1.5.12.5.2.14.1
-- 1.3.6.1.4.1.37950.1.1.5.12.5.2.14.1
-- 1.3.6.1.4.1.37950.1.1.5.12.5.2.14.1
-- 1.3.6.1.4.1.37950.1.1.5.12.5.2.14.1
-- 1.3.6.1.4.1.37950.1.1.5.12.5.2.14.1
-- 1.3.6.1.4.1.37950.1.1.5.12.5.2.14.1
-- 1.3.6.1.4.1.37950.1.1.5.12.5.2.14.1
-- 1.3.6.1.4.1.37950.1.1.5.12.5.2.14.1
		-- 1.3.6.1.4.1.37950.1.1.5.12.5.2.14.1
		mcVlanCfg OBJECT IDENTIFIER ::= { onuPortIgmpCfg 1 }

		
--          1.3.6.1.4.1.37950.1.1.5.12.5.2.14.1.1
-- 1.3.6.1.4.1.37950.1.1.5.12.5.2.14.1.1
-- 1.3.6.1.4.1.37950.1.1.5.12.5.2.14.1.1
-- 1.3.6.1.4.1.37950.1.1.5.12.5.2.14.1.1
-- 1.3.6.1.4.1.37950.1.1.5.12.5.2.14.1.1
-- 1.3.6.1.4.1.37950.1.1.5.12.5.2.14.1.1
-- 1.3.6.1.4.1.37950.1.1.5.12.5.2.14.1.1
-- 1.3.6.1.4.1.37950.1.1.5.12.5.2.14.1.1
-- 1.3.6.1.4.1.37950.1.1.5.12.5.2.14.1.1
		-- 1.3.6.1.4.1.37950.1.1.5.12.5.2.14.1.1
		mcVlanPonNo OBJECT-TYPE
			SYNTAX INTEGER (1..16)
			MAX-ACCESS read-write
			STATUS current
			DESCRIPTION
				"Description."
			::= { mcVlanCfg 1 }

		
--          1.3.6.1.4.1.37950.1.1.5.12.5.2.14.1.2
-- 1.3.6.1.4.1.37950.1.1.5.12.5.2.14.1.2
-- 1.3.6.1.4.1.37950.1.1.5.12.5.2.14.1.2
-- 1.3.6.1.4.1.37950.1.1.5.12.5.2.14.1.2
-- 1.3.6.1.4.1.37950.1.1.5.12.5.2.14.1.2
-- 1.3.6.1.4.1.37950.1.1.5.12.5.2.14.1.2
-- 1.3.6.1.4.1.37950.1.1.5.12.5.2.14.1.2
-- 1.3.6.1.4.1.37950.1.1.5.12.5.2.14.1.2
-- 1.3.6.1.4.1.37950.1.1.5.12.5.2.14.1.2
		-- 1.3.6.1.4.1.37950.1.1.5.12.5.2.14.1.2
		mcVlanOnuNo OBJECT-TYPE
			SYNTAX INTEGER (1..65535)
			MAX-ACCESS read-write
			STATUS current
			DESCRIPTION
				"Description."
			::= { mcVlanCfg 2 }

		
--          1.3.6.1.4.1.37950.1.1.5.12.5.2.14.1.3
-- 1.3.6.1.4.1.37950.1.1.5.12.5.2.14.1.3
-- 1.3.6.1.4.1.37950.1.1.5.12.5.2.14.1.3
-- 1.3.6.1.4.1.37950.1.1.5.12.5.2.14.1.3
-- 1.3.6.1.4.1.37950.1.1.5.12.5.2.14.1.3
-- 1.3.6.1.4.1.37950.1.1.5.12.5.2.14.1.3
-- 1.3.6.1.4.1.37950.1.1.5.12.5.2.14.1.3
-- 1.3.6.1.4.1.37950.1.1.5.12.5.2.14.1.3
-- 1.3.6.1.4.1.37950.1.1.5.12.5.2.14.1.3
		-- 1.3.6.1.4.1.37950.1.1.5.12.5.2.14.1.3
		mcVlanPortNo OBJECT-TYPE
			SYNTAX INTEGER (1..255)
			MAX-ACCESS read-write
			STATUS current
			DESCRIPTION
				"Description."
			::= { mcVlanCfg 3 }

		
--          1.3.6.1.4.1.37950.1.1.5.12.5.2.14.1.4
-- 1.3.6.1.4.1.37950.1.1.5.12.5.2.14.1.4
-- 1.3.6.1.4.1.37950.1.1.5.12.5.2.14.1.4
-- 1.3.6.1.4.1.37950.1.1.5.12.5.2.14.1.4
-- 1.3.6.1.4.1.37950.1.1.5.12.5.2.14.1.4
-- 1.3.6.1.4.1.37950.1.1.5.12.5.2.14.1.4
-- 1.3.6.1.4.1.37950.1.1.5.12.5.2.14.1.4
-- 1.3.6.1.4.1.37950.1.1.5.12.5.2.14.1.4
-- 1.3.6.1.4.1.37950.1.1.5.12.5.2.14.1.4
		-- 1.3.6.1.4.1.37950.1.1.5.12.5.2.14.1.4
		mcVlanVal OBJECT-TYPE
			SYNTAX INTEGER (1..4095)
			MAX-ACCESS read-write
			STATUS current
			DESCRIPTION
				"Description."
			::= { mcVlanCfg 4 }

		
--          1.3.6.1.4.1.37950.1.1.5.12.5.2.14.1.5
-- 1.3.6.1.4.1.37950.1.1.5.12.5.2.14.1.5
-- 1.3.6.1.4.1.37950.1.1.5.12.5.2.14.1.5
-- 1.3.6.1.4.1.37950.1.1.5.12.5.2.14.1.5
-- 1.3.6.1.4.1.37950.1.1.5.12.5.2.14.1.5
-- 1.3.6.1.4.1.37950.1.1.5.12.5.2.14.1.5
-- 1.3.6.1.4.1.37950.1.1.5.12.5.2.14.1.5
-- 1.3.6.1.4.1.37950.1.1.5.12.5.2.14.1.5
-- 1.3.6.1.4.1.37950.1.1.5.12.5.2.14.1.5
		-- 1.3.6.1.4.1.37950.1.1.5.12.5.2.14.1.5
		mcVlanAction OBJECT-TYPE
			SYNTAX INTEGER
				{
				add(1),
				delete(2),
				clear(3)
				}
			MAX-ACCESS read-write
			STATUS current
			DESCRIPTION
				"Description."
			::= { mcVlanCfg 5 }

		
--          1.3.6.1.4.1.37950.1.1.5.12.5.2.14.2
-- 1.3.6.1.4.1.37950.1.1.5.12.5.2.14.2
-- 1.3.6.1.4.1.37950.1.1.5.12.5.2.14.2
-- 1.3.6.1.4.1.37950.1.1.5.12.5.2.14.2
-- 1.3.6.1.4.1.37950.1.1.5.12.5.2.14.2
-- 1.3.6.1.4.1.37950.1.1.5.12.5.2.14.2
-- 1.3.6.1.4.1.37950.1.1.5.12.5.2.14.2
-- 1.3.6.1.4.1.37950.1.1.5.12.5.2.14.2
-- 1.3.6.1.4.1.37950.1.1.5.12.5.2.14.2
		-- 1.3.6.1.4.1.37950.1.1.5.12.5.2.14.2
		mcVlanTable OBJECT-TYPE
			SYNTAX SEQUENCE OF McVlanEntry
			MAX-ACCESS not-accessible
			STATUS current
			DESCRIPTION
				"Description."
			::= { onuPortIgmpCfg 2 }

		
--          1.3.6.1.4.1.37950.1.1.5.12.5.2.14.2.1
-- 1.3.6.1.4.1.37950.1.1.5.12.5.2.14.2.1
-- 1.3.6.1.4.1.37950.1.1.5.12.5.2.14.2.1
-- 1.3.6.1.4.1.37950.1.1.5.12.5.2.14.2.1
-- 1.3.6.1.4.1.37950.1.1.5.12.5.2.14.2.1
-- 1.3.6.1.4.1.37950.1.1.5.12.5.2.14.2.1
-- 1.3.6.1.4.1.37950.1.1.5.12.5.2.14.2.1
-- 1.3.6.1.4.1.37950.1.1.5.12.5.2.14.2.1
-- 1.3.6.1.4.1.37950.1.1.5.12.5.2.14.2.1
		-- 1.3.6.1.4.1.37950.1.1.5.12.5.2.14.2.1
		mcVlanEntry OBJECT-TYPE
			SYNTAX McVlanEntry
			MAX-ACCESS not-accessible
			STATUS current
			DESCRIPTION
				"Description."
			INDEX { mVlanItem }
			::= { mcVlanTable 1 }

		
		McVlanEntry ::=
			SEQUENCE { 
				mVlanItem
					Integer32,
				mVlanPonNo
					INTEGER,
				mVlanOnuNo
					INTEGER,
				mVlanPortNo
					INTEGER,
				mVlanVal
					INTEGER
			 }

--          1.3.6.1.4.1.37950.1.1.5.12.5.2.14.2.1.1
-- 1.3.6.1.4.1.37950.1.1.5.12.5.2.14.2.1.1
-- 1.3.6.1.4.1.37950.1.1.5.12.5.2.14.2.1.1
-- 1.3.6.1.4.1.37950.1.1.5.12.5.2.14.2.1.1
-- 1.3.6.1.4.1.37950.1.1.5.12.5.2.14.2.1.1
-- 1.3.6.1.4.1.37950.1.1.5.12.5.2.14.2.1.1
-- 1.3.6.1.4.1.37950.1.1.5.12.5.2.14.2.1.1
-- 1.3.6.1.4.1.37950.1.1.5.12.5.2.14.2.1.1
-- 1.3.6.1.4.1.37950.1.1.5.12.5.2.14.2.1.1
		-- 1.3.6.1.4.1.37950.1.1.5.12.5.2.14.2.1.1
		mVlanItem OBJECT-TYPE
			SYNTAX Integer32
			MAX-ACCESS read-only
			STATUS current
			DESCRIPTION
				"Description."
			::= { mcVlanEntry 1 }

		
--          1.3.6.1.4.1.37950.1.1.5.12.5.2.14.2.1.2
-- 1.3.6.1.4.1.37950.1.1.5.12.5.2.14.2.1.2
-- 1.3.6.1.4.1.37950.1.1.5.12.5.2.14.2.1.2
-- 1.3.6.1.4.1.37950.1.1.5.12.5.2.14.2.1.2
-- 1.3.6.1.4.1.37950.1.1.5.12.5.2.14.2.1.2
-- 1.3.6.1.4.1.37950.1.1.5.12.5.2.14.2.1.2
-- 1.3.6.1.4.1.37950.1.1.5.12.5.2.14.2.1.2
-- 1.3.6.1.4.1.37950.1.1.5.12.5.2.14.2.1.2
-- 1.3.6.1.4.1.37950.1.1.5.12.5.2.14.2.1.2
		-- 1.3.6.1.4.1.37950.1.1.5.12.5.2.14.2.1.2
		mVlanPonNo OBJECT-TYPE
			SYNTAX INTEGER (1..16)
			MAX-ACCESS read-only
			STATUS current
			DESCRIPTION
				"Description."
			::= { mcVlanEntry 2 }

		
--          1.3.6.1.4.1.37950.1.1.5.12.5.2.14.2.1.3
-- 1.3.6.1.4.1.37950.1.1.5.12.5.2.14.2.1.3
-- 1.3.6.1.4.1.37950.1.1.5.12.5.2.14.2.1.3
-- 1.3.6.1.4.1.37950.1.1.5.12.5.2.14.2.1.3
-- 1.3.6.1.4.1.37950.1.1.5.12.5.2.14.2.1.3
-- 1.3.6.1.4.1.37950.1.1.5.12.5.2.14.2.1.3
-- 1.3.6.1.4.1.37950.1.1.5.12.5.2.14.2.1.3
-- 1.3.6.1.4.1.37950.1.1.5.12.5.2.14.2.1.3
-- 1.3.6.1.4.1.37950.1.1.5.12.5.2.14.2.1.3
		-- 1.3.6.1.4.1.37950.1.1.5.12.5.2.14.2.1.3
		mVlanOnuNo OBJECT-TYPE
			SYNTAX INTEGER (1..65535)
			MAX-ACCESS read-only
			STATUS current
			DESCRIPTION
				"Description."
			::= { mcVlanEntry 3 }

		
--          1.3.6.1.4.1.37950.1.1.5.12.5.2.14.2.1.4
-- 1.3.6.1.4.1.37950.1.1.5.12.5.2.14.2.1.4
-- 1.3.6.1.4.1.37950.1.1.5.12.5.2.14.2.1.4
-- 1.3.6.1.4.1.37950.1.1.5.12.5.2.14.2.1.4
-- 1.3.6.1.4.1.37950.1.1.5.12.5.2.14.2.1.4
-- 1.3.6.1.4.1.37950.1.1.5.12.5.2.14.2.1.4
-- 1.3.6.1.4.1.37950.1.1.5.12.5.2.14.2.1.4
-- 1.3.6.1.4.1.37950.1.1.5.12.5.2.14.2.1.4
-- 1.3.6.1.4.1.37950.1.1.5.12.5.2.14.2.1.4
		-- 1.3.6.1.4.1.37950.1.1.5.12.5.2.14.2.1.4
		mVlanPortNo OBJECT-TYPE
			SYNTAX INTEGER (1..65535)
			MAX-ACCESS read-only
			STATUS current
			DESCRIPTION
				"Description."
			::= { mcVlanEntry 4 }

		
--          1.3.6.1.4.1.37950.1.1.5.12.5.2.14.2.1.5
-- 1.3.6.1.4.1.37950.1.1.5.12.5.2.14.2.1.5
-- 1.3.6.1.4.1.37950.1.1.5.12.5.2.14.2.1.5
-- 1.3.6.1.4.1.37950.1.1.5.12.5.2.14.2.1.5
-- 1.3.6.1.4.1.37950.1.1.5.12.5.2.14.2.1.5
-- 1.3.6.1.4.1.37950.1.1.5.12.5.2.14.2.1.5
-- 1.3.6.1.4.1.37950.1.1.5.12.5.2.14.2.1.5
-- 1.3.6.1.4.1.37950.1.1.5.12.5.2.14.2.1.5
-- 1.3.6.1.4.1.37950.1.1.5.12.5.2.14.2.1.5
		-- 1.3.6.1.4.1.37950.1.1.5.12.5.2.14.2.1.5
		mVlanVal OBJECT-TYPE
			SYNTAX INTEGER (1..4095)
			MAX-ACCESS read-only
			STATUS current
			DESCRIPTION
				"Description."
			::= { mcVlanEntry 5 }

		
--          1.3.6.1.4.1.37950.1.1.5.12.5.2.14.3
-- 1.3.6.1.4.1.37950.1.1.5.12.5.2.14.3
-- 1.3.6.1.4.1.37950.1.1.5.12.5.2.14.3
-- 1.3.6.1.4.1.37950.1.1.5.12.5.2.14.3
-- 1.3.6.1.4.1.37950.1.1.5.12.5.2.14.3
-- 1.3.6.1.4.1.37950.1.1.5.12.5.2.14.3
-- 1.3.6.1.4.1.37950.1.1.5.12.5.2.14.3
-- 1.3.6.1.4.1.37950.1.1.5.12.5.2.14.3
-- 1.3.6.1.4.1.37950.1.1.5.12.5.2.14.3
		-- 1.3.6.1.4.1.37950.1.1.5.12.5.2.14.3
		mcMaxGroupCfg OBJECT IDENTIFIER ::= { onuPortIgmpCfg 3 }

		
--          1.3.6.1.4.1.37950.1.1.5.12.5.2.14.3.1
-- 1.3.6.1.4.1.37950.1.1.5.12.5.2.14.3.1
-- 1.3.6.1.4.1.37950.1.1.5.12.5.2.14.3.1
-- 1.3.6.1.4.1.37950.1.1.5.12.5.2.14.3.1
-- 1.3.6.1.4.1.37950.1.1.5.12.5.2.14.3.1
-- 1.3.6.1.4.1.37950.1.1.5.12.5.2.14.3.1
-- 1.3.6.1.4.1.37950.1.1.5.12.5.2.14.3.1
-- 1.3.6.1.4.1.37950.1.1.5.12.5.2.14.3.1
-- 1.3.6.1.4.1.37950.1.1.5.12.5.2.14.3.1
		-- 1.3.6.1.4.1.37950.1.1.5.12.5.2.14.3.1
		maxgrpPonNo OBJECT-TYPE
			SYNTAX INTEGER (1..16)
			MAX-ACCESS read-write
			STATUS current
			DESCRIPTION
				"Description."
			::= { mcMaxGroupCfg 1 }

		
--          1.3.6.1.4.1.37950.1.1.5.12.5.2.14.3.2
-- 1.3.6.1.4.1.37950.1.1.5.12.5.2.14.3.2
-- 1.3.6.1.4.1.37950.1.1.5.12.5.2.14.3.2
-- 1.3.6.1.4.1.37950.1.1.5.12.5.2.14.3.2
-- 1.3.6.1.4.1.37950.1.1.5.12.5.2.14.3.2
-- 1.3.6.1.4.1.37950.1.1.5.12.5.2.14.3.2
-- 1.3.6.1.4.1.37950.1.1.5.12.5.2.14.3.2
-- 1.3.6.1.4.1.37950.1.1.5.12.5.2.14.3.2
-- 1.3.6.1.4.1.37950.1.1.5.12.5.2.14.3.2
		-- 1.3.6.1.4.1.37950.1.1.5.12.5.2.14.3.2
		maxgrpOnuNo OBJECT-TYPE
			SYNTAX INTEGER (1..65535)
			MAX-ACCESS read-write
			STATUS current
			DESCRIPTION
				"Description."
			::= { mcMaxGroupCfg 2 }

		
--          1.3.6.1.4.1.37950.1.1.5.12.5.2.14.3.3
-- 1.3.6.1.4.1.37950.1.1.5.12.5.2.14.3.3
-- 1.3.6.1.4.1.37950.1.1.5.12.5.2.14.3.3
-- 1.3.6.1.4.1.37950.1.1.5.12.5.2.14.3.3
-- 1.3.6.1.4.1.37950.1.1.5.12.5.2.14.3.3
-- 1.3.6.1.4.1.37950.1.1.5.12.5.2.14.3.3
-- 1.3.6.1.4.1.37950.1.1.5.12.5.2.14.3.3
-- 1.3.6.1.4.1.37950.1.1.5.12.5.2.14.3.3
-- 1.3.6.1.4.1.37950.1.1.5.12.5.2.14.3.3
		-- 1.3.6.1.4.1.37950.1.1.5.12.5.2.14.3.3
		maxgrpPortNo OBJECT-TYPE
			SYNTAX INTEGER (1..255)
			MAX-ACCESS read-write
			STATUS current
			DESCRIPTION
				"Description."
			::= { mcMaxGroupCfg 3 }

		
--          1.3.6.1.4.1.37950.1.1.5.12.5.2.14.3.4
-- 1.3.6.1.4.1.37950.1.1.5.12.5.2.14.3.4
-- 1.3.6.1.4.1.37950.1.1.5.12.5.2.14.3.4
-- 1.3.6.1.4.1.37950.1.1.5.12.5.2.14.3.4
-- 1.3.6.1.4.1.37950.1.1.5.12.5.2.14.3.4
-- 1.3.6.1.4.1.37950.1.1.5.12.5.2.14.3.4
-- 1.3.6.1.4.1.37950.1.1.5.12.5.2.14.3.4
-- 1.3.6.1.4.1.37950.1.1.5.12.5.2.14.3.4
-- 1.3.6.1.4.1.37950.1.1.5.12.5.2.14.3.4
		-- 1.3.6.1.4.1.37950.1.1.5.12.5.2.14.3.4
		maxgrpVal OBJECT-TYPE
			SYNTAX INTEGER (0..4096)
			MAX-ACCESS read-write
			STATUS current
			DESCRIPTION
				"Description."
			::= { mcMaxGroupCfg 4 }

		
--          1.3.6.1.4.1.37950.1.1.5.12.5.2.14.4
-- 1.3.6.1.4.1.37950.1.1.5.12.5.2.14.4
-- 1.3.6.1.4.1.37950.1.1.5.12.5.2.14.4
-- 1.3.6.1.4.1.37950.1.1.5.12.5.2.14.4
-- 1.3.6.1.4.1.37950.1.1.5.12.5.2.14.4
-- 1.3.6.1.4.1.37950.1.1.5.12.5.2.14.4
-- 1.3.6.1.4.1.37950.1.1.5.12.5.2.14.4
-- 1.3.6.1.4.1.37950.1.1.5.12.5.2.14.4
-- 1.3.6.1.4.1.37950.1.1.5.12.5.2.14.4
		-- 1.3.6.1.4.1.37950.1.1.5.12.5.2.14.4
		mcTagstrip OBJECT IDENTIFIER ::= { onuPortIgmpCfg 4 }

		
--          1.3.6.1.4.1.37950.1.1.5.12.5.2.14.4.1
-- 1.3.6.1.4.1.37950.1.1.5.12.5.2.14.4.1
-- 1.3.6.1.4.1.37950.1.1.5.12.5.2.14.4.1
-- 1.3.6.1.4.1.37950.1.1.5.12.5.2.14.4.1
-- 1.3.6.1.4.1.37950.1.1.5.12.5.2.14.4.1
-- 1.3.6.1.4.1.37950.1.1.5.12.5.2.14.4.1
-- 1.3.6.1.4.1.37950.1.1.5.12.5.2.14.4.1
-- 1.3.6.1.4.1.37950.1.1.5.12.5.2.14.4.1
-- 1.3.6.1.4.1.37950.1.1.5.12.5.2.14.4.1
		-- 1.3.6.1.4.1.37950.1.1.5.12.5.2.14.4.1
		tagstripPonNo OBJECT-TYPE
			SYNTAX INTEGER (1..16)
			MAX-ACCESS read-write
			STATUS current
			DESCRIPTION
				"Description."
			::= { mcTagstrip 1 }

		
--          1.3.6.1.4.1.37950.1.1.5.12.5.2.14.4.2
-- 1.3.6.1.4.1.37950.1.1.5.12.5.2.14.4.2
-- 1.3.6.1.4.1.37950.1.1.5.12.5.2.14.4.2
-- 1.3.6.1.4.1.37950.1.1.5.12.5.2.14.4.2
-- 1.3.6.1.4.1.37950.1.1.5.12.5.2.14.4.2
-- 1.3.6.1.4.1.37950.1.1.5.12.5.2.14.4.2
-- 1.3.6.1.4.1.37950.1.1.5.12.5.2.14.4.2
-- 1.3.6.1.4.1.37950.1.1.5.12.5.2.14.4.2
-- 1.3.6.1.4.1.37950.1.1.5.12.5.2.14.4.2
		-- 1.3.6.1.4.1.37950.1.1.5.12.5.2.14.4.2
		tagstripOnuNo OBJECT-TYPE
			SYNTAX INTEGER (1..65535)
			MAX-ACCESS read-write
			STATUS current
			DESCRIPTION
				"Description."
			::= { mcTagstrip 2 }

		
--          1.3.6.1.4.1.37950.1.1.5.12.5.2.14.4.3
-- 1.3.6.1.4.1.37950.1.1.5.12.5.2.14.4.3
-- 1.3.6.1.4.1.37950.1.1.5.12.5.2.14.4.3
-- 1.3.6.1.4.1.37950.1.1.5.12.5.2.14.4.3
-- 1.3.6.1.4.1.37950.1.1.5.12.5.2.14.4.3
-- 1.3.6.1.4.1.37950.1.1.5.12.5.2.14.4.3
-- 1.3.6.1.4.1.37950.1.1.5.12.5.2.14.4.3
-- 1.3.6.1.4.1.37950.1.1.5.12.5.2.14.4.3
-- 1.3.6.1.4.1.37950.1.1.5.12.5.2.14.4.3
		-- 1.3.6.1.4.1.37950.1.1.5.12.5.2.14.4.3
		tagstripPortNo OBJECT-TYPE
			SYNTAX INTEGER (1..255)
			MAX-ACCESS read-write
			STATUS current
			DESCRIPTION
				"Description."
			::= { mcTagstrip 3 }

		
--          1.3.6.1.4.1.37950.1.1.5.12.5.2.14.4.4
-- 1.3.6.1.4.1.37950.1.1.5.12.5.2.14.4.4
-- 1.3.6.1.4.1.37950.1.1.5.12.5.2.14.4.4
-- 1.3.6.1.4.1.37950.1.1.5.12.5.2.14.4.4
-- 1.3.6.1.4.1.37950.1.1.5.12.5.2.14.4.4
-- 1.3.6.1.4.1.37950.1.1.5.12.5.2.14.4.4
-- 1.3.6.1.4.1.37950.1.1.5.12.5.2.14.4.4
-- 1.3.6.1.4.1.37950.1.1.5.12.5.2.14.4.4
-- 1.3.6.1.4.1.37950.1.1.5.12.5.2.14.4.4
		-- 1.3.6.1.4.1.37950.1.1.5.12.5.2.14.4.4
		tagstripGroupVlan0 OBJECT-TYPE
			SYNTAX Integer32 (0..4095)
			MAX-ACCESS read-write
			STATUS current
			DESCRIPTION
				"Description."
			::= { mcTagstrip 4 }

		
--          1.3.6.1.4.1.37950.1.1.5.12.5.2.14.4.5
-- 1.3.6.1.4.1.37950.1.1.5.12.5.2.14.4.5
-- 1.3.6.1.4.1.37950.1.1.5.12.5.2.14.4.5
-- 1.3.6.1.4.1.37950.1.1.5.12.5.2.14.4.5
-- 1.3.6.1.4.1.37950.1.1.5.12.5.2.14.4.5
-- 1.3.6.1.4.1.37950.1.1.5.12.5.2.14.4.5
-- 1.3.6.1.4.1.37950.1.1.5.12.5.2.14.4.5
-- 1.3.6.1.4.1.37950.1.1.5.12.5.2.14.4.5
-- 1.3.6.1.4.1.37950.1.1.5.12.5.2.14.4.5
		-- 1.3.6.1.4.1.37950.1.1.5.12.5.2.14.4.5
		tagstripUserVlan0 OBJECT-TYPE
			SYNTAX Integer32 (0..4095)
			MAX-ACCESS read-write
			STATUS current
			DESCRIPTION
				"Description."
			::= { mcTagstrip 5 }

		
--          1.3.6.1.4.1.37950.1.1.5.12.5.2.14.4.6
-- 1.3.6.1.4.1.37950.1.1.5.12.5.2.14.4.6
-- 1.3.6.1.4.1.37950.1.1.5.12.5.2.14.4.6
-- 1.3.6.1.4.1.37950.1.1.5.12.5.2.14.4.6
-- 1.3.6.1.4.1.37950.1.1.5.12.5.2.14.4.6
-- 1.3.6.1.4.1.37950.1.1.5.12.5.2.14.4.6
-- 1.3.6.1.4.1.37950.1.1.5.12.5.2.14.4.6
-- 1.3.6.1.4.1.37950.1.1.5.12.5.2.14.4.6
-- 1.3.6.1.4.1.37950.1.1.5.12.5.2.14.4.6
		-- 1.3.6.1.4.1.37950.1.1.5.12.5.2.14.4.6
		tagstripGroupVlan1 OBJECT-TYPE
			SYNTAX Integer32 (0..4095)
			MAX-ACCESS read-write
			STATUS current
			DESCRIPTION
				"Description."
			::= { mcTagstrip 6 }

		
--          1.3.6.1.4.1.37950.1.1.5.12.5.2.14.4.7
-- 1.3.6.1.4.1.37950.1.1.5.12.5.2.14.4.7
-- 1.3.6.1.4.1.37950.1.1.5.12.5.2.14.4.7
-- 1.3.6.1.4.1.37950.1.1.5.12.5.2.14.4.7
-- 1.3.6.1.4.1.37950.1.1.5.12.5.2.14.4.7
-- 1.3.6.1.4.1.37950.1.1.5.12.5.2.14.4.7
-- 1.3.6.1.4.1.37950.1.1.5.12.5.2.14.4.7
-- 1.3.6.1.4.1.37950.1.1.5.12.5.2.14.4.7
-- 1.3.6.1.4.1.37950.1.1.5.12.5.2.14.4.7
		-- 1.3.6.1.4.1.37950.1.1.5.12.5.2.14.4.7
		tagstripUserVlan1 OBJECT-TYPE
			SYNTAX Integer32 (0..4095)
			MAX-ACCESS read-write
			STATUS current
			DESCRIPTION
				"Description."
			::= { mcTagstrip 7 }

		
--          1.3.6.1.4.1.37950.1.1.5.12.5.2.14.4.8
-- 1.3.6.1.4.1.37950.1.1.5.12.5.2.14.4.8
-- 1.3.6.1.4.1.37950.1.1.5.12.5.2.14.4.8
-- 1.3.6.1.4.1.37950.1.1.5.12.5.2.14.4.8
-- 1.3.6.1.4.1.37950.1.1.5.12.5.2.14.4.8
-- 1.3.6.1.4.1.37950.1.1.5.12.5.2.14.4.8
-- 1.3.6.1.4.1.37950.1.1.5.12.5.2.14.4.8
-- 1.3.6.1.4.1.37950.1.1.5.12.5.2.14.4.8
-- 1.3.6.1.4.1.37950.1.1.5.12.5.2.14.4.8
		-- 1.3.6.1.4.1.37950.1.1.5.12.5.2.14.4.8
		tagstripGroupVlan2 OBJECT-TYPE
			SYNTAX Integer32 (0..4095)
			MAX-ACCESS read-write
			STATUS current
			DESCRIPTION
				"Description."
			::= { mcTagstrip 8 }

		
--          1.3.6.1.4.1.37950.1.1.5.12.5.2.14.4.9
-- 1.3.6.1.4.1.37950.1.1.5.12.5.2.14.4.9
-- 1.3.6.1.4.1.37950.1.1.5.12.5.2.14.4.9
-- 1.3.6.1.4.1.37950.1.1.5.12.5.2.14.4.9
-- 1.3.6.1.4.1.37950.1.1.5.12.5.2.14.4.9
-- 1.3.6.1.4.1.37950.1.1.5.12.5.2.14.4.9
-- 1.3.6.1.4.1.37950.1.1.5.12.5.2.14.4.9
-- 1.3.6.1.4.1.37950.1.1.5.12.5.2.14.4.9
-- 1.3.6.1.4.1.37950.1.1.5.12.5.2.14.4.9
		-- 1.3.6.1.4.1.37950.1.1.5.12.5.2.14.4.9
		tagstripUserVlan2 OBJECT-TYPE
			SYNTAX Integer32 (0..4095)
			MAX-ACCESS read-write
			STATUS current
			DESCRIPTION
				"Description."
			::= { mcTagstrip 9 }

		
--          1.3.6.1.4.1.37950.1.1.5.12.5.2.14.4.10
-- 1.3.6.1.4.1.37950.1.1.5.12.5.2.14.4.10
-- 1.3.6.1.4.1.37950.1.1.5.12.5.2.14.4.10
-- 1.3.6.1.4.1.37950.1.1.5.12.5.2.14.4.10
-- 1.3.6.1.4.1.37950.1.1.5.12.5.2.14.4.10
-- 1.3.6.1.4.1.37950.1.1.5.12.5.2.14.4.10
-- 1.3.6.1.4.1.37950.1.1.5.12.5.2.14.4.10
-- 1.3.6.1.4.1.37950.1.1.5.12.5.2.14.4.10
-- 1.3.6.1.4.1.37950.1.1.5.12.5.2.14.4.10
		-- 1.3.6.1.4.1.37950.1.1.5.12.5.2.14.4.10
		tagstripGroupVlan3 OBJECT-TYPE
			SYNTAX Integer32 (0..4095)
			MAX-ACCESS read-write
			STATUS current
			DESCRIPTION
				"Description."
			::= { mcTagstrip 10 }

		
--          1.3.6.1.4.1.37950.1.1.5.12.5.2.14.4.11
-- 1.3.6.1.4.1.37950.1.1.5.12.5.2.14.4.11
-- 1.3.6.1.4.1.37950.1.1.5.12.5.2.14.4.11
-- 1.3.6.1.4.1.37950.1.1.5.12.5.2.14.4.11
-- 1.3.6.1.4.1.37950.1.1.5.12.5.2.14.4.11
-- 1.3.6.1.4.1.37950.1.1.5.12.5.2.14.4.11
-- 1.3.6.1.4.1.37950.1.1.5.12.5.2.14.4.11
-- 1.3.6.1.4.1.37950.1.1.5.12.5.2.14.4.11
-- 1.3.6.1.4.1.37950.1.1.5.12.5.2.14.4.11
		-- 1.3.6.1.4.1.37950.1.1.5.12.5.2.14.4.11
		tagstripUserVlan3 OBJECT-TYPE
			SYNTAX Integer32 (0..4095)
			MAX-ACCESS read-write
			STATUS current
			DESCRIPTION
				"Description."
			::= { mcTagstrip 11 }

		
--          1.3.6.1.4.1.37950.1.1.5.12.5.2.14.4.12
-- 1.3.6.1.4.1.37950.1.1.5.12.5.2.14.4.12
-- 1.3.6.1.4.1.37950.1.1.5.12.5.2.14.4.12
-- 1.3.6.1.4.1.37950.1.1.5.12.5.2.14.4.12
-- 1.3.6.1.4.1.37950.1.1.5.12.5.2.14.4.12
-- 1.3.6.1.4.1.37950.1.1.5.12.5.2.14.4.12
-- 1.3.6.1.4.1.37950.1.1.5.12.5.2.14.4.12
-- 1.3.6.1.4.1.37950.1.1.5.12.5.2.14.4.12
-- 1.3.6.1.4.1.37950.1.1.5.12.5.2.14.4.12
		-- 1.3.6.1.4.1.37950.1.1.5.12.5.2.14.4.12
		tagstripGroupVlan4 OBJECT-TYPE
			SYNTAX Integer32 (0..4095)
			MAX-ACCESS read-write
			STATUS current
			DESCRIPTION
				"Description."
			::= { mcTagstrip 12 }

		
--          1.3.6.1.4.1.37950.1.1.5.12.5.2.14.4.13
-- 1.3.6.1.4.1.37950.1.1.5.12.5.2.14.4.13
-- 1.3.6.1.4.1.37950.1.1.5.12.5.2.14.4.13
-- 1.3.6.1.4.1.37950.1.1.5.12.5.2.14.4.13
-- 1.3.6.1.4.1.37950.1.1.5.12.5.2.14.4.13
-- 1.3.6.1.4.1.37950.1.1.5.12.5.2.14.4.13
-- 1.3.6.1.4.1.37950.1.1.5.12.5.2.14.4.13
-- 1.3.6.1.4.1.37950.1.1.5.12.5.2.14.4.13
-- 1.3.6.1.4.1.37950.1.1.5.12.5.2.14.4.13
		-- 1.3.6.1.4.1.37950.1.1.5.12.5.2.14.4.13
		tagstripUserVlan4 OBJECT-TYPE
			SYNTAX Integer32 (0..4095)
			MAX-ACCESS read-write
			STATUS current
			DESCRIPTION
				"Description."
			::= { mcTagstrip 13 }

		
--          1.3.6.1.4.1.37950.1.1.5.12.5.2.14.4.14
-- 1.3.6.1.4.1.37950.1.1.5.12.5.2.14.4.14
-- 1.3.6.1.4.1.37950.1.1.5.12.5.2.14.4.14
-- 1.3.6.1.4.1.37950.1.1.5.12.5.2.14.4.14
-- 1.3.6.1.4.1.37950.1.1.5.12.5.2.14.4.14
-- 1.3.6.1.4.1.37950.1.1.5.12.5.2.14.4.14
-- 1.3.6.1.4.1.37950.1.1.5.12.5.2.14.4.14
-- 1.3.6.1.4.1.37950.1.1.5.12.5.2.14.4.14
-- 1.3.6.1.4.1.37950.1.1.5.12.5.2.14.4.14
		-- 1.3.6.1.4.1.37950.1.1.5.12.5.2.14.4.14
		tagstripGroupVlan5 OBJECT-TYPE
			SYNTAX Integer32 (0..4095)
			MAX-ACCESS read-write
			STATUS current
			DESCRIPTION
				"Description."
			::= { mcTagstrip 14 }

		
--          1.3.6.1.4.1.37950.1.1.5.12.5.2.14.4.15
-- 1.3.6.1.4.1.37950.1.1.5.12.5.2.14.4.15
-- 1.3.6.1.4.1.37950.1.1.5.12.5.2.14.4.15
-- 1.3.6.1.4.1.37950.1.1.5.12.5.2.14.4.15
-- 1.3.6.1.4.1.37950.1.1.5.12.5.2.14.4.15
-- 1.3.6.1.4.1.37950.1.1.5.12.5.2.14.4.15
-- 1.3.6.1.4.1.37950.1.1.5.12.5.2.14.4.15
-- 1.3.6.1.4.1.37950.1.1.5.12.5.2.14.4.15
-- 1.3.6.1.4.1.37950.1.1.5.12.5.2.14.4.15
		-- 1.3.6.1.4.1.37950.1.1.5.12.5.2.14.4.15
		tagstripUserVlan5 OBJECT-TYPE
			SYNTAX Integer32 (0..4095)
			MAX-ACCESS read-write
			STATUS current
			DESCRIPTION
				"Description."
			::= { mcTagstrip 15 }

		
--          1.3.6.1.4.1.37950.1.1.5.12.5.2.14.4.16
-- 1.3.6.1.4.1.37950.1.1.5.12.5.2.14.4.16
-- 1.3.6.1.4.1.37950.1.1.5.12.5.2.14.4.16
-- 1.3.6.1.4.1.37950.1.1.5.12.5.2.14.4.16
-- 1.3.6.1.4.1.37950.1.1.5.12.5.2.14.4.16
-- 1.3.6.1.4.1.37950.1.1.5.12.5.2.14.4.16
-- 1.3.6.1.4.1.37950.1.1.5.12.5.2.14.4.16
-- 1.3.6.1.4.1.37950.1.1.5.12.5.2.14.4.16
-- 1.3.6.1.4.1.37950.1.1.5.12.5.2.14.4.16
		-- 1.3.6.1.4.1.37950.1.1.5.12.5.2.14.4.16
		tagstripGroupVlan6 OBJECT-TYPE
			SYNTAX Integer32 (0..4095)
			MAX-ACCESS read-write
			STATUS current
			DESCRIPTION
				"Description."
			::= { mcTagstrip 16 }

		
--          1.3.6.1.4.1.37950.1.1.5.12.5.2.14.4.17
-- 1.3.6.1.4.1.37950.1.1.5.12.5.2.14.4.17
-- 1.3.6.1.4.1.37950.1.1.5.12.5.2.14.4.17
-- 1.3.6.1.4.1.37950.1.1.5.12.5.2.14.4.17
-- 1.3.6.1.4.1.37950.1.1.5.12.5.2.14.4.17
-- 1.3.6.1.4.1.37950.1.1.5.12.5.2.14.4.17
-- 1.3.6.1.4.1.37950.1.1.5.12.5.2.14.4.17
-- 1.3.6.1.4.1.37950.1.1.5.12.5.2.14.4.17
-- 1.3.6.1.4.1.37950.1.1.5.12.5.2.14.4.17
		-- 1.3.6.1.4.1.37950.1.1.5.12.5.2.14.4.17
		tagstripUserVlan6 OBJECT-TYPE
			SYNTAX Integer32 (0..4095)
			MAX-ACCESS read-write
			STATUS current
			DESCRIPTION
				"Description."
			::= { mcTagstrip 17 }

		
--          1.3.6.1.4.1.37950.1.1.5.12.5.2.14.4.18
-- 1.3.6.1.4.1.37950.1.1.5.12.5.2.14.4.18
-- 1.3.6.1.4.1.37950.1.1.5.12.5.2.14.4.18
-- 1.3.6.1.4.1.37950.1.1.5.12.5.2.14.4.18
-- 1.3.6.1.4.1.37950.1.1.5.12.5.2.14.4.18
-- 1.3.6.1.4.1.37950.1.1.5.12.5.2.14.4.18
-- 1.3.6.1.4.1.37950.1.1.5.12.5.2.14.4.18
-- 1.3.6.1.4.1.37950.1.1.5.12.5.2.14.4.18
-- 1.3.6.1.4.1.37950.1.1.5.12.5.2.14.4.18
		-- 1.3.6.1.4.1.37950.1.1.5.12.5.2.14.4.18
		tagstripGroupVlan7 OBJECT-TYPE
			SYNTAX Integer32 (0..4095)
			MAX-ACCESS read-write
			STATUS current
			DESCRIPTION
				"Description."
			::= { mcTagstrip 18 }

		
--          1.3.6.1.4.1.37950.1.1.5.12.5.2.14.4.19
-- 1.3.6.1.4.1.37950.1.1.5.12.5.2.14.4.19
-- 1.3.6.1.4.1.37950.1.1.5.12.5.2.14.4.19
-- 1.3.6.1.4.1.37950.1.1.5.12.5.2.14.4.19
-- 1.3.6.1.4.1.37950.1.1.5.12.5.2.14.4.19
-- 1.3.6.1.4.1.37950.1.1.5.12.5.2.14.4.19
-- 1.3.6.1.4.1.37950.1.1.5.12.5.2.14.4.19
-- 1.3.6.1.4.1.37950.1.1.5.12.5.2.14.4.19
-- 1.3.6.1.4.1.37950.1.1.5.12.5.2.14.4.19
		-- 1.3.6.1.4.1.37950.1.1.5.12.5.2.14.4.19
		tagstripUserVlan7 OBJECT-TYPE
			SYNTAX Integer32 (0..4095)
			MAX-ACCESS read-write
			STATUS current
			DESCRIPTION
				"Description."
			::= { mcTagstrip 19 }

		
--          1.3.6.1.4.1.37950.1.1.5.12.5.2.14.4.20
-- 1.3.6.1.4.1.37950.1.1.5.12.5.2.14.4.20
-- 1.3.6.1.4.1.37950.1.1.5.12.5.2.14.4.20
-- 1.3.6.1.4.1.37950.1.1.5.12.5.2.14.4.20
-- 1.3.6.1.4.1.37950.1.1.5.12.5.2.14.4.20
-- 1.3.6.1.4.1.37950.1.1.5.12.5.2.14.4.20
-- 1.3.6.1.4.1.37950.1.1.5.12.5.2.14.4.20
-- 1.3.6.1.4.1.37950.1.1.5.12.5.2.14.4.20
-- 1.3.6.1.4.1.37950.1.1.5.12.5.2.14.4.20
		-- 1.3.6.1.4.1.37950.1.1.5.12.5.2.14.4.20
		tagstripMode OBJECT-TYPE
			SYNTAX INTEGER
				{
				disable(0),
				enable(1),
				tagStrip(2)
				}
			MAX-ACCESS read-write
			STATUS current
			DESCRIPTION
				"Description."
			::= { mcTagstrip 20 }

		
--          1.3.6.1.4.1.37950.1.1.5.12.5.2.14.5
-- 1.3.6.1.4.1.37950.1.1.5.12.5.2.14.5
-- 1.3.6.1.4.1.37950.1.1.5.12.5.2.14.5
-- 1.3.6.1.4.1.37950.1.1.5.12.5.2.14.5
-- 1.3.6.1.4.1.37950.1.1.5.12.5.2.14.5
-- 1.3.6.1.4.1.37950.1.1.5.12.5.2.14.5
-- 1.3.6.1.4.1.37950.1.1.5.12.5.2.14.5
-- 1.3.6.1.4.1.37950.1.1.5.12.5.2.14.5
-- 1.3.6.1.4.1.37950.1.1.5.12.5.2.14.5
		-- 1.3.6.1.4.1.37950.1.1.5.12.5.2.14.5
		mcVlanTagStripTable OBJECT-TYPE
			SYNTAX SEQUENCE OF McVlanTagStripEntry
			MAX-ACCESS not-accessible
			STATUS current
			DESCRIPTION
				"Description."
			::= { onuPortIgmpCfg 5 }

		
--          1.3.6.1.4.1.37950.1.1.5.12.5.2.14.5.1
-- 1.3.6.1.4.1.37950.1.1.5.12.5.2.14.5.1
-- 1.3.6.1.4.1.37950.1.1.5.12.5.2.14.5.1
-- 1.3.6.1.4.1.37950.1.1.5.12.5.2.14.5.1
-- 1.3.6.1.4.1.37950.1.1.5.12.5.2.14.5.1
-- 1.3.6.1.4.1.37950.1.1.5.12.5.2.14.5.1
-- 1.3.6.1.4.1.37950.1.1.5.12.5.2.14.5.1
-- 1.3.6.1.4.1.37950.1.1.5.12.5.2.14.5.1
-- 1.3.6.1.4.1.37950.1.1.5.12.5.2.14.5.1
		-- 1.3.6.1.4.1.37950.1.1.5.12.5.2.14.5.1
		mcVlanTagStripEntry OBJECT-TYPE
			SYNTAX McVlanTagStripEntry
			MAX-ACCESS not-accessible
			STATUS current
			DESCRIPTION
				"Description."
			INDEX { mVlanTagsPonNo, mVlanTagsOnuNo, mVlanTagsPortNo }
			::= { mcVlanTagStripTable 1 }

		
		McVlanTagStripEntry ::=
			SEQUENCE { 
				mVlanTagsPonNo
					INTEGER,
				mVlanTagsOnuNo
					INTEGER,
				mVlanTagsPortNo
					INTEGER,
				mVlanTagsMode
					INTEGER,
				mVlanTagsVlanTrans
					OCTET STRING
			 }

--          1.3.6.1.4.1.37950.1.1.5.12.5.2.14.5.1.1
-- 1.3.6.1.4.1.37950.1.1.5.12.5.2.14.5.1.1
-- 1.3.6.1.4.1.37950.1.1.5.12.5.2.14.5.1.1
-- 1.3.6.1.4.1.37950.1.1.5.12.5.2.14.5.1.1
-- 1.3.6.1.4.1.37950.1.1.5.12.5.2.14.5.1.1
-- 1.3.6.1.4.1.37950.1.1.5.12.5.2.14.5.1.1
-- 1.3.6.1.4.1.37950.1.1.5.12.5.2.14.5.1.1
-- 1.3.6.1.4.1.37950.1.1.5.12.5.2.14.5.1.1
-- 1.3.6.1.4.1.37950.1.1.5.12.5.2.14.5.1.1
		-- 1.3.6.1.4.1.37950.1.1.5.12.5.2.14.5.1.1
		mVlanTagsPonNo OBJECT-TYPE
			SYNTAX INTEGER (1..16)
			MAX-ACCESS read-only
			STATUS current
			DESCRIPTION
				"Description."
			::= { mcVlanTagStripEntry 1 }

		
--          1.3.6.1.4.1.37950.1.1.5.12.5.2.14.5.1.2
-- 1.3.6.1.4.1.37950.1.1.5.12.5.2.14.5.1.2
-- 1.3.6.1.4.1.37950.1.1.5.12.5.2.14.5.1.2
-- 1.3.6.1.4.1.37950.1.1.5.12.5.2.14.5.1.2
-- 1.3.6.1.4.1.37950.1.1.5.12.5.2.14.5.1.2
-- 1.3.6.1.4.1.37950.1.1.5.12.5.2.14.5.1.2
-- 1.3.6.1.4.1.37950.1.1.5.12.5.2.14.5.1.2
-- 1.3.6.1.4.1.37950.1.1.5.12.5.2.14.5.1.2
-- 1.3.6.1.4.1.37950.1.1.5.12.5.2.14.5.1.2
		-- 1.3.6.1.4.1.37950.1.1.5.12.5.2.14.5.1.2
		mVlanTagsOnuNo OBJECT-TYPE
			SYNTAX INTEGER (1..65535)
			MAX-ACCESS read-only
			STATUS current
			DESCRIPTION
				"Description."
			::= { mcVlanTagStripEntry 2 }

		
--          1.3.6.1.4.1.37950.1.1.5.12.5.2.14.5.1.3
-- 1.3.6.1.4.1.37950.1.1.5.12.5.2.14.5.1.3
-- 1.3.6.1.4.1.37950.1.1.5.12.5.2.14.5.1.3
-- 1.3.6.1.4.1.37950.1.1.5.12.5.2.14.5.1.3
-- 1.3.6.1.4.1.37950.1.1.5.12.5.2.14.5.1.3
-- 1.3.6.1.4.1.37950.1.1.5.12.5.2.14.5.1.3
-- 1.3.6.1.4.1.37950.1.1.5.12.5.2.14.5.1.3
-- 1.3.6.1.4.1.37950.1.1.5.12.5.2.14.5.1.3
-- 1.3.6.1.4.1.37950.1.1.5.12.5.2.14.5.1.3
		-- 1.3.6.1.4.1.37950.1.1.5.12.5.2.14.5.1.3
		mVlanTagsPortNo OBJECT-TYPE
			SYNTAX INTEGER (1..255)
			MAX-ACCESS read-only
			STATUS current
			DESCRIPTION
				"Description."
			::= { mcVlanTagStripEntry 3 }

		
--          1.3.6.1.4.1.37950.1.1.5.12.5.2.14.5.1.4
-- 1.3.6.1.4.1.37950.1.1.5.12.5.2.14.5.1.4
-- 1.3.6.1.4.1.37950.1.1.5.12.5.2.14.5.1.4
-- 1.3.6.1.4.1.37950.1.1.5.12.5.2.14.5.1.4
-- 1.3.6.1.4.1.37950.1.1.5.12.5.2.14.5.1.4
-- 1.3.6.1.4.1.37950.1.1.5.12.5.2.14.5.1.4
-- 1.3.6.1.4.1.37950.1.1.5.12.5.2.14.5.1.4
-- 1.3.6.1.4.1.37950.1.1.5.12.5.2.14.5.1.4
-- 1.3.6.1.4.1.37950.1.1.5.12.5.2.14.5.1.4
		-- 1.3.6.1.4.1.37950.1.1.5.12.5.2.14.5.1.4
		mVlanTagsMode OBJECT-TYPE
			SYNTAX INTEGER
				{
				no-strip(0),
				strip(1),
				vlanTrans(2)
				}
			MAX-ACCESS read-only
			STATUS current
			DESCRIPTION
				"Description."
			::= { mcVlanTagStripEntry 4 }

		
--          1.3.6.1.4.1.37950.1.1.5.12.5.2.14.5.1.5
-- 1.3.6.1.4.1.37950.1.1.5.12.5.2.14.5.1.5
-- 1.3.6.1.4.1.37950.1.1.5.12.5.2.14.5.1.5
-- 1.3.6.1.4.1.37950.1.1.5.12.5.2.14.5.1.5
-- 1.3.6.1.4.1.37950.1.1.5.12.5.2.14.5.1.5
-- 1.3.6.1.4.1.37950.1.1.5.12.5.2.14.5.1.5
-- 1.3.6.1.4.1.37950.1.1.5.12.5.2.14.5.1.5
-- 1.3.6.1.4.1.37950.1.1.5.12.5.2.14.5.1.5
-- 1.3.6.1.4.1.37950.1.1.5.12.5.2.14.5.1.5
		-- 1.3.6.1.4.1.37950.1.1.5.12.5.2.14.5.1.5
		mVlanTagsVlanTrans OBJECT-TYPE
			SYNTAX OCTET STRING
			MAX-ACCESS read-only
			STATUS current
			DESCRIPTION
				"Description."
			::= { mcVlanTagStripEntry 5 }

		
--          1.3.6.1.4.1.37950.1.1.5.12.5.2.14.6
-- 1.3.6.1.4.1.37950.1.1.5.12.5.2.14.6
-- 1.3.6.1.4.1.37950.1.1.5.12.5.2.14.6
-- 1.3.6.1.4.1.37950.1.1.5.12.5.2.14.6
-- 1.3.6.1.4.1.37950.1.1.5.12.5.2.14.6
-- 1.3.6.1.4.1.37950.1.1.5.12.5.2.14.6
-- 1.3.6.1.4.1.37950.1.1.5.12.5.2.14.6
-- 1.3.6.1.4.1.37950.1.1.5.12.5.2.14.6
-- 1.3.6.1.4.1.37950.1.1.5.12.5.2.14.6
		-- 1.3.6.1.4.1.37950.1.1.5.12.5.2.14.6
		mcMaxGroupTable OBJECT-TYPE
			SYNTAX SEQUENCE OF McMaxGroupEntry
			MAX-ACCESS not-accessible
			STATUS current
			DESCRIPTION
				"Description."
			::= { onuPortIgmpCfg 6 }

		
--          1.3.6.1.4.1.37950.1.1.5.12.5.2.14.6.1
-- 1.3.6.1.4.1.37950.1.1.5.12.5.2.14.6.1
-- 1.3.6.1.4.1.37950.1.1.5.12.5.2.14.6.1
-- 1.3.6.1.4.1.37950.1.1.5.12.5.2.14.6.1
-- 1.3.6.1.4.1.37950.1.1.5.12.5.2.14.6.1
-- 1.3.6.1.4.1.37950.1.1.5.12.5.2.14.6.1
-- 1.3.6.1.4.1.37950.1.1.5.12.5.2.14.6.1
-- 1.3.6.1.4.1.37950.1.1.5.12.5.2.14.6.1
-- 1.3.6.1.4.1.37950.1.1.5.12.5.2.14.6.1
		-- 1.3.6.1.4.1.37950.1.1.5.12.5.2.14.6.1
		mcMaxGroupEntry OBJECT-TYPE
			SYNTAX McMaxGroupEntry
			MAX-ACCESS not-accessible
			STATUS current
			DESCRIPTION
				"Description."
			INDEX { mcMaxGrpPonNo, mcMaxGrpOnuNo, mcMaxGrpPortNo }
			::= { mcMaxGroupTable 1 }

		
		McMaxGroupEntry ::=
			SEQUENCE { 
				mcMaxGrpPonNo
					Integer32,
				mcMaxGrpOnuNo
					Integer32,
				mcMaxGrpPortNo
					Integer32,
				mcMaxGrpVal
					Integer32
			 }

--          1.3.6.1.4.1.37950.1.1.5.12.5.2.14.6.1.1
-- 1.3.6.1.4.1.37950.1.1.5.12.5.2.14.6.1.1
-- 1.3.6.1.4.1.37950.1.1.5.12.5.2.14.6.1.1
-- 1.3.6.1.4.1.37950.1.1.5.12.5.2.14.6.1.1
-- 1.3.6.1.4.1.37950.1.1.5.12.5.2.14.6.1.1
-- 1.3.6.1.4.1.37950.1.1.5.12.5.2.14.6.1.1
-- 1.3.6.1.4.1.37950.1.1.5.12.5.2.14.6.1.1
-- 1.3.6.1.4.1.37950.1.1.5.12.5.2.14.6.1.1
-- 1.3.6.1.4.1.37950.1.1.5.12.5.2.14.6.1.1
		-- 1.3.6.1.4.1.37950.1.1.5.12.5.2.14.6.1.1
		mcMaxGrpPonNo OBJECT-TYPE
			SYNTAX Integer32
			MAX-ACCESS read-only
			STATUS current
			DESCRIPTION
				"Description."
			::= { mcMaxGroupEntry 1 }

		
--          1.3.6.1.4.1.37950.1.1.5.12.5.2.14.6.1.2
-- 1.3.6.1.4.1.37950.1.1.5.12.5.2.14.6.1.2
-- 1.3.6.1.4.1.37950.1.1.5.12.5.2.14.6.1.2
-- 1.3.6.1.4.1.37950.1.1.5.12.5.2.14.6.1.2
-- 1.3.6.1.4.1.37950.1.1.5.12.5.2.14.6.1.2
-- 1.3.6.1.4.1.37950.1.1.5.12.5.2.14.6.1.2
-- 1.3.6.1.4.1.37950.1.1.5.12.5.2.14.6.1.2
-- 1.3.6.1.4.1.37950.1.1.5.12.5.2.14.6.1.2
-- 1.3.6.1.4.1.37950.1.1.5.12.5.2.14.6.1.2
		-- 1.3.6.1.4.1.37950.1.1.5.12.5.2.14.6.1.2
		mcMaxGrpOnuNo OBJECT-TYPE
			SYNTAX Integer32
			MAX-ACCESS read-only
			STATUS current
			DESCRIPTION
				"Description."
			::= { mcMaxGroupEntry 2 }

		
--          1.3.6.1.4.1.37950.1.1.5.12.5.2.14.6.1.3
-- 1.3.6.1.4.1.37950.1.1.5.12.5.2.14.6.1.3
-- 1.3.6.1.4.1.37950.1.1.5.12.5.2.14.6.1.3
-- 1.3.6.1.4.1.37950.1.1.5.12.5.2.14.6.1.3
-- 1.3.6.1.4.1.37950.1.1.5.12.5.2.14.6.1.3
-- 1.3.6.1.4.1.37950.1.1.5.12.5.2.14.6.1.3
-- 1.3.6.1.4.1.37950.1.1.5.12.5.2.14.6.1.3
-- 1.3.6.1.4.1.37950.1.1.5.12.5.2.14.6.1.3
-- 1.3.6.1.4.1.37950.1.1.5.12.5.2.14.6.1.3
		-- 1.3.6.1.4.1.37950.1.1.5.12.5.2.14.6.1.3
		mcMaxGrpPortNo OBJECT-TYPE
			SYNTAX Integer32
			MAX-ACCESS read-only
			STATUS current
			DESCRIPTION
				"Description."
			::= { mcMaxGroupEntry 3 }

		
--          1.3.6.1.4.1.37950.1.1.5.12.5.2.14.6.1.4
-- 1.3.6.1.4.1.37950.1.1.5.12.5.2.14.6.1.4
-- 1.3.6.1.4.1.37950.1.1.5.12.5.2.14.6.1.4
-- 1.3.6.1.4.1.37950.1.1.5.12.5.2.14.6.1.4
-- 1.3.6.1.4.1.37950.1.1.5.12.5.2.14.6.1.4
-- 1.3.6.1.4.1.37950.1.1.5.12.5.2.14.6.1.4
-- 1.3.6.1.4.1.37950.1.1.5.12.5.2.14.6.1.4
-- 1.3.6.1.4.1.37950.1.1.5.12.5.2.14.6.1.4
-- 1.3.6.1.4.1.37950.1.1.5.12.5.2.14.6.1.4
		-- 1.3.6.1.4.1.37950.1.1.5.12.5.2.14.6.1.4
		mcMaxGrpVal OBJECT-TYPE
			SYNTAX Integer32
			MAX-ACCESS read-only
			STATUS current
			DESCRIPTION
				"Description."
			::= { mcMaxGroupEntry 4 }

		
--          1.3.6.1.4.1.37950.1.1.5.12.5.2.15
-- 1.3.6.1.4.1.37950.1.1.5.12.5.2.15
-- 1.3.6.1.4.1.37950.1.1.5.12.5.2.15
-- 1.3.6.1.4.1.37950.1.1.5.12.5.2.15
-- 1.3.6.1.4.1.37950.1.1.5.12.5.2.15
-- 1.3.6.1.4.1.37950.1.1.5.12.5.2.15
-- 1.3.6.1.4.1.37950.1.1.5.12.5.2.15
-- 1.3.6.1.4.1.37950.1.1.5.12.5.2.15
-- 1.3.6.1.4.1.37950.1.1.5.12.5.2.15
		-- 1.3.6.1.4.1.37950.1.1.5.12.5.2.15
		onuPortStatOnOff OBJECT IDENTIFIER ::= { onuPortCfg 15 }

		
--          1.3.6.1.4.1.37950.1.1.5.12.5.2.15.1
-- 1.3.6.1.4.1.37950.1.1.5.12.5.2.15.1
-- 1.3.6.1.4.1.37950.1.1.5.12.5.2.15.1
-- 1.3.6.1.4.1.37950.1.1.5.12.5.2.15.1
-- 1.3.6.1.4.1.37950.1.1.5.12.5.2.15.1
-- 1.3.6.1.4.1.37950.1.1.5.12.5.2.15.1
-- 1.3.6.1.4.1.37950.1.1.5.12.5.2.15.1
-- 1.3.6.1.4.1.37950.1.1.5.12.5.2.15.1
-- 1.3.6.1.4.1.37950.1.1.5.12.5.2.15.1
		-- 1.3.6.1.4.1.37950.1.1.5.12.5.2.15.1
		statOnOffPonNo OBJECT-TYPE
			SYNTAX INTEGER (1..16)
			MAX-ACCESS read-write
			STATUS current
			DESCRIPTION
				"Description."
			::= { onuPortStatOnOff 1 }

		
--          1.3.6.1.4.1.37950.1.1.5.12.5.2.15.2
-- 1.3.6.1.4.1.37950.1.1.5.12.5.2.15.2
-- 1.3.6.1.4.1.37950.1.1.5.12.5.2.15.2
-- 1.3.6.1.4.1.37950.1.1.5.12.5.2.15.2
-- 1.3.6.1.4.1.37950.1.1.5.12.5.2.15.2
-- 1.3.6.1.4.1.37950.1.1.5.12.5.2.15.2
-- 1.3.6.1.4.1.37950.1.1.5.12.5.2.15.2
-- 1.3.6.1.4.1.37950.1.1.5.12.5.2.15.2
-- 1.3.6.1.4.1.37950.1.1.5.12.5.2.15.2
		-- 1.3.6.1.4.1.37950.1.1.5.12.5.2.15.2
		statOnOffOnuNo OBJECT-TYPE
			SYNTAX INTEGER (1..65535)
			MAX-ACCESS read-write
			STATUS current
			DESCRIPTION
				"Description."
			::= { onuPortStatOnOff 2 }

		
--          1.3.6.1.4.1.37950.1.1.5.12.5.2.15.3
-- 1.3.6.1.4.1.37950.1.1.5.12.5.2.15.3
-- 1.3.6.1.4.1.37950.1.1.5.12.5.2.15.3
-- 1.3.6.1.4.1.37950.1.1.5.12.5.2.15.3
-- 1.3.6.1.4.1.37950.1.1.5.12.5.2.15.3
-- 1.3.6.1.4.1.37950.1.1.5.12.5.2.15.3
-- 1.3.6.1.4.1.37950.1.1.5.12.5.2.15.3
-- 1.3.6.1.4.1.37950.1.1.5.12.5.2.15.3
-- 1.3.6.1.4.1.37950.1.1.5.12.5.2.15.3
		-- 1.3.6.1.4.1.37950.1.1.5.12.5.2.15.3
		statOnOffEthNo OBJECT-TYPE
			SYNTAX INTEGER (1..255)
			MAX-ACCESS read-write
			STATUS current
			DESCRIPTION
				"Description."
			::= { onuPortStatOnOff 3 }

		
--          1.3.6.1.4.1.37950.1.1.5.12.5.2.15.4
-- 1.3.6.1.4.1.37950.1.1.5.12.5.2.15.4
-- 1.3.6.1.4.1.37950.1.1.5.12.5.2.15.4
-- 1.3.6.1.4.1.37950.1.1.5.12.5.2.15.4
-- 1.3.6.1.4.1.37950.1.1.5.12.5.2.15.4
-- 1.3.6.1.4.1.37950.1.1.5.12.5.2.15.4
-- 1.3.6.1.4.1.37950.1.1.5.12.5.2.15.4
-- 1.3.6.1.4.1.37950.1.1.5.12.5.2.15.4
-- 1.3.6.1.4.1.37950.1.1.5.12.5.2.15.4
		-- 1.3.6.1.4.1.37950.1.1.5.12.5.2.15.4
		monitorStatus OBJECT-TYPE
			SYNTAX INTEGER
				{
				disable(0),
				enable(1)
				}
			MAX-ACCESS read-write
			STATUS current
			DESCRIPTION
				"Description."
			::= { onuPortStatOnOff 4 }

		
--          1.3.6.1.4.1.37950.1.1.5.12.5.2.15.5
-- 1.3.6.1.4.1.37950.1.1.5.12.5.2.15.5
-- 1.3.6.1.4.1.37950.1.1.5.12.5.2.15.5
-- 1.3.6.1.4.1.37950.1.1.5.12.5.2.15.5
-- 1.3.6.1.4.1.37950.1.1.5.12.5.2.15.5
-- 1.3.6.1.4.1.37950.1.1.5.12.5.2.15.5
-- 1.3.6.1.4.1.37950.1.1.5.12.5.2.15.5
-- 1.3.6.1.4.1.37950.1.1.5.12.5.2.15.5
-- 1.3.6.1.4.1.37950.1.1.5.12.5.2.15.5
		-- 1.3.6.1.4.1.37950.1.1.5.12.5.2.15.5
		statisticCycle OBJECT-TYPE
			SYNTAX INTEGER (0..65535)
			MAX-ACCESS read-write
			STATUS current
			DESCRIPTION
				"Description."
			::= { onuPortStatOnOff 5 }

		
--          1.3.6.1.4.1.37950.1.1.5.12.5.2.15.6
-- 1.3.6.1.4.1.37950.1.1.5.12.5.2.15.6
-- 1.3.6.1.4.1.37950.1.1.5.12.5.2.15.6
-- 1.3.6.1.4.1.37950.1.1.5.12.5.2.15.6
-- 1.3.6.1.4.1.37950.1.1.5.12.5.2.15.6
-- 1.3.6.1.4.1.37950.1.1.5.12.5.2.15.6
-- 1.3.6.1.4.1.37950.1.1.5.12.5.2.15.6
-- 1.3.6.1.4.1.37950.1.1.5.12.5.2.15.6
-- 1.3.6.1.4.1.37950.1.1.5.12.5.2.15.6
		-- 1.3.6.1.4.1.37950.1.1.5.12.5.2.15.6
		statOnOffAction OBJECT-TYPE
			SYNTAX INTEGER { commit(1) }
			MAX-ACCESS read-write
			STATUS current
			DESCRIPTION
				"Description."
			::= { onuPortStatOnOff 6 }

		
--          1.3.6.1.4.1.37950.1.1.5.12.5.2.16
-- 1.3.6.1.4.1.37950.1.1.5.12.5.2.16
-- 1.3.6.1.4.1.37950.1.1.5.12.5.2.16
-- 1.3.6.1.4.1.37950.1.1.5.12.5.2.16
-- 1.3.6.1.4.1.37950.1.1.5.12.5.2.16
-- 1.3.6.1.4.1.37950.1.1.5.12.5.2.16
-- 1.3.6.1.4.1.37950.1.1.5.12.5.2.16
-- 1.3.6.1.4.1.37950.1.1.5.12.5.2.16
-- 1.3.6.1.4.1.37950.1.1.5.12.5.2.16
		-- 1.3.6.1.4.1.37950.1.1.5.12.5.2.16
		onuPortStat OBJECT IDENTIFIER ::= { onuPortCfg 16 }

		
--          1.3.6.1.4.1.37950.1.1.5.12.5.2.16.1
-- 1.3.6.1.4.1.37950.1.1.5.12.5.2.16.1
-- 1.3.6.1.4.1.37950.1.1.5.12.5.2.16.1
-- 1.3.6.1.4.1.37950.1.1.5.12.5.2.16.1
-- 1.3.6.1.4.1.37950.1.1.5.12.5.2.16.1
-- 1.3.6.1.4.1.37950.1.1.5.12.5.2.16.1
-- 1.3.6.1.4.1.37950.1.1.5.12.5.2.16.1
-- 1.3.6.1.4.1.37950.1.1.5.12.5.2.16.1
-- 1.3.6.1.4.1.37950.1.1.5.12.5.2.16.1
		-- 1.3.6.1.4.1.37950.1.1.5.12.5.2.16.1
		onuPortStatClr OBJECT IDENTIFIER ::= { onuPortStat 1 }

		
--          1.3.6.1.4.1.37950.1.1.5.12.5.2.16.1.1
-- 1.3.6.1.4.1.37950.1.1.5.12.5.2.16.1.1
-- 1.3.6.1.4.1.37950.1.1.5.12.5.2.16.1.1
-- 1.3.6.1.4.1.37950.1.1.5.12.5.2.16.1.1
-- 1.3.6.1.4.1.37950.1.1.5.12.5.2.16.1.1
-- 1.3.6.1.4.1.37950.1.1.5.12.5.2.16.1.1
-- 1.3.6.1.4.1.37950.1.1.5.12.5.2.16.1.1
-- 1.3.6.1.4.1.37950.1.1.5.12.5.2.16.1.1
-- 1.3.6.1.4.1.37950.1.1.5.12.5.2.16.1.1
		-- 1.3.6.1.4.1.37950.1.1.5.12.5.2.16.1.1
		clrStatPonNo OBJECT-TYPE
			SYNTAX INTEGER (1..16)
			MAX-ACCESS read-write
			STATUS current
			DESCRIPTION
				"Description."
			::= { onuPortStatClr 1 }

		
--          1.3.6.1.4.1.37950.1.1.5.12.5.2.16.1.2
-- 1.3.6.1.4.1.37950.1.1.5.12.5.2.16.1.2
-- 1.3.6.1.4.1.37950.1.1.5.12.5.2.16.1.2
-- 1.3.6.1.4.1.37950.1.1.5.12.5.2.16.1.2
-- 1.3.6.1.4.1.37950.1.1.5.12.5.2.16.1.2
-- 1.3.6.1.4.1.37950.1.1.5.12.5.2.16.1.2
-- 1.3.6.1.4.1.37950.1.1.5.12.5.2.16.1.2
-- 1.3.6.1.4.1.37950.1.1.5.12.5.2.16.1.2
-- 1.3.6.1.4.1.37950.1.1.5.12.5.2.16.1.2
		-- 1.3.6.1.4.1.37950.1.1.5.12.5.2.16.1.2
		clrStatOnuNo OBJECT-TYPE
			SYNTAX INTEGER (1..65535)
			MAX-ACCESS read-write
			STATUS current
			DESCRIPTION
				"Description."
			::= { onuPortStatClr 2 }

		
--          1.3.6.1.4.1.37950.1.1.5.12.5.2.16.1.3
-- 1.3.6.1.4.1.37950.1.1.5.12.5.2.16.1.3
-- 1.3.6.1.4.1.37950.1.1.5.12.5.2.16.1.3
-- 1.3.6.1.4.1.37950.1.1.5.12.5.2.16.1.3
-- 1.3.6.1.4.1.37950.1.1.5.12.5.2.16.1.3
-- 1.3.6.1.4.1.37950.1.1.5.12.5.2.16.1.3
-- 1.3.6.1.4.1.37950.1.1.5.12.5.2.16.1.3
-- 1.3.6.1.4.1.37950.1.1.5.12.5.2.16.1.3
-- 1.3.6.1.4.1.37950.1.1.5.12.5.2.16.1.3
		-- 1.3.6.1.4.1.37950.1.1.5.12.5.2.16.1.3
		clrStatPortNo OBJECT-TYPE
			SYNTAX INTEGER (1..255)
			MAX-ACCESS read-write
			STATUS current
			DESCRIPTION
				"Description."
			::= { onuPortStatClr 3 }

		
--          1.3.6.1.4.1.37950.1.1.5.12.5.2.16.1.4
-- 1.3.6.1.4.1.37950.1.1.5.12.5.2.16.1.4
-- 1.3.6.1.4.1.37950.1.1.5.12.5.2.16.1.4
-- 1.3.6.1.4.1.37950.1.1.5.12.5.2.16.1.4
-- 1.3.6.1.4.1.37950.1.1.5.12.5.2.16.1.4
-- 1.3.6.1.4.1.37950.1.1.5.12.5.2.16.1.4
-- 1.3.6.1.4.1.37950.1.1.5.12.5.2.16.1.4
-- 1.3.6.1.4.1.37950.1.1.5.12.5.2.16.1.4
-- 1.3.6.1.4.1.37950.1.1.5.12.5.2.16.1.4
		-- 1.3.6.1.4.1.37950.1.1.5.12.5.2.16.1.4
		clrStatAction OBJECT-TYPE
			SYNTAX INTEGER { clear(1) }
			MAX-ACCESS read-write
			STATUS current
			DESCRIPTION
				"Description."
			::= { onuPortStatClr 4 }

		
--          1.3.6.1.4.1.37950.1.1.5.12.5.2.16.2
-- 1.3.6.1.4.1.37950.1.1.5.12.5.2.16.2
-- 1.3.6.1.4.1.37950.1.1.5.12.5.2.16.2
-- 1.3.6.1.4.1.37950.1.1.5.12.5.2.16.2
-- 1.3.6.1.4.1.37950.1.1.5.12.5.2.16.2
-- 1.3.6.1.4.1.37950.1.1.5.12.5.2.16.2
-- 1.3.6.1.4.1.37950.1.1.5.12.5.2.16.2
-- 1.3.6.1.4.1.37950.1.1.5.12.5.2.16.2
-- 1.3.6.1.4.1.37950.1.1.5.12.5.2.16.2
		-- 1.3.6.1.4.1.37950.1.1.5.12.5.2.16.2
		onuPortStatQueryMode OBJECT IDENTIFIER ::= { onuPortStat 2 }

		
--          1.3.6.1.4.1.37950.1.1.5.12.5.2.16.2.1
-- 1.3.6.1.4.1.37950.1.1.5.12.5.2.16.2.1
-- 1.3.6.1.4.1.37950.1.1.5.12.5.2.16.2.1
-- 1.3.6.1.4.1.37950.1.1.5.12.5.2.16.2.1
-- 1.3.6.1.4.1.37950.1.1.5.12.5.2.16.2.1
-- 1.3.6.1.4.1.37950.1.1.5.12.5.2.16.2.1
-- 1.3.6.1.4.1.37950.1.1.5.12.5.2.16.2.1
-- 1.3.6.1.4.1.37950.1.1.5.12.5.2.16.2.1
-- 1.3.6.1.4.1.37950.1.1.5.12.5.2.16.2.1
		-- 1.3.6.1.4.1.37950.1.1.5.12.5.2.16.2.1
		queryPonNo OBJECT-TYPE
			SYNTAX INTEGER (1..16)
			MAX-ACCESS read-write
			STATUS current
			DESCRIPTION
				"Description."
			::= { onuPortStatQueryMode 1 }

		
--          1.3.6.1.4.1.37950.1.1.5.12.5.2.16.2.2
-- 1.3.6.1.4.1.37950.1.1.5.12.5.2.16.2.2
-- 1.3.6.1.4.1.37950.1.1.5.12.5.2.16.2.2
-- 1.3.6.1.4.1.37950.1.1.5.12.5.2.16.2.2
-- 1.3.6.1.4.1.37950.1.1.5.12.5.2.16.2.2
-- 1.3.6.1.4.1.37950.1.1.5.12.5.2.16.2.2
-- 1.3.6.1.4.1.37950.1.1.5.12.5.2.16.2.2
-- 1.3.6.1.4.1.37950.1.1.5.12.5.2.16.2.2
-- 1.3.6.1.4.1.37950.1.1.5.12.5.2.16.2.2
		-- 1.3.6.1.4.1.37950.1.1.5.12.5.2.16.2.2
		queryOnuNo OBJECT-TYPE
			SYNTAX INTEGER (1..65535)
			MAX-ACCESS read-write
			STATUS current
			DESCRIPTION
				"Description."
			::= { onuPortStatQueryMode 2 }

		
--          1.3.6.1.4.1.37950.1.1.5.12.5.2.16.2.3
-- 1.3.6.1.4.1.37950.1.1.5.12.5.2.16.2.3
-- 1.3.6.1.4.1.37950.1.1.5.12.5.2.16.2.3
-- 1.3.6.1.4.1.37950.1.1.5.12.5.2.16.2.3
-- 1.3.6.1.4.1.37950.1.1.5.12.5.2.16.2.3
-- 1.3.6.1.4.1.37950.1.1.5.12.5.2.16.2.3
-- 1.3.6.1.4.1.37950.1.1.5.12.5.2.16.2.3
-- 1.3.6.1.4.1.37950.1.1.5.12.5.2.16.2.3
-- 1.3.6.1.4.1.37950.1.1.5.12.5.2.16.2.3
		-- 1.3.6.1.4.1.37950.1.1.5.12.5.2.16.2.3
		queryPortNo OBJECT-TYPE
			SYNTAX INTEGER (1..255)
			MAX-ACCESS read-write
			STATUS current
			DESCRIPTION
				"Description."
			::= { onuPortStatQueryMode 3 }

		
--          1.3.6.1.4.1.37950.1.1.5.12.5.2.16.2.4
-- 1.3.6.1.4.1.37950.1.1.5.12.5.2.16.2.4
-- 1.3.6.1.4.1.37950.1.1.5.12.5.2.16.2.4
-- 1.3.6.1.4.1.37950.1.1.5.12.5.2.16.2.4
-- 1.3.6.1.4.1.37950.1.1.5.12.5.2.16.2.4
-- 1.3.6.1.4.1.37950.1.1.5.12.5.2.16.2.4
-- 1.3.6.1.4.1.37950.1.1.5.12.5.2.16.2.4
-- 1.3.6.1.4.1.37950.1.1.5.12.5.2.16.2.4
-- 1.3.6.1.4.1.37950.1.1.5.12.5.2.16.2.4
		-- 1.3.6.1.4.1.37950.1.1.5.12.5.2.16.2.4
		queryMode OBJECT-TYPE
			SYNTAX INTEGER
				{
				monitor-current(1),
				monitor-history(2)
				}
			MAX-ACCESS read-write
			STATUS current
			DESCRIPTION
				"Description."
			::= { onuPortStatQueryMode 4 }

		
--          1.3.6.1.4.1.37950.1.1.5.12.5.2.16.2.5
-- 1.3.6.1.4.1.37950.1.1.5.12.5.2.16.2.5
-- 1.3.6.1.4.1.37950.1.1.5.12.5.2.16.2.5
-- 1.3.6.1.4.1.37950.1.1.5.12.5.2.16.2.5
-- 1.3.6.1.4.1.37950.1.1.5.12.5.2.16.2.5
-- 1.3.6.1.4.1.37950.1.1.5.12.5.2.16.2.5
-- 1.3.6.1.4.1.37950.1.1.5.12.5.2.16.2.5
-- 1.3.6.1.4.1.37950.1.1.5.12.5.2.16.2.5
-- 1.3.6.1.4.1.37950.1.1.5.12.5.2.16.2.5
		-- 1.3.6.1.4.1.37950.1.1.5.12.5.2.16.2.5
		queryAction OBJECT-TYPE
			SYNTAX INTEGER { commit(1) }
			MAX-ACCESS read-write
			STATUS current
			DESCRIPTION
				"Description."
			::= { onuPortStatQueryMode 5 }

		
--          1.3.6.1.4.1.37950.1.1.5.12.5.2.16.3
-- 1.3.6.1.4.1.37950.1.1.5.12.5.2.16.3
-- 1.3.6.1.4.1.37950.1.1.5.12.5.2.16.3
-- 1.3.6.1.4.1.37950.1.1.5.12.5.2.16.3
-- 1.3.6.1.4.1.37950.1.1.5.12.5.2.16.3
-- 1.3.6.1.4.1.37950.1.1.5.12.5.2.16.3
-- 1.3.6.1.4.1.37950.1.1.5.12.5.2.16.3
-- 1.3.6.1.4.1.37950.1.1.5.12.5.2.16.3
-- 1.3.6.1.4.1.37950.1.1.5.12.5.2.16.3
		-- 1.3.6.1.4.1.37950.1.1.5.12.5.2.16.3
		onuPortStatDisplay OBJECT IDENTIFIER ::= { onuPortStat 3 }

		
--          1.3.6.1.4.1.37950.1.1.5.12.5.2.16.3.1
-- 1.3.6.1.4.1.37950.1.1.5.12.5.2.16.3.1
-- 1.3.6.1.4.1.37950.1.1.5.12.5.2.16.3.1
-- 1.3.6.1.4.1.37950.1.1.5.12.5.2.16.3.1
-- 1.3.6.1.4.1.37950.1.1.5.12.5.2.16.3.1
-- 1.3.6.1.4.1.37950.1.1.5.12.5.2.16.3.1
-- 1.3.6.1.4.1.37950.1.1.5.12.5.2.16.3.1
-- 1.3.6.1.4.1.37950.1.1.5.12.5.2.16.3.1
-- 1.3.6.1.4.1.37950.1.1.5.12.5.2.16.3.1
		-- 1.3.6.1.4.1.37950.1.1.5.12.5.2.16.3.1
		statDisplayPortNo OBJECT-TYPE
			SYNTAX Integer32
			MAX-ACCESS read-write
			STATUS current
			DESCRIPTION
				"Description."
			::= { onuPortStatDisplay 1 }

		
--          1.3.6.1.4.1.37950.1.1.5.12.5.2.16.3.2
-- 1.3.6.1.4.1.37950.1.1.5.12.5.2.16.3.2
-- 1.3.6.1.4.1.37950.1.1.5.12.5.2.16.3.2
-- 1.3.6.1.4.1.37950.1.1.5.12.5.2.16.3.2
-- 1.3.6.1.4.1.37950.1.1.5.12.5.2.16.3.2
-- 1.3.6.1.4.1.37950.1.1.5.12.5.2.16.3.2
-- 1.3.6.1.4.1.37950.1.1.5.12.5.2.16.3.2
-- 1.3.6.1.4.1.37950.1.1.5.12.5.2.16.3.2
-- 1.3.6.1.4.1.37950.1.1.5.12.5.2.16.3.2
		-- 1.3.6.1.4.1.37950.1.1.5.12.5.2.16.3.2
		dnDropEvents OBJECT-TYPE
			SYNTAX Counter32
			MAX-ACCESS read-only
			STATUS current
			DESCRIPTION
				"Description."
			::= { onuPortStatDisplay 2 }

		
--          1.3.6.1.4.1.37950.1.1.5.12.5.2.16.3.3
-- 1.3.6.1.4.1.37950.1.1.5.12.5.2.16.3.3
-- 1.3.6.1.4.1.37950.1.1.5.12.5.2.16.3.3
-- 1.3.6.1.4.1.37950.1.1.5.12.5.2.16.3.3
-- 1.3.6.1.4.1.37950.1.1.5.12.5.2.16.3.3
-- 1.3.6.1.4.1.37950.1.1.5.12.5.2.16.3.3
-- 1.3.6.1.4.1.37950.1.1.5.12.5.2.16.3.3
-- 1.3.6.1.4.1.37950.1.1.5.12.5.2.16.3.3
-- 1.3.6.1.4.1.37950.1.1.5.12.5.2.16.3.3
		-- 1.3.6.1.4.1.37950.1.1.5.12.5.2.16.3.3
		upDropEvents OBJECT-TYPE
			SYNTAX Counter32
			MAX-ACCESS read-only
			STATUS current
			DESCRIPTION
				"Description."
			::= { onuPortStatDisplay 3 }

		
--          1.3.6.1.4.1.37950.1.1.5.12.5.2.16.3.4
-- 1.3.6.1.4.1.37950.1.1.5.12.5.2.16.3.4
-- 1.3.6.1.4.1.37950.1.1.5.12.5.2.16.3.4
-- 1.3.6.1.4.1.37950.1.1.5.12.5.2.16.3.4
-- 1.3.6.1.4.1.37950.1.1.5.12.5.2.16.3.4
-- 1.3.6.1.4.1.37950.1.1.5.12.5.2.16.3.4
-- 1.3.6.1.4.1.37950.1.1.5.12.5.2.16.3.4
-- 1.3.6.1.4.1.37950.1.1.5.12.5.2.16.3.4
-- 1.3.6.1.4.1.37950.1.1.5.12.5.2.16.3.4
		-- 1.3.6.1.4.1.37950.1.1.5.12.5.2.16.3.4
		dnOctets OBJECT-TYPE
			SYNTAX Counter32
			MAX-ACCESS read-only
			STATUS current
			DESCRIPTION
				"Description."
			::= { onuPortStatDisplay 4 }

		
--          1.3.6.1.4.1.37950.1.1.5.12.5.2.16.3.5
-- 1.3.6.1.4.1.37950.1.1.5.12.5.2.16.3.5
-- 1.3.6.1.4.1.37950.1.1.5.12.5.2.16.3.5
-- 1.3.6.1.4.1.37950.1.1.5.12.5.2.16.3.5
-- 1.3.6.1.4.1.37950.1.1.5.12.5.2.16.3.5
-- 1.3.6.1.4.1.37950.1.1.5.12.5.2.16.3.5
-- 1.3.6.1.4.1.37950.1.1.5.12.5.2.16.3.5
-- 1.3.6.1.4.1.37950.1.1.5.12.5.2.16.3.5
-- 1.3.6.1.4.1.37950.1.1.5.12.5.2.16.3.5
		-- 1.3.6.1.4.1.37950.1.1.5.12.5.2.16.3.5
		upOctets OBJECT-TYPE
			SYNTAX Counter32
			MAX-ACCESS read-only
			STATUS current
			DESCRIPTION
				"Description."
			::= { onuPortStatDisplay 5 }

		
--          1.3.6.1.4.1.37950.1.1.5.12.5.2.16.3.6
-- 1.3.6.1.4.1.37950.1.1.5.12.5.2.16.3.6
-- 1.3.6.1.4.1.37950.1.1.5.12.5.2.16.3.6
-- 1.3.6.1.4.1.37950.1.1.5.12.5.2.16.3.6
-- 1.3.6.1.4.1.37950.1.1.5.12.5.2.16.3.6
-- 1.3.6.1.4.1.37950.1.1.5.12.5.2.16.3.6
-- 1.3.6.1.4.1.37950.1.1.5.12.5.2.16.3.6
-- 1.3.6.1.4.1.37950.1.1.5.12.5.2.16.3.6
-- 1.3.6.1.4.1.37950.1.1.5.12.5.2.16.3.6
		-- 1.3.6.1.4.1.37950.1.1.5.12.5.2.16.3.6
		dnFrames OBJECT-TYPE
			SYNTAX Counter32
			MAX-ACCESS read-only
			STATUS current
			DESCRIPTION
				"Description."
			::= { onuPortStatDisplay 6 }

		
--          1.3.6.1.4.1.37950.1.1.5.12.5.2.16.3.7
-- 1.3.6.1.4.1.37950.1.1.5.12.5.2.16.3.7
-- 1.3.6.1.4.1.37950.1.1.5.12.5.2.16.3.7
-- 1.3.6.1.4.1.37950.1.1.5.12.5.2.16.3.7
-- 1.3.6.1.4.1.37950.1.1.5.12.5.2.16.3.7
-- 1.3.6.1.4.1.37950.1.1.5.12.5.2.16.3.7
-- 1.3.6.1.4.1.37950.1.1.5.12.5.2.16.3.7
-- 1.3.6.1.4.1.37950.1.1.5.12.5.2.16.3.7
-- 1.3.6.1.4.1.37950.1.1.5.12.5.2.16.3.7
		-- 1.3.6.1.4.1.37950.1.1.5.12.5.2.16.3.7
		upFrames OBJECT-TYPE
			SYNTAX Counter32
			MAX-ACCESS read-only
			STATUS current
			DESCRIPTION
				"Description."
			::= { onuPortStatDisplay 7 }

		
--          1.3.6.1.4.1.37950.1.1.5.12.5.2.16.3.8
-- 1.3.6.1.4.1.37950.1.1.5.12.5.2.16.3.8
-- 1.3.6.1.4.1.37950.1.1.5.12.5.2.16.3.8
-- 1.3.6.1.4.1.37950.1.1.5.12.5.2.16.3.8
-- 1.3.6.1.4.1.37950.1.1.5.12.5.2.16.3.8
-- 1.3.6.1.4.1.37950.1.1.5.12.5.2.16.3.8
-- 1.3.6.1.4.1.37950.1.1.5.12.5.2.16.3.8
-- 1.3.6.1.4.1.37950.1.1.5.12.5.2.16.3.8
-- 1.3.6.1.4.1.37950.1.1.5.12.5.2.16.3.8
		-- 1.3.6.1.4.1.37950.1.1.5.12.5.2.16.3.8
		dnBcFrames OBJECT-TYPE
			SYNTAX Counter32
			MAX-ACCESS read-only
			STATUS current
			DESCRIPTION
				"Description."
			::= { onuPortStatDisplay 8 }

		
--          1.3.6.1.4.1.37950.1.1.5.12.5.2.16.3.9
-- 1.3.6.1.4.1.37950.1.1.5.12.5.2.16.3.9
-- 1.3.6.1.4.1.37950.1.1.5.12.5.2.16.3.9
-- 1.3.6.1.4.1.37950.1.1.5.12.5.2.16.3.9
-- 1.3.6.1.4.1.37950.1.1.5.12.5.2.16.3.9
-- 1.3.6.1.4.1.37950.1.1.5.12.5.2.16.3.9
-- 1.3.6.1.4.1.37950.1.1.5.12.5.2.16.3.9
-- 1.3.6.1.4.1.37950.1.1.5.12.5.2.16.3.9
-- 1.3.6.1.4.1.37950.1.1.5.12.5.2.16.3.9
		-- 1.3.6.1.4.1.37950.1.1.5.12.5.2.16.3.9
		upBcFrames OBJECT-TYPE
			SYNTAX Counter32
			MAX-ACCESS read-only
			STATUS current
			DESCRIPTION
				"Description."
			::= { onuPortStatDisplay 9 }

		
--          1.3.6.1.4.1.37950.1.1.5.12.5.2.16.3.10
-- 1.3.6.1.4.1.37950.1.1.5.12.5.2.16.3.10
-- 1.3.6.1.4.1.37950.1.1.5.12.5.2.16.3.10
-- 1.3.6.1.4.1.37950.1.1.5.12.5.2.16.3.10
-- 1.3.6.1.4.1.37950.1.1.5.12.5.2.16.3.10
-- 1.3.6.1.4.1.37950.1.1.5.12.5.2.16.3.10
-- 1.3.6.1.4.1.37950.1.1.5.12.5.2.16.3.10
-- 1.3.6.1.4.1.37950.1.1.5.12.5.2.16.3.10
-- 1.3.6.1.4.1.37950.1.1.5.12.5.2.16.3.10
		-- 1.3.6.1.4.1.37950.1.1.5.12.5.2.16.3.10
		dnMcFrames OBJECT-TYPE
			SYNTAX Counter32
			MAX-ACCESS read-only
			STATUS current
			DESCRIPTION
				"Description."
			::= { onuPortStatDisplay 10 }

		
--          1.3.6.1.4.1.37950.1.1.5.12.5.2.16.3.11
-- 1.3.6.1.4.1.37950.1.1.5.12.5.2.16.3.11
-- 1.3.6.1.4.1.37950.1.1.5.12.5.2.16.3.11
-- 1.3.6.1.4.1.37950.1.1.5.12.5.2.16.3.11
-- 1.3.6.1.4.1.37950.1.1.5.12.5.2.16.3.11
-- 1.3.6.1.4.1.37950.1.1.5.12.5.2.16.3.11
-- 1.3.6.1.4.1.37950.1.1.5.12.5.2.16.3.11
-- 1.3.6.1.4.1.37950.1.1.5.12.5.2.16.3.11
-- 1.3.6.1.4.1.37950.1.1.5.12.5.2.16.3.11
		-- 1.3.6.1.4.1.37950.1.1.5.12.5.2.16.3.11
		upMcFrames OBJECT-TYPE
			SYNTAX Counter32
			MAX-ACCESS read-only
			STATUS current
			DESCRIPTION
				"Description."
			::= { onuPortStatDisplay 11 }

		
--          1.3.6.1.4.1.37950.1.1.5.12.5.2.16.3.12
-- 1.3.6.1.4.1.37950.1.1.5.12.5.2.16.3.12
-- 1.3.6.1.4.1.37950.1.1.5.12.5.2.16.3.12
-- 1.3.6.1.4.1.37950.1.1.5.12.5.2.16.3.12
-- 1.3.6.1.4.1.37950.1.1.5.12.5.2.16.3.12
-- 1.3.6.1.4.1.37950.1.1.5.12.5.2.16.3.12
-- 1.3.6.1.4.1.37950.1.1.5.12.5.2.16.3.12
-- 1.3.6.1.4.1.37950.1.1.5.12.5.2.16.3.12
-- 1.3.6.1.4.1.37950.1.1.5.12.5.2.16.3.12
		-- 1.3.6.1.4.1.37950.1.1.5.12.5.2.16.3.12
		dnCrcErrFrames OBJECT-TYPE
			SYNTAX Counter32
			MAX-ACCESS read-only
			STATUS current
			DESCRIPTION
				"Description."
			::= { onuPortStatDisplay 12 }

		
--          1.3.6.1.4.1.37950.1.1.5.12.5.2.16.3.13
-- 1.3.6.1.4.1.37950.1.1.5.12.5.2.16.3.13
-- 1.3.6.1.4.1.37950.1.1.5.12.5.2.16.3.13
-- 1.3.6.1.4.1.37950.1.1.5.12.5.2.16.3.13
-- 1.3.6.1.4.1.37950.1.1.5.12.5.2.16.3.13
-- 1.3.6.1.4.1.37950.1.1.5.12.5.2.16.3.13
-- 1.3.6.1.4.1.37950.1.1.5.12.5.2.16.3.13
-- 1.3.6.1.4.1.37950.1.1.5.12.5.2.16.3.13
-- 1.3.6.1.4.1.37950.1.1.5.12.5.2.16.3.13
		-- 1.3.6.1.4.1.37950.1.1.5.12.5.2.16.3.13
		upCrcErrFrames OBJECT-TYPE
			SYNTAX Counter32
			MAX-ACCESS read-only
			STATUS current
			DESCRIPTION
				"Description."
			::= { onuPortStatDisplay 13 }

		
--          1.3.6.1.4.1.37950.1.1.5.12.5.2.16.3.14
-- 1.3.6.1.4.1.37950.1.1.5.12.5.2.16.3.14
-- 1.3.6.1.4.1.37950.1.1.5.12.5.2.16.3.14
-- 1.3.6.1.4.1.37950.1.1.5.12.5.2.16.3.14
-- 1.3.6.1.4.1.37950.1.1.5.12.5.2.16.3.14
-- 1.3.6.1.4.1.37950.1.1.5.12.5.2.16.3.14
-- 1.3.6.1.4.1.37950.1.1.5.12.5.2.16.3.14
-- 1.3.6.1.4.1.37950.1.1.5.12.5.2.16.3.14
-- 1.3.6.1.4.1.37950.1.1.5.12.5.2.16.3.14
		-- 1.3.6.1.4.1.37950.1.1.5.12.5.2.16.3.14
		dnUndersizeFrames OBJECT-TYPE
			SYNTAX Counter32
			MAX-ACCESS read-only
			STATUS current
			DESCRIPTION
				"Description."
			::= { onuPortStatDisplay 14 }

		
--          1.3.6.1.4.1.37950.1.1.5.12.5.2.16.3.15
-- 1.3.6.1.4.1.37950.1.1.5.12.5.2.16.3.15
-- 1.3.6.1.4.1.37950.1.1.5.12.5.2.16.3.15
-- 1.3.6.1.4.1.37950.1.1.5.12.5.2.16.3.15
-- 1.3.6.1.4.1.37950.1.1.5.12.5.2.16.3.15
-- 1.3.6.1.4.1.37950.1.1.5.12.5.2.16.3.15
-- 1.3.6.1.4.1.37950.1.1.5.12.5.2.16.3.15
-- 1.3.6.1.4.1.37950.1.1.5.12.5.2.16.3.15
-- 1.3.6.1.4.1.37950.1.1.5.12.5.2.16.3.15
		-- 1.3.6.1.4.1.37950.1.1.5.12.5.2.16.3.15
		upUndersizeFrames OBJECT-TYPE
			SYNTAX Counter32
			MAX-ACCESS read-only
			STATUS current
			DESCRIPTION
				"Description."
			::= { onuPortStatDisplay 15 }

		
--          1.3.6.1.4.1.37950.1.1.5.12.5.2.16.3.16
-- 1.3.6.1.4.1.37950.1.1.5.12.5.2.16.3.16
-- 1.3.6.1.4.1.37950.1.1.5.12.5.2.16.3.16
-- 1.3.6.1.4.1.37950.1.1.5.12.5.2.16.3.16
-- 1.3.6.1.4.1.37950.1.1.5.12.5.2.16.3.16
-- 1.3.6.1.4.1.37950.1.1.5.12.5.2.16.3.16
-- 1.3.6.1.4.1.37950.1.1.5.12.5.2.16.3.16
-- 1.3.6.1.4.1.37950.1.1.5.12.5.2.16.3.16
-- 1.3.6.1.4.1.37950.1.1.5.12.5.2.16.3.16
		-- 1.3.6.1.4.1.37950.1.1.5.12.5.2.16.3.16
		dnOversizeFrames OBJECT-TYPE
			SYNTAX Counter32
			MAX-ACCESS read-only
			STATUS current
			DESCRIPTION
				"Description."
			::= { onuPortStatDisplay 16 }

		
--          1.3.6.1.4.1.37950.1.1.5.12.5.2.16.3.17
-- 1.3.6.1.4.1.37950.1.1.5.12.5.2.16.3.17
-- 1.3.6.1.4.1.37950.1.1.5.12.5.2.16.3.17
-- 1.3.6.1.4.1.37950.1.1.5.12.5.2.16.3.17
-- 1.3.6.1.4.1.37950.1.1.5.12.5.2.16.3.17
-- 1.3.6.1.4.1.37950.1.1.5.12.5.2.16.3.17
-- 1.3.6.1.4.1.37950.1.1.5.12.5.2.16.3.17
-- 1.3.6.1.4.1.37950.1.1.5.12.5.2.16.3.17
-- 1.3.6.1.4.1.37950.1.1.5.12.5.2.16.3.17
		-- 1.3.6.1.4.1.37950.1.1.5.12.5.2.16.3.17
		upOversizeFrames OBJECT-TYPE
			SYNTAX Counter32
			MAX-ACCESS read-only
			STATUS current
			DESCRIPTION
				"Description."
			::= { onuPortStatDisplay 17 }

		
--          1.3.6.1.4.1.37950.1.1.5.12.5.2.16.3.18
-- 1.3.6.1.4.1.37950.1.1.5.12.5.2.16.3.18
-- 1.3.6.1.4.1.37950.1.1.5.12.5.2.16.3.18
-- 1.3.6.1.4.1.37950.1.1.5.12.5.2.16.3.18
-- 1.3.6.1.4.1.37950.1.1.5.12.5.2.16.3.18
-- 1.3.6.1.4.1.37950.1.1.5.12.5.2.16.3.18
-- 1.3.6.1.4.1.37950.1.1.5.12.5.2.16.3.18
-- 1.3.6.1.4.1.37950.1.1.5.12.5.2.16.3.18
-- 1.3.6.1.4.1.37950.1.1.5.12.5.2.16.3.18
		-- 1.3.6.1.4.1.37950.1.1.5.12.5.2.16.3.18
		dnFragments OBJECT-TYPE
			SYNTAX Counter32
			MAX-ACCESS read-only
			STATUS current
			DESCRIPTION
				"Description."
			::= { onuPortStatDisplay 18 }

		
--          1.3.6.1.4.1.37950.1.1.5.12.5.2.16.3.19
-- 1.3.6.1.4.1.37950.1.1.5.12.5.2.16.3.19
-- 1.3.6.1.4.1.37950.1.1.5.12.5.2.16.3.19
-- 1.3.6.1.4.1.37950.1.1.5.12.5.2.16.3.19
-- 1.3.6.1.4.1.37950.1.1.5.12.5.2.16.3.19
-- 1.3.6.1.4.1.37950.1.1.5.12.5.2.16.3.19
-- 1.3.6.1.4.1.37950.1.1.5.12.5.2.16.3.19
-- 1.3.6.1.4.1.37950.1.1.5.12.5.2.16.3.19
-- 1.3.6.1.4.1.37950.1.1.5.12.5.2.16.3.19
		-- 1.3.6.1.4.1.37950.1.1.5.12.5.2.16.3.19
		upFragments OBJECT-TYPE
			SYNTAX Counter32
			MAX-ACCESS read-only
			STATUS current
			DESCRIPTION
				"Description."
			::= { onuPortStatDisplay 19 }

		
--          1.3.6.1.4.1.37950.1.1.5.12.5.2.16.3.20
-- 1.3.6.1.4.1.37950.1.1.5.12.5.2.16.3.20
-- 1.3.6.1.4.1.37950.1.1.5.12.5.2.16.3.20
-- 1.3.6.1.4.1.37950.1.1.5.12.5.2.16.3.20
-- 1.3.6.1.4.1.37950.1.1.5.12.5.2.16.3.20
-- 1.3.6.1.4.1.37950.1.1.5.12.5.2.16.3.20
-- 1.3.6.1.4.1.37950.1.1.5.12.5.2.16.3.20
-- 1.3.6.1.4.1.37950.1.1.5.12.5.2.16.3.20
-- 1.3.6.1.4.1.37950.1.1.5.12.5.2.16.3.20
		-- 1.3.6.1.4.1.37950.1.1.5.12.5.2.16.3.20
		dnJabbers OBJECT-TYPE
			SYNTAX Counter32
			MAX-ACCESS read-only
			STATUS current
			DESCRIPTION
				"Description."
			::= { onuPortStatDisplay 20 }

		
--          1.3.6.1.4.1.37950.1.1.5.12.5.2.16.3.21
-- 1.3.6.1.4.1.37950.1.1.5.12.5.2.16.3.21
-- 1.3.6.1.4.1.37950.1.1.5.12.5.2.16.3.21
-- 1.3.6.1.4.1.37950.1.1.5.12.5.2.16.3.21
-- 1.3.6.1.4.1.37950.1.1.5.12.5.2.16.3.21
-- 1.3.6.1.4.1.37950.1.1.5.12.5.2.16.3.21
-- 1.3.6.1.4.1.37950.1.1.5.12.5.2.16.3.21
-- 1.3.6.1.4.1.37950.1.1.5.12.5.2.16.3.21
-- 1.3.6.1.4.1.37950.1.1.5.12.5.2.16.3.21
		-- 1.3.6.1.4.1.37950.1.1.5.12.5.2.16.3.21
		upJabbers OBJECT-TYPE
			SYNTAX Counter32
			MAX-ACCESS read-only
			STATUS current
			DESCRIPTION
				"Description."
			::= { onuPortStatDisplay 21 }

		
--          1.3.6.1.4.1.37950.1.1.5.12.5.2.16.3.22
-- 1.3.6.1.4.1.37950.1.1.5.12.5.2.16.3.22
-- 1.3.6.1.4.1.37950.1.1.5.12.5.2.16.3.22
-- 1.3.6.1.4.1.37950.1.1.5.12.5.2.16.3.22
-- 1.3.6.1.4.1.37950.1.1.5.12.5.2.16.3.22
-- 1.3.6.1.4.1.37950.1.1.5.12.5.2.16.3.22
-- 1.3.6.1.4.1.37950.1.1.5.12.5.2.16.3.22
-- 1.3.6.1.4.1.37950.1.1.5.12.5.2.16.3.22
-- 1.3.6.1.4.1.37950.1.1.5.12.5.2.16.3.22
		-- 1.3.6.1.4.1.37950.1.1.5.12.5.2.16.3.22
		dn64OctetsFrames OBJECT-TYPE
			SYNTAX Counter32
			MAX-ACCESS read-only
			STATUS current
			DESCRIPTION
				"Description."
			::= { onuPortStatDisplay 22 }

		
--          1.3.6.1.4.1.37950.1.1.5.12.5.2.16.3.23
-- 1.3.6.1.4.1.37950.1.1.5.12.5.2.16.3.23
-- 1.3.6.1.4.1.37950.1.1.5.12.5.2.16.3.23
-- 1.3.6.1.4.1.37950.1.1.5.12.5.2.16.3.23
-- 1.3.6.1.4.1.37950.1.1.5.12.5.2.16.3.23
-- 1.3.6.1.4.1.37950.1.1.5.12.5.2.16.3.23
-- 1.3.6.1.4.1.37950.1.1.5.12.5.2.16.3.23
-- 1.3.6.1.4.1.37950.1.1.5.12.5.2.16.3.23
-- 1.3.6.1.4.1.37950.1.1.5.12.5.2.16.3.23
		-- 1.3.6.1.4.1.37950.1.1.5.12.5.2.16.3.23
		dn65to127OctetsFrames OBJECT-TYPE
			SYNTAX Counter32
			MAX-ACCESS read-only
			STATUS current
			DESCRIPTION
				"Description."
			::= { onuPortStatDisplay 23 }

		
--          1.3.6.1.4.1.37950.1.1.5.12.5.2.16.3.24
-- 1.3.6.1.4.1.37950.1.1.5.12.5.2.16.3.24
-- 1.3.6.1.4.1.37950.1.1.5.12.5.2.16.3.24
-- 1.3.6.1.4.1.37950.1.1.5.12.5.2.16.3.24
-- 1.3.6.1.4.1.37950.1.1.5.12.5.2.16.3.24
-- 1.3.6.1.4.1.37950.1.1.5.12.5.2.16.3.24
-- 1.3.6.1.4.1.37950.1.1.5.12.5.2.16.3.24
-- 1.3.6.1.4.1.37950.1.1.5.12.5.2.16.3.24
-- 1.3.6.1.4.1.37950.1.1.5.12.5.2.16.3.24
		-- 1.3.6.1.4.1.37950.1.1.5.12.5.2.16.3.24
		dn128to255OctetsFrames OBJECT-TYPE
			SYNTAX Counter32
			MAX-ACCESS read-only
			STATUS current
			DESCRIPTION
				"Description."
			::= { onuPortStatDisplay 24 }

		
--          1.3.6.1.4.1.37950.1.1.5.12.5.2.16.3.25
-- 1.3.6.1.4.1.37950.1.1.5.12.5.2.16.3.25
-- 1.3.6.1.4.1.37950.1.1.5.12.5.2.16.3.25
-- 1.3.6.1.4.1.37950.1.1.5.12.5.2.16.3.25
-- 1.3.6.1.4.1.37950.1.1.5.12.5.2.16.3.25
-- 1.3.6.1.4.1.37950.1.1.5.12.5.2.16.3.25
-- 1.3.6.1.4.1.37950.1.1.5.12.5.2.16.3.25
-- 1.3.6.1.4.1.37950.1.1.5.12.5.2.16.3.25
-- 1.3.6.1.4.1.37950.1.1.5.12.5.2.16.3.25
		-- 1.3.6.1.4.1.37950.1.1.5.12.5.2.16.3.25
		dn256to511OctetsFrames OBJECT-TYPE
			SYNTAX Counter32
			MAX-ACCESS read-only
			STATUS current
			DESCRIPTION
				"Description."
			::= { onuPortStatDisplay 25 }

		
--          1.3.6.1.4.1.37950.1.1.5.12.5.2.16.3.26
-- 1.3.6.1.4.1.37950.1.1.5.12.5.2.16.3.26
-- 1.3.6.1.4.1.37950.1.1.5.12.5.2.16.3.26
-- 1.3.6.1.4.1.37950.1.1.5.12.5.2.16.3.26
-- 1.3.6.1.4.1.37950.1.1.5.12.5.2.16.3.26
-- 1.3.6.1.4.1.37950.1.1.5.12.5.2.16.3.26
-- 1.3.6.1.4.1.37950.1.1.5.12.5.2.16.3.26
-- 1.3.6.1.4.1.37950.1.1.5.12.5.2.16.3.26
-- 1.3.6.1.4.1.37950.1.1.5.12.5.2.16.3.26
		-- 1.3.6.1.4.1.37950.1.1.5.12.5.2.16.3.26
		dn512to1023OctetsFrames OBJECT-TYPE
			SYNTAX Counter32
			MAX-ACCESS read-only
			STATUS current
			DESCRIPTION
				"Description."
			::= { onuPortStatDisplay 26 }

		
--          1.3.6.1.4.1.37950.1.1.5.12.5.2.16.3.27
-- 1.3.6.1.4.1.37950.1.1.5.12.5.2.16.3.27
-- 1.3.6.1.4.1.37950.1.1.5.12.5.2.16.3.27
-- 1.3.6.1.4.1.37950.1.1.5.12.5.2.16.3.27
-- 1.3.6.1.4.1.37950.1.1.5.12.5.2.16.3.27
-- 1.3.6.1.4.1.37950.1.1.5.12.5.2.16.3.27
-- 1.3.6.1.4.1.37950.1.1.5.12.5.2.16.3.27
-- 1.3.6.1.4.1.37950.1.1.5.12.5.2.16.3.27
-- 1.3.6.1.4.1.37950.1.1.5.12.5.2.16.3.27
		-- 1.3.6.1.4.1.37950.1.1.5.12.5.2.16.3.27
		dn1024to1518OctetsFrames OBJECT-TYPE
			SYNTAX Counter32
			MAX-ACCESS read-only
			STATUS current
			DESCRIPTION
				"Description."
			::= { onuPortStatDisplay 27 }

		
--          1.3.6.1.4.1.37950.1.1.5.12.5.2.16.3.28
-- 1.3.6.1.4.1.37950.1.1.5.12.5.2.16.3.28
-- 1.3.6.1.4.1.37950.1.1.5.12.5.2.16.3.28
-- 1.3.6.1.4.1.37950.1.1.5.12.5.2.16.3.28
-- 1.3.6.1.4.1.37950.1.1.5.12.5.2.16.3.28
-- 1.3.6.1.4.1.37950.1.1.5.12.5.2.16.3.28
-- 1.3.6.1.4.1.37950.1.1.5.12.5.2.16.3.28
-- 1.3.6.1.4.1.37950.1.1.5.12.5.2.16.3.28
-- 1.3.6.1.4.1.37950.1.1.5.12.5.2.16.3.28
		-- 1.3.6.1.4.1.37950.1.1.5.12.5.2.16.3.28
		up64OctetsFrames OBJECT-TYPE
			SYNTAX Counter32
			MAX-ACCESS read-only
			STATUS current
			DESCRIPTION
				"Description."
			::= { onuPortStatDisplay 28 }

		
--          1.3.6.1.4.1.37950.1.1.5.12.5.2.16.3.29
-- 1.3.6.1.4.1.37950.1.1.5.12.5.2.16.3.29
-- 1.3.6.1.4.1.37950.1.1.5.12.5.2.16.3.29
-- 1.3.6.1.4.1.37950.1.1.5.12.5.2.16.3.29
-- 1.3.6.1.4.1.37950.1.1.5.12.5.2.16.3.29
-- 1.3.6.1.4.1.37950.1.1.5.12.5.2.16.3.29
-- 1.3.6.1.4.1.37950.1.1.5.12.5.2.16.3.29
-- 1.3.6.1.4.1.37950.1.1.5.12.5.2.16.3.29
-- 1.3.6.1.4.1.37950.1.1.5.12.5.2.16.3.29
		-- 1.3.6.1.4.1.37950.1.1.5.12.5.2.16.3.29
		up65to127OctetsFrames OBJECT-TYPE
			SYNTAX Counter32
			MAX-ACCESS read-only
			STATUS current
			DESCRIPTION
				"Description."
			::= { onuPortStatDisplay 29 }

		
--          1.3.6.1.4.1.37950.1.1.5.12.5.2.16.3.30
-- 1.3.6.1.4.1.37950.1.1.5.12.5.2.16.3.30
-- 1.3.6.1.4.1.37950.1.1.5.12.5.2.16.3.30
-- 1.3.6.1.4.1.37950.1.1.5.12.5.2.16.3.30
-- 1.3.6.1.4.1.37950.1.1.5.12.5.2.16.3.30
-- 1.3.6.1.4.1.37950.1.1.5.12.5.2.16.3.30
-- 1.3.6.1.4.1.37950.1.1.5.12.5.2.16.3.30
-- 1.3.6.1.4.1.37950.1.1.5.12.5.2.16.3.30
-- 1.3.6.1.4.1.37950.1.1.5.12.5.2.16.3.30
		-- 1.3.6.1.4.1.37950.1.1.5.12.5.2.16.3.30
		up128to255OctetsFrames OBJECT-TYPE
			SYNTAX Counter32
			MAX-ACCESS read-only
			STATUS current
			DESCRIPTION
				"Description."
			::= { onuPortStatDisplay 30 }

		
--          1.3.6.1.4.1.37950.1.1.5.12.5.2.16.3.31
-- 1.3.6.1.4.1.37950.1.1.5.12.5.2.16.3.31
-- 1.3.6.1.4.1.37950.1.1.5.12.5.2.16.3.31
-- 1.3.6.1.4.1.37950.1.1.5.12.5.2.16.3.31
-- 1.3.6.1.4.1.37950.1.1.5.12.5.2.16.3.31
-- 1.3.6.1.4.1.37950.1.1.5.12.5.2.16.3.31
-- 1.3.6.1.4.1.37950.1.1.5.12.5.2.16.3.31
-- 1.3.6.1.4.1.37950.1.1.5.12.5.2.16.3.31
-- 1.3.6.1.4.1.37950.1.1.5.12.5.2.16.3.31
		-- 1.3.6.1.4.1.37950.1.1.5.12.5.2.16.3.31
		up256to511OctetsFrames OBJECT-TYPE
			SYNTAX Counter32
			MAX-ACCESS read-only
			STATUS current
			DESCRIPTION
				"Description."
			::= { onuPortStatDisplay 31 }

		
--          1.3.6.1.4.1.37950.1.1.5.12.5.2.16.3.32
-- 1.3.6.1.4.1.37950.1.1.5.12.5.2.16.3.32
-- 1.3.6.1.4.1.37950.1.1.5.12.5.2.16.3.32
-- 1.3.6.1.4.1.37950.1.1.5.12.5.2.16.3.32
-- 1.3.6.1.4.1.37950.1.1.5.12.5.2.16.3.32
-- 1.3.6.1.4.1.37950.1.1.5.12.5.2.16.3.32
-- 1.3.6.1.4.1.37950.1.1.5.12.5.2.16.3.32
-- 1.3.6.1.4.1.37950.1.1.5.12.5.2.16.3.32
-- 1.3.6.1.4.1.37950.1.1.5.12.5.2.16.3.32
		-- 1.3.6.1.4.1.37950.1.1.5.12.5.2.16.3.32
		up512to1023OctetsFrames OBJECT-TYPE
			SYNTAX Counter32
			MAX-ACCESS read-only
			STATUS current
			DESCRIPTION
				"Description."
			::= { onuPortStatDisplay 32 }

		
--          1.3.6.1.4.1.37950.1.1.5.12.5.2.16.3.33
-- 1.3.6.1.4.1.37950.1.1.5.12.5.2.16.3.33
-- 1.3.6.1.4.1.37950.1.1.5.12.5.2.16.3.33
-- 1.3.6.1.4.1.37950.1.1.5.12.5.2.16.3.33
-- 1.3.6.1.4.1.37950.1.1.5.12.5.2.16.3.33
-- 1.3.6.1.4.1.37950.1.1.5.12.5.2.16.3.33
-- 1.3.6.1.4.1.37950.1.1.5.12.5.2.16.3.33
-- 1.3.6.1.4.1.37950.1.1.5.12.5.2.16.3.33
-- 1.3.6.1.4.1.37950.1.1.5.12.5.2.16.3.33
		-- 1.3.6.1.4.1.37950.1.1.5.12.5.2.16.3.33
		up1024to1518OctetsFrames OBJECT-TYPE
			SYNTAX Counter32
			MAX-ACCESS read-only
			STATUS current
			DESCRIPTION
				"Description."
			::= { onuPortStatDisplay 33 }

		
--          1.3.6.1.4.1.37950.1.1.5.12.5.2.16.3.34
-- 1.3.6.1.4.1.37950.1.1.5.12.5.2.16.3.34
-- 1.3.6.1.4.1.37950.1.1.5.12.5.2.16.3.34
-- 1.3.6.1.4.1.37950.1.1.5.12.5.2.16.3.34
-- 1.3.6.1.4.1.37950.1.1.5.12.5.2.16.3.34
-- 1.3.6.1.4.1.37950.1.1.5.12.5.2.16.3.34
-- 1.3.6.1.4.1.37950.1.1.5.12.5.2.16.3.34
-- 1.3.6.1.4.1.37950.1.1.5.12.5.2.16.3.34
-- 1.3.6.1.4.1.37950.1.1.5.12.5.2.16.3.34
		-- 1.3.6.1.4.1.37950.1.1.5.12.5.2.16.3.34
		dnDiscardFrames OBJECT-TYPE
			SYNTAX Counter32
			MAX-ACCESS read-only
			STATUS current
			DESCRIPTION
				"Description."
			::= { onuPortStatDisplay 34 }

		
--          1.3.6.1.4.1.37950.1.1.5.12.5.2.16.3.35
-- 1.3.6.1.4.1.37950.1.1.5.12.5.2.16.3.35
-- 1.3.6.1.4.1.37950.1.1.5.12.5.2.16.3.35
-- 1.3.6.1.4.1.37950.1.1.5.12.5.2.16.3.35
-- 1.3.6.1.4.1.37950.1.1.5.12.5.2.16.3.35
-- 1.3.6.1.4.1.37950.1.1.5.12.5.2.16.3.35
-- 1.3.6.1.4.1.37950.1.1.5.12.5.2.16.3.35
-- 1.3.6.1.4.1.37950.1.1.5.12.5.2.16.3.35
-- 1.3.6.1.4.1.37950.1.1.5.12.5.2.16.3.35
		-- 1.3.6.1.4.1.37950.1.1.5.12.5.2.16.3.35
		upDiscardFrames OBJECT-TYPE
			SYNTAX Counter32
			MAX-ACCESS read-only
			STATUS current
			DESCRIPTION
				"Description."
			::= { onuPortStatDisplay 35 }

		
--          1.3.6.1.4.1.37950.1.1.5.12.5.2.16.3.36
-- 1.3.6.1.4.1.37950.1.1.5.12.5.2.16.3.36
-- 1.3.6.1.4.1.37950.1.1.5.12.5.2.16.3.36
-- 1.3.6.1.4.1.37950.1.1.5.12.5.2.16.3.36
-- 1.3.6.1.4.1.37950.1.1.5.12.5.2.16.3.36
-- 1.3.6.1.4.1.37950.1.1.5.12.5.2.16.3.36
-- 1.3.6.1.4.1.37950.1.1.5.12.5.2.16.3.36
-- 1.3.6.1.4.1.37950.1.1.5.12.5.2.16.3.36
-- 1.3.6.1.4.1.37950.1.1.5.12.5.2.16.3.36
		-- 1.3.6.1.4.1.37950.1.1.5.12.5.2.16.3.36
		dnErrFrames OBJECT-TYPE
			SYNTAX Counter32
			MAX-ACCESS read-only
			STATUS current
			DESCRIPTION
				"Description."
			::= { onuPortStatDisplay 36 }

		
--          1.3.6.1.4.1.37950.1.1.5.12.5.2.16.3.37
-- 1.3.6.1.4.1.37950.1.1.5.12.5.2.16.3.37
-- 1.3.6.1.4.1.37950.1.1.5.12.5.2.16.3.37
-- 1.3.6.1.4.1.37950.1.1.5.12.5.2.16.3.37
-- 1.3.6.1.4.1.37950.1.1.5.12.5.2.16.3.37
-- 1.3.6.1.4.1.37950.1.1.5.12.5.2.16.3.37
-- 1.3.6.1.4.1.37950.1.1.5.12.5.2.16.3.37
-- 1.3.6.1.4.1.37950.1.1.5.12.5.2.16.3.37
-- 1.3.6.1.4.1.37950.1.1.5.12.5.2.16.3.37
		-- 1.3.6.1.4.1.37950.1.1.5.12.5.2.16.3.37
		upErrFrames OBJECT-TYPE
			SYNTAX Counter32
			MAX-ACCESS read-only
			STATUS current
			DESCRIPTION
				"Description."
			::= { onuPortStatDisplay 37 }

		
--          1.3.6.1.4.1.37950.1.1.5.12.5.2.16.3.38
-- 1.3.6.1.4.1.37950.1.1.5.12.5.2.16.3.38
-- 1.3.6.1.4.1.37950.1.1.5.12.5.2.16.3.38
-- 1.3.6.1.4.1.37950.1.1.5.12.5.2.16.3.38
-- 1.3.6.1.4.1.37950.1.1.5.12.5.2.16.3.38
-- 1.3.6.1.4.1.37950.1.1.5.12.5.2.16.3.38
-- 1.3.6.1.4.1.37950.1.1.5.12.5.2.16.3.38
-- 1.3.6.1.4.1.37950.1.1.5.12.5.2.16.3.38
-- 1.3.6.1.4.1.37950.1.1.5.12.5.2.16.3.38
		-- 1.3.6.1.4.1.37950.1.1.5.12.5.2.16.3.38
		statusChangeTimes OBJECT-TYPE
			SYNTAX Counter32
			MAX-ACCESS read-only
			STATUS current
			DESCRIPTION
				"Description."
			::= { onuPortStatDisplay 38 }

		
--          1.3.6.1.4.1.37950.1.1.5.12.5.3
-- 1.3.6.1.4.1.37950.1.1.5.12.5.3
-- 1.3.6.1.4.1.37950.1.1.5.12.5.3
-- 1.3.6.1.4.1.37950.1.1.5.12.5.3
-- 1.3.6.1.4.1.37950.1.1.5.12.5.3
-- 1.3.6.1.4.1.37950.1.1.5.12.5.3
-- 1.3.6.1.4.1.37950.1.1.5.12.5.3
-- 1.3.6.1.4.1.37950.1.1.5.12.5.3
-- 1.3.6.1.4.1.37950.1.1.5.12.5.3
		-- 1.3.6.1.4.1.37950.1.1.5.12.5.3
		onuPortGlobalView OBJECT IDENTIFIER ::= { onuPort 3 }

		
--          1.3.6.1.4.1.37950.1.1.5.12.5.3.1
-- 1.3.6.1.4.1.37950.1.1.5.12.5.3.1
-- 1.3.6.1.4.1.37950.1.1.5.12.5.3.1
-- 1.3.6.1.4.1.37950.1.1.5.12.5.3.1
-- 1.3.6.1.4.1.37950.1.1.5.12.5.3.1
-- 1.3.6.1.4.1.37950.1.1.5.12.5.3.1
-- 1.3.6.1.4.1.37950.1.1.5.12.5.3.1
-- 1.3.6.1.4.1.37950.1.1.5.12.5.3.1
-- 1.3.6.1.4.1.37950.1.1.5.12.5.3.1
		-- 1.3.6.1.4.1.37950.1.1.5.12.5.3.1
		globalViewPonNum OBJECT-TYPE
			SYNTAX Integer32 (1..16)
			MAX-ACCESS read-write
			STATUS current
			DESCRIPTION
				"Description."
			::= { onuPortGlobalView 1 }

		
--          1.3.6.1.4.1.37950.1.1.5.12.5.3.2
-- 1.3.6.1.4.1.37950.1.1.5.12.5.3.2
-- 1.3.6.1.4.1.37950.1.1.5.12.5.3.2
-- 1.3.6.1.4.1.37950.1.1.5.12.5.3.2
-- 1.3.6.1.4.1.37950.1.1.5.12.5.3.2
-- 1.3.6.1.4.1.37950.1.1.5.12.5.3.2
-- 1.3.6.1.4.1.37950.1.1.5.12.5.3.2
-- 1.3.6.1.4.1.37950.1.1.5.12.5.3.2
-- 1.3.6.1.4.1.37950.1.1.5.12.5.3.2
		-- 1.3.6.1.4.1.37950.1.1.5.12.5.3.2
		globalViewOnuNum OBJECT-TYPE
			SYNTAX Integer32 (1..65535)
			MAX-ACCESS read-write
			STATUS current
			DESCRIPTION
				"Description."
			::= { onuPortGlobalView 2 }

		
--          1.3.6.1.4.1.37950.1.1.5.12.5.3.3
-- 1.3.6.1.4.1.37950.1.1.5.12.5.3.3
-- 1.3.6.1.4.1.37950.1.1.5.12.5.3.3
-- 1.3.6.1.4.1.37950.1.1.5.12.5.3.3
-- 1.3.6.1.4.1.37950.1.1.5.12.5.3.3
-- 1.3.6.1.4.1.37950.1.1.5.12.5.3.3
-- 1.3.6.1.4.1.37950.1.1.5.12.5.3.3
-- 1.3.6.1.4.1.37950.1.1.5.12.5.3.3
-- 1.3.6.1.4.1.37950.1.1.5.12.5.3.3
		-- 1.3.6.1.4.1.37950.1.1.5.12.5.3.3
		globalViewPortNum OBJECT-TYPE
			SYNTAX Integer32 (1..64)
			MAX-ACCESS read-write
			STATUS current
			DESCRIPTION
				"Description."
			::= { onuPortGlobalView 3 }

		
--          1.3.6.1.4.1.37950.1.1.5.12.6
-- 1.3.6.1.4.1.37950.1.1.5.12.6
-- 1.3.6.1.4.1.37950.1.1.5.12.6
-- 1.3.6.1.4.1.37950.1.1.5.12.6
-- 1.3.6.1.4.1.37950.1.1.5.12.6
-- 1.3.6.1.4.1.37950.1.1.5.12.6
-- 1.3.6.1.4.1.37950.1.1.5.12.6
-- 1.3.6.1.4.1.37950.1.1.5.12.6
-- 1.3.6.1.4.1.37950.1.1.5.12.6
		-- 1.3.6.1.4.1.37950.1.1.5.12.6
		onuVoipCfg OBJECT IDENTIFIER ::= { v1600dOnuMgmt 6 }

		
--          1.3.6.1.4.1.37950.1.1.5.12.6.1
-- 1.3.6.1.4.1.37950.1.1.5.12.6.1
-- 1.3.6.1.4.1.37950.1.1.5.12.6.1
-- 1.3.6.1.4.1.37950.1.1.5.12.6.1
-- 1.3.6.1.4.1.37950.1.1.5.12.6.1
-- 1.3.6.1.4.1.37950.1.1.5.12.6.1
-- 1.3.6.1.4.1.37950.1.1.5.12.6.1
-- 1.3.6.1.4.1.37950.1.1.5.12.6.1
-- 1.3.6.1.4.1.37950.1.1.5.12.6.1
		-- 1.3.6.1.4.1.37950.1.1.5.12.6.1
		voipInfo OBJECT IDENTIFIER ::= { onuVoipCfg 1 }

		
--          1.3.6.1.4.1.37950.1.1.5.12.6.1.2
-- 1.3.6.1.4.1.37950.1.1.5.12.6.1.2
-- 1.3.6.1.4.1.37950.1.1.5.12.6.1.2
-- 1.3.6.1.4.1.37950.1.1.5.12.6.1.2
-- 1.3.6.1.4.1.37950.1.1.5.12.6.1.2
-- 1.3.6.1.4.1.37950.1.1.5.12.6.1.2
-- 1.3.6.1.4.1.37950.1.1.5.12.6.1.2
-- 1.3.6.1.4.1.37950.1.1.5.12.6.1.2
-- 1.3.6.1.4.1.37950.1.1.5.12.6.1.2
		-- 1.3.6.1.4.1.37950.1.1.5.12.6.1.2
		voipGlobalInfo OBJECT IDENTIFIER ::= { voipInfo 2 }

		
--          1.3.6.1.4.1.37950.1.1.5.12.6.1.2.1
-- 1.3.6.1.4.1.37950.1.1.5.12.6.1.2.1
-- 1.3.6.1.4.1.37950.1.1.5.12.6.1.2.1
-- 1.3.6.1.4.1.37950.1.1.5.12.6.1.2.1
-- 1.3.6.1.4.1.37950.1.1.5.12.6.1.2.1
-- 1.3.6.1.4.1.37950.1.1.5.12.6.1.2.1
-- 1.3.6.1.4.1.37950.1.1.5.12.6.1.2.1
-- 1.3.6.1.4.1.37950.1.1.5.12.6.1.2.1
-- 1.3.6.1.4.1.37950.1.1.5.12.6.1.2.1
		-- 1.3.6.1.4.1.37950.1.1.5.12.6.1.2.1
		voipGlobalIPTable OBJECT-TYPE
			SYNTAX SEQUENCE OF VoipGlobalIPEntry
			MAX-ACCESS not-accessible
			STATUS current
			DESCRIPTION
				"Description."
			::= { voipGlobalInfo 1 }

		
--          1.3.6.1.4.1.37950.1.1.5.12.6.1.2.1.1
-- 1.3.6.1.4.1.37950.1.1.5.12.6.1.2.1.1
-- 1.3.6.1.4.1.37950.1.1.5.12.6.1.2.1.1
-- 1.3.6.1.4.1.37950.1.1.5.12.6.1.2.1.1
-- 1.3.6.1.4.1.37950.1.1.5.12.6.1.2.1.1
-- 1.3.6.1.4.1.37950.1.1.5.12.6.1.2.1.1
-- 1.3.6.1.4.1.37950.1.1.5.12.6.1.2.1.1
-- 1.3.6.1.4.1.37950.1.1.5.12.6.1.2.1.1
-- 1.3.6.1.4.1.37950.1.1.5.12.6.1.2.1.1
		-- 1.3.6.1.4.1.37950.1.1.5.12.6.1.2.1.1
		voipGlobalIPEntry OBJECT-TYPE
			SYNTAX VoipGlobalIPEntry
			MAX-ACCESS not-accessible
			STATUS current
			DESCRIPTION
				"Description."
			INDEX { voipGIPPonNo, voipGIPOnuNo }
			::= { voipGlobalIPTable 1 }

		
		VoipGlobalIPEntry ::=
			SEQUENCE { 
				voipGIPPonNo
					Integer32,
				voipGIPOnuNo
					Integer32,
				voipGIPMode
					INTEGER,
				voipGIPAddr
					IpAddress,
				voipGIPMask
					IpAddress,
				voipGIPGateway
					IpAddress,
				voipGIPPPPoEMode
					INTEGER,
				voipGIPPPPoEUserName
					OCTET STRING,
				voipGIPPPPoEPasswd
					OCTET STRING,
				voipGIPTagFlag
					INTEGER,
				voipGIPCVlan
					Integer32,
				voipGIPSVlan
					Integer32,
				voipGIPPriority
					Integer32
			 }

--          1.3.6.1.4.1.37950.1.1.5.12.6.1.2.1.1.1
-- 1.3.6.1.4.1.37950.1.1.5.12.6.1.2.1.1.1
-- 1.3.6.1.4.1.37950.1.1.5.12.6.1.2.1.1.1
-- 1.3.6.1.4.1.37950.1.1.5.12.6.1.2.1.1.1
-- 1.3.6.1.4.1.37950.1.1.5.12.6.1.2.1.1.1
-- 1.3.6.1.4.1.37950.1.1.5.12.6.1.2.1.1.1
-- 1.3.6.1.4.1.37950.1.1.5.12.6.1.2.1.1.1
-- 1.3.6.1.4.1.37950.1.1.5.12.6.1.2.1.1.1
-- 1.3.6.1.4.1.37950.1.1.5.12.6.1.2.1.1.1
		-- 1.3.6.1.4.1.37950.1.1.5.12.6.1.2.1.1.1
		voipGIPPonNo OBJECT-TYPE
			SYNTAX Integer32
			MAX-ACCESS read-only
			STATUS current
			DESCRIPTION
				"Description."
			::= { voipGlobalIPEntry 1 }

		
--          1.3.6.1.4.1.37950.1.1.5.12.6.1.2.1.1.2
-- 1.3.6.1.4.1.37950.1.1.5.12.6.1.2.1.1.2
-- 1.3.6.1.4.1.37950.1.1.5.12.6.1.2.1.1.2
-- 1.3.6.1.4.1.37950.1.1.5.12.6.1.2.1.1.2
-- 1.3.6.1.4.1.37950.1.1.5.12.6.1.2.1.1.2
-- 1.3.6.1.4.1.37950.1.1.5.12.6.1.2.1.1.2
-- 1.3.6.1.4.1.37950.1.1.5.12.6.1.2.1.1.2
-- 1.3.6.1.4.1.37950.1.1.5.12.6.1.2.1.1.2
-- 1.3.6.1.4.1.37950.1.1.5.12.6.1.2.1.1.2
		-- 1.3.6.1.4.1.37950.1.1.5.12.6.1.2.1.1.2
		voipGIPOnuNo OBJECT-TYPE
			SYNTAX Integer32
			MAX-ACCESS read-only
			STATUS current
			DESCRIPTION
				"Description."
			::= { voipGlobalIPEntry 2 }

		
--          1.3.6.1.4.1.37950.1.1.5.12.6.1.2.1.1.3
-- 1.3.6.1.4.1.37950.1.1.5.12.6.1.2.1.1.3
-- 1.3.6.1.4.1.37950.1.1.5.12.6.1.2.1.1.3
-- 1.3.6.1.4.1.37950.1.1.5.12.6.1.2.1.1.3
-- 1.3.6.1.4.1.37950.1.1.5.12.6.1.2.1.1.3
-- 1.3.6.1.4.1.37950.1.1.5.12.6.1.2.1.1.3
-- 1.3.6.1.4.1.37950.1.1.5.12.6.1.2.1.1.3
-- 1.3.6.1.4.1.37950.1.1.5.12.6.1.2.1.1.3
-- 1.3.6.1.4.1.37950.1.1.5.12.6.1.2.1.1.3
		-- 1.3.6.1.4.1.37950.1.1.5.12.6.1.2.1.1.3
		voipGIPMode OBJECT-TYPE
			SYNTAX INTEGER
				{
				static-ip(0),
				dhcp(1),
				pppoe(2)
				}
			MAX-ACCESS read-only
			STATUS current
			DESCRIPTION
				"Description."
			::= { voipGlobalIPEntry 3 }

		
--          1.3.6.1.4.1.37950.1.1.5.12.6.1.2.1.1.4
-- 1.3.6.1.4.1.37950.1.1.5.12.6.1.2.1.1.4
-- 1.3.6.1.4.1.37950.1.1.5.12.6.1.2.1.1.4
-- 1.3.6.1.4.1.37950.1.1.5.12.6.1.2.1.1.4
-- 1.3.6.1.4.1.37950.1.1.5.12.6.1.2.1.1.4
-- 1.3.6.1.4.1.37950.1.1.5.12.6.1.2.1.1.4
-- 1.3.6.1.4.1.37950.1.1.5.12.6.1.2.1.1.4
-- 1.3.6.1.4.1.37950.1.1.5.12.6.1.2.1.1.4
-- 1.3.6.1.4.1.37950.1.1.5.12.6.1.2.1.1.4
		-- 1.3.6.1.4.1.37950.1.1.5.12.6.1.2.1.1.4
		voipGIPAddr OBJECT-TYPE
			SYNTAX IpAddress
			MAX-ACCESS read-only
			STATUS current
			DESCRIPTION
				"Description."
			::= { voipGlobalIPEntry 4 }

		
--          1.3.6.1.4.1.37950.1.1.5.12.6.1.2.1.1.5
-- 1.3.6.1.4.1.37950.1.1.5.12.6.1.2.1.1.5
-- 1.3.6.1.4.1.37950.1.1.5.12.6.1.2.1.1.5
-- 1.3.6.1.4.1.37950.1.1.5.12.6.1.2.1.1.5
-- 1.3.6.1.4.1.37950.1.1.5.12.6.1.2.1.1.5
-- 1.3.6.1.4.1.37950.1.1.5.12.6.1.2.1.1.5
-- 1.3.6.1.4.1.37950.1.1.5.12.6.1.2.1.1.5
-- 1.3.6.1.4.1.37950.1.1.5.12.6.1.2.1.1.5
-- 1.3.6.1.4.1.37950.1.1.5.12.6.1.2.1.1.5
		-- 1.3.6.1.4.1.37950.1.1.5.12.6.1.2.1.1.5
		voipGIPMask OBJECT-TYPE
			SYNTAX IpAddress
			MAX-ACCESS read-only
			STATUS current
			DESCRIPTION
				"Description."
			::= { voipGlobalIPEntry 5 }

		
--          1.3.6.1.4.1.37950.1.1.5.12.6.1.2.1.1.6
-- 1.3.6.1.4.1.37950.1.1.5.12.6.1.2.1.1.6
-- 1.3.6.1.4.1.37950.1.1.5.12.6.1.2.1.1.6
-- 1.3.6.1.4.1.37950.1.1.5.12.6.1.2.1.1.6
-- 1.3.6.1.4.1.37950.1.1.5.12.6.1.2.1.1.6
-- 1.3.6.1.4.1.37950.1.1.5.12.6.1.2.1.1.6
-- 1.3.6.1.4.1.37950.1.1.5.12.6.1.2.1.1.6
-- 1.3.6.1.4.1.37950.1.1.5.12.6.1.2.1.1.6
-- 1.3.6.1.4.1.37950.1.1.5.12.6.1.2.1.1.6
		-- 1.3.6.1.4.1.37950.1.1.5.12.6.1.2.1.1.6
		voipGIPGateway OBJECT-TYPE
			SYNTAX IpAddress
			MAX-ACCESS read-only
			STATUS current
			DESCRIPTION
				"Description."
			::= { voipGlobalIPEntry 6 }

		
--          1.3.6.1.4.1.37950.1.1.5.12.6.1.2.1.1.7
-- 1.3.6.1.4.1.37950.1.1.5.12.6.1.2.1.1.7
-- 1.3.6.1.4.1.37950.1.1.5.12.6.1.2.1.1.7
-- 1.3.6.1.4.1.37950.1.1.5.12.6.1.2.1.1.7
-- 1.3.6.1.4.1.37950.1.1.5.12.6.1.2.1.1.7
-- 1.3.6.1.4.1.37950.1.1.5.12.6.1.2.1.1.7
-- 1.3.6.1.4.1.37950.1.1.5.12.6.1.2.1.1.7
-- 1.3.6.1.4.1.37950.1.1.5.12.6.1.2.1.1.7
-- 1.3.6.1.4.1.37950.1.1.5.12.6.1.2.1.1.7
		-- 1.3.6.1.4.1.37950.1.1.5.12.6.1.2.1.1.7
		voipGIPPPPoEMode OBJECT-TYPE
			SYNTAX INTEGER
				{
				auto(0),
				chap(1),
				pap(2)
				}
			MAX-ACCESS read-only
			STATUS current
			DESCRIPTION
				"Description."
			::= { voipGlobalIPEntry 7 }

		
--          1.3.6.1.4.1.37950.1.1.5.12.6.1.2.1.1.8
-- 1.3.6.1.4.1.37950.1.1.5.12.6.1.2.1.1.8
-- 1.3.6.1.4.1.37950.1.1.5.12.6.1.2.1.1.8
-- 1.3.6.1.4.1.37950.1.1.5.12.6.1.2.1.1.8
-- 1.3.6.1.4.1.37950.1.1.5.12.6.1.2.1.1.8
-- 1.3.6.1.4.1.37950.1.1.5.12.6.1.2.1.1.8
-- 1.3.6.1.4.1.37950.1.1.5.12.6.1.2.1.1.8
-- 1.3.6.1.4.1.37950.1.1.5.12.6.1.2.1.1.8
-- 1.3.6.1.4.1.37950.1.1.5.12.6.1.2.1.1.8
		-- 1.3.6.1.4.1.37950.1.1.5.12.6.1.2.1.1.8
		voipGIPPPPoEUserName OBJECT-TYPE
			SYNTAX OCTET STRING
			MAX-ACCESS read-only
			STATUS current
			DESCRIPTION
				"Description."
			::= { voipGlobalIPEntry 8 }

		
--          1.3.6.1.4.1.37950.1.1.5.12.6.1.2.1.1.9
-- 1.3.6.1.4.1.37950.1.1.5.12.6.1.2.1.1.9
-- 1.3.6.1.4.1.37950.1.1.5.12.6.1.2.1.1.9
-- 1.3.6.1.4.1.37950.1.1.5.12.6.1.2.1.1.9
-- 1.3.6.1.4.1.37950.1.1.5.12.6.1.2.1.1.9
-- 1.3.6.1.4.1.37950.1.1.5.12.6.1.2.1.1.9
-- 1.3.6.1.4.1.37950.1.1.5.12.6.1.2.1.1.9
-- 1.3.6.1.4.1.37950.1.1.5.12.6.1.2.1.1.9
-- 1.3.6.1.4.1.37950.1.1.5.12.6.1.2.1.1.9
		-- 1.3.6.1.4.1.37950.1.1.5.12.6.1.2.1.1.9
		voipGIPPPPoEPasswd OBJECT-TYPE
			SYNTAX OCTET STRING
			MAX-ACCESS read-only
			STATUS current
			DESCRIPTION
				"Description."
			::= { voipGlobalIPEntry 9 }

		
--          1.3.6.1.4.1.37950.1.1.5.12.6.1.2.1.1.10
-- 1.3.6.1.4.1.37950.1.1.5.12.6.1.2.1.1.10
-- 1.3.6.1.4.1.37950.1.1.5.12.6.1.2.1.1.10
-- 1.3.6.1.4.1.37950.1.1.5.12.6.1.2.1.1.10
-- 1.3.6.1.4.1.37950.1.1.5.12.6.1.2.1.1.10
-- 1.3.6.1.4.1.37950.1.1.5.12.6.1.2.1.1.10
-- 1.3.6.1.4.1.37950.1.1.5.12.6.1.2.1.1.10
-- 1.3.6.1.4.1.37950.1.1.5.12.6.1.2.1.1.10
-- 1.3.6.1.4.1.37950.1.1.5.12.6.1.2.1.1.10
		-- 1.3.6.1.4.1.37950.1.1.5.12.6.1.2.1.1.10
		voipGIPTagFlag OBJECT-TYPE
			SYNTAX INTEGER
				{
				transparent(0),
				tag(1),
				vlan-stacking(2)
				}
			MAX-ACCESS read-only
			STATUS current
			DESCRIPTION
				"Description."
			::= { voipGlobalIPEntry 10 }

		
--          1.3.6.1.4.1.37950.1.1.5.12.6.1.2.1.1.11
-- 1.3.6.1.4.1.37950.1.1.5.12.6.1.2.1.1.11
-- 1.3.6.1.4.1.37950.1.1.5.12.6.1.2.1.1.11
-- 1.3.6.1.4.1.37950.1.1.5.12.6.1.2.1.1.11
-- 1.3.6.1.4.1.37950.1.1.5.12.6.1.2.1.1.11
-- 1.3.6.1.4.1.37950.1.1.5.12.6.1.2.1.1.11
-- 1.3.6.1.4.1.37950.1.1.5.12.6.1.2.1.1.11
-- 1.3.6.1.4.1.37950.1.1.5.12.6.1.2.1.1.11
-- 1.3.6.1.4.1.37950.1.1.5.12.6.1.2.1.1.11
		-- 1.3.6.1.4.1.37950.1.1.5.12.6.1.2.1.1.11
		voipGIPCVlan OBJECT-TYPE
			SYNTAX Integer32
			MAX-ACCESS read-only
			STATUS current
			DESCRIPTION
				"Description."
			::= { voipGlobalIPEntry 11 }

		
--          1.3.6.1.4.1.37950.1.1.5.12.6.1.2.1.1.12
-- 1.3.6.1.4.1.37950.1.1.5.12.6.1.2.1.1.12
-- 1.3.6.1.4.1.37950.1.1.5.12.6.1.2.1.1.12
-- 1.3.6.1.4.1.37950.1.1.5.12.6.1.2.1.1.12
-- 1.3.6.1.4.1.37950.1.1.5.12.6.1.2.1.1.12
-- 1.3.6.1.4.1.37950.1.1.5.12.6.1.2.1.1.12
-- 1.3.6.1.4.1.37950.1.1.5.12.6.1.2.1.1.12
-- 1.3.6.1.4.1.37950.1.1.5.12.6.1.2.1.1.12
-- 1.3.6.1.4.1.37950.1.1.5.12.6.1.2.1.1.12
		-- 1.3.6.1.4.1.37950.1.1.5.12.6.1.2.1.1.12
		voipGIPSVlan OBJECT-TYPE
			SYNTAX Integer32
			MAX-ACCESS read-only
			STATUS current
			DESCRIPTION
				"Description."
			::= { voipGlobalIPEntry 12 }

		
--          1.3.6.1.4.1.37950.1.1.5.12.6.1.2.1.1.13
-- 1.3.6.1.4.1.37950.1.1.5.12.6.1.2.1.1.13
-- 1.3.6.1.4.1.37950.1.1.5.12.6.1.2.1.1.13
-- 1.3.6.1.4.1.37950.1.1.5.12.6.1.2.1.1.13
-- 1.3.6.1.4.1.37950.1.1.5.12.6.1.2.1.1.13
-- 1.3.6.1.4.1.37950.1.1.5.12.6.1.2.1.1.13
-- 1.3.6.1.4.1.37950.1.1.5.12.6.1.2.1.1.13
-- 1.3.6.1.4.1.37950.1.1.5.12.6.1.2.1.1.13
-- 1.3.6.1.4.1.37950.1.1.5.12.6.1.2.1.1.13
		-- 1.3.6.1.4.1.37950.1.1.5.12.6.1.2.1.1.13
		voipGIPPriority OBJECT-TYPE
			SYNTAX Integer32
			MAX-ACCESS read-only
			STATUS current
			DESCRIPTION
				"Description."
			::= { voipGlobalIPEntry 13 }

		
--          1.3.6.1.4.1.37950.1.1.5.12.6.1.2.2
-- 1.3.6.1.4.1.37950.1.1.5.12.6.1.2.2
-- 1.3.6.1.4.1.37950.1.1.5.12.6.1.2.2
-- 1.3.6.1.4.1.37950.1.1.5.12.6.1.2.2
-- 1.3.6.1.4.1.37950.1.1.5.12.6.1.2.2
-- 1.3.6.1.4.1.37950.1.1.5.12.6.1.2.2
-- 1.3.6.1.4.1.37950.1.1.5.12.6.1.2.2
-- 1.3.6.1.4.1.37950.1.1.5.12.6.1.2.2
-- 1.3.6.1.4.1.37950.1.1.5.12.6.1.2.2
		-- 1.3.6.1.4.1.37950.1.1.5.12.6.1.2.2
		voipPortMngTable OBJECT-TYPE
			SYNTAX SEQUENCE OF VoipPortMngEntry
			MAX-ACCESS not-accessible
			STATUS current
			DESCRIPTION
				"Description."
			::= { voipGlobalInfo 2 }

		
--          1.3.6.1.4.1.37950.1.1.5.12.6.1.2.2.1
-- 1.3.6.1.4.1.37950.1.1.5.12.6.1.2.2.1
-- 1.3.6.1.4.1.37950.1.1.5.12.6.1.2.2.1
-- 1.3.6.1.4.1.37950.1.1.5.12.6.1.2.2.1
-- 1.3.6.1.4.1.37950.1.1.5.12.6.1.2.2.1
-- 1.3.6.1.4.1.37950.1.1.5.12.6.1.2.2.1
-- 1.3.6.1.4.1.37950.1.1.5.12.6.1.2.2.1
-- 1.3.6.1.4.1.37950.1.1.5.12.6.1.2.2.1
-- 1.3.6.1.4.1.37950.1.1.5.12.6.1.2.2.1
		-- 1.3.6.1.4.1.37950.1.1.5.12.6.1.2.2.1
		voipPortMngEntry OBJECT-TYPE
			SYNTAX VoipPortMngEntry
			MAX-ACCESS not-accessible
			STATUS current
			DESCRIPTION
				"Description."
			INDEX { voipMngTPonNo, voipMngTOnuNo, voipMngTPotsNo }
			::= { voipPortMngTable 1 }

		
		VoipPortMngEntry ::=
			SEQUENCE { 
				voipMngTPonNo
					Integer32,
				voipMngTOnuNo
					Integer32,
				voipMngTPotsNo
					Integer32,
				voipMngTPortManage
					INTEGER
			 }

--          1.3.6.1.4.1.37950.1.1.5.12.6.1.2.2.1.1
-- 1.3.6.1.4.1.37950.1.1.5.12.6.1.2.2.1.1
-- 1.3.6.1.4.1.37950.1.1.5.12.6.1.2.2.1.1
-- 1.3.6.1.4.1.37950.1.1.5.12.6.1.2.2.1.1
-- 1.3.6.1.4.1.37950.1.1.5.12.6.1.2.2.1.1
-- 1.3.6.1.4.1.37950.1.1.5.12.6.1.2.2.1.1
-- 1.3.6.1.4.1.37950.1.1.5.12.6.1.2.2.1.1
-- 1.3.6.1.4.1.37950.1.1.5.12.6.1.2.2.1.1
-- 1.3.6.1.4.1.37950.1.1.5.12.6.1.2.2.1.1
		-- 1.3.6.1.4.1.37950.1.1.5.12.6.1.2.2.1.1
		voipMngTPonNo OBJECT-TYPE
			SYNTAX Integer32
			MAX-ACCESS read-only
			STATUS current
			DESCRIPTION
				"Description."
			::= { voipPortMngEntry 1 }

		
--          1.3.6.1.4.1.37950.1.1.5.12.6.1.2.2.1.2
-- 1.3.6.1.4.1.37950.1.1.5.12.6.1.2.2.1.2
-- 1.3.6.1.4.1.37950.1.1.5.12.6.1.2.2.1.2
-- 1.3.6.1.4.1.37950.1.1.5.12.6.1.2.2.1.2
-- 1.3.6.1.4.1.37950.1.1.5.12.6.1.2.2.1.2
-- 1.3.6.1.4.1.37950.1.1.5.12.6.1.2.2.1.2
-- 1.3.6.1.4.1.37950.1.1.5.12.6.1.2.2.1.2
-- 1.3.6.1.4.1.37950.1.1.5.12.6.1.2.2.1.2
-- 1.3.6.1.4.1.37950.1.1.5.12.6.1.2.2.1.2
		-- 1.3.6.1.4.1.37950.1.1.5.12.6.1.2.2.1.2
		voipMngTOnuNo OBJECT-TYPE
			SYNTAX Integer32
			MAX-ACCESS read-only
			STATUS current
			DESCRIPTION
				"Description."
			::= { voipPortMngEntry 2 }

		
--          1.3.6.1.4.1.37950.1.1.5.12.6.1.2.2.1.3
-- 1.3.6.1.4.1.37950.1.1.5.12.6.1.2.2.1.3
-- 1.3.6.1.4.1.37950.1.1.5.12.6.1.2.2.1.3
-- 1.3.6.1.4.1.37950.1.1.5.12.6.1.2.2.1.3
-- 1.3.6.1.4.1.37950.1.1.5.12.6.1.2.2.1.3
-- 1.3.6.1.4.1.37950.1.1.5.12.6.1.2.2.1.3
-- 1.3.6.1.4.1.37950.1.1.5.12.6.1.2.2.1.3
-- 1.3.6.1.4.1.37950.1.1.5.12.6.1.2.2.1.3
-- 1.3.6.1.4.1.37950.1.1.5.12.6.1.2.2.1.3
		-- 1.3.6.1.4.1.37950.1.1.5.12.6.1.2.2.1.3
		voipMngTPotsNo OBJECT-TYPE
			SYNTAX Integer32
			MAX-ACCESS read-only
			STATUS current
			DESCRIPTION
				"Description."
			::= { voipPortMngEntry 3 }

		
--          1.3.6.1.4.1.37950.1.1.5.12.6.1.2.2.1.4
-- 1.3.6.1.4.1.37950.1.1.5.12.6.1.2.2.1.4
-- 1.3.6.1.4.1.37950.1.1.5.12.6.1.2.2.1.4
-- 1.3.6.1.4.1.37950.1.1.5.12.6.1.2.2.1.4
-- 1.3.6.1.4.1.37950.1.1.5.12.6.1.2.2.1.4
-- 1.3.6.1.4.1.37950.1.1.5.12.6.1.2.2.1.4
-- 1.3.6.1.4.1.37950.1.1.5.12.6.1.2.2.1.4
-- 1.3.6.1.4.1.37950.1.1.5.12.6.1.2.2.1.4
-- 1.3.6.1.4.1.37950.1.1.5.12.6.1.2.2.1.4
		-- 1.3.6.1.4.1.37950.1.1.5.12.6.1.2.2.1.4
		voipMngTPortManage OBJECT-TYPE
			SYNTAX INTEGER
				{
				disactive(0),
				active(1)
				}
			MAX-ACCESS read-only
			STATUS current
			DESCRIPTION
				"Description."
			::= { voipPortMngEntry 4 }

		
--          1.3.6.1.4.1.37950.1.1.5.12.6.1.2.3
-- 1.3.6.1.4.1.37950.1.1.5.12.6.1.2.3
-- 1.3.6.1.4.1.37950.1.1.5.12.6.1.2.3
-- 1.3.6.1.4.1.37950.1.1.5.12.6.1.2.3
-- 1.3.6.1.4.1.37950.1.1.5.12.6.1.2.3
-- 1.3.6.1.4.1.37950.1.1.5.12.6.1.2.3
-- 1.3.6.1.4.1.37950.1.1.5.12.6.1.2.3
-- 1.3.6.1.4.1.37950.1.1.5.12.6.1.2.3
-- 1.3.6.1.4.1.37950.1.1.5.12.6.1.2.3
		-- 1.3.6.1.4.1.37950.1.1.5.12.6.1.2.3
		voipIADInfoTable OBJECT-TYPE
			SYNTAX SEQUENCE OF VoipIADInfoEntry
			MAX-ACCESS not-accessible
			STATUS current
			DESCRIPTION
				"Description."
			::= { voipGlobalInfo 3 }

		
--          1.3.6.1.4.1.37950.1.1.5.12.6.1.2.3.1
-- 1.3.6.1.4.1.37950.1.1.5.12.6.1.2.3.1
-- 1.3.6.1.4.1.37950.1.1.5.12.6.1.2.3.1
-- 1.3.6.1.4.1.37950.1.1.5.12.6.1.2.3.1
-- 1.3.6.1.4.1.37950.1.1.5.12.6.1.2.3.1
-- 1.3.6.1.4.1.37950.1.1.5.12.6.1.2.3.1
-- 1.3.6.1.4.1.37950.1.1.5.12.6.1.2.3.1
-- 1.3.6.1.4.1.37950.1.1.5.12.6.1.2.3.1
-- 1.3.6.1.4.1.37950.1.1.5.12.6.1.2.3.1
		-- 1.3.6.1.4.1.37950.1.1.5.12.6.1.2.3.1
		voipIADInfoEntry OBJECT-TYPE
			SYNTAX VoipIADInfoEntry
			MAX-ACCESS not-accessible
			STATUS current
			DESCRIPTION
				"Description."
			INDEX { voipIADInfoPonNo, voipIADInfoOnuNo }
			::= { voipIADInfoTable 1 }

		
		VoipIADInfoEntry ::=
			SEQUENCE { 
				voipIADInfoPonNo
					Integer32,
				voipIADInfoOnuNo
					Integer32,
				voipIADInfoMacAddr
					OCTET STRING,
				voipIADInfoProtocolSupport
					INTEGER,
				voipIADInfoSoftVersion
					OCTET STRING,
				voipIADInfoSoftTime
					OCTET STRING,
				voipIADInfoUserCount
					Integer32
			 }

--          1.3.6.1.4.1.37950.1.1.5.12.6.1.2.3.1.1
-- 1.3.6.1.4.1.37950.1.1.5.12.6.1.2.3.1.1
-- 1.3.6.1.4.1.37950.1.1.5.12.6.1.2.3.1.1
-- 1.3.6.1.4.1.37950.1.1.5.12.6.1.2.3.1.1
-- 1.3.6.1.4.1.37950.1.1.5.12.6.1.2.3.1.1
-- 1.3.6.1.4.1.37950.1.1.5.12.6.1.2.3.1.1
-- 1.3.6.1.4.1.37950.1.1.5.12.6.1.2.3.1.1
-- 1.3.6.1.4.1.37950.1.1.5.12.6.1.2.3.1.1
-- 1.3.6.1.4.1.37950.1.1.5.12.6.1.2.3.1.1
		-- 1.3.6.1.4.1.37950.1.1.5.12.6.1.2.3.1.1
		voipIADInfoPonNo OBJECT-TYPE
			SYNTAX Integer32
			MAX-ACCESS read-only
			STATUS current
			DESCRIPTION
				"Description."
			::= { voipIADInfoEntry 1 }

		
--          1.3.6.1.4.1.37950.1.1.5.12.6.1.2.3.1.2
-- 1.3.6.1.4.1.37950.1.1.5.12.6.1.2.3.1.2
-- 1.3.6.1.4.1.37950.1.1.5.12.6.1.2.3.1.2
-- 1.3.6.1.4.1.37950.1.1.5.12.6.1.2.3.1.2
-- 1.3.6.1.4.1.37950.1.1.5.12.6.1.2.3.1.2
-- 1.3.6.1.4.1.37950.1.1.5.12.6.1.2.3.1.2
-- 1.3.6.1.4.1.37950.1.1.5.12.6.1.2.3.1.2
-- 1.3.6.1.4.1.37950.1.1.5.12.6.1.2.3.1.2
-- 1.3.6.1.4.1.37950.1.1.5.12.6.1.2.3.1.2
		-- 1.3.6.1.4.1.37950.1.1.5.12.6.1.2.3.1.2
		voipIADInfoOnuNo OBJECT-TYPE
			SYNTAX Integer32
			MAX-ACCESS read-only
			STATUS current
			DESCRIPTION
				"Description."
			::= { voipIADInfoEntry 2 }

		
--          1.3.6.1.4.1.37950.1.1.5.12.6.1.2.3.1.3
-- 1.3.6.1.4.1.37950.1.1.5.12.6.1.2.3.1.3
-- 1.3.6.1.4.1.37950.1.1.5.12.6.1.2.3.1.3
-- 1.3.6.1.4.1.37950.1.1.5.12.6.1.2.3.1.3
-- 1.3.6.1.4.1.37950.1.1.5.12.6.1.2.3.1.3
-- 1.3.6.1.4.1.37950.1.1.5.12.6.1.2.3.1.3
-- 1.3.6.1.4.1.37950.1.1.5.12.6.1.2.3.1.3
-- 1.3.6.1.4.1.37950.1.1.5.12.6.1.2.3.1.3
-- 1.3.6.1.4.1.37950.1.1.5.12.6.1.2.3.1.3
		-- 1.3.6.1.4.1.37950.1.1.5.12.6.1.2.3.1.3
		voipIADInfoMacAddr OBJECT-TYPE
			SYNTAX OCTET STRING
			MAX-ACCESS read-only
			STATUS current
			DESCRIPTION
				"Description."
			::= { voipIADInfoEntry 3 }

		
--          1.3.6.1.4.1.37950.1.1.5.12.6.1.2.3.1.4
-- 1.3.6.1.4.1.37950.1.1.5.12.6.1.2.3.1.4
-- 1.3.6.1.4.1.37950.1.1.5.12.6.1.2.3.1.4
-- 1.3.6.1.4.1.37950.1.1.5.12.6.1.2.3.1.4
-- 1.3.6.1.4.1.37950.1.1.5.12.6.1.2.3.1.4
-- 1.3.6.1.4.1.37950.1.1.5.12.6.1.2.3.1.4
-- 1.3.6.1.4.1.37950.1.1.5.12.6.1.2.3.1.4
-- 1.3.6.1.4.1.37950.1.1.5.12.6.1.2.3.1.4
-- 1.3.6.1.4.1.37950.1.1.5.12.6.1.2.3.1.4
		-- 1.3.6.1.4.1.37950.1.1.5.12.6.1.2.3.1.4
		voipIADInfoProtocolSupport OBJECT-TYPE
			SYNTAX INTEGER
				{
				h248(0),
				sip(1)
				}
			MAX-ACCESS read-only
			STATUS current
			DESCRIPTION
				"Description."
			::= { voipIADInfoEntry 4 }

		
--          1.3.6.1.4.1.37950.1.1.5.12.6.1.2.3.1.5
-- 1.3.6.1.4.1.37950.1.1.5.12.6.1.2.3.1.5
-- 1.3.6.1.4.1.37950.1.1.5.12.6.1.2.3.1.5
-- 1.3.6.1.4.1.37950.1.1.5.12.6.1.2.3.1.5
-- 1.3.6.1.4.1.37950.1.1.5.12.6.1.2.3.1.5
-- 1.3.6.1.4.1.37950.1.1.5.12.6.1.2.3.1.5
-- 1.3.6.1.4.1.37950.1.1.5.12.6.1.2.3.1.5
-- 1.3.6.1.4.1.37950.1.1.5.12.6.1.2.3.1.5
-- 1.3.6.1.4.1.37950.1.1.5.12.6.1.2.3.1.5
		-- 1.3.6.1.4.1.37950.1.1.5.12.6.1.2.3.1.5
		voipIADInfoSoftVersion OBJECT-TYPE
			SYNTAX OCTET STRING
			MAX-ACCESS read-only
			STATUS current
			DESCRIPTION
				"Description."
			::= { voipIADInfoEntry 5 }

		
--          1.3.6.1.4.1.37950.1.1.5.12.6.1.2.3.1.6
-- 1.3.6.1.4.1.37950.1.1.5.12.6.1.2.3.1.6
-- 1.3.6.1.4.1.37950.1.1.5.12.6.1.2.3.1.6
-- 1.3.6.1.4.1.37950.1.1.5.12.6.1.2.3.1.6
-- 1.3.6.1.4.1.37950.1.1.5.12.6.1.2.3.1.6
-- 1.3.6.1.4.1.37950.1.1.5.12.6.1.2.3.1.6
-- 1.3.6.1.4.1.37950.1.1.5.12.6.1.2.3.1.6
-- 1.3.6.1.4.1.37950.1.1.5.12.6.1.2.3.1.6
-- 1.3.6.1.4.1.37950.1.1.5.12.6.1.2.3.1.6
		-- 1.3.6.1.4.1.37950.1.1.5.12.6.1.2.3.1.6
		voipIADInfoSoftTime OBJECT-TYPE
			SYNTAX OCTET STRING
			MAX-ACCESS read-only
			STATUS current
			DESCRIPTION
				"Description."
			::= { voipIADInfoEntry 6 }

		
--          1.3.6.1.4.1.37950.1.1.5.12.6.1.2.3.1.7
-- 1.3.6.1.4.1.37950.1.1.5.12.6.1.2.3.1.7
-- 1.3.6.1.4.1.37950.1.1.5.12.6.1.2.3.1.7
-- 1.3.6.1.4.1.37950.1.1.5.12.6.1.2.3.1.7
-- 1.3.6.1.4.1.37950.1.1.5.12.6.1.2.3.1.7
-- 1.3.6.1.4.1.37950.1.1.5.12.6.1.2.3.1.7
-- 1.3.6.1.4.1.37950.1.1.5.12.6.1.2.3.1.7
-- 1.3.6.1.4.1.37950.1.1.5.12.6.1.2.3.1.7
-- 1.3.6.1.4.1.37950.1.1.5.12.6.1.2.3.1.7
		-- 1.3.6.1.4.1.37950.1.1.5.12.6.1.2.3.1.7
		voipIADInfoUserCount OBJECT-TYPE
			SYNTAX Integer32
			MAX-ACCESS read-only
			STATUS current
			DESCRIPTION
				"Description."
			::= { voipIADInfoEntry 7 }

		
--          1.3.6.1.4.1.37950.1.1.5.12.6.1.2.4
-- 1.3.6.1.4.1.37950.1.1.5.12.6.1.2.4
-- 1.3.6.1.4.1.37950.1.1.5.12.6.1.2.4
-- 1.3.6.1.4.1.37950.1.1.5.12.6.1.2.4
-- 1.3.6.1.4.1.37950.1.1.5.12.6.1.2.4
-- 1.3.6.1.4.1.37950.1.1.5.12.6.1.2.4
-- 1.3.6.1.4.1.37950.1.1.5.12.6.1.2.4
-- 1.3.6.1.4.1.37950.1.1.5.12.6.1.2.4
-- 1.3.6.1.4.1.37950.1.1.5.12.6.1.2.4
		-- 1.3.6.1.4.1.37950.1.1.5.12.6.1.2.4
		voipPotsStatusTable OBJECT-TYPE
			SYNTAX SEQUENCE OF VoipPotsStatusEntry
			MAX-ACCESS not-accessible
			STATUS current
			DESCRIPTION
				"Description."
			::= { voipGlobalInfo 4 }

		
--          1.3.6.1.4.1.37950.1.1.5.12.6.1.2.4.1
-- 1.3.6.1.4.1.37950.1.1.5.12.6.1.2.4.1
-- 1.3.6.1.4.1.37950.1.1.5.12.6.1.2.4.1
-- 1.3.6.1.4.1.37950.1.1.5.12.6.1.2.4.1
-- 1.3.6.1.4.1.37950.1.1.5.12.6.1.2.4.1
-- 1.3.6.1.4.1.37950.1.1.5.12.6.1.2.4.1
-- 1.3.6.1.4.1.37950.1.1.5.12.6.1.2.4.1
-- 1.3.6.1.4.1.37950.1.1.5.12.6.1.2.4.1
-- 1.3.6.1.4.1.37950.1.1.5.12.6.1.2.4.1
		-- 1.3.6.1.4.1.37950.1.1.5.12.6.1.2.4.1
		voipPotsStatusEntry OBJECT-TYPE
			SYNTAX VoipPotsStatusEntry
			MAX-ACCESS not-accessible
			STATUS current
			DESCRIPTION
				"Description."
			INDEX { voipPostStatusPonNo, voipPostStatusOnuNo, voipPostStatusPotsNo }
			::= { voipPotsStatusTable 1 }

		
		VoipPotsStatusEntry ::=
			SEQUENCE { 
				voipPostStatusPonNo
					Integer32,
				voipPostStatusOnuNo
					Integer32,
				voipPostStatusPotsNo
					Integer32,
				voipPostStatusPortStatus
					INTEGER,
				voipPostStatusServicesState
					INTEGER,
				voipPostStatusCodecMode
					INTEGER
			 }

--          1.3.6.1.4.1.37950.1.1.5.12.6.1.2.4.1.1
-- 1.3.6.1.4.1.37950.1.1.5.12.6.1.2.4.1.1
-- 1.3.6.1.4.1.37950.1.1.5.12.6.1.2.4.1.1
-- 1.3.6.1.4.1.37950.1.1.5.12.6.1.2.4.1.1
-- 1.3.6.1.4.1.37950.1.1.5.12.6.1.2.4.1.1
-- 1.3.6.1.4.1.37950.1.1.5.12.6.1.2.4.1.1
-- 1.3.6.1.4.1.37950.1.1.5.12.6.1.2.4.1.1
-- 1.3.6.1.4.1.37950.1.1.5.12.6.1.2.4.1.1
-- 1.3.6.1.4.1.37950.1.1.5.12.6.1.2.4.1.1
		-- 1.3.6.1.4.1.37950.1.1.5.12.6.1.2.4.1.1
		voipPostStatusPonNo OBJECT-TYPE
			SYNTAX Integer32
			MAX-ACCESS read-only
			STATUS current
			DESCRIPTION
				"Description."
			::= { voipPotsStatusEntry 1 }

		
--          1.3.6.1.4.1.37950.1.1.5.12.6.1.2.4.1.2
-- 1.3.6.1.4.1.37950.1.1.5.12.6.1.2.4.1.2
-- 1.3.6.1.4.1.37950.1.1.5.12.6.1.2.4.1.2
-- 1.3.6.1.4.1.37950.1.1.5.12.6.1.2.4.1.2
-- 1.3.6.1.4.1.37950.1.1.5.12.6.1.2.4.1.2
-- 1.3.6.1.4.1.37950.1.1.5.12.6.1.2.4.1.2
-- 1.3.6.1.4.1.37950.1.1.5.12.6.1.2.4.1.2
-- 1.3.6.1.4.1.37950.1.1.5.12.6.1.2.4.1.2
-- 1.3.6.1.4.1.37950.1.1.5.12.6.1.2.4.1.2
		-- 1.3.6.1.4.1.37950.1.1.5.12.6.1.2.4.1.2
		voipPostStatusOnuNo OBJECT-TYPE
			SYNTAX Integer32
			MAX-ACCESS read-only
			STATUS current
			DESCRIPTION
				"Description."
			::= { voipPotsStatusEntry 2 }

		
--          1.3.6.1.4.1.37950.1.1.5.12.6.1.2.4.1.3
-- 1.3.6.1.4.1.37950.1.1.5.12.6.1.2.4.1.3
-- 1.3.6.1.4.1.37950.1.1.5.12.6.1.2.4.1.3
-- 1.3.6.1.4.1.37950.1.1.5.12.6.1.2.4.1.3
-- 1.3.6.1.4.1.37950.1.1.5.12.6.1.2.4.1.3
-- 1.3.6.1.4.1.37950.1.1.5.12.6.1.2.4.1.3
-- 1.3.6.1.4.1.37950.1.1.5.12.6.1.2.4.1.3
-- 1.3.6.1.4.1.37950.1.1.5.12.6.1.2.4.1.3
-- 1.3.6.1.4.1.37950.1.1.5.12.6.1.2.4.1.3
		-- 1.3.6.1.4.1.37950.1.1.5.12.6.1.2.4.1.3
		voipPostStatusPotsNo OBJECT-TYPE
			SYNTAX Integer32
			MAX-ACCESS read-only
			STATUS current
			DESCRIPTION
				"Description."
			::= { voipPotsStatusEntry 3 }

		
--          1.3.6.1.4.1.37950.1.1.5.12.6.1.2.4.1.4
-- 1.3.6.1.4.1.37950.1.1.5.12.6.1.2.4.1.4
-- 1.3.6.1.4.1.37950.1.1.5.12.6.1.2.4.1.4
-- 1.3.6.1.4.1.37950.1.1.5.12.6.1.2.4.1.4
-- 1.3.6.1.4.1.37950.1.1.5.12.6.1.2.4.1.4
-- 1.3.6.1.4.1.37950.1.1.5.12.6.1.2.4.1.4
-- 1.3.6.1.4.1.37950.1.1.5.12.6.1.2.4.1.4
-- 1.3.6.1.4.1.37950.1.1.5.12.6.1.2.4.1.4
-- 1.3.6.1.4.1.37950.1.1.5.12.6.1.2.4.1.4
		-- 1.3.6.1.4.1.37950.1.1.5.12.6.1.2.4.1.4
		voipPostStatusPortStatus OBJECT-TYPE
			SYNTAX INTEGER
				{
				registering(0),
				idle(1),
				offhook(2),
				dialing(3),
				ringing(4),
				ring-back(5),
				connecting(6),
				connected(7),
				release-connection(8),
				register-fail(9),
				inactive(10)
				}
			MAX-ACCESS read-only
			STATUS current
			DESCRIPTION
				"Description."
			::= { voipPotsStatusEntry 4 }

		
--          1.3.6.1.4.1.37950.1.1.5.12.6.1.2.4.1.5
-- 1.3.6.1.4.1.37950.1.1.5.12.6.1.2.4.1.5
-- 1.3.6.1.4.1.37950.1.1.5.12.6.1.2.4.1.5
-- 1.3.6.1.4.1.37950.1.1.5.12.6.1.2.4.1.5
-- 1.3.6.1.4.1.37950.1.1.5.12.6.1.2.4.1.5
-- 1.3.6.1.4.1.37950.1.1.5.12.6.1.2.4.1.5
-- 1.3.6.1.4.1.37950.1.1.5.12.6.1.2.4.1.5
-- 1.3.6.1.4.1.37950.1.1.5.12.6.1.2.4.1.5
-- 1.3.6.1.4.1.37950.1.1.5.12.6.1.2.4.1.5
		-- 1.3.6.1.4.1.37950.1.1.5.12.6.1.2.4.1.5
		voipPostStatusServicesState OBJECT-TYPE
			SYNTAX INTEGER
				{
				endlocal(0),
				endremote(1),
				endauto(2),
				endnormal(3)
				}
			MAX-ACCESS read-only
			STATUS current
			DESCRIPTION
				"Description."
			::= { voipPotsStatusEntry 5 }

		
--          1.3.6.1.4.1.37950.1.1.5.12.6.1.2.4.1.6
-- 1.3.6.1.4.1.37950.1.1.5.12.6.1.2.4.1.6
-- 1.3.6.1.4.1.37950.1.1.5.12.6.1.2.4.1.6
-- 1.3.6.1.4.1.37950.1.1.5.12.6.1.2.4.1.6
-- 1.3.6.1.4.1.37950.1.1.5.12.6.1.2.4.1.6
-- 1.3.6.1.4.1.37950.1.1.5.12.6.1.2.4.1.6
-- 1.3.6.1.4.1.37950.1.1.5.12.6.1.2.4.1.6
-- 1.3.6.1.4.1.37950.1.1.5.12.6.1.2.4.1.6
-- 1.3.6.1.4.1.37950.1.1.5.12.6.1.2.4.1.6
		-- 1.3.6.1.4.1.37950.1.1.5.12.6.1.2.4.1.6
		voipPostStatusCodecMode OBJECT-TYPE
			SYNTAX INTEGER
				{
				g711a(0),
				g729(1),
				g711u(2),
				g723(3),
				g726(4),
				t38(5)
				}
			MAX-ACCESS read-only
			STATUS current
			DESCRIPTION
				"Description."
			::= { voipPotsStatusEntry 6 }

		
--          1.3.6.1.4.1.37950.1.1.5.12.6.1.3
-- 1.3.6.1.4.1.37950.1.1.5.12.6.1.3
-- 1.3.6.1.4.1.37950.1.1.5.12.6.1.3
-- 1.3.6.1.4.1.37950.1.1.5.12.6.1.3
-- 1.3.6.1.4.1.37950.1.1.5.12.6.1.3
-- 1.3.6.1.4.1.37950.1.1.5.12.6.1.3
-- 1.3.6.1.4.1.37950.1.1.5.12.6.1.3
-- 1.3.6.1.4.1.37950.1.1.5.12.6.1.3
-- 1.3.6.1.4.1.37950.1.1.5.12.6.1.3
		-- 1.3.6.1.4.1.37950.1.1.5.12.6.1.3
		voipH248Info OBJECT IDENTIFIER ::= { voipInfo 3 }

		
--          1.3.6.1.4.1.37950.1.1.5.12.6.1.3.1
-- 1.3.6.1.4.1.37950.1.1.5.12.6.1.3.1
-- 1.3.6.1.4.1.37950.1.1.5.12.6.1.3.1
-- 1.3.6.1.4.1.37950.1.1.5.12.6.1.3.1
-- 1.3.6.1.4.1.37950.1.1.5.12.6.1.3.1
-- 1.3.6.1.4.1.37950.1.1.5.12.6.1.3.1
-- 1.3.6.1.4.1.37950.1.1.5.12.6.1.3.1
-- 1.3.6.1.4.1.37950.1.1.5.12.6.1.3.1
-- 1.3.6.1.4.1.37950.1.1.5.12.6.1.3.1
		-- 1.3.6.1.4.1.37950.1.1.5.12.6.1.3.1
		h248IADStatusTable OBJECT-TYPE
			SYNTAX SEQUENCE OF H248IADStatusEntry
			MAX-ACCESS not-accessible
			STATUS current
			DESCRIPTION
				"Description."
			::= { voipH248Info 1 }

		
--          1.3.6.1.4.1.37950.1.1.5.12.6.1.3.1.1
-- 1.3.6.1.4.1.37950.1.1.5.12.6.1.3.1.1
-- 1.3.6.1.4.1.37950.1.1.5.12.6.1.3.1.1
-- 1.3.6.1.4.1.37950.1.1.5.12.6.1.3.1.1
-- 1.3.6.1.4.1.37950.1.1.5.12.6.1.3.1.1
-- 1.3.6.1.4.1.37950.1.1.5.12.6.1.3.1.1
-- 1.3.6.1.4.1.37950.1.1.5.12.6.1.3.1.1
-- 1.3.6.1.4.1.37950.1.1.5.12.6.1.3.1.1
-- 1.3.6.1.4.1.37950.1.1.5.12.6.1.3.1.1
		-- 1.3.6.1.4.1.37950.1.1.5.12.6.1.3.1.1
		h248IADStatusEntry OBJECT-TYPE
			SYNTAX H248IADStatusEntry
			MAX-ACCESS not-accessible
			STATUS current
			DESCRIPTION
				"Description."
			INDEX { h248IADStatusPonNo, h248IADStatusOnuNo }
			::= { h248IADStatusTable 1 }

		
		H248IADStatusEntry ::=
			SEQUENCE { 
				h248IADStatusPonNo
					Integer32,
				h248IADStatusOnuNo
					Integer32,
				h248IADOperStatus
					INTEGER
			 }

--          1.3.6.1.4.1.37950.1.1.5.12.6.1.3.1.1.1
-- 1.3.6.1.4.1.37950.1.1.5.12.6.1.3.1.1.1
-- 1.3.6.1.4.1.37950.1.1.5.12.6.1.3.1.1.1
-- 1.3.6.1.4.1.37950.1.1.5.12.6.1.3.1.1.1
-- 1.3.6.1.4.1.37950.1.1.5.12.6.1.3.1.1.1
-- 1.3.6.1.4.1.37950.1.1.5.12.6.1.3.1.1.1
-- 1.3.6.1.4.1.37950.1.1.5.12.6.1.3.1.1.1
-- 1.3.6.1.4.1.37950.1.1.5.12.6.1.3.1.1.1
-- 1.3.6.1.4.1.37950.1.1.5.12.6.1.3.1.1.1
		-- 1.3.6.1.4.1.37950.1.1.5.12.6.1.3.1.1.1
		h248IADStatusPonNo OBJECT-TYPE
			SYNTAX Integer32
			MAX-ACCESS read-only
			STATUS current
			DESCRIPTION
				"Description."
			::= { h248IADStatusEntry 1 }

		
--          1.3.6.1.4.1.37950.1.1.5.12.6.1.3.1.1.2
-- 1.3.6.1.4.1.37950.1.1.5.12.6.1.3.1.1.2
-- 1.3.6.1.4.1.37950.1.1.5.12.6.1.3.1.1.2
-- 1.3.6.1.4.1.37950.1.1.5.12.6.1.3.1.1.2
-- 1.3.6.1.4.1.37950.1.1.5.12.6.1.3.1.1.2
-- 1.3.6.1.4.1.37950.1.1.5.12.6.1.3.1.1.2
-- 1.3.6.1.4.1.37950.1.1.5.12.6.1.3.1.1.2
-- 1.3.6.1.4.1.37950.1.1.5.12.6.1.3.1.1.2
-- 1.3.6.1.4.1.37950.1.1.5.12.6.1.3.1.1.2
		-- 1.3.6.1.4.1.37950.1.1.5.12.6.1.3.1.1.2
		h248IADStatusOnuNo OBJECT-TYPE
			SYNTAX Integer32
			MAX-ACCESS read-only
			STATUS current
			DESCRIPTION
				"Description."
			::= { h248IADStatusEntry 2 }

		
--          1.3.6.1.4.1.37950.1.1.5.12.6.1.3.1.1.3
-- 1.3.6.1.4.1.37950.1.1.5.12.6.1.3.1.1.3
-- 1.3.6.1.4.1.37950.1.1.5.12.6.1.3.1.1.3
-- 1.3.6.1.4.1.37950.1.1.5.12.6.1.3.1.1.3
-- 1.3.6.1.4.1.37950.1.1.5.12.6.1.3.1.1.3
-- 1.3.6.1.4.1.37950.1.1.5.12.6.1.3.1.1.3
-- 1.3.6.1.4.1.37950.1.1.5.12.6.1.3.1.1.3
-- 1.3.6.1.4.1.37950.1.1.5.12.6.1.3.1.1.3
-- 1.3.6.1.4.1.37950.1.1.5.12.6.1.3.1.1.3
		-- 1.3.6.1.4.1.37950.1.1.5.12.6.1.3.1.1.3
		h248IADOperStatus OBJECT-TYPE
			SYNTAX INTEGER
				{
				registering(0),
				register-success(1),
				iad-fault(2),
				deregister(3),
				iad-restarting(4)
				}
			MAX-ACCESS read-only
			STATUS current
			DESCRIPTION
				"Description."
			::= { h248IADStatusEntry 3 }

		
--          1.3.6.1.4.1.37950.1.1.5.12.6.1.3.2
-- 1.3.6.1.4.1.37950.1.1.5.12.6.1.3.2
-- 1.3.6.1.4.1.37950.1.1.5.12.6.1.3.2
-- 1.3.6.1.4.1.37950.1.1.5.12.6.1.3.2
-- 1.3.6.1.4.1.37950.1.1.5.12.6.1.3.2
-- 1.3.6.1.4.1.37950.1.1.5.12.6.1.3.2
-- 1.3.6.1.4.1.37950.1.1.5.12.6.1.3.2
-- 1.3.6.1.4.1.37950.1.1.5.12.6.1.3.2
-- 1.3.6.1.4.1.37950.1.1.5.12.6.1.3.2
		-- 1.3.6.1.4.1.37950.1.1.5.12.6.1.3.2
		h248ParamTable OBJECT-TYPE
			SYNTAX SEQUENCE OF H248ParamEntry
			MAX-ACCESS not-accessible
			STATUS current
			DESCRIPTION
				"Description."
			::= { voipH248Info 2 }

		
--          1.3.6.1.4.1.37950.1.1.5.12.6.1.3.2.1
-- 1.3.6.1.4.1.37950.1.1.5.12.6.1.3.2.1
-- 1.3.6.1.4.1.37950.1.1.5.12.6.1.3.2.1
-- 1.3.6.1.4.1.37950.1.1.5.12.6.1.3.2.1
-- 1.3.6.1.4.1.37950.1.1.5.12.6.1.3.2.1
-- 1.3.6.1.4.1.37950.1.1.5.12.6.1.3.2.1
-- 1.3.6.1.4.1.37950.1.1.5.12.6.1.3.2.1
-- 1.3.6.1.4.1.37950.1.1.5.12.6.1.3.2.1
-- 1.3.6.1.4.1.37950.1.1.5.12.6.1.3.2.1
		-- 1.3.6.1.4.1.37950.1.1.5.12.6.1.3.2.1
		h248ParamEntry OBJECT-TYPE
			SYNTAX H248ParamEntry
			MAX-ACCESS not-accessible
			STATUS current
			DESCRIPTION
				"Description."
			INDEX { h248ParamTPonNo, h248ParamTOnuNo }
			::= { h248ParamTable 1 }

		
		H248ParamEntry ::=
			SEQUENCE { 
				h248ParamTPonNo
					Integer32,
				h248ParamTOnuNo
					Integer32,
				h248ParamTMGPortNo
					Integer32,
				h248ParamTMGCIP
					IpAddress,
				h248ParamTMgcComPortNo
					Integer32,
				h248ParamTBackupMGCIP
					IpAddress,
				h248ParamTBackupMgcComPortNo
					Integer32,
				h248ParamTActiveMGC
					INTEGER,
				h248ParamTRegMode
					INTEGER,
				h248ParamTMID
					OCTET STRING,
				h248ParamTHBMode
					INTEGER,
				h248ParamTHBCycle
					Integer32,
				h248ParamTHBCount
					Integer32
			 }

--          1.3.6.1.4.1.37950.1.1.5.12.6.1.3.2.1.1
-- 1.3.6.1.4.1.37950.1.1.5.12.6.1.3.2.1.1
-- 1.3.6.1.4.1.37950.1.1.5.12.6.1.3.2.1.1
-- 1.3.6.1.4.1.37950.1.1.5.12.6.1.3.2.1.1
-- 1.3.6.1.4.1.37950.1.1.5.12.6.1.3.2.1.1
-- 1.3.6.1.4.1.37950.1.1.5.12.6.1.3.2.1.1
-- 1.3.6.1.4.1.37950.1.1.5.12.6.1.3.2.1.1
-- 1.3.6.1.4.1.37950.1.1.5.12.6.1.3.2.1.1
-- 1.3.6.1.4.1.37950.1.1.5.12.6.1.3.2.1.1
		-- 1.3.6.1.4.1.37950.1.1.5.12.6.1.3.2.1.1
		h248ParamTPonNo OBJECT-TYPE
			SYNTAX Integer32
			MAX-ACCESS read-only
			STATUS current
			DESCRIPTION
				"Description."
			::= { h248ParamEntry 1 }

		
--          1.3.6.1.4.1.37950.1.1.5.12.6.1.3.2.1.2
-- 1.3.6.1.4.1.37950.1.1.5.12.6.1.3.2.1.2
-- 1.3.6.1.4.1.37950.1.1.5.12.6.1.3.2.1.2
-- 1.3.6.1.4.1.37950.1.1.5.12.6.1.3.2.1.2
-- 1.3.6.1.4.1.37950.1.1.5.12.6.1.3.2.1.2
-- 1.3.6.1.4.1.37950.1.1.5.12.6.1.3.2.1.2
-- 1.3.6.1.4.1.37950.1.1.5.12.6.1.3.2.1.2
-- 1.3.6.1.4.1.37950.1.1.5.12.6.1.3.2.1.2
-- 1.3.6.1.4.1.37950.1.1.5.12.6.1.3.2.1.2
		-- 1.3.6.1.4.1.37950.1.1.5.12.6.1.3.2.1.2
		h248ParamTOnuNo OBJECT-TYPE
			SYNTAX Integer32
			MAX-ACCESS read-only
			STATUS current
			DESCRIPTION
				"Description."
			::= { h248ParamEntry 2 }

		
--          1.3.6.1.4.1.37950.1.1.5.12.6.1.3.2.1.3
-- 1.3.6.1.4.1.37950.1.1.5.12.6.1.3.2.1.3
-- 1.3.6.1.4.1.37950.1.1.5.12.6.1.3.2.1.3
-- 1.3.6.1.4.1.37950.1.1.5.12.6.1.3.2.1.3
-- 1.3.6.1.4.1.37950.1.1.5.12.6.1.3.2.1.3
-- 1.3.6.1.4.1.37950.1.1.5.12.6.1.3.2.1.3
-- 1.3.6.1.4.1.37950.1.1.5.12.6.1.3.2.1.3
-- 1.3.6.1.4.1.37950.1.1.5.12.6.1.3.2.1.3
-- 1.3.6.1.4.1.37950.1.1.5.12.6.1.3.2.1.3
		-- 1.3.6.1.4.1.37950.1.1.5.12.6.1.3.2.1.3
		h248ParamTMGPortNo OBJECT-TYPE
			SYNTAX Integer32
			MAX-ACCESS read-only
			STATUS current
			DESCRIPTION
				"Description."
			::= { h248ParamEntry 3 }

		
--          1.3.6.1.4.1.37950.1.1.5.12.6.1.3.2.1.4
-- 1.3.6.1.4.1.37950.1.1.5.12.6.1.3.2.1.4
-- 1.3.6.1.4.1.37950.1.1.5.12.6.1.3.2.1.4
-- 1.3.6.1.4.1.37950.1.1.5.12.6.1.3.2.1.4
-- 1.3.6.1.4.1.37950.1.1.5.12.6.1.3.2.1.4
-- 1.3.6.1.4.1.37950.1.1.5.12.6.1.3.2.1.4
-- 1.3.6.1.4.1.37950.1.1.5.12.6.1.3.2.1.4
-- 1.3.6.1.4.1.37950.1.1.5.12.6.1.3.2.1.4
-- 1.3.6.1.4.1.37950.1.1.5.12.6.1.3.2.1.4
		-- 1.3.6.1.4.1.37950.1.1.5.12.6.1.3.2.1.4
		h248ParamTMGCIP OBJECT-TYPE
			SYNTAX IpAddress
			MAX-ACCESS read-only
			STATUS current
			DESCRIPTION
				"Description."
			::= { h248ParamEntry 4 }

		
--          1.3.6.1.4.1.37950.1.1.5.12.6.1.3.2.1.5
-- 1.3.6.1.4.1.37950.1.1.5.12.6.1.3.2.1.5
-- 1.3.6.1.4.1.37950.1.1.5.12.6.1.3.2.1.5
-- 1.3.6.1.4.1.37950.1.1.5.12.6.1.3.2.1.5
-- 1.3.6.1.4.1.37950.1.1.5.12.6.1.3.2.1.5
-- 1.3.6.1.4.1.37950.1.1.5.12.6.1.3.2.1.5
-- 1.3.6.1.4.1.37950.1.1.5.12.6.1.3.2.1.5
-- 1.3.6.1.4.1.37950.1.1.5.12.6.1.3.2.1.5
-- 1.3.6.1.4.1.37950.1.1.5.12.6.1.3.2.1.5
		-- 1.3.6.1.4.1.37950.1.1.5.12.6.1.3.2.1.5
		h248ParamTMgcComPortNo OBJECT-TYPE
			SYNTAX Integer32
			MAX-ACCESS read-only
			STATUS current
			DESCRIPTION
				"Description."
			::= { h248ParamEntry 5 }

		
--          1.3.6.1.4.1.37950.1.1.5.12.6.1.3.2.1.6
-- 1.3.6.1.4.1.37950.1.1.5.12.6.1.3.2.1.6
-- 1.3.6.1.4.1.37950.1.1.5.12.6.1.3.2.1.6
-- 1.3.6.1.4.1.37950.1.1.5.12.6.1.3.2.1.6
-- 1.3.6.1.4.1.37950.1.1.5.12.6.1.3.2.1.6
-- 1.3.6.1.4.1.37950.1.1.5.12.6.1.3.2.1.6
-- 1.3.6.1.4.1.37950.1.1.5.12.6.1.3.2.1.6
-- 1.3.6.1.4.1.37950.1.1.5.12.6.1.3.2.1.6
-- 1.3.6.1.4.1.37950.1.1.5.12.6.1.3.2.1.6
		-- 1.3.6.1.4.1.37950.1.1.5.12.6.1.3.2.1.6
		h248ParamTBackupMGCIP OBJECT-TYPE
			SYNTAX IpAddress
			MAX-ACCESS read-only
			STATUS current
			DESCRIPTION
				"Description."
			::= { h248ParamEntry 6 }

		
--          1.3.6.1.4.1.37950.1.1.5.12.6.1.3.2.1.7
-- 1.3.6.1.4.1.37950.1.1.5.12.6.1.3.2.1.7
-- 1.3.6.1.4.1.37950.1.1.5.12.6.1.3.2.1.7
-- 1.3.6.1.4.1.37950.1.1.5.12.6.1.3.2.1.7
-- 1.3.6.1.4.1.37950.1.1.5.12.6.1.3.2.1.7
-- 1.3.6.1.4.1.37950.1.1.5.12.6.1.3.2.1.7
-- 1.3.6.1.4.1.37950.1.1.5.12.6.1.3.2.1.7
-- 1.3.6.1.4.1.37950.1.1.5.12.6.1.3.2.1.7
-- 1.3.6.1.4.1.37950.1.1.5.12.6.1.3.2.1.7
		-- 1.3.6.1.4.1.37950.1.1.5.12.6.1.3.2.1.7
		h248ParamTBackupMgcComPortNo OBJECT-TYPE
			SYNTAX Integer32
			MAX-ACCESS read-only
			STATUS current
			DESCRIPTION
				"Description."
			::= { h248ParamEntry 7 }

		
--          1.3.6.1.4.1.37950.1.1.5.12.6.1.3.2.1.8
-- 1.3.6.1.4.1.37950.1.1.5.12.6.1.3.2.1.8
-- 1.3.6.1.4.1.37950.1.1.5.12.6.1.3.2.1.8
-- 1.3.6.1.4.1.37950.1.1.5.12.6.1.3.2.1.8
-- 1.3.6.1.4.1.37950.1.1.5.12.6.1.3.2.1.8
-- 1.3.6.1.4.1.37950.1.1.5.12.6.1.3.2.1.8
-- 1.3.6.1.4.1.37950.1.1.5.12.6.1.3.2.1.8
-- 1.3.6.1.4.1.37950.1.1.5.12.6.1.3.2.1.8
-- 1.3.6.1.4.1.37950.1.1.5.12.6.1.3.2.1.8
		-- 1.3.6.1.4.1.37950.1.1.5.12.6.1.3.2.1.8
		h248ParamTActiveMGC OBJECT-TYPE
			SYNTAX INTEGER
				{
				backupmgc(0),
				mainmgc(1)
				}
			MAX-ACCESS read-only
			STATUS current
			DESCRIPTION
				"Description."
			::= { h248ParamEntry 8 }

		
--          1.3.6.1.4.1.37950.1.1.5.12.6.1.3.2.1.9
-- 1.3.6.1.4.1.37950.1.1.5.12.6.1.3.2.1.9
-- 1.3.6.1.4.1.37950.1.1.5.12.6.1.3.2.1.9
-- 1.3.6.1.4.1.37950.1.1.5.12.6.1.3.2.1.9
-- 1.3.6.1.4.1.37950.1.1.5.12.6.1.3.2.1.9
-- 1.3.6.1.4.1.37950.1.1.5.12.6.1.3.2.1.9
-- 1.3.6.1.4.1.37950.1.1.5.12.6.1.3.2.1.9
-- 1.3.6.1.4.1.37950.1.1.5.12.6.1.3.2.1.9
-- 1.3.6.1.4.1.37950.1.1.5.12.6.1.3.2.1.9
		-- 1.3.6.1.4.1.37950.1.1.5.12.6.1.3.2.1.9
		h248ParamTRegMode OBJECT-TYPE
			SYNTAX INTEGER
				{
				ipaddr(0),
				domain-name(1),
				device-name(2)
				}
			MAX-ACCESS read-only
			STATUS current
			DESCRIPTION
				"Description."
			::= { h248ParamEntry 9 }

		
--          1.3.6.1.4.1.37950.1.1.5.12.6.1.3.2.1.10
-- 1.3.6.1.4.1.37950.1.1.5.12.6.1.3.2.1.10
-- 1.3.6.1.4.1.37950.1.1.5.12.6.1.3.2.1.10
-- 1.3.6.1.4.1.37950.1.1.5.12.6.1.3.2.1.10
-- 1.3.6.1.4.1.37950.1.1.5.12.6.1.3.2.1.10
-- 1.3.6.1.4.1.37950.1.1.5.12.6.1.3.2.1.10
-- 1.3.6.1.4.1.37950.1.1.5.12.6.1.3.2.1.10
-- 1.3.6.1.4.1.37950.1.1.5.12.6.1.3.2.1.10
-- 1.3.6.1.4.1.37950.1.1.5.12.6.1.3.2.1.10
		-- 1.3.6.1.4.1.37950.1.1.5.12.6.1.3.2.1.10
		h248ParamTMID OBJECT-TYPE
			SYNTAX OCTET STRING
			MAX-ACCESS read-only
			STATUS current
			DESCRIPTION
				"Description."
			::= { h248ParamEntry 10 }

		
--          1.3.6.1.4.1.37950.1.1.5.12.6.1.3.2.1.11
-- 1.3.6.1.4.1.37950.1.1.5.12.6.1.3.2.1.11
-- 1.3.6.1.4.1.37950.1.1.5.12.6.1.3.2.1.11
-- 1.3.6.1.4.1.37950.1.1.5.12.6.1.3.2.1.11
-- 1.3.6.1.4.1.37950.1.1.5.12.6.1.3.2.1.11
-- 1.3.6.1.4.1.37950.1.1.5.12.6.1.3.2.1.11
-- 1.3.6.1.4.1.37950.1.1.5.12.6.1.3.2.1.11
-- 1.3.6.1.4.1.37950.1.1.5.12.6.1.3.2.1.11
-- 1.3.6.1.4.1.37950.1.1.5.12.6.1.3.2.1.11
		-- 1.3.6.1.4.1.37950.1.1.5.12.6.1.3.2.1.11
		h248ParamTHBMode OBJECT-TYPE
			SYNTAX INTEGER
				{
				disable(0),
				h248(1)
				}
			MAX-ACCESS read-only
			STATUS current
			DESCRIPTION
				"Description."
			::= { h248ParamEntry 11 }

		
--          1.3.6.1.4.1.37950.1.1.5.12.6.1.3.2.1.12
-- 1.3.6.1.4.1.37950.1.1.5.12.6.1.3.2.1.12
-- 1.3.6.1.4.1.37950.1.1.5.12.6.1.3.2.1.12
-- 1.3.6.1.4.1.37950.1.1.5.12.6.1.3.2.1.12
-- 1.3.6.1.4.1.37950.1.1.5.12.6.1.3.2.1.12
-- 1.3.6.1.4.1.37950.1.1.5.12.6.1.3.2.1.12
-- 1.3.6.1.4.1.37950.1.1.5.12.6.1.3.2.1.12
-- 1.3.6.1.4.1.37950.1.1.5.12.6.1.3.2.1.12
-- 1.3.6.1.4.1.37950.1.1.5.12.6.1.3.2.1.12
		-- 1.3.6.1.4.1.37950.1.1.5.12.6.1.3.2.1.12
		h248ParamTHBCycle OBJECT-TYPE
			SYNTAX Integer32
			MAX-ACCESS read-only
			STATUS current
			DESCRIPTION
				"Description."
			::= { h248ParamEntry 12 }

		
--          1.3.6.1.4.1.37950.1.1.5.12.6.1.3.2.1.13
-- 1.3.6.1.4.1.37950.1.1.5.12.6.1.3.2.1.13
-- 1.3.6.1.4.1.37950.1.1.5.12.6.1.3.2.1.13
-- 1.3.6.1.4.1.37950.1.1.5.12.6.1.3.2.1.13
-- 1.3.6.1.4.1.37950.1.1.5.12.6.1.3.2.1.13
-- 1.3.6.1.4.1.37950.1.1.5.12.6.1.3.2.1.13
-- 1.3.6.1.4.1.37950.1.1.5.12.6.1.3.2.1.13
-- 1.3.6.1.4.1.37950.1.1.5.12.6.1.3.2.1.13
-- 1.3.6.1.4.1.37950.1.1.5.12.6.1.3.2.1.13
		-- 1.3.6.1.4.1.37950.1.1.5.12.6.1.3.2.1.13
		h248ParamTHBCount OBJECT-TYPE
			SYNTAX Integer32
			MAX-ACCESS read-only
			STATUS current
			DESCRIPTION
				"Description."
			::= { h248ParamEntry 13 }

		
--          1.3.6.1.4.1.37950.1.1.5.12.6.1.3.3
-- 1.3.6.1.4.1.37950.1.1.5.12.6.1.3.3
-- 1.3.6.1.4.1.37950.1.1.5.12.6.1.3.3
-- 1.3.6.1.4.1.37950.1.1.5.12.6.1.3.3
-- 1.3.6.1.4.1.37950.1.1.5.12.6.1.3.3
-- 1.3.6.1.4.1.37950.1.1.5.12.6.1.3.3
-- 1.3.6.1.4.1.37950.1.1.5.12.6.1.3.3
-- 1.3.6.1.4.1.37950.1.1.5.12.6.1.3.3
-- 1.3.6.1.4.1.37950.1.1.5.12.6.1.3.3
		-- 1.3.6.1.4.1.37950.1.1.5.12.6.1.3.3
		h248UserTidTable OBJECT-TYPE
			SYNTAX SEQUENCE OF H248UserTidEntry
			MAX-ACCESS not-accessible
			STATUS current
			DESCRIPTION
				"Description."
			::= { voipH248Info 3 }

		
--          1.3.6.1.4.1.37950.1.1.5.12.6.1.3.3.1
-- 1.3.6.1.4.1.37950.1.1.5.12.6.1.3.3.1
-- 1.3.6.1.4.1.37950.1.1.5.12.6.1.3.3.1
-- 1.3.6.1.4.1.37950.1.1.5.12.6.1.3.3.1
-- 1.3.6.1.4.1.37950.1.1.5.12.6.1.3.3.1
-- 1.3.6.1.4.1.37950.1.1.5.12.6.1.3.3.1
-- 1.3.6.1.4.1.37950.1.1.5.12.6.1.3.3.1
-- 1.3.6.1.4.1.37950.1.1.5.12.6.1.3.3.1
-- 1.3.6.1.4.1.37950.1.1.5.12.6.1.3.3.1
		-- 1.3.6.1.4.1.37950.1.1.5.12.6.1.3.3.1
		h248UserTidEntry OBJECT-TYPE
			SYNTAX H248UserTidEntry
			MAX-ACCESS not-accessible
			STATUS current
			DESCRIPTION
				"Description."
			INDEX { h248UserTIDPonNo, h248UserTIDOnuNo, h248UserTIDPotsNo }
			::= { h248UserTidTable 1 }

		
		H248UserTidEntry ::=
			SEQUENCE { 
				h248UserTIDPonNo
					Integer32,
				h248UserTIDOnuNo
					Integer32,
				h248UserTIDPotsNo
					Integer32,
				h248UserTIDName
					OCTET STRING
			 }

--          1.3.6.1.4.1.37950.1.1.5.12.6.1.3.3.1.1
-- 1.3.6.1.4.1.37950.1.1.5.12.6.1.3.3.1.1
-- 1.3.6.1.4.1.37950.1.1.5.12.6.1.3.3.1.1
-- 1.3.6.1.4.1.37950.1.1.5.12.6.1.3.3.1.1
-- 1.3.6.1.4.1.37950.1.1.5.12.6.1.3.3.1.1
-- 1.3.6.1.4.1.37950.1.1.5.12.6.1.3.3.1.1
-- 1.3.6.1.4.1.37950.1.1.5.12.6.1.3.3.1.1
-- 1.3.6.1.4.1.37950.1.1.5.12.6.1.3.3.1.1
-- 1.3.6.1.4.1.37950.1.1.5.12.6.1.3.3.1.1
		-- 1.3.6.1.4.1.37950.1.1.5.12.6.1.3.3.1.1
		h248UserTIDPonNo OBJECT-TYPE
			SYNTAX Integer32
			MAX-ACCESS read-only
			STATUS current
			DESCRIPTION
				"Description."
			::= { h248UserTidEntry 1 }

		
--          1.3.6.1.4.1.37950.1.1.5.12.6.1.3.3.1.2
-- 1.3.6.1.4.1.37950.1.1.5.12.6.1.3.3.1.2
-- 1.3.6.1.4.1.37950.1.1.5.12.6.1.3.3.1.2
-- 1.3.6.1.4.1.37950.1.1.5.12.6.1.3.3.1.2
-- 1.3.6.1.4.1.37950.1.1.5.12.6.1.3.3.1.2
-- 1.3.6.1.4.1.37950.1.1.5.12.6.1.3.3.1.2
-- 1.3.6.1.4.1.37950.1.1.5.12.6.1.3.3.1.2
-- 1.3.6.1.4.1.37950.1.1.5.12.6.1.3.3.1.2
-- 1.3.6.1.4.1.37950.1.1.5.12.6.1.3.3.1.2
		-- 1.3.6.1.4.1.37950.1.1.5.12.6.1.3.3.1.2
		h248UserTIDOnuNo OBJECT-TYPE
			SYNTAX Integer32
			MAX-ACCESS read-only
			STATUS current
			DESCRIPTION
				"Description."
			::= { h248UserTidEntry 2 }

		
--          1.3.6.1.4.1.37950.1.1.5.12.6.1.3.3.1.3
-- 1.3.6.1.4.1.37950.1.1.5.12.6.1.3.3.1.3
-- 1.3.6.1.4.1.37950.1.1.5.12.6.1.3.3.1.3
-- 1.3.6.1.4.1.37950.1.1.5.12.6.1.3.3.1.3
-- 1.3.6.1.4.1.37950.1.1.5.12.6.1.3.3.1.3
-- 1.3.6.1.4.1.37950.1.1.5.12.6.1.3.3.1.3
-- 1.3.6.1.4.1.37950.1.1.5.12.6.1.3.3.1.3
-- 1.3.6.1.4.1.37950.1.1.5.12.6.1.3.3.1.3
-- 1.3.6.1.4.1.37950.1.1.5.12.6.1.3.3.1.3
		-- 1.3.6.1.4.1.37950.1.1.5.12.6.1.3.3.1.3
		h248UserTIDPotsNo OBJECT-TYPE
			SYNTAX Integer32
			MAX-ACCESS read-only
			STATUS current
			DESCRIPTION
				"Description."
			::= { h248UserTidEntry 3 }

		
--          1.3.6.1.4.1.37950.1.1.5.12.6.1.3.3.1.4
-- 1.3.6.1.4.1.37950.1.1.5.12.6.1.3.3.1.4
-- 1.3.6.1.4.1.37950.1.1.5.12.6.1.3.3.1.4
-- 1.3.6.1.4.1.37950.1.1.5.12.6.1.3.3.1.4
-- 1.3.6.1.4.1.37950.1.1.5.12.6.1.3.3.1.4
-- 1.3.6.1.4.1.37950.1.1.5.12.6.1.3.3.1.4
-- 1.3.6.1.4.1.37950.1.1.5.12.6.1.3.3.1.4
-- 1.3.6.1.4.1.37950.1.1.5.12.6.1.3.3.1.4
-- 1.3.6.1.4.1.37950.1.1.5.12.6.1.3.3.1.4
		-- 1.3.6.1.4.1.37950.1.1.5.12.6.1.3.3.1.4
		h248UserTIDName OBJECT-TYPE
			SYNTAX OCTET STRING
			MAX-ACCESS read-only
			STATUS current
			DESCRIPTION
				"Description."
			::= { h248UserTidEntry 4 }

		
--          1.3.6.1.4.1.37950.1.1.5.12.6.1.3.4
-- 1.3.6.1.4.1.37950.1.1.5.12.6.1.3.4
-- 1.3.6.1.4.1.37950.1.1.5.12.6.1.3.4
-- 1.3.6.1.4.1.37950.1.1.5.12.6.1.3.4
-- 1.3.6.1.4.1.37950.1.1.5.12.6.1.3.4
-- 1.3.6.1.4.1.37950.1.1.5.12.6.1.3.4
-- 1.3.6.1.4.1.37950.1.1.5.12.6.1.3.4
-- 1.3.6.1.4.1.37950.1.1.5.12.6.1.3.4
-- 1.3.6.1.4.1.37950.1.1.5.12.6.1.3.4
		-- 1.3.6.1.4.1.37950.1.1.5.12.6.1.3.4
		h248RTPTIDTable OBJECT-TYPE
			SYNTAX SEQUENCE OF H248RTPTIDEntry
			MAX-ACCESS not-accessible
			STATUS current
			DESCRIPTION
				"Description."
			::= { voipH248Info 4 }

		
--          1.3.6.1.4.1.37950.1.1.5.12.6.1.3.4.1
-- 1.3.6.1.4.1.37950.1.1.5.12.6.1.3.4.1
-- 1.3.6.1.4.1.37950.1.1.5.12.6.1.3.4.1
-- 1.3.6.1.4.1.37950.1.1.5.12.6.1.3.4.1
-- 1.3.6.1.4.1.37950.1.1.5.12.6.1.3.4.1
-- 1.3.6.1.4.1.37950.1.1.5.12.6.1.3.4.1
-- 1.3.6.1.4.1.37950.1.1.5.12.6.1.3.4.1
-- 1.3.6.1.4.1.37950.1.1.5.12.6.1.3.4.1
-- 1.3.6.1.4.1.37950.1.1.5.12.6.1.3.4.1
		-- 1.3.6.1.4.1.37950.1.1.5.12.6.1.3.4.1
		h248RTPTIDEntry OBJECT-TYPE
			SYNTAX H248RTPTIDEntry
			MAX-ACCESS not-accessible
			STATUS current
			DESCRIPTION
				"Description."
			INDEX { h248RTPTIDPonNo, h248RTPTIDOnuNo }
			::= { h248RTPTIDTable 1 }

		
		H248RTPTIDEntry ::=
			SEQUENCE { 
				h248RTPTIDPonNo
					Integer32,
				h248RTPTIDOnuNo
					Integer32,
				h248RTPTIDNumber
					Integer32,
				h248RTPTIDFirstName
					OCTET STRING
			 }

--          1.3.6.1.4.1.37950.1.1.5.12.6.1.3.4.1.1
-- 1.3.6.1.4.1.37950.1.1.5.12.6.1.3.4.1.1
-- 1.3.6.1.4.1.37950.1.1.5.12.6.1.3.4.1.1
-- 1.3.6.1.4.1.37950.1.1.5.12.6.1.3.4.1.1
-- 1.3.6.1.4.1.37950.1.1.5.12.6.1.3.4.1.1
-- 1.3.6.1.4.1.37950.1.1.5.12.6.1.3.4.1.1
-- 1.3.6.1.4.1.37950.1.1.5.12.6.1.3.4.1.1
-- 1.3.6.1.4.1.37950.1.1.5.12.6.1.3.4.1.1
-- 1.3.6.1.4.1.37950.1.1.5.12.6.1.3.4.1.1
		-- 1.3.6.1.4.1.37950.1.1.5.12.6.1.3.4.1.1
		h248RTPTIDPonNo OBJECT-TYPE
			SYNTAX Integer32
			MAX-ACCESS read-only
			STATUS current
			DESCRIPTION
				"Description."
			::= { h248RTPTIDEntry 1 }

		
--          1.3.6.1.4.1.37950.1.1.5.12.6.1.3.4.1.2
-- 1.3.6.1.4.1.37950.1.1.5.12.6.1.3.4.1.2
-- 1.3.6.1.4.1.37950.1.1.5.12.6.1.3.4.1.2
-- 1.3.6.1.4.1.37950.1.1.5.12.6.1.3.4.1.2
-- 1.3.6.1.4.1.37950.1.1.5.12.6.1.3.4.1.2
-- 1.3.6.1.4.1.37950.1.1.5.12.6.1.3.4.1.2
-- 1.3.6.1.4.1.37950.1.1.5.12.6.1.3.4.1.2
-- 1.3.6.1.4.1.37950.1.1.5.12.6.1.3.4.1.2
-- 1.3.6.1.4.1.37950.1.1.5.12.6.1.3.4.1.2
		-- 1.3.6.1.4.1.37950.1.1.5.12.6.1.3.4.1.2
		h248RTPTIDOnuNo OBJECT-TYPE
			SYNTAX Integer32
			MAX-ACCESS read-only
			STATUS current
			DESCRIPTION
				"Description."
			::= { h248RTPTIDEntry 2 }

		
--          1.3.6.1.4.1.37950.1.1.5.12.6.1.3.4.1.3
-- 1.3.6.1.4.1.37950.1.1.5.12.6.1.3.4.1.3
-- 1.3.6.1.4.1.37950.1.1.5.12.6.1.3.4.1.3
-- 1.3.6.1.4.1.37950.1.1.5.12.6.1.3.4.1.3
-- 1.3.6.1.4.1.37950.1.1.5.12.6.1.3.4.1.3
-- 1.3.6.1.4.1.37950.1.1.5.12.6.1.3.4.1.3
-- 1.3.6.1.4.1.37950.1.1.5.12.6.1.3.4.1.3
-- 1.3.6.1.4.1.37950.1.1.5.12.6.1.3.4.1.3
-- 1.3.6.1.4.1.37950.1.1.5.12.6.1.3.4.1.3
		-- 1.3.6.1.4.1.37950.1.1.5.12.6.1.3.4.1.3
		h248RTPTIDNumber OBJECT-TYPE
			SYNTAX Integer32
			MAX-ACCESS read-only
			STATUS current
			DESCRIPTION
				"Description."
			::= { h248RTPTIDEntry 3 }

		
--          1.3.6.1.4.1.37950.1.1.5.12.6.1.3.4.1.4
-- 1.3.6.1.4.1.37950.1.1.5.12.6.1.3.4.1.4
-- 1.3.6.1.4.1.37950.1.1.5.12.6.1.3.4.1.4
-- 1.3.6.1.4.1.37950.1.1.5.12.6.1.3.4.1.4
-- 1.3.6.1.4.1.37950.1.1.5.12.6.1.3.4.1.4
-- 1.3.6.1.4.1.37950.1.1.5.12.6.1.3.4.1.4
-- 1.3.6.1.4.1.37950.1.1.5.12.6.1.3.4.1.4
-- 1.3.6.1.4.1.37950.1.1.5.12.6.1.3.4.1.4
-- 1.3.6.1.4.1.37950.1.1.5.12.6.1.3.4.1.4
		-- 1.3.6.1.4.1.37950.1.1.5.12.6.1.3.4.1.4
		h248RTPTIDFirstName OBJECT-TYPE
			SYNTAX OCTET STRING
			MAX-ACCESS read-only
			STATUS current
			DESCRIPTION
				"Description."
			::= { h248RTPTIDEntry 4 }

		
--          1.3.6.1.4.1.37950.1.1.5.12.6.1.4
-- 1.3.6.1.4.1.37950.1.1.5.12.6.1.4
-- 1.3.6.1.4.1.37950.1.1.5.12.6.1.4
-- 1.3.6.1.4.1.37950.1.1.5.12.6.1.4
-- 1.3.6.1.4.1.37950.1.1.5.12.6.1.4
-- 1.3.6.1.4.1.37950.1.1.5.12.6.1.4
-- 1.3.6.1.4.1.37950.1.1.5.12.6.1.4
-- 1.3.6.1.4.1.37950.1.1.5.12.6.1.4
-- 1.3.6.1.4.1.37950.1.1.5.12.6.1.4
		-- 1.3.6.1.4.1.37950.1.1.5.12.6.1.4
		voipSipInfo OBJECT IDENTIFIER ::= { voipInfo 4 }

		
--          1.3.6.1.4.1.37950.1.1.5.12.6.1.4.1
-- 1.3.6.1.4.1.37950.1.1.5.12.6.1.4.1
-- 1.3.6.1.4.1.37950.1.1.5.12.6.1.4.1
-- 1.3.6.1.4.1.37950.1.1.5.12.6.1.4.1
-- 1.3.6.1.4.1.37950.1.1.5.12.6.1.4.1
-- 1.3.6.1.4.1.37950.1.1.5.12.6.1.4.1
-- 1.3.6.1.4.1.37950.1.1.5.12.6.1.4.1
-- 1.3.6.1.4.1.37950.1.1.5.12.6.1.4.1
-- 1.3.6.1.4.1.37950.1.1.5.12.6.1.4.1
		-- 1.3.6.1.4.1.37950.1.1.5.12.6.1.4.1
		sipParamTable OBJECT-TYPE
			SYNTAX SEQUENCE OF SipParamEntry
			MAX-ACCESS not-accessible
			STATUS current
			DESCRIPTION
				"Description."
			::= { voipSipInfo 1 }

		
--          1.3.6.1.4.1.37950.1.1.5.12.6.1.4.1.1
-- 1.3.6.1.4.1.37950.1.1.5.12.6.1.4.1.1
-- 1.3.6.1.4.1.37950.1.1.5.12.6.1.4.1.1
-- 1.3.6.1.4.1.37950.1.1.5.12.6.1.4.1.1
-- 1.3.6.1.4.1.37950.1.1.5.12.6.1.4.1.1
-- 1.3.6.1.4.1.37950.1.1.5.12.6.1.4.1.1
-- 1.3.6.1.4.1.37950.1.1.5.12.6.1.4.1.1
-- 1.3.6.1.4.1.37950.1.1.5.12.6.1.4.1.1
-- 1.3.6.1.4.1.37950.1.1.5.12.6.1.4.1.1
		-- 1.3.6.1.4.1.37950.1.1.5.12.6.1.4.1.1
		sipParamEntry OBJECT-TYPE
			SYNTAX SipParamEntry
			MAX-ACCESS not-accessible
			STATUS current
			DESCRIPTION
				"Description."
			INDEX { sipPTPonNo, sipPTOnuNo }
			::= { sipParamTable 1 }

		
		SipParamEntry ::=
			SEQUENCE { 
				sipPTPonNo
					Integer32,
				sipPTOnuNo
					Integer32,
				sipPTMGPortNo
					Integer32,
				sipPTProxyServIp
					IpAddress,
				sipPTPorxyServPortNo
					Integer32,
				sipPTBackupProxyServIp
					IpAddress,
				sipPTBackupPorxyServPortNo
					Integer32,
				sipPTActiveProxyServer
					IpAddress,
				sipPTRegServIp
					IpAddress,
				sipPTRegServPortNo
					Integer32,
				sipPTBackupRegServIp
					IpAddress,
				sipPTBackupRegServPortNo
					Integer32,
				sipPTOutBoundServIp
					IpAddress,
				sipPTOutBoundServPortNo
					Integer32,
				sipPTRegInterval
					Integer32,
				sipPTHeartbeatEn
					INTEGER,
				sipPTHeartbeatCycle
					INTEGER,
				sipPTHeartbeatCount
					INTEGER
			 }

--          1.3.6.1.4.1.37950.1.1.5.12.6.1.4.1.1.1
-- 1.3.6.1.4.1.37950.1.1.5.12.6.1.4.1.1.1
-- 1.3.6.1.4.1.37950.1.1.5.12.6.1.4.1.1.1
-- 1.3.6.1.4.1.37950.1.1.5.12.6.1.4.1.1.1
-- 1.3.6.1.4.1.37950.1.1.5.12.6.1.4.1.1.1
-- 1.3.6.1.4.1.37950.1.1.5.12.6.1.4.1.1.1
-- 1.3.6.1.4.1.37950.1.1.5.12.6.1.4.1.1.1
-- 1.3.6.1.4.1.37950.1.1.5.12.6.1.4.1.1.1
-- 1.3.6.1.4.1.37950.1.1.5.12.6.1.4.1.1.1
		-- 1.3.6.1.4.1.37950.1.1.5.12.6.1.4.1.1.1
		sipPTPonNo OBJECT-TYPE
			SYNTAX Integer32
			MAX-ACCESS read-only
			STATUS current
			DESCRIPTION
				"Description."
			::= { sipParamEntry 1 }

		
--          1.3.6.1.4.1.37950.1.1.5.12.6.1.4.1.1.2
-- 1.3.6.1.4.1.37950.1.1.5.12.6.1.4.1.1.2
-- 1.3.6.1.4.1.37950.1.1.5.12.6.1.4.1.1.2
-- 1.3.6.1.4.1.37950.1.1.5.12.6.1.4.1.1.2
-- 1.3.6.1.4.1.37950.1.1.5.12.6.1.4.1.1.2
-- 1.3.6.1.4.1.37950.1.1.5.12.6.1.4.1.1.2
-- 1.3.6.1.4.1.37950.1.1.5.12.6.1.4.1.1.2
-- 1.3.6.1.4.1.37950.1.1.5.12.6.1.4.1.1.2
-- 1.3.6.1.4.1.37950.1.1.5.12.6.1.4.1.1.2
		-- 1.3.6.1.4.1.37950.1.1.5.12.6.1.4.1.1.2
		sipPTOnuNo OBJECT-TYPE
			SYNTAX Integer32
			MAX-ACCESS read-only
			STATUS current
			DESCRIPTION
				"Description."
			::= { sipParamEntry 2 }

		
--          1.3.6.1.4.1.37950.1.1.5.12.6.1.4.1.1.3
-- 1.3.6.1.4.1.37950.1.1.5.12.6.1.4.1.1.3
-- 1.3.6.1.4.1.37950.1.1.5.12.6.1.4.1.1.3
-- 1.3.6.1.4.1.37950.1.1.5.12.6.1.4.1.1.3
-- 1.3.6.1.4.1.37950.1.1.5.12.6.1.4.1.1.3
-- 1.3.6.1.4.1.37950.1.1.5.12.6.1.4.1.1.3
-- 1.3.6.1.4.1.37950.1.1.5.12.6.1.4.1.1.3
-- 1.3.6.1.4.1.37950.1.1.5.12.6.1.4.1.1.3
-- 1.3.6.1.4.1.37950.1.1.5.12.6.1.4.1.1.3
		-- 1.3.6.1.4.1.37950.1.1.5.12.6.1.4.1.1.3
		sipPTMGPortNo OBJECT-TYPE
			SYNTAX Integer32
			MAX-ACCESS read-only
			STATUS current
			DESCRIPTION
				"Description."
			::= { sipParamEntry 3 }

		
--          1.3.6.1.4.1.37950.1.1.5.12.6.1.4.1.1.4
-- 1.3.6.1.4.1.37950.1.1.5.12.6.1.4.1.1.4
-- 1.3.6.1.4.1.37950.1.1.5.12.6.1.4.1.1.4
-- 1.3.6.1.4.1.37950.1.1.5.12.6.1.4.1.1.4
-- 1.3.6.1.4.1.37950.1.1.5.12.6.1.4.1.1.4
-- 1.3.6.1.4.1.37950.1.1.5.12.6.1.4.1.1.4
-- 1.3.6.1.4.1.37950.1.1.5.12.6.1.4.1.1.4
-- 1.3.6.1.4.1.37950.1.1.5.12.6.1.4.1.1.4
-- 1.3.6.1.4.1.37950.1.1.5.12.6.1.4.1.1.4
		-- 1.3.6.1.4.1.37950.1.1.5.12.6.1.4.1.1.4
		sipPTProxyServIp OBJECT-TYPE
			SYNTAX IpAddress
			MAX-ACCESS read-only
			STATUS current
			DESCRIPTION
				"Description."
			::= { sipParamEntry 4 }

		
--          1.3.6.1.4.1.37950.1.1.5.12.6.1.4.1.1.5
-- 1.3.6.1.4.1.37950.1.1.5.12.6.1.4.1.1.5
-- 1.3.6.1.4.1.37950.1.1.5.12.6.1.4.1.1.5
-- 1.3.6.1.4.1.37950.1.1.5.12.6.1.4.1.1.5
-- 1.3.6.1.4.1.37950.1.1.5.12.6.1.4.1.1.5
-- 1.3.6.1.4.1.37950.1.1.5.12.6.1.4.1.1.5
-- 1.3.6.1.4.1.37950.1.1.5.12.6.1.4.1.1.5
-- 1.3.6.1.4.1.37950.1.1.5.12.6.1.4.1.1.5
-- 1.3.6.1.4.1.37950.1.1.5.12.6.1.4.1.1.5
		-- 1.3.6.1.4.1.37950.1.1.5.12.6.1.4.1.1.5
		sipPTPorxyServPortNo OBJECT-TYPE
			SYNTAX Integer32
			MAX-ACCESS read-only
			STATUS current
			DESCRIPTION
				"Description."
			::= { sipParamEntry 5 }

		
--          1.3.6.1.4.1.37950.1.1.5.12.6.1.4.1.1.6
-- 1.3.6.1.4.1.37950.1.1.5.12.6.1.4.1.1.6
-- 1.3.6.1.4.1.37950.1.1.5.12.6.1.4.1.1.6
-- 1.3.6.1.4.1.37950.1.1.5.12.6.1.4.1.1.6
-- 1.3.6.1.4.1.37950.1.1.5.12.6.1.4.1.1.6
-- 1.3.6.1.4.1.37950.1.1.5.12.6.1.4.1.1.6
-- 1.3.6.1.4.1.37950.1.1.5.12.6.1.4.1.1.6
-- 1.3.6.1.4.1.37950.1.1.5.12.6.1.4.1.1.6
-- 1.3.6.1.4.1.37950.1.1.5.12.6.1.4.1.1.6
		-- 1.3.6.1.4.1.37950.1.1.5.12.6.1.4.1.1.6
		sipPTBackupProxyServIp OBJECT-TYPE
			SYNTAX IpAddress
			MAX-ACCESS read-only
			STATUS current
			DESCRIPTION
				"Description."
			::= { sipParamEntry 6 }

		
--          1.3.6.1.4.1.37950.1.1.5.12.6.1.4.1.1.7
-- 1.3.6.1.4.1.37950.1.1.5.12.6.1.4.1.1.7
-- 1.3.6.1.4.1.37950.1.1.5.12.6.1.4.1.1.7
-- 1.3.6.1.4.1.37950.1.1.5.12.6.1.4.1.1.7
-- 1.3.6.1.4.1.37950.1.1.5.12.6.1.4.1.1.7
-- 1.3.6.1.4.1.37950.1.1.5.12.6.1.4.1.1.7
-- 1.3.6.1.4.1.37950.1.1.5.12.6.1.4.1.1.7
-- 1.3.6.1.4.1.37950.1.1.5.12.6.1.4.1.1.7
-- 1.3.6.1.4.1.37950.1.1.5.12.6.1.4.1.1.7
		-- 1.3.6.1.4.1.37950.1.1.5.12.6.1.4.1.1.7
		sipPTBackupPorxyServPortNo OBJECT-TYPE
			SYNTAX Integer32
			MAX-ACCESS read-only
			STATUS current
			DESCRIPTION
				"Description."
			::= { sipParamEntry 7 }

		
--          1.3.6.1.4.1.37950.1.1.5.12.6.1.4.1.1.8
-- 1.3.6.1.4.1.37950.1.1.5.12.6.1.4.1.1.8
-- 1.3.6.1.4.1.37950.1.1.5.12.6.1.4.1.1.8
-- 1.3.6.1.4.1.37950.1.1.5.12.6.1.4.1.1.8
-- 1.3.6.1.4.1.37950.1.1.5.12.6.1.4.1.1.8
-- 1.3.6.1.4.1.37950.1.1.5.12.6.1.4.1.1.8
-- 1.3.6.1.4.1.37950.1.1.5.12.6.1.4.1.1.8
-- 1.3.6.1.4.1.37950.1.1.5.12.6.1.4.1.1.8
-- 1.3.6.1.4.1.37950.1.1.5.12.6.1.4.1.1.8
		-- 1.3.6.1.4.1.37950.1.1.5.12.6.1.4.1.1.8
		sipPTActiveProxyServer OBJECT-TYPE
			SYNTAX IpAddress
			MAX-ACCESS read-only
			STATUS current
			DESCRIPTION
				"Description."
			::= { sipParamEntry 8 }

		
--          1.3.6.1.4.1.37950.1.1.5.12.6.1.4.1.1.9
-- 1.3.6.1.4.1.37950.1.1.5.12.6.1.4.1.1.9
-- 1.3.6.1.4.1.37950.1.1.5.12.6.1.4.1.1.9
-- 1.3.6.1.4.1.37950.1.1.5.12.6.1.4.1.1.9
-- 1.3.6.1.4.1.37950.1.1.5.12.6.1.4.1.1.9
-- 1.3.6.1.4.1.37950.1.1.5.12.6.1.4.1.1.9
-- 1.3.6.1.4.1.37950.1.1.5.12.6.1.4.1.1.9
-- 1.3.6.1.4.1.37950.1.1.5.12.6.1.4.1.1.9
-- 1.3.6.1.4.1.37950.1.1.5.12.6.1.4.1.1.9
		-- 1.3.6.1.4.1.37950.1.1.5.12.6.1.4.1.1.9
		sipPTRegServIp OBJECT-TYPE
			SYNTAX IpAddress
			MAX-ACCESS read-only
			STATUS current
			DESCRIPTION
				"Description."
			::= { sipParamEntry 9 }

		
--          1.3.6.1.4.1.37950.1.1.5.12.6.1.4.1.1.10
-- 1.3.6.1.4.1.37950.1.1.5.12.6.1.4.1.1.10
-- 1.3.6.1.4.1.37950.1.1.5.12.6.1.4.1.1.10
-- 1.3.6.1.4.1.37950.1.1.5.12.6.1.4.1.1.10
-- 1.3.6.1.4.1.37950.1.1.5.12.6.1.4.1.1.10
-- 1.3.6.1.4.1.37950.1.1.5.12.6.1.4.1.1.10
-- 1.3.6.1.4.1.37950.1.1.5.12.6.1.4.1.1.10
-- 1.3.6.1.4.1.37950.1.1.5.12.6.1.4.1.1.10
-- 1.3.6.1.4.1.37950.1.1.5.12.6.1.4.1.1.10
		-- 1.3.6.1.4.1.37950.1.1.5.12.6.1.4.1.1.10
		sipPTRegServPortNo OBJECT-TYPE
			SYNTAX Integer32
			MAX-ACCESS read-only
			STATUS current
			DESCRIPTION
				"Description."
			::= { sipParamEntry 10 }

		
--          1.3.6.1.4.1.37950.1.1.5.12.6.1.4.1.1.11
-- 1.3.6.1.4.1.37950.1.1.5.12.6.1.4.1.1.11
-- 1.3.6.1.4.1.37950.1.1.5.12.6.1.4.1.1.11
-- 1.3.6.1.4.1.37950.1.1.5.12.6.1.4.1.1.11
-- 1.3.6.1.4.1.37950.1.1.5.12.6.1.4.1.1.11
-- 1.3.6.1.4.1.37950.1.1.5.12.6.1.4.1.1.11
-- 1.3.6.1.4.1.37950.1.1.5.12.6.1.4.1.1.11
-- 1.3.6.1.4.1.37950.1.1.5.12.6.1.4.1.1.11
-- 1.3.6.1.4.1.37950.1.1.5.12.6.1.4.1.1.11
		-- 1.3.6.1.4.1.37950.1.1.5.12.6.1.4.1.1.11
		sipPTBackupRegServIp OBJECT-TYPE
			SYNTAX IpAddress
			MAX-ACCESS read-only
			STATUS current
			DESCRIPTION
				"Description."
			::= { sipParamEntry 11 }

		
--          1.3.6.1.4.1.37950.1.1.5.12.6.1.4.1.1.12
-- 1.3.6.1.4.1.37950.1.1.5.12.6.1.4.1.1.12
-- 1.3.6.1.4.1.37950.1.1.5.12.6.1.4.1.1.12
-- 1.3.6.1.4.1.37950.1.1.5.12.6.1.4.1.1.12
-- 1.3.6.1.4.1.37950.1.1.5.12.6.1.4.1.1.12
-- 1.3.6.1.4.1.37950.1.1.5.12.6.1.4.1.1.12
-- 1.3.6.1.4.1.37950.1.1.5.12.6.1.4.1.1.12
-- 1.3.6.1.4.1.37950.1.1.5.12.6.1.4.1.1.12
-- 1.3.6.1.4.1.37950.1.1.5.12.6.1.4.1.1.12
		-- 1.3.6.1.4.1.37950.1.1.5.12.6.1.4.1.1.12
		sipPTBackupRegServPortNo OBJECT-TYPE
			SYNTAX Integer32
			MAX-ACCESS read-only
			STATUS current
			DESCRIPTION
				"Description."
			::= { sipParamEntry 12 }

		
--          1.3.6.1.4.1.37950.1.1.5.12.6.1.4.1.1.13
-- 1.3.6.1.4.1.37950.1.1.5.12.6.1.4.1.1.13
-- 1.3.6.1.4.1.37950.1.1.5.12.6.1.4.1.1.13
-- 1.3.6.1.4.1.37950.1.1.5.12.6.1.4.1.1.13
-- 1.3.6.1.4.1.37950.1.1.5.12.6.1.4.1.1.13
-- 1.3.6.1.4.1.37950.1.1.5.12.6.1.4.1.1.13
-- 1.3.6.1.4.1.37950.1.1.5.12.6.1.4.1.1.13
-- 1.3.6.1.4.1.37950.1.1.5.12.6.1.4.1.1.13
-- 1.3.6.1.4.1.37950.1.1.5.12.6.1.4.1.1.13
		-- 1.3.6.1.4.1.37950.1.1.5.12.6.1.4.1.1.13
		sipPTOutBoundServIp OBJECT-TYPE
			SYNTAX IpAddress
			MAX-ACCESS read-only
			STATUS current
			DESCRIPTION
				"Description."
			::= { sipParamEntry 13 }

		
--          1.3.6.1.4.1.37950.1.1.5.12.6.1.4.1.1.14
-- 1.3.6.1.4.1.37950.1.1.5.12.6.1.4.1.1.14
-- 1.3.6.1.4.1.37950.1.1.5.12.6.1.4.1.1.14
-- 1.3.6.1.4.1.37950.1.1.5.12.6.1.4.1.1.14
-- 1.3.6.1.4.1.37950.1.1.5.12.6.1.4.1.1.14
-- 1.3.6.1.4.1.37950.1.1.5.12.6.1.4.1.1.14
-- 1.3.6.1.4.1.37950.1.1.5.12.6.1.4.1.1.14
-- 1.3.6.1.4.1.37950.1.1.5.12.6.1.4.1.1.14
-- 1.3.6.1.4.1.37950.1.1.5.12.6.1.4.1.1.14
		-- 1.3.6.1.4.1.37950.1.1.5.12.6.1.4.1.1.14
		sipPTOutBoundServPortNo OBJECT-TYPE
			SYNTAX Integer32
			MAX-ACCESS read-only
			STATUS current
			DESCRIPTION
				"Description."
			::= { sipParamEntry 14 }

		
--          1.3.6.1.4.1.37950.1.1.5.12.6.1.4.1.1.15
-- 1.3.6.1.4.1.37950.1.1.5.12.6.1.4.1.1.15
-- 1.3.6.1.4.1.37950.1.1.5.12.6.1.4.1.1.15
-- 1.3.6.1.4.1.37950.1.1.5.12.6.1.4.1.1.15
-- 1.3.6.1.4.1.37950.1.1.5.12.6.1.4.1.1.15
-- 1.3.6.1.4.1.37950.1.1.5.12.6.1.4.1.1.15
-- 1.3.6.1.4.1.37950.1.1.5.12.6.1.4.1.1.15
-- 1.3.6.1.4.1.37950.1.1.5.12.6.1.4.1.1.15
-- 1.3.6.1.4.1.37950.1.1.5.12.6.1.4.1.1.15
		-- 1.3.6.1.4.1.37950.1.1.5.12.6.1.4.1.1.15
		sipPTRegInterval OBJECT-TYPE
			SYNTAX Integer32
			MAX-ACCESS read-only
			STATUS current
			DESCRIPTION
				"Description."
			::= { sipParamEntry 15 }

		
--          1.3.6.1.4.1.37950.1.1.5.12.6.1.4.1.1.16
-- 1.3.6.1.4.1.37950.1.1.5.12.6.1.4.1.1.16
-- 1.3.6.1.4.1.37950.1.1.5.12.6.1.4.1.1.16
-- 1.3.6.1.4.1.37950.1.1.5.12.6.1.4.1.1.16
-- 1.3.6.1.4.1.37950.1.1.5.12.6.1.4.1.1.16
-- 1.3.6.1.4.1.37950.1.1.5.12.6.1.4.1.1.16
-- 1.3.6.1.4.1.37950.1.1.5.12.6.1.4.1.1.16
-- 1.3.6.1.4.1.37950.1.1.5.12.6.1.4.1.1.16
-- 1.3.6.1.4.1.37950.1.1.5.12.6.1.4.1.1.16
		-- 1.3.6.1.4.1.37950.1.1.5.12.6.1.4.1.1.16
		sipPTHeartbeatEn OBJECT-TYPE
			SYNTAX INTEGER
				{
				enable(0),
				disable(1)
				}
			MAX-ACCESS read-only
			STATUS current
			DESCRIPTION
				"Description."
			::= { sipParamEntry 16 }

		
--          1.3.6.1.4.1.37950.1.1.5.12.6.1.4.1.1.17
-- 1.3.6.1.4.1.37950.1.1.5.12.6.1.4.1.1.17
-- 1.3.6.1.4.1.37950.1.1.5.12.6.1.4.1.1.17
-- 1.3.6.1.4.1.37950.1.1.5.12.6.1.4.1.1.17
-- 1.3.6.1.4.1.37950.1.1.5.12.6.1.4.1.1.17
-- 1.3.6.1.4.1.37950.1.1.5.12.6.1.4.1.1.17
-- 1.3.6.1.4.1.37950.1.1.5.12.6.1.4.1.1.17
-- 1.3.6.1.4.1.37950.1.1.5.12.6.1.4.1.1.17
-- 1.3.6.1.4.1.37950.1.1.5.12.6.1.4.1.1.17
		-- 1.3.6.1.4.1.37950.1.1.5.12.6.1.4.1.1.17
		sipPTHeartbeatCycle OBJECT-TYPE
			SYNTAX INTEGER
			MAX-ACCESS read-only
			STATUS current
			DESCRIPTION
				"Description."
			::= { sipParamEntry 17 }

		
--          1.3.6.1.4.1.37950.1.1.5.12.6.1.4.1.1.18
-- 1.3.6.1.4.1.37950.1.1.5.12.6.1.4.1.1.18
-- 1.3.6.1.4.1.37950.1.1.5.12.6.1.4.1.1.18
-- 1.3.6.1.4.1.37950.1.1.5.12.6.1.4.1.1.18
-- 1.3.6.1.4.1.37950.1.1.5.12.6.1.4.1.1.18
-- 1.3.6.1.4.1.37950.1.1.5.12.6.1.4.1.1.18
-- 1.3.6.1.4.1.37950.1.1.5.12.6.1.4.1.1.18
-- 1.3.6.1.4.1.37950.1.1.5.12.6.1.4.1.1.18
-- 1.3.6.1.4.1.37950.1.1.5.12.6.1.4.1.1.18
		-- 1.3.6.1.4.1.37950.1.1.5.12.6.1.4.1.1.18
		sipPTHeartbeatCount OBJECT-TYPE
			SYNTAX INTEGER
			MAX-ACCESS read-only
			STATUS current
			DESCRIPTION
				"Description."
			::= { sipParamEntry 18 }

		
--          1.3.6.1.4.1.37950.1.1.5.12.6.1.4.2
-- 1.3.6.1.4.1.37950.1.1.5.12.6.1.4.2
-- 1.3.6.1.4.1.37950.1.1.5.12.6.1.4.2
-- 1.3.6.1.4.1.37950.1.1.5.12.6.1.4.2
-- 1.3.6.1.4.1.37950.1.1.5.12.6.1.4.2
-- 1.3.6.1.4.1.37950.1.1.5.12.6.1.4.2
-- 1.3.6.1.4.1.37950.1.1.5.12.6.1.4.2
-- 1.3.6.1.4.1.37950.1.1.5.12.6.1.4.2
-- 1.3.6.1.4.1.37950.1.1.5.12.6.1.4.2
		-- 1.3.6.1.4.1.37950.1.1.5.12.6.1.4.2
		sipUserParamTable OBJECT-TYPE
			SYNTAX SEQUENCE OF SipUserParamEntry
			MAX-ACCESS not-accessible
			STATUS current
			DESCRIPTION
				"Description."
			::= { voipSipInfo 2 }

		
--          1.3.6.1.4.1.37950.1.1.5.12.6.1.4.2.1
-- 1.3.6.1.4.1.37950.1.1.5.12.6.1.4.2.1
-- 1.3.6.1.4.1.37950.1.1.5.12.6.1.4.2.1
-- 1.3.6.1.4.1.37950.1.1.5.12.6.1.4.2.1
-- 1.3.6.1.4.1.37950.1.1.5.12.6.1.4.2.1
-- 1.3.6.1.4.1.37950.1.1.5.12.6.1.4.2.1
-- 1.3.6.1.4.1.37950.1.1.5.12.6.1.4.2.1
-- 1.3.6.1.4.1.37950.1.1.5.12.6.1.4.2.1
-- 1.3.6.1.4.1.37950.1.1.5.12.6.1.4.2.1
		-- 1.3.6.1.4.1.37950.1.1.5.12.6.1.4.2.1
		sipUserParamEntry OBJECT-TYPE
			SYNTAX SipUserParamEntry
			MAX-ACCESS not-accessible
			STATUS current
			DESCRIPTION
				"Description."
			INDEX { sipUserParamPonNo, sipUserParamOnuNo, sipUserParamPotsNo }
			::= { sipUserParamTable 1 }

		
		SipUserParamEntry ::=
			SEQUENCE { 
				sipUserParamPonNo
					Integer32,
				sipUserParamOnuNo
					Integer32,
				sipUserParamPotsNo
					Integer32,
				sipUserParamUserAccount
					OCTET STRING,
				sipUserParamUserName
					OCTET STRING,
				sipUserParamUserPasswd
					OCTET STRING
			 }

--          1.3.6.1.4.1.37950.1.1.5.12.6.1.4.2.1.1
-- 1.3.6.1.4.1.37950.1.1.5.12.6.1.4.2.1.1
-- 1.3.6.1.4.1.37950.1.1.5.12.6.1.4.2.1.1
-- 1.3.6.1.4.1.37950.1.1.5.12.6.1.4.2.1.1
-- 1.3.6.1.4.1.37950.1.1.5.12.6.1.4.2.1.1
-- 1.3.6.1.4.1.37950.1.1.5.12.6.1.4.2.1.1
-- 1.3.6.1.4.1.37950.1.1.5.12.6.1.4.2.1.1
-- 1.3.6.1.4.1.37950.1.1.5.12.6.1.4.2.1.1
-- 1.3.6.1.4.1.37950.1.1.5.12.6.1.4.2.1.1
		-- 1.3.6.1.4.1.37950.1.1.5.12.6.1.4.2.1.1
		sipUserParamPonNo OBJECT-TYPE
			SYNTAX Integer32
			MAX-ACCESS read-only
			STATUS current
			DESCRIPTION
				"Description."
			::= { sipUserParamEntry 1 }

		
--          1.3.6.1.4.1.37950.1.1.5.12.6.1.4.2.1.2
-- 1.3.6.1.4.1.37950.1.1.5.12.6.1.4.2.1.2
-- 1.3.6.1.4.1.37950.1.1.5.12.6.1.4.2.1.2
-- 1.3.6.1.4.1.37950.1.1.5.12.6.1.4.2.1.2
-- 1.3.6.1.4.1.37950.1.1.5.12.6.1.4.2.1.2
-- 1.3.6.1.4.1.37950.1.1.5.12.6.1.4.2.1.2
-- 1.3.6.1.4.1.37950.1.1.5.12.6.1.4.2.1.2
-- 1.3.6.1.4.1.37950.1.1.5.12.6.1.4.2.1.2
-- 1.3.6.1.4.1.37950.1.1.5.12.6.1.4.2.1.2
		-- 1.3.6.1.4.1.37950.1.1.5.12.6.1.4.2.1.2
		sipUserParamOnuNo OBJECT-TYPE
			SYNTAX Integer32
			MAX-ACCESS read-only
			STATUS current
			DESCRIPTION
				"Description."
			::= { sipUserParamEntry 2 }

		
--          1.3.6.1.4.1.37950.1.1.5.12.6.1.4.2.1.3
-- 1.3.6.1.4.1.37950.1.1.5.12.6.1.4.2.1.3
-- 1.3.6.1.4.1.37950.1.1.5.12.6.1.4.2.1.3
-- 1.3.6.1.4.1.37950.1.1.5.12.6.1.4.2.1.3
-- 1.3.6.1.4.1.37950.1.1.5.12.6.1.4.2.1.3
-- 1.3.6.1.4.1.37950.1.1.5.12.6.1.4.2.1.3
-- 1.3.6.1.4.1.37950.1.1.5.12.6.1.4.2.1.3
-- 1.3.6.1.4.1.37950.1.1.5.12.6.1.4.2.1.3
-- 1.3.6.1.4.1.37950.1.1.5.12.6.1.4.2.1.3
		-- 1.3.6.1.4.1.37950.1.1.5.12.6.1.4.2.1.3
		sipUserParamPotsNo OBJECT-TYPE
			SYNTAX Integer32
			MAX-ACCESS read-only
			STATUS current
			DESCRIPTION
				"Description."
			::= { sipUserParamEntry 3 }

		
--          1.3.6.1.4.1.37950.1.1.5.12.6.1.4.2.1.4
-- 1.3.6.1.4.1.37950.1.1.5.12.6.1.4.2.1.4
-- 1.3.6.1.4.1.37950.1.1.5.12.6.1.4.2.1.4
-- 1.3.6.1.4.1.37950.1.1.5.12.6.1.4.2.1.4
-- 1.3.6.1.4.1.37950.1.1.5.12.6.1.4.2.1.4
-- 1.3.6.1.4.1.37950.1.1.5.12.6.1.4.2.1.4
-- 1.3.6.1.4.1.37950.1.1.5.12.6.1.4.2.1.4
-- 1.3.6.1.4.1.37950.1.1.5.12.6.1.4.2.1.4
-- 1.3.6.1.4.1.37950.1.1.5.12.6.1.4.2.1.4
		-- 1.3.6.1.4.1.37950.1.1.5.12.6.1.4.2.1.4
		sipUserParamUserAccount OBJECT-TYPE
			SYNTAX OCTET STRING
			MAX-ACCESS read-only
			STATUS current
			DESCRIPTION
				"Description."
			::= { sipUserParamEntry 4 }

		
--          1.3.6.1.4.1.37950.1.1.5.12.6.1.4.2.1.5
-- 1.3.6.1.4.1.37950.1.1.5.12.6.1.4.2.1.5
-- 1.3.6.1.4.1.37950.1.1.5.12.6.1.4.2.1.5
-- 1.3.6.1.4.1.37950.1.1.5.12.6.1.4.2.1.5
-- 1.3.6.1.4.1.37950.1.1.5.12.6.1.4.2.1.5
-- 1.3.6.1.4.1.37950.1.1.5.12.6.1.4.2.1.5
-- 1.3.6.1.4.1.37950.1.1.5.12.6.1.4.2.1.5
-- 1.3.6.1.4.1.37950.1.1.5.12.6.1.4.2.1.5
-- 1.3.6.1.4.1.37950.1.1.5.12.6.1.4.2.1.5
		-- 1.3.6.1.4.1.37950.1.1.5.12.6.1.4.2.1.5
		sipUserParamUserName OBJECT-TYPE
			SYNTAX OCTET STRING
			MAX-ACCESS read-only
			STATUS current
			DESCRIPTION
				"Description."
			::= { sipUserParamEntry 5 }

		
--          1.3.6.1.4.1.37950.1.1.5.12.6.1.4.2.1.6
-- 1.3.6.1.4.1.37950.1.1.5.12.6.1.4.2.1.6
-- 1.3.6.1.4.1.37950.1.1.5.12.6.1.4.2.1.6
-- 1.3.6.1.4.1.37950.1.1.5.12.6.1.4.2.1.6
-- 1.3.6.1.4.1.37950.1.1.5.12.6.1.4.2.1.6
-- 1.3.6.1.4.1.37950.1.1.5.12.6.1.4.2.1.6
-- 1.3.6.1.4.1.37950.1.1.5.12.6.1.4.2.1.6
-- 1.3.6.1.4.1.37950.1.1.5.12.6.1.4.2.1.6
-- 1.3.6.1.4.1.37950.1.1.5.12.6.1.4.2.1.6
		-- 1.3.6.1.4.1.37950.1.1.5.12.6.1.4.2.1.6
		sipUserParamUserPasswd OBJECT-TYPE
			SYNTAX OCTET STRING
			MAX-ACCESS read-only
			STATUS current
			DESCRIPTION
				"Description."
			::= { sipUserParamEntry 6 }

		
--          1.3.6.1.4.1.37950.1.1.5.12.6.1.4.3
-- 1.3.6.1.4.1.37950.1.1.5.12.6.1.4.3
-- 1.3.6.1.4.1.37950.1.1.5.12.6.1.4.3
-- 1.3.6.1.4.1.37950.1.1.5.12.6.1.4.3
-- 1.3.6.1.4.1.37950.1.1.5.12.6.1.4.3
-- 1.3.6.1.4.1.37950.1.1.5.12.6.1.4.3
-- 1.3.6.1.4.1.37950.1.1.5.12.6.1.4.3
-- 1.3.6.1.4.1.37950.1.1.5.12.6.1.4.3
-- 1.3.6.1.4.1.37950.1.1.5.12.6.1.4.3
		-- 1.3.6.1.4.1.37950.1.1.5.12.6.1.4.3
		faxModemCfgTable OBJECT-TYPE
			SYNTAX SEQUENCE OF FaxModemCfgEntry
			MAX-ACCESS not-accessible
			STATUS current
			DESCRIPTION
				"Description."
			::= { voipSipInfo 3 }

		
--          1.3.6.1.4.1.37950.1.1.5.12.6.1.4.3.1
-- 1.3.6.1.4.1.37950.1.1.5.12.6.1.4.3.1
-- 1.3.6.1.4.1.37950.1.1.5.12.6.1.4.3.1
-- 1.3.6.1.4.1.37950.1.1.5.12.6.1.4.3.1
-- 1.3.6.1.4.1.37950.1.1.5.12.6.1.4.3.1
-- 1.3.6.1.4.1.37950.1.1.5.12.6.1.4.3.1
-- 1.3.6.1.4.1.37950.1.1.5.12.6.1.4.3.1
-- 1.3.6.1.4.1.37950.1.1.5.12.6.1.4.3.1
-- 1.3.6.1.4.1.37950.1.1.5.12.6.1.4.3.1
		-- 1.3.6.1.4.1.37950.1.1.5.12.6.1.4.3.1
		faxModemCfgEntry OBJECT-TYPE
			SYNTAX FaxModemCfgEntry
			MAX-ACCESS not-accessible
			STATUS current
			DESCRIPTION
				"Description."
			INDEX { faxModemPonNo, faxModemOnuNo }
			::= { faxModemCfgTable 1 }

		
		FaxModemCfgEntry ::=
			SEQUENCE { 
				faxModemPonNo
					Integer32,
				faxModemOnuNo
					Integer32,
				faxModemVoiceT38En
					INTEGER,
				faxModemVoiceCtl
					INTEGER
			 }

--          1.3.6.1.4.1.37950.1.1.5.12.6.1.4.3.1.1
-- 1.3.6.1.4.1.37950.1.1.5.12.6.1.4.3.1.1
-- 1.3.6.1.4.1.37950.1.1.5.12.6.1.4.3.1.1
-- 1.3.6.1.4.1.37950.1.1.5.12.6.1.4.3.1.1
-- 1.3.6.1.4.1.37950.1.1.5.12.6.1.4.3.1.1
-- 1.3.6.1.4.1.37950.1.1.5.12.6.1.4.3.1.1
-- 1.3.6.1.4.1.37950.1.1.5.12.6.1.4.3.1.1
-- 1.3.6.1.4.1.37950.1.1.5.12.6.1.4.3.1.1
-- 1.3.6.1.4.1.37950.1.1.5.12.6.1.4.3.1.1
		-- 1.3.6.1.4.1.37950.1.1.5.12.6.1.4.3.1.1
		faxModemPonNo OBJECT-TYPE
			SYNTAX Integer32
			MAX-ACCESS read-only
			STATUS current
			DESCRIPTION
				"Description."
			::= { faxModemCfgEntry 1 }

		
--          1.3.6.1.4.1.37950.1.1.5.12.6.1.4.3.1.2
-- 1.3.6.1.4.1.37950.1.1.5.12.6.1.4.3.1.2
-- 1.3.6.1.4.1.37950.1.1.5.12.6.1.4.3.1.2
-- 1.3.6.1.4.1.37950.1.1.5.12.6.1.4.3.1.2
-- 1.3.6.1.4.1.37950.1.1.5.12.6.1.4.3.1.2
-- 1.3.6.1.4.1.37950.1.1.5.12.6.1.4.3.1.2
-- 1.3.6.1.4.1.37950.1.1.5.12.6.1.4.3.1.2
-- 1.3.6.1.4.1.37950.1.1.5.12.6.1.4.3.1.2
-- 1.3.6.1.4.1.37950.1.1.5.12.6.1.4.3.1.2
		-- 1.3.6.1.4.1.37950.1.1.5.12.6.1.4.3.1.2
		faxModemOnuNo OBJECT-TYPE
			SYNTAX Integer32
			MAX-ACCESS read-only
			STATUS current
			DESCRIPTION
				"Description."
			::= { faxModemCfgEntry 2 }

		
--          1.3.6.1.4.1.37950.1.1.5.12.6.1.4.3.1.3
-- 1.3.6.1.4.1.37950.1.1.5.12.6.1.4.3.1.3
-- 1.3.6.1.4.1.37950.1.1.5.12.6.1.4.3.1.3
-- 1.3.6.1.4.1.37950.1.1.5.12.6.1.4.3.1.3
-- 1.3.6.1.4.1.37950.1.1.5.12.6.1.4.3.1.3
-- 1.3.6.1.4.1.37950.1.1.5.12.6.1.4.3.1.3
-- 1.3.6.1.4.1.37950.1.1.5.12.6.1.4.3.1.3
-- 1.3.6.1.4.1.37950.1.1.5.12.6.1.4.3.1.3
-- 1.3.6.1.4.1.37950.1.1.5.12.6.1.4.3.1.3
		-- 1.3.6.1.4.1.37950.1.1.5.12.6.1.4.3.1.3
		faxModemVoiceT38En OBJECT-TYPE
			SYNTAX INTEGER
				{
				t30(0),
				t38(1)
				}
			MAX-ACCESS read-only
			STATUS current
			DESCRIPTION
				"Description."
			::= { faxModemCfgEntry 3 }

		
--          1.3.6.1.4.1.37950.1.1.5.12.6.1.4.3.1.4
-- 1.3.6.1.4.1.37950.1.1.5.12.6.1.4.3.1.4
-- 1.3.6.1.4.1.37950.1.1.5.12.6.1.4.3.1.4
-- 1.3.6.1.4.1.37950.1.1.5.12.6.1.4.3.1.4
-- 1.3.6.1.4.1.37950.1.1.5.12.6.1.4.3.1.4
-- 1.3.6.1.4.1.37950.1.1.5.12.6.1.4.3.1.4
-- 1.3.6.1.4.1.37950.1.1.5.12.6.1.4.3.1.4
-- 1.3.6.1.4.1.37950.1.1.5.12.6.1.4.3.1.4
-- 1.3.6.1.4.1.37950.1.1.5.12.6.1.4.3.1.4
		-- 1.3.6.1.4.1.37950.1.1.5.12.6.1.4.3.1.4
		faxModemVoiceCtl OBJECT-TYPE
			SYNTAX INTEGER
				{
				negotiation(0),
				auto-vbd(1)
				}
			MAX-ACCESS read-only
			STATUS current
			DESCRIPTION
				"Description."
			::= { faxModemCfgEntry 4 }

		
--         1.3.6.1.4.1.37950.1.1.5.12.6.1.4.4
-- 1.3.6.1.4.1.37950.1.1.5.12.6.1.4.4
-- 1.3.6.1.4.1.37950.1.1.5.12.6.1.4.4
-- 1.3.6.1.4.1.37950.1.1.5.12.6.1.4.4
-- 1.3.6.1.4.1.37950.1.1.5.12.6.1.4.4
-- 1.3.6.1.4.1.37950.1.1.5.12.6.1.4.4
-- 1.3.6.1.4.1.37950.1.1.5.12.6.1.4.4
-- 1.3.6.1.4.1.37950.1.1.5.12.6.1.4.4
		-- 1.3.6.1.4.1.37950.1.1.5.12.6.1.4.4
		sipDigitMapTable OBJECT-TYPE
			SYNTAX SEQUENCE OF SipDigitMapEntry
			MAX-ACCESS not-accessible
			STATUS current
			DESCRIPTION
				"Description."
			::= { voipSipInfo 4 }

		
--         1.3.6.1.4.1.37950.1.1.5.12.6.1.4.4.1
-- 1.3.6.1.4.1.37950.1.1.5.12.6.1.4.4.1
-- 1.3.6.1.4.1.37950.1.1.5.12.6.1.4.4.1
-- 1.3.6.1.4.1.37950.1.1.5.12.6.1.4.4.1
-- 1.3.6.1.4.1.37950.1.1.5.12.6.1.4.4.1
-- 1.3.6.1.4.1.37950.1.1.5.12.6.1.4.4.1
-- 1.3.6.1.4.1.37950.1.1.5.12.6.1.4.4.1
-- 1.3.6.1.4.1.37950.1.1.5.12.6.1.4.4.1
		-- 1.3.6.1.4.1.37950.1.1.5.12.6.1.4.4.1
		sipDigitMapEntry OBJECT-TYPE
			SYNTAX SipDigitMapEntry
			MAX-ACCESS not-accessible
			STATUS current
			DESCRIPTION
				"Description."
			INDEX { sipDigitMapPonNo, sipDigitMapOnuNo }
			::= { sipDigitMapTable 1 }

		
		SipDigitMapEntry ::=
			SEQUENCE { 
				sipDigitMapPonNo
					Integer32,
				sipDigitMapOnuNo
					Integer32,
				sipDigitMap
					OCTET STRING
			 }

--         1.3.6.1.4.1.37950.1.1.5.12.6.1.4.4.1.1
-- 1.3.6.1.4.1.37950.1.1.5.12.6.1.4.4.1.1
-- 1.3.6.1.4.1.37950.1.1.5.12.6.1.4.4.1.1
-- 1.3.6.1.4.1.37950.1.1.5.12.6.1.4.4.1.1
-- 1.3.6.1.4.1.37950.1.1.5.12.6.1.4.4.1.1
-- 1.3.6.1.4.1.37950.1.1.5.12.6.1.4.4.1.1
-- 1.3.6.1.4.1.37950.1.1.5.12.6.1.4.4.1.1
-- 1.3.6.1.4.1.37950.1.1.5.12.6.1.4.4.1.1
		-- 1.3.6.1.4.1.37950.1.1.5.12.6.1.4.4.1.1
		sipDigitMapPonNo OBJECT-TYPE
			SYNTAX Integer32
			MAX-ACCESS read-only
			STATUS current
			DESCRIPTION
				"Description."
			::= { sipDigitMapEntry 1 }

		
--         1.3.6.1.4.1.37950.1.1.5.12.6.1.4.4.1.2
-- 1.3.6.1.4.1.37950.1.1.5.12.6.1.4.4.1.2
-- 1.3.6.1.4.1.37950.1.1.5.12.6.1.4.4.1.2
-- 1.3.6.1.4.1.37950.1.1.5.12.6.1.4.4.1.2
-- 1.3.6.1.4.1.37950.1.1.5.12.6.1.4.4.1.2
-- 1.3.6.1.4.1.37950.1.1.5.12.6.1.4.4.1.2
-- 1.3.6.1.4.1.37950.1.1.5.12.6.1.4.4.1.2
-- 1.3.6.1.4.1.37950.1.1.5.12.6.1.4.4.1.2
		-- 1.3.6.1.4.1.37950.1.1.5.12.6.1.4.4.1.2
		sipDigitMapOnuNo OBJECT-TYPE
			SYNTAX Integer32
			MAX-ACCESS read-only
			STATUS current
			DESCRIPTION
				"Description."
			::= { sipDigitMapEntry 2 }

		
--         1.3.6.1.4.1.37950.1.1.5.12.6.1.4.4.1.3
-- 1.3.6.1.4.1.37950.1.1.5.12.6.1.4.4.1.3
-- 1.3.6.1.4.1.37950.1.1.5.12.6.1.4.4.1.3
-- 1.3.6.1.4.1.37950.1.1.5.12.6.1.4.4.1.3
-- 1.3.6.1.4.1.37950.1.1.5.12.6.1.4.4.1.3
-- 1.3.6.1.4.1.37950.1.1.5.12.6.1.4.4.1.3
-- 1.3.6.1.4.1.37950.1.1.5.12.6.1.4.4.1.3
-- 1.3.6.1.4.1.37950.1.1.5.12.6.1.4.4.1.3
		-- 1.3.6.1.4.1.37950.1.1.5.12.6.1.4.4.1.3
		sipDigitMap OBJECT-TYPE
			SYNTAX OCTET STRING
			MAX-ACCESS read-only
			STATUS current
			DESCRIPTION
				"Description."
			::= { sipDigitMapEntry 3 }

		
--          1.3.6.1.4.1.37950.1.1.5.12.6.2
-- 1.3.6.1.4.1.37950.1.1.5.12.6.2
-- 1.3.6.1.4.1.37950.1.1.5.12.6.2
-- 1.3.6.1.4.1.37950.1.1.5.12.6.2
-- 1.3.6.1.4.1.37950.1.1.5.12.6.2
-- 1.3.6.1.4.1.37950.1.1.5.12.6.2
-- 1.3.6.1.4.1.37950.1.1.5.12.6.2
-- 1.3.6.1.4.1.37950.1.1.5.12.6.2
-- 1.3.6.1.4.1.37950.1.1.5.12.6.2
		-- 1.3.6.1.4.1.37950.1.1.5.12.6.2
		voipGlobalCfg OBJECT IDENTIFIER ::= { onuVoipCfg 2 }

		
--          1.3.6.1.4.1.37950.1.1.5.12.6.2.1
-- 1.3.6.1.4.1.37950.1.1.5.12.6.2.1
-- 1.3.6.1.4.1.37950.1.1.5.12.6.2.1
-- 1.3.6.1.4.1.37950.1.1.5.12.6.2.1
-- 1.3.6.1.4.1.37950.1.1.5.12.6.2.1
-- 1.3.6.1.4.1.37950.1.1.5.12.6.2.1
-- 1.3.6.1.4.1.37950.1.1.5.12.6.2.1
-- 1.3.6.1.4.1.37950.1.1.5.12.6.2.1
-- 1.3.6.1.4.1.37950.1.1.5.12.6.2.1
		-- 1.3.6.1.4.1.37950.1.1.5.12.6.2.1
		voipGlobalIpCfg OBJECT IDENTIFIER ::= { voipGlobalCfg 1 }

		
--          1.3.6.1.4.1.37950.1.1.5.12.6.2.1.1
-- 1.3.6.1.4.1.37950.1.1.5.12.6.2.1.1
-- 1.3.6.1.4.1.37950.1.1.5.12.6.2.1.1
-- 1.3.6.1.4.1.37950.1.1.5.12.6.2.1.1
-- 1.3.6.1.4.1.37950.1.1.5.12.6.2.1.1
-- 1.3.6.1.4.1.37950.1.1.5.12.6.2.1.1
-- 1.3.6.1.4.1.37950.1.1.5.12.6.2.1.1
-- 1.3.6.1.4.1.37950.1.1.5.12.6.2.1.1
-- 1.3.6.1.4.1.37950.1.1.5.12.6.2.1.1
		-- 1.3.6.1.4.1.37950.1.1.5.12.6.2.1.1
		voipIpPonNo OBJECT-TYPE
			SYNTAX INTEGER (1..16)
			MAX-ACCESS read-write
			STATUS current
			DESCRIPTION
				"Description."
			::= { voipGlobalIpCfg 1 }

		
--          1.3.6.1.4.1.37950.1.1.5.12.6.2.1.2
-- 1.3.6.1.4.1.37950.1.1.5.12.6.2.1.2
-- 1.3.6.1.4.1.37950.1.1.5.12.6.2.1.2
-- 1.3.6.1.4.1.37950.1.1.5.12.6.2.1.2
-- 1.3.6.1.4.1.37950.1.1.5.12.6.2.1.2
-- 1.3.6.1.4.1.37950.1.1.5.12.6.2.1.2
-- 1.3.6.1.4.1.37950.1.1.5.12.6.2.1.2
-- 1.3.6.1.4.1.37950.1.1.5.12.6.2.1.2
-- 1.3.6.1.4.1.37950.1.1.5.12.6.2.1.2
		-- 1.3.6.1.4.1.37950.1.1.5.12.6.2.1.2
		voipIpOnuNo OBJECT-TYPE
			SYNTAX INTEGER (1..65535)
			MAX-ACCESS read-write
			STATUS current
			DESCRIPTION
				"Description."
			::= { voipGlobalIpCfg 2 }

		
--          1.3.6.1.4.1.37950.1.1.5.12.6.2.1.3
-- 1.3.6.1.4.1.37950.1.1.5.12.6.2.1.3
-- 1.3.6.1.4.1.37950.1.1.5.12.6.2.1.3
-- 1.3.6.1.4.1.37950.1.1.5.12.6.2.1.3
-- 1.3.6.1.4.1.37950.1.1.5.12.6.2.1.3
-- 1.3.6.1.4.1.37950.1.1.5.12.6.2.1.3
-- 1.3.6.1.4.1.37950.1.1.5.12.6.2.1.3
-- 1.3.6.1.4.1.37950.1.1.5.12.6.2.1.3
-- 1.3.6.1.4.1.37950.1.1.5.12.6.2.1.3
		-- 1.3.6.1.4.1.37950.1.1.5.12.6.2.1.3
		voipIpMode OBJECT-TYPE
			SYNTAX INTEGER
				{
				static-ip(0),
				dhcp(1),
				pppoe(2)
				}
			MAX-ACCESS read-write
			STATUS current
			DESCRIPTION
				"Description."
			::= { voipGlobalIpCfg 3 }

		
--          1.3.6.1.4.1.37950.1.1.5.12.6.2.1.4
-- 1.3.6.1.4.1.37950.1.1.5.12.6.2.1.4
-- 1.3.6.1.4.1.37950.1.1.5.12.6.2.1.4
-- 1.3.6.1.4.1.37950.1.1.5.12.6.2.1.4
-- 1.3.6.1.4.1.37950.1.1.5.12.6.2.1.4
-- 1.3.6.1.4.1.37950.1.1.5.12.6.2.1.4
-- 1.3.6.1.4.1.37950.1.1.5.12.6.2.1.4
-- 1.3.6.1.4.1.37950.1.1.5.12.6.2.1.4
-- 1.3.6.1.4.1.37950.1.1.5.12.6.2.1.4
		-- 1.3.6.1.4.1.37950.1.1.5.12.6.2.1.4
		voipStaticIpAddr OBJECT-TYPE
			SYNTAX IpAddress
			MAX-ACCESS read-write
			STATUS current
			DESCRIPTION
				"Description."
			::= { voipGlobalIpCfg 4 }

		
--          1.3.6.1.4.1.37950.1.1.5.12.6.2.1.5
-- 1.3.6.1.4.1.37950.1.1.5.12.6.2.1.5
-- 1.3.6.1.4.1.37950.1.1.5.12.6.2.1.5
-- 1.3.6.1.4.1.37950.1.1.5.12.6.2.1.5
-- 1.3.6.1.4.1.37950.1.1.5.12.6.2.1.5
-- 1.3.6.1.4.1.37950.1.1.5.12.6.2.1.5
-- 1.3.6.1.4.1.37950.1.1.5.12.6.2.1.5
-- 1.3.6.1.4.1.37950.1.1.5.12.6.2.1.5
-- 1.3.6.1.4.1.37950.1.1.5.12.6.2.1.5
		-- 1.3.6.1.4.1.37950.1.1.5.12.6.2.1.5
		voipStaticIpMask OBJECT-TYPE
			SYNTAX IpAddress
			MAX-ACCESS read-write
			STATUS current
			DESCRIPTION
				"Description."
			::= { voipGlobalIpCfg 5 }

		
--          1.3.6.1.4.1.37950.1.1.5.12.6.2.1.6
-- 1.3.6.1.4.1.37950.1.1.5.12.6.2.1.6
-- 1.3.6.1.4.1.37950.1.1.5.12.6.2.1.6
-- 1.3.6.1.4.1.37950.1.1.5.12.6.2.1.6
-- 1.3.6.1.4.1.37950.1.1.5.12.6.2.1.6
-- 1.3.6.1.4.1.37950.1.1.5.12.6.2.1.6
-- 1.3.6.1.4.1.37950.1.1.5.12.6.2.1.6
-- 1.3.6.1.4.1.37950.1.1.5.12.6.2.1.6
-- 1.3.6.1.4.1.37950.1.1.5.12.6.2.1.6
		-- 1.3.6.1.4.1.37950.1.1.5.12.6.2.1.6
		voipStaticIpGw OBJECT-TYPE
			SYNTAX IpAddress
			MAX-ACCESS read-write
			STATUS current
			DESCRIPTION
				"Description."
			::= { voipGlobalIpCfg 6 }

		
--          1.3.6.1.4.1.37950.1.1.5.12.6.2.1.7
-- 1.3.6.1.4.1.37950.1.1.5.12.6.2.1.7
-- 1.3.6.1.4.1.37950.1.1.5.12.6.2.1.7
-- 1.3.6.1.4.1.37950.1.1.5.12.6.2.1.7
-- 1.3.6.1.4.1.37950.1.1.5.12.6.2.1.7
-- 1.3.6.1.4.1.37950.1.1.5.12.6.2.1.7
-- 1.3.6.1.4.1.37950.1.1.5.12.6.2.1.7
-- 1.3.6.1.4.1.37950.1.1.5.12.6.2.1.7
-- 1.3.6.1.4.1.37950.1.1.5.12.6.2.1.7
		-- 1.3.6.1.4.1.37950.1.1.5.12.6.2.1.7
		voipPPPoEMode OBJECT-TYPE
			SYNTAX INTEGER
				{
				auto(0),
				chap(1),
				pap(2)
				}
			MAX-ACCESS read-write
			STATUS current
			DESCRIPTION
				"Description."
			::= { voipGlobalIpCfg 7 }

		
--          1.3.6.1.4.1.37950.1.1.5.12.6.2.1.8
-- 1.3.6.1.4.1.37950.1.1.5.12.6.2.1.8
-- 1.3.6.1.4.1.37950.1.1.5.12.6.2.1.8
-- 1.3.6.1.4.1.37950.1.1.5.12.6.2.1.8
-- 1.3.6.1.4.1.37950.1.1.5.12.6.2.1.8
-- 1.3.6.1.4.1.37950.1.1.5.12.6.2.1.8
-- 1.3.6.1.4.1.37950.1.1.5.12.6.2.1.8
-- 1.3.6.1.4.1.37950.1.1.5.12.6.2.1.8
-- 1.3.6.1.4.1.37950.1.1.5.12.6.2.1.8
		-- 1.3.6.1.4.1.37950.1.1.5.12.6.2.1.8
		voipPPPOEUserName OBJECT-TYPE
			SYNTAX OCTET STRING (SIZE (0..32))
			MAX-ACCESS read-write
			STATUS current
			DESCRIPTION
				"Description."
			::= { voipGlobalIpCfg 8 }

		
--          1.3.6.1.4.1.37950.1.1.5.12.6.2.1.9
-- 1.3.6.1.4.1.37950.1.1.5.12.6.2.1.9
-- 1.3.6.1.4.1.37950.1.1.5.12.6.2.1.9
-- 1.3.6.1.4.1.37950.1.1.5.12.6.2.1.9
-- 1.3.6.1.4.1.37950.1.1.5.12.6.2.1.9
-- 1.3.6.1.4.1.37950.1.1.5.12.6.2.1.9
-- 1.3.6.1.4.1.37950.1.1.5.12.6.2.1.9
-- 1.3.6.1.4.1.37950.1.1.5.12.6.2.1.9
-- 1.3.6.1.4.1.37950.1.1.5.12.6.2.1.9
		-- 1.3.6.1.4.1.37950.1.1.5.12.6.2.1.9
		voipPPPOEPasswd OBJECT-TYPE
			SYNTAX OCTET STRING (SIZE (0..32))
			MAX-ACCESS read-write
			STATUS current
			DESCRIPTION
				"Description."
			::= { voipGlobalIpCfg 9 }

		
--          1.3.6.1.4.1.37950.1.1.5.12.6.2.1.10
-- 1.3.6.1.4.1.37950.1.1.5.12.6.2.1.10
-- 1.3.6.1.4.1.37950.1.1.5.12.6.2.1.10
-- 1.3.6.1.4.1.37950.1.1.5.12.6.2.1.10
-- 1.3.6.1.4.1.37950.1.1.5.12.6.2.1.10
-- 1.3.6.1.4.1.37950.1.1.5.12.6.2.1.10
-- 1.3.6.1.4.1.37950.1.1.5.12.6.2.1.10
-- 1.3.6.1.4.1.37950.1.1.5.12.6.2.1.10
-- 1.3.6.1.4.1.37950.1.1.5.12.6.2.1.10
		-- 1.3.6.1.4.1.37950.1.1.5.12.6.2.1.10
		voipTagFlag OBJECT-TYPE
			SYNTAX INTEGER
				{
				transparent(0),
				tag(1),
				vlan-stacking(2)
				}
			MAX-ACCESS read-write
			STATUS current
			DESCRIPTION
				"Description."
			::= { voipGlobalIpCfg 10 }

		
--          1.3.6.1.4.1.37950.1.1.5.12.6.2.1.11
-- 1.3.6.1.4.1.37950.1.1.5.12.6.2.1.11
-- 1.3.6.1.4.1.37950.1.1.5.12.6.2.1.11
-- 1.3.6.1.4.1.37950.1.1.5.12.6.2.1.11
-- 1.3.6.1.4.1.37950.1.1.5.12.6.2.1.11
-- 1.3.6.1.4.1.37950.1.1.5.12.6.2.1.11
-- 1.3.6.1.4.1.37950.1.1.5.12.6.2.1.11
-- 1.3.6.1.4.1.37950.1.1.5.12.6.2.1.11
-- 1.3.6.1.4.1.37950.1.1.5.12.6.2.1.11
		-- 1.3.6.1.4.1.37950.1.1.5.12.6.2.1.11
		voipCVlan OBJECT-TYPE
			SYNTAX Integer32 (0..4095)
			MAX-ACCESS read-write
			STATUS current
			DESCRIPTION
				"Description."
			::= { voipGlobalIpCfg 11 }

		
--          1.3.6.1.4.1.37950.1.1.5.12.6.2.1.12
-- 1.3.6.1.4.1.37950.1.1.5.12.6.2.1.12
-- 1.3.6.1.4.1.37950.1.1.5.12.6.2.1.12
-- 1.3.6.1.4.1.37950.1.1.5.12.6.2.1.12
-- 1.3.6.1.4.1.37950.1.1.5.12.6.2.1.12
-- 1.3.6.1.4.1.37950.1.1.5.12.6.2.1.12
-- 1.3.6.1.4.1.37950.1.1.5.12.6.2.1.12
-- 1.3.6.1.4.1.37950.1.1.5.12.6.2.1.12
-- 1.3.6.1.4.1.37950.1.1.5.12.6.2.1.12
		-- 1.3.6.1.4.1.37950.1.1.5.12.6.2.1.12
		voipSVlan OBJECT-TYPE
			SYNTAX Integer32 (0..4095)
			MAX-ACCESS read-write
			STATUS current
			DESCRIPTION
				"Description."
			::= { voipGlobalIpCfg 12 }

		
--          1.3.6.1.4.1.37950.1.1.5.12.6.2.1.13
-- 1.3.6.1.4.1.37950.1.1.5.12.6.2.1.13
-- 1.3.6.1.4.1.37950.1.1.5.12.6.2.1.13
-- 1.3.6.1.4.1.37950.1.1.5.12.6.2.1.13
-- 1.3.6.1.4.1.37950.1.1.5.12.6.2.1.13
-- 1.3.6.1.4.1.37950.1.1.5.12.6.2.1.13
-- 1.3.6.1.4.1.37950.1.1.5.12.6.2.1.13
-- 1.3.6.1.4.1.37950.1.1.5.12.6.2.1.13
-- 1.3.6.1.4.1.37950.1.1.5.12.6.2.1.13
		-- 1.3.6.1.4.1.37950.1.1.5.12.6.2.1.13
		voipPriority OBJECT-TYPE
			SYNTAX Integer32 (0..7)
			MAX-ACCESS read-write
			STATUS current
			DESCRIPTION
				"Description."
			::= { voipGlobalIpCfg 13 }

		
--          1.3.6.1.4.1.37950.1.1.5.12.6.2.1.14
-- 1.3.6.1.4.1.37950.1.1.5.12.6.2.1.14
-- 1.3.6.1.4.1.37950.1.1.5.12.6.2.1.14
-- 1.3.6.1.4.1.37950.1.1.5.12.6.2.1.14
-- 1.3.6.1.4.1.37950.1.1.5.12.6.2.1.14
-- 1.3.6.1.4.1.37950.1.1.5.12.6.2.1.14
-- 1.3.6.1.4.1.37950.1.1.5.12.6.2.1.14
-- 1.3.6.1.4.1.37950.1.1.5.12.6.2.1.14
-- 1.3.6.1.4.1.37950.1.1.5.12.6.2.1.14
		-- 1.3.6.1.4.1.37950.1.1.5.12.6.2.1.14
		staticIpAction OBJECT-TYPE
			SYNTAX INTEGER { commit(1) }
			MAX-ACCESS read-write
			STATUS current
			DESCRIPTION
				"Description."
			::= { voipGlobalIpCfg 14 }

		
--          1.3.6.1.4.1.37950.1.1.5.12.6.2.2
-- 1.3.6.1.4.1.37950.1.1.5.12.6.2.2
-- 1.3.6.1.4.1.37950.1.1.5.12.6.2.2
-- 1.3.6.1.4.1.37950.1.1.5.12.6.2.2
-- 1.3.6.1.4.1.37950.1.1.5.12.6.2.2
-- 1.3.6.1.4.1.37950.1.1.5.12.6.2.2
-- 1.3.6.1.4.1.37950.1.1.5.12.6.2.2
-- 1.3.6.1.4.1.37950.1.1.5.12.6.2.2
-- 1.3.6.1.4.1.37950.1.1.5.12.6.2.2
		-- 1.3.6.1.4.1.37950.1.1.5.12.6.2.2
		voipPortMng OBJECT IDENTIFIER ::= { voipGlobalCfg 2 }

		
--          1.3.6.1.4.1.37950.1.1.5.12.6.2.2.1
-- 1.3.6.1.4.1.37950.1.1.5.12.6.2.2.1
-- 1.3.6.1.4.1.37950.1.1.5.12.6.2.2.1
-- 1.3.6.1.4.1.37950.1.1.5.12.6.2.2.1
-- 1.3.6.1.4.1.37950.1.1.5.12.6.2.2.1
-- 1.3.6.1.4.1.37950.1.1.5.12.6.2.2.1
-- 1.3.6.1.4.1.37950.1.1.5.12.6.2.2.1
-- 1.3.6.1.4.1.37950.1.1.5.12.6.2.2.1
-- 1.3.6.1.4.1.37950.1.1.5.12.6.2.2.1
		-- 1.3.6.1.4.1.37950.1.1.5.12.6.2.2.1
		voipMngPonNo OBJECT-TYPE
			SYNTAX Integer32 (0..16)
			MAX-ACCESS read-write
			STATUS current
			DESCRIPTION
				"Description."
			::= { voipPortMng 1 }

		
--          1.3.6.1.4.1.37950.1.1.5.12.6.2.2.2
-- 1.3.6.1.4.1.37950.1.1.5.12.6.2.2.2
-- 1.3.6.1.4.1.37950.1.1.5.12.6.2.2.2
-- 1.3.6.1.4.1.37950.1.1.5.12.6.2.2.2
-- 1.3.6.1.4.1.37950.1.1.5.12.6.2.2.2
-- 1.3.6.1.4.1.37950.1.1.5.12.6.2.2.2
-- 1.3.6.1.4.1.37950.1.1.5.12.6.2.2.2
-- 1.3.6.1.4.1.37950.1.1.5.12.6.2.2.2
-- 1.3.6.1.4.1.37950.1.1.5.12.6.2.2.2
		-- 1.3.6.1.4.1.37950.1.1.5.12.6.2.2.2
		voipMngOnuNo OBJECT-TYPE
			SYNTAX Integer32 (1..65535)
			MAX-ACCESS read-write
			STATUS current
			DESCRIPTION
				"Description."
			::= { voipPortMng 2 }

		
--          1.3.6.1.4.1.37950.1.1.5.12.6.2.2.3
-- 1.3.6.1.4.1.37950.1.1.5.12.6.2.2.3
-- 1.3.6.1.4.1.37950.1.1.5.12.6.2.2.3
-- 1.3.6.1.4.1.37950.1.1.5.12.6.2.2.3
-- 1.3.6.1.4.1.37950.1.1.5.12.6.2.2.3
-- 1.3.6.1.4.1.37950.1.1.5.12.6.2.2.3
-- 1.3.6.1.4.1.37950.1.1.5.12.6.2.2.3
-- 1.3.6.1.4.1.37950.1.1.5.12.6.2.2.3
-- 1.3.6.1.4.1.37950.1.1.5.12.6.2.2.3
		-- 1.3.6.1.4.1.37950.1.1.5.12.6.2.2.3
		voipMngPotsNo OBJECT-TYPE
			SYNTAX Integer32 (1..64)
			MAX-ACCESS read-write
			STATUS current
			DESCRIPTION
				"Description."
			::= { voipPortMng 3 }

		
--          1.3.6.1.4.1.37950.1.1.5.12.6.2.2.4
-- 1.3.6.1.4.1.37950.1.1.5.12.6.2.2.4
-- 1.3.6.1.4.1.37950.1.1.5.12.6.2.2.4
-- 1.3.6.1.4.1.37950.1.1.5.12.6.2.2.4
-- 1.3.6.1.4.1.37950.1.1.5.12.6.2.2.4
-- 1.3.6.1.4.1.37950.1.1.5.12.6.2.2.4
-- 1.3.6.1.4.1.37950.1.1.5.12.6.2.2.4
-- 1.3.6.1.4.1.37950.1.1.5.12.6.2.2.4
-- 1.3.6.1.4.1.37950.1.1.5.12.6.2.2.4
		-- 1.3.6.1.4.1.37950.1.1.5.12.6.2.2.4
		voipPortManage OBJECT-TYPE
			SYNTAX INTEGER
				{
				disable(0),
				enable(1)
				}
			MAX-ACCESS read-write
			STATUS current
			DESCRIPTION
				"Description."
			::= { voipPortMng 4 }

		
--          1.3.6.1.4.1.37950.1.1.5.12.6.3
-- 1.3.6.1.4.1.37950.1.1.5.12.6.3
-- 1.3.6.1.4.1.37950.1.1.5.12.6.3
-- 1.3.6.1.4.1.37950.1.1.5.12.6.3
-- 1.3.6.1.4.1.37950.1.1.5.12.6.3
-- 1.3.6.1.4.1.37950.1.1.5.12.6.3
-- 1.3.6.1.4.1.37950.1.1.5.12.6.3
-- 1.3.6.1.4.1.37950.1.1.5.12.6.3
-- 1.3.6.1.4.1.37950.1.1.5.12.6.3
		-- 1.3.6.1.4.1.37950.1.1.5.12.6.3
		voipH248Cfg OBJECT IDENTIFIER ::= { onuVoipCfg 3 }

		
--          1.3.6.1.4.1.37950.1.1.5.12.6.3.1
-- 1.3.6.1.4.1.37950.1.1.5.12.6.3.1
-- 1.3.6.1.4.1.37950.1.1.5.12.6.3.1
-- 1.3.6.1.4.1.37950.1.1.5.12.6.3.1
-- 1.3.6.1.4.1.37950.1.1.5.12.6.3.1
-- 1.3.6.1.4.1.37950.1.1.5.12.6.3.1
-- 1.3.6.1.4.1.37950.1.1.5.12.6.3.1
-- 1.3.6.1.4.1.37950.1.1.5.12.6.3.1
-- 1.3.6.1.4.1.37950.1.1.5.12.6.3.1
		-- 1.3.6.1.4.1.37950.1.1.5.12.6.3.1
		h248ProParam OBJECT IDENTIFIER ::= { voipH248Cfg 1 }

		
--          1.3.6.1.4.1.37950.1.1.5.12.6.3.1.1
-- 1.3.6.1.4.1.37950.1.1.5.12.6.3.1.1
-- 1.3.6.1.4.1.37950.1.1.5.12.6.3.1.1
-- 1.3.6.1.4.1.37950.1.1.5.12.6.3.1.1
-- 1.3.6.1.4.1.37950.1.1.5.12.6.3.1.1
-- 1.3.6.1.4.1.37950.1.1.5.12.6.3.1.1
-- 1.3.6.1.4.1.37950.1.1.5.12.6.3.1.1
-- 1.3.6.1.4.1.37950.1.1.5.12.6.3.1.1
-- 1.3.6.1.4.1.37950.1.1.5.12.6.3.1.1
		-- 1.3.6.1.4.1.37950.1.1.5.12.6.3.1.1
		ipRegModeCfg OBJECT IDENTIFIER ::= { h248ProParam 1 }

		
--          1.3.6.1.4.1.37950.1.1.5.12.6.3.1.1.1
-- 1.3.6.1.4.1.37950.1.1.5.12.6.3.1.1.1
-- 1.3.6.1.4.1.37950.1.1.5.12.6.3.1.1.1
-- 1.3.6.1.4.1.37950.1.1.5.12.6.3.1.1.1
-- 1.3.6.1.4.1.37950.1.1.5.12.6.3.1.1.1
-- 1.3.6.1.4.1.37950.1.1.5.12.6.3.1.1.1
-- 1.3.6.1.4.1.37950.1.1.5.12.6.3.1.1.1
-- 1.3.6.1.4.1.37950.1.1.5.12.6.3.1.1.1
-- 1.3.6.1.4.1.37950.1.1.5.12.6.3.1.1.1
		-- 1.3.6.1.4.1.37950.1.1.5.12.6.3.1.1.1
		ipRegPonNo OBJECT-TYPE
			SYNTAX INTEGER (1..16)
			MAX-ACCESS read-write
			STATUS current
			DESCRIPTION
				"Description."
			::= { ipRegModeCfg 1 }

		
--          1.3.6.1.4.1.37950.1.1.5.12.6.3.1.1.2
-- 1.3.6.1.4.1.37950.1.1.5.12.6.3.1.1.2
-- 1.3.6.1.4.1.37950.1.1.5.12.6.3.1.1.2
-- 1.3.6.1.4.1.37950.1.1.5.12.6.3.1.1.2
-- 1.3.6.1.4.1.37950.1.1.5.12.6.3.1.1.2
-- 1.3.6.1.4.1.37950.1.1.5.12.6.3.1.1.2
-- 1.3.6.1.4.1.37950.1.1.5.12.6.3.1.1.2
-- 1.3.6.1.4.1.37950.1.1.5.12.6.3.1.1.2
-- 1.3.6.1.4.1.37950.1.1.5.12.6.3.1.1.2
		-- 1.3.6.1.4.1.37950.1.1.5.12.6.3.1.1.2
		ipRegOnuNo OBJECT-TYPE
			SYNTAX INTEGER (1..65535)
			MAX-ACCESS read-write
			STATUS current
			DESCRIPTION
				"Description."
			::= { ipRegModeCfg 2 }

		
--          1.3.6.1.4.1.37950.1.1.5.12.6.3.1.1.3
-- 1.3.6.1.4.1.37950.1.1.5.12.6.3.1.1.3
-- 1.3.6.1.4.1.37950.1.1.5.12.6.3.1.1.3
-- 1.3.6.1.4.1.37950.1.1.5.12.6.3.1.1.3
-- 1.3.6.1.4.1.37950.1.1.5.12.6.3.1.1.3
-- 1.3.6.1.4.1.37950.1.1.5.12.6.3.1.1.3
-- 1.3.6.1.4.1.37950.1.1.5.12.6.3.1.1.3
-- 1.3.6.1.4.1.37950.1.1.5.12.6.3.1.1.3
-- 1.3.6.1.4.1.37950.1.1.5.12.6.3.1.1.3
		-- 1.3.6.1.4.1.37950.1.1.5.12.6.3.1.1.3
		ipRegMode OBJECT-TYPE
			SYNTAX INTEGER { ip-addr(1) }
			MAX-ACCESS read-write
			STATUS current
			DESCRIPTION
				"Description."
			::= { ipRegModeCfg 3 }

		
--          1.3.6.1.4.1.37950.1.1.5.12.6.3.1.1.5
-- 1.3.6.1.4.1.37950.1.1.5.12.6.3.1.1.5
-- 1.3.6.1.4.1.37950.1.1.5.12.6.3.1.1.5
-- 1.3.6.1.4.1.37950.1.1.5.12.6.3.1.1.5
-- 1.3.6.1.4.1.37950.1.1.5.12.6.3.1.1.5
-- 1.3.6.1.4.1.37950.1.1.5.12.6.3.1.1.5
-- 1.3.6.1.4.1.37950.1.1.5.12.6.3.1.1.5
-- 1.3.6.1.4.1.37950.1.1.5.12.6.3.1.1.5
-- 1.3.6.1.4.1.37950.1.1.5.12.6.3.1.1.5
		-- 1.3.6.1.4.1.37950.1.1.5.12.6.3.1.1.5
		ipRegAction OBJECT-TYPE
			SYNTAX INTEGER { commit(1) }
			MAX-ACCESS read-write
			STATUS current
			DESCRIPTION
				"Description."
			::= { ipRegModeCfg 5 }

		
--          1.3.6.1.4.1.37950.1.1.5.12.6.3.1.2
-- 1.3.6.1.4.1.37950.1.1.5.12.6.3.1.2
-- 1.3.6.1.4.1.37950.1.1.5.12.6.3.1.2
-- 1.3.6.1.4.1.37950.1.1.5.12.6.3.1.2
-- 1.3.6.1.4.1.37950.1.1.5.12.6.3.1.2
-- 1.3.6.1.4.1.37950.1.1.5.12.6.3.1.2
-- 1.3.6.1.4.1.37950.1.1.5.12.6.3.1.2
-- 1.3.6.1.4.1.37950.1.1.5.12.6.3.1.2
-- 1.3.6.1.4.1.37950.1.1.5.12.6.3.1.2
		-- 1.3.6.1.4.1.37950.1.1.5.12.6.3.1.2
		nameCfg OBJECT IDENTIFIER ::= { h248ProParam 2 }

		
--          1.3.6.1.4.1.37950.1.1.5.12.6.3.1.2.1
-- 1.3.6.1.4.1.37950.1.1.5.12.6.3.1.2.1
-- 1.3.6.1.4.1.37950.1.1.5.12.6.3.1.2.1
-- 1.3.6.1.4.1.37950.1.1.5.12.6.3.1.2.1
-- 1.3.6.1.4.1.37950.1.1.5.12.6.3.1.2.1
-- 1.3.6.1.4.1.37950.1.1.5.12.6.3.1.2.1
-- 1.3.6.1.4.1.37950.1.1.5.12.6.3.1.2.1
-- 1.3.6.1.4.1.37950.1.1.5.12.6.3.1.2.1
-- 1.3.6.1.4.1.37950.1.1.5.12.6.3.1.2.1
		-- 1.3.6.1.4.1.37950.1.1.5.12.6.3.1.2.1
		namePonNo OBJECT-TYPE
			SYNTAX INTEGER (1..16)
			MAX-ACCESS read-write
			STATUS current
			DESCRIPTION
				"Description."
			::= { nameCfg 1 }

		
--          1.3.6.1.4.1.37950.1.1.5.12.6.3.1.2.2
-- 1.3.6.1.4.1.37950.1.1.5.12.6.3.1.2.2
-- 1.3.6.1.4.1.37950.1.1.5.12.6.3.1.2.2
-- 1.3.6.1.4.1.37950.1.1.5.12.6.3.1.2.2
-- 1.3.6.1.4.1.37950.1.1.5.12.6.3.1.2.2
-- 1.3.6.1.4.1.37950.1.1.5.12.6.3.1.2.2
-- 1.3.6.1.4.1.37950.1.1.5.12.6.3.1.2.2
-- 1.3.6.1.4.1.37950.1.1.5.12.6.3.1.2.2
-- 1.3.6.1.4.1.37950.1.1.5.12.6.3.1.2.2
		-- 1.3.6.1.4.1.37950.1.1.5.12.6.3.1.2.2
		nameOnuNo OBJECT-TYPE
			SYNTAX INTEGER (1..65535)
			MAX-ACCESS read-write
			STATUS current
			DESCRIPTION
				"Description."
			::= { nameCfg 2 }

		
--          1.3.6.1.4.1.37950.1.1.5.12.6.3.1.2.3
-- 1.3.6.1.4.1.37950.1.1.5.12.6.3.1.2.3
-- 1.3.6.1.4.1.37950.1.1.5.12.6.3.1.2.3
-- 1.3.6.1.4.1.37950.1.1.5.12.6.3.1.2.3
-- 1.3.6.1.4.1.37950.1.1.5.12.6.3.1.2.3
-- 1.3.6.1.4.1.37950.1.1.5.12.6.3.1.2.3
-- 1.3.6.1.4.1.37950.1.1.5.12.6.3.1.2.3
-- 1.3.6.1.4.1.37950.1.1.5.12.6.3.1.2.3
-- 1.3.6.1.4.1.37950.1.1.5.12.6.3.1.2.3
		-- 1.3.6.1.4.1.37950.1.1.5.12.6.3.1.2.3
		nameSel OBJECT-TYPE
			SYNTAX INTEGER
				{
				realmName(1),
				deviceName(2)
				}
			MAX-ACCESS read-write
			STATUS current
			DESCRIPTION
				"Description."
			::= { nameCfg 3 }

		
--          1.3.6.1.4.1.37950.1.1.5.12.6.3.1.2.4
-- 1.3.6.1.4.1.37950.1.1.5.12.6.3.1.2.4
-- 1.3.6.1.4.1.37950.1.1.5.12.6.3.1.2.4
-- 1.3.6.1.4.1.37950.1.1.5.12.6.3.1.2.4
-- 1.3.6.1.4.1.37950.1.1.5.12.6.3.1.2.4
-- 1.3.6.1.4.1.37950.1.1.5.12.6.3.1.2.4
-- 1.3.6.1.4.1.37950.1.1.5.12.6.3.1.2.4
-- 1.3.6.1.4.1.37950.1.1.5.12.6.3.1.2.4
-- 1.3.6.1.4.1.37950.1.1.5.12.6.3.1.2.4
		-- 1.3.6.1.4.1.37950.1.1.5.12.6.3.1.2.4
		nameValue OBJECT-TYPE
			SYNTAX OCTET STRING
			MAX-ACCESS read-write
			STATUS current
			DESCRIPTION
				"Description."
			::= { nameCfg 4 }

		
--          1.3.6.1.4.1.37950.1.1.5.12.6.3.1.2.5
-- 1.3.6.1.4.1.37950.1.1.5.12.6.3.1.2.5
-- 1.3.6.1.4.1.37950.1.1.5.12.6.3.1.2.5
-- 1.3.6.1.4.1.37950.1.1.5.12.6.3.1.2.5
-- 1.3.6.1.4.1.37950.1.1.5.12.6.3.1.2.5
-- 1.3.6.1.4.1.37950.1.1.5.12.6.3.1.2.5
-- 1.3.6.1.4.1.37950.1.1.5.12.6.3.1.2.5
-- 1.3.6.1.4.1.37950.1.1.5.12.6.3.1.2.5
-- 1.3.6.1.4.1.37950.1.1.5.12.6.3.1.2.5
		-- 1.3.6.1.4.1.37950.1.1.5.12.6.3.1.2.5
		nameAction OBJECT-TYPE
			SYNTAX INTEGER { commit(1) }
			MAX-ACCESS read-write
			STATUS current
			DESCRIPTION
				"Description."
			::= { nameCfg 5 }

		
--          1.3.6.1.4.1.37950.1.1.5.12.6.3.1.3
-- 1.3.6.1.4.1.37950.1.1.5.12.6.3.1.3
-- 1.3.6.1.4.1.37950.1.1.5.12.6.3.1.3
-- 1.3.6.1.4.1.37950.1.1.5.12.6.3.1.3
-- 1.3.6.1.4.1.37950.1.1.5.12.6.3.1.3
-- 1.3.6.1.4.1.37950.1.1.5.12.6.3.1.3
-- 1.3.6.1.4.1.37950.1.1.5.12.6.3.1.3
-- 1.3.6.1.4.1.37950.1.1.5.12.6.3.1.3
-- 1.3.6.1.4.1.37950.1.1.5.12.6.3.1.3
		-- 1.3.6.1.4.1.37950.1.1.5.12.6.3.1.3
		heartbeatCfg OBJECT IDENTIFIER ::= { h248ProParam 3 }

		
--          1.3.6.1.4.1.37950.1.1.5.12.6.3.1.3.1
-- 1.3.6.1.4.1.37950.1.1.5.12.6.3.1.3.1
-- 1.3.6.1.4.1.37950.1.1.5.12.6.3.1.3.1
-- 1.3.6.1.4.1.37950.1.1.5.12.6.3.1.3.1
-- 1.3.6.1.4.1.37950.1.1.5.12.6.3.1.3.1
-- 1.3.6.1.4.1.37950.1.1.5.12.6.3.1.3.1
-- 1.3.6.1.4.1.37950.1.1.5.12.6.3.1.3.1
-- 1.3.6.1.4.1.37950.1.1.5.12.6.3.1.3.1
-- 1.3.6.1.4.1.37950.1.1.5.12.6.3.1.3.1
		-- 1.3.6.1.4.1.37950.1.1.5.12.6.3.1.3.1
		heartbeatPonNo OBJECT-TYPE
			SYNTAX INTEGER (1..16)
			MAX-ACCESS read-write
			STATUS current
			DESCRIPTION
				"Description."
			::= { heartbeatCfg 1 }

		
--          1.3.6.1.4.1.37950.1.1.5.12.6.3.1.3.2
-- 1.3.6.1.4.1.37950.1.1.5.12.6.3.1.3.2
-- 1.3.6.1.4.1.37950.1.1.5.12.6.3.1.3.2
-- 1.3.6.1.4.1.37950.1.1.5.12.6.3.1.3.2
-- 1.3.6.1.4.1.37950.1.1.5.12.6.3.1.3.2
-- 1.3.6.1.4.1.37950.1.1.5.12.6.3.1.3.2
-- 1.3.6.1.4.1.37950.1.1.5.12.6.3.1.3.2
-- 1.3.6.1.4.1.37950.1.1.5.12.6.3.1.3.2
-- 1.3.6.1.4.1.37950.1.1.5.12.6.3.1.3.2
		-- 1.3.6.1.4.1.37950.1.1.5.12.6.3.1.3.2
		heartbeatOnuNo OBJECT-TYPE
			SYNTAX INTEGER (1..65535)
			MAX-ACCESS read-write
			STATUS current
			DESCRIPTION
				"Description."
			::= { heartbeatCfg 2 }

		
--          1.3.6.1.4.1.37950.1.1.5.12.6.3.1.3.3
-- 1.3.6.1.4.1.37950.1.1.5.12.6.3.1.3.3
-- 1.3.6.1.4.1.37950.1.1.5.12.6.3.1.3.3
-- 1.3.6.1.4.1.37950.1.1.5.12.6.3.1.3.3
-- 1.3.6.1.4.1.37950.1.1.5.12.6.3.1.3.3
-- 1.3.6.1.4.1.37950.1.1.5.12.6.3.1.3.3
-- 1.3.6.1.4.1.37950.1.1.5.12.6.3.1.3.3
-- 1.3.6.1.4.1.37950.1.1.5.12.6.3.1.3.3
-- 1.3.6.1.4.1.37950.1.1.5.12.6.3.1.3.3
		-- 1.3.6.1.4.1.37950.1.1.5.12.6.3.1.3.3
		heartbeatMode OBJECT-TYPE
			SYNTAX INTEGER
				{
				disable(0),
				h248(1)
				}
			MAX-ACCESS read-write
			STATUS current
			DESCRIPTION
				"Description."
			::= { heartbeatCfg 3 }

		
--          1.3.6.1.4.1.37950.1.1.5.12.6.3.1.3.4
-- 1.3.6.1.4.1.37950.1.1.5.12.6.3.1.3.4
-- 1.3.6.1.4.1.37950.1.1.5.12.6.3.1.3.4
-- 1.3.6.1.4.1.37950.1.1.5.12.6.3.1.3.4
-- 1.3.6.1.4.1.37950.1.1.5.12.6.3.1.3.4
-- 1.3.6.1.4.1.37950.1.1.5.12.6.3.1.3.4
-- 1.3.6.1.4.1.37950.1.1.5.12.6.3.1.3.4
-- 1.3.6.1.4.1.37950.1.1.5.12.6.3.1.3.4
-- 1.3.6.1.4.1.37950.1.1.5.12.6.3.1.3.4
		-- 1.3.6.1.4.1.37950.1.1.5.12.6.3.1.3.4
		heartbeatCycle OBJECT-TYPE
			SYNTAX INTEGER (1..65535)
			MAX-ACCESS read-write
			STATUS current
			DESCRIPTION
				"Description."
			::= { heartbeatCfg 4 }

		
--          1.3.6.1.4.1.37950.1.1.5.12.6.3.1.3.5
-- 1.3.6.1.4.1.37950.1.1.5.12.6.3.1.3.5
-- 1.3.6.1.4.1.37950.1.1.5.12.6.3.1.3.5
-- 1.3.6.1.4.1.37950.1.1.5.12.6.3.1.3.5
-- 1.3.6.1.4.1.37950.1.1.5.12.6.3.1.3.5
-- 1.3.6.1.4.1.37950.1.1.5.12.6.3.1.3.5
-- 1.3.6.1.4.1.37950.1.1.5.12.6.3.1.3.5
-- 1.3.6.1.4.1.37950.1.1.5.12.6.3.1.3.5
-- 1.3.6.1.4.1.37950.1.1.5.12.6.3.1.3.5
		-- 1.3.6.1.4.1.37950.1.1.5.12.6.3.1.3.5
		heartbeatCount OBJECT-TYPE
			SYNTAX INTEGER (1..65535)
			MAX-ACCESS read-write
			STATUS current
			DESCRIPTION
				"Description."
			::= { heartbeatCfg 5 }

		
--          1.3.6.1.4.1.37950.1.1.5.12.6.3.1.3.6
-- 1.3.6.1.4.1.37950.1.1.5.12.6.3.1.3.6
-- 1.3.6.1.4.1.37950.1.1.5.12.6.3.1.3.6
-- 1.3.6.1.4.1.37950.1.1.5.12.6.3.1.3.6
-- 1.3.6.1.4.1.37950.1.1.5.12.6.3.1.3.6
-- 1.3.6.1.4.1.37950.1.1.5.12.6.3.1.3.6
-- 1.3.6.1.4.1.37950.1.1.5.12.6.3.1.3.6
-- 1.3.6.1.4.1.37950.1.1.5.12.6.3.1.3.6
-- 1.3.6.1.4.1.37950.1.1.5.12.6.3.1.3.6
		-- 1.3.6.1.4.1.37950.1.1.5.12.6.3.1.3.6
		heartbeatAction OBJECT-TYPE
			SYNTAX INTEGER { commit(1) }
			MAX-ACCESS read-write
			STATUS current
			DESCRIPTION
				"Description."
			::= { heartbeatCfg 6 }

		
--          1.3.6.1.4.1.37950.1.1.5.12.6.3.1.4
-- 1.3.6.1.4.1.37950.1.1.5.12.6.3.1.4
-- 1.3.6.1.4.1.37950.1.1.5.12.6.3.1.4
-- 1.3.6.1.4.1.37950.1.1.5.12.6.3.1.4
-- 1.3.6.1.4.1.37950.1.1.5.12.6.3.1.4
-- 1.3.6.1.4.1.37950.1.1.5.12.6.3.1.4
-- 1.3.6.1.4.1.37950.1.1.5.12.6.3.1.4
-- 1.3.6.1.4.1.37950.1.1.5.12.6.3.1.4
-- 1.3.6.1.4.1.37950.1.1.5.12.6.3.1.4
		-- 1.3.6.1.4.1.37950.1.1.5.12.6.3.1.4
		mgcCfg OBJECT IDENTIFIER ::= { h248ProParam 4 }

		
--          1.3.6.1.4.1.37950.1.1.5.12.6.3.1.4.1
-- 1.3.6.1.4.1.37950.1.1.5.12.6.3.1.4.1
-- 1.3.6.1.4.1.37950.1.1.5.12.6.3.1.4.1
-- 1.3.6.1.4.1.37950.1.1.5.12.6.3.1.4.1
-- 1.3.6.1.4.1.37950.1.1.5.12.6.3.1.4.1
-- 1.3.6.1.4.1.37950.1.1.5.12.6.3.1.4.1
-- 1.3.6.1.4.1.37950.1.1.5.12.6.3.1.4.1
-- 1.3.6.1.4.1.37950.1.1.5.12.6.3.1.4.1
-- 1.3.6.1.4.1.37950.1.1.5.12.6.3.1.4.1
		-- 1.3.6.1.4.1.37950.1.1.5.12.6.3.1.4.1
		mgcPonNo OBJECT-TYPE
			SYNTAX INTEGER (1..16)
			MAX-ACCESS read-write
			STATUS current
			DESCRIPTION
				"Description."
			::= { mgcCfg 1 }

		
--          1.3.6.1.4.1.37950.1.1.5.12.6.3.1.4.2
-- 1.3.6.1.4.1.37950.1.1.5.12.6.3.1.4.2
-- 1.3.6.1.4.1.37950.1.1.5.12.6.3.1.4.2
-- 1.3.6.1.4.1.37950.1.1.5.12.6.3.1.4.2
-- 1.3.6.1.4.1.37950.1.1.5.12.6.3.1.4.2
-- 1.3.6.1.4.1.37950.1.1.5.12.6.3.1.4.2
-- 1.3.6.1.4.1.37950.1.1.5.12.6.3.1.4.2
-- 1.3.6.1.4.1.37950.1.1.5.12.6.3.1.4.2
-- 1.3.6.1.4.1.37950.1.1.5.12.6.3.1.4.2
		-- 1.3.6.1.4.1.37950.1.1.5.12.6.3.1.4.2
		mgcOnuNo OBJECT-TYPE
			SYNTAX INTEGER (1..65535)
			MAX-ACCESS read-write
			STATUS current
			DESCRIPTION
				"Description."
			::= { mgcCfg 2 }

		
--          1.3.6.1.4.1.37950.1.1.5.12.6.3.1.4.3
-- 1.3.6.1.4.1.37950.1.1.5.12.6.3.1.4.3
-- 1.3.6.1.4.1.37950.1.1.5.12.6.3.1.4.3
-- 1.3.6.1.4.1.37950.1.1.5.12.6.3.1.4.3
-- 1.3.6.1.4.1.37950.1.1.5.12.6.3.1.4.3
-- 1.3.6.1.4.1.37950.1.1.5.12.6.3.1.4.3
-- 1.3.6.1.4.1.37950.1.1.5.12.6.3.1.4.3
-- 1.3.6.1.4.1.37950.1.1.5.12.6.3.1.4.3
-- 1.3.6.1.4.1.37950.1.1.5.12.6.3.1.4.3
		-- 1.3.6.1.4.1.37950.1.1.5.12.6.3.1.4.3
		mgPort OBJECT-TYPE
			SYNTAX INTEGER (1..65535)
			MAX-ACCESS read-write
			STATUS current
			DESCRIPTION
				"Description."
			::= { mgcCfg 3 }

		
--          1.3.6.1.4.1.37950.1.1.5.12.6.3.1.4.4
-- 1.3.6.1.4.1.37950.1.1.5.12.6.3.1.4.4
-- 1.3.6.1.4.1.37950.1.1.5.12.6.3.1.4.4
-- 1.3.6.1.4.1.37950.1.1.5.12.6.3.1.4.4
-- 1.3.6.1.4.1.37950.1.1.5.12.6.3.1.4.4
-- 1.3.6.1.4.1.37950.1.1.5.12.6.3.1.4.4
-- 1.3.6.1.4.1.37950.1.1.5.12.6.3.1.4.4
-- 1.3.6.1.4.1.37950.1.1.5.12.6.3.1.4.4
-- 1.3.6.1.4.1.37950.1.1.5.12.6.3.1.4.4
		-- 1.3.6.1.4.1.37950.1.1.5.12.6.3.1.4.4
		mgcIp OBJECT-TYPE
			SYNTAX IpAddress
			MAX-ACCESS read-write
			STATUS current
			DESCRIPTION
				"Description."
			::= { mgcCfg 4 }

		
--          1.3.6.1.4.1.37950.1.1.5.12.6.3.1.4.5
-- 1.3.6.1.4.1.37950.1.1.5.12.6.3.1.4.5
-- 1.3.6.1.4.1.37950.1.1.5.12.6.3.1.4.5
-- 1.3.6.1.4.1.37950.1.1.5.12.6.3.1.4.5
-- 1.3.6.1.4.1.37950.1.1.5.12.6.3.1.4.5
-- 1.3.6.1.4.1.37950.1.1.5.12.6.3.1.4.5
-- 1.3.6.1.4.1.37950.1.1.5.12.6.3.1.4.5
-- 1.3.6.1.4.1.37950.1.1.5.12.6.3.1.4.5
-- 1.3.6.1.4.1.37950.1.1.5.12.6.3.1.4.5
		-- 1.3.6.1.4.1.37950.1.1.5.12.6.3.1.4.5
		mgcPort OBJECT-TYPE
			SYNTAX INTEGER (1..65535)
			MAX-ACCESS read-write
			STATUS current
			DESCRIPTION
				"Description."
			::= { mgcCfg 5 }

		
--          1.3.6.1.4.1.37950.1.1.5.12.6.3.1.4.6
-- 1.3.6.1.4.1.37950.1.1.5.12.6.3.1.4.6
-- 1.3.6.1.4.1.37950.1.1.5.12.6.3.1.4.6
-- 1.3.6.1.4.1.37950.1.1.5.12.6.3.1.4.6
-- 1.3.6.1.4.1.37950.1.1.5.12.6.3.1.4.6
-- 1.3.6.1.4.1.37950.1.1.5.12.6.3.1.4.6
-- 1.3.6.1.4.1.37950.1.1.5.12.6.3.1.4.6
-- 1.3.6.1.4.1.37950.1.1.5.12.6.3.1.4.6
-- 1.3.6.1.4.1.37950.1.1.5.12.6.3.1.4.6
		-- 1.3.6.1.4.1.37950.1.1.5.12.6.3.1.4.6
		bakMgcIp OBJECT-TYPE
			SYNTAX IpAddress
			MAX-ACCESS read-write
			STATUS current
			DESCRIPTION
				"Description."
			::= { mgcCfg 6 }

		
--          1.3.6.1.4.1.37950.1.1.5.12.6.3.1.4.7
-- 1.3.6.1.4.1.37950.1.1.5.12.6.3.1.4.7
-- 1.3.6.1.4.1.37950.1.1.5.12.6.3.1.4.7
-- 1.3.6.1.4.1.37950.1.1.5.12.6.3.1.4.7
-- 1.3.6.1.4.1.37950.1.1.5.12.6.3.1.4.7
-- 1.3.6.1.4.1.37950.1.1.5.12.6.3.1.4.7
-- 1.3.6.1.4.1.37950.1.1.5.12.6.3.1.4.7
-- 1.3.6.1.4.1.37950.1.1.5.12.6.3.1.4.7
-- 1.3.6.1.4.1.37950.1.1.5.12.6.3.1.4.7
		-- 1.3.6.1.4.1.37950.1.1.5.12.6.3.1.4.7
		bakMgcPort OBJECT-TYPE
			SYNTAX INTEGER (1..65535)
			MAX-ACCESS read-write
			STATUS current
			DESCRIPTION
				"Description."
			::= { mgcCfg 7 }

		
--          1.3.6.1.4.1.37950.1.1.5.12.6.3.1.4.8
-- 1.3.6.1.4.1.37950.1.1.5.12.6.3.1.4.8
-- 1.3.6.1.4.1.37950.1.1.5.12.6.3.1.4.8
-- 1.3.6.1.4.1.37950.1.1.5.12.6.3.1.4.8
-- 1.3.6.1.4.1.37950.1.1.5.12.6.3.1.4.8
-- 1.3.6.1.4.1.37950.1.1.5.12.6.3.1.4.8
-- 1.3.6.1.4.1.37950.1.1.5.12.6.3.1.4.8
-- 1.3.6.1.4.1.37950.1.1.5.12.6.3.1.4.8
-- 1.3.6.1.4.1.37950.1.1.5.12.6.3.1.4.8
		-- 1.3.6.1.4.1.37950.1.1.5.12.6.3.1.4.8
		mgcAction OBJECT-TYPE
			SYNTAX INTEGER { commit(1) }
			MAX-ACCESS read-write
			STATUS current
			DESCRIPTION
				"Description."
			::= { mgcCfg 8 }

		
--          1.3.6.1.4.1.37950.1.1.5.12.6.3.1.5
-- 1.3.6.1.4.1.37950.1.1.5.12.6.3.1.5
-- 1.3.6.1.4.1.37950.1.1.5.12.6.3.1.5
-- 1.3.6.1.4.1.37950.1.1.5.12.6.3.1.5
-- 1.3.6.1.4.1.37950.1.1.5.12.6.3.1.5
-- 1.3.6.1.4.1.37950.1.1.5.12.6.3.1.5
-- 1.3.6.1.4.1.37950.1.1.5.12.6.3.1.5
-- 1.3.6.1.4.1.37950.1.1.5.12.6.3.1.5
-- 1.3.6.1.4.1.37950.1.1.5.12.6.3.1.5
		-- 1.3.6.1.4.1.37950.1.1.5.12.6.3.1.5
		h248ParamCfg OBJECT IDENTIFIER ::= { h248ProParam 5 }

		
--          1.3.6.1.4.1.37950.1.1.5.12.6.3.1.5.1
-- 1.3.6.1.4.1.37950.1.1.5.12.6.3.1.5.1
-- 1.3.6.1.4.1.37950.1.1.5.12.6.3.1.5.1
-- 1.3.6.1.4.1.37950.1.1.5.12.6.3.1.5.1
-- 1.3.6.1.4.1.37950.1.1.5.12.6.3.1.5.1
-- 1.3.6.1.4.1.37950.1.1.5.12.6.3.1.5.1
-- 1.3.6.1.4.1.37950.1.1.5.12.6.3.1.5.1
-- 1.3.6.1.4.1.37950.1.1.5.12.6.3.1.5.1
-- 1.3.6.1.4.1.37950.1.1.5.12.6.3.1.5.1
		-- 1.3.6.1.4.1.37950.1.1.5.12.6.3.1.5.1
		h248ParamPonNo OBJECT-TYPE
			SYNTAX Integer32 (1..16)
			MAX-ACCESS read-write
			STATUS current
			DESCRIPTION
				"Description."
			::= { h248ParamCfg 1 }

		
--          1.3.6.1.4.1.37950.1.1.5.12.6.3.1.5.2
-- 1.3.6.1.4.1.37950.1.1.5.12.6.3.1.5.2
-- 1.3.6.1.4.1.37950.1.1.5.12.6.3.1.5.2
-- 1.3.6.1.4.1.37950.1.1.5.12.6.3.1.5.2
-- 1.3.6.1.4.1.37950.1.1.5.12.6.3.1.5.2
-- 1.3.6.1.4.1.37950.1.1.5.12.6.3.1.5.2
-- 1.3.6.1.4.1.37950.1.1.5.12.6.3.1.5.2
-- 1.3.6.1.4.1.37950.1.1.5.12.6.3.1.5.2
-- 1.3.6.1.4.1.37950.1.1.5.12.6.3.1.5.2
		-- 1.3.6.1.4.1.37950.1.1.5.12.6.3.1.5.2
		h248ParamOnuNo OBJECT-TYPE
			SYNTAX INTEGER (1..65535)
			MAX-ACCESS read-write
			STATUS current
			DESCRIPTION
				"Description."
			::= { h248ParamCfg 2 }

		
--          1.3.6.1.4.1.37950.1.1.5.12.6.3.1.5.3
-- 1.3.6.1.4.1.37950.1.1.5.12.6.3.1.5.3
-- 1.3.6.1.4.1.37950.1.1.5.12.6.3.1.5.3
-- 1.3.6.1.4.1.37950.1.1.5.12.6.3.1.5.3
-- 1.3.6.1.4.1.37950.1.1.5.12.6.3.1.5.3
-- 1.3.6.1.4.1.37950.1.1.5.12.6.3.1.5.3
-- 1.3.6.1.4.1.37950.1.1.5.12.6.3.1.5.3
-- 1.3.6.1.4.1.37950.1.1.5.12.6.3.1.5.3
-- 1.3.6.1.4.1.37950.1.1.5.12.6.3.1.5.3
		-- 1.3.6.1.4.1.37950.1.1.5.12.6.3.1.5.3
		h248ParamMGPortNo OBJECT-TYPE
			SYNTAX INTEGER (1..65535)
			MAX-ACCESS read-write
			STATUS current
			DESCRIPTION
				"Description."
			::= { h248ParamCfg 3 }

		
--          1.3.6.1.4.1.37950.1.1.5.12.6.3.1.5.4
-- 1.3.6.1.4.1.37950.1.1.5.12.6.3.1.5.4
-- 1.3.6.1.4.1.37950.1.1.5.12.6.3.1.5.4
-- 1.3.6.1.4.1.37950.1.1.5.12.6.3.1.5.4
-- 1.3.6.1.4.1.37950.1.1.5.12.6.3.1.5.4
-- 1.3.6.1.4.1.37950.1.1.5.12.6.3.1.5.4
-- 1.3.6.1.4.1.37950.1.1.5.12.6.3.1.5.4
-- 1.3.6.1.4.1.37950.1.1.5.12.6.3.1.5.4
-- 1.3.6.1.4.1.37950.1.1.5.12.6.3.1.5.4
		-- 1.3.6.1.4.1.37950.1.1.5.12.6.3.1.5.4
		h248ParamMGCIP OBJECT-TYPE
			SYNTAX IpAddress
			MAX-ACCESS read-write
			STATUS current
			DESCRIPTION
				"Description."
			::= { h248ParamCfg 4 }

		
--          1.3.6.1.4.1.37950.1.1.5.12.6.3.1.5.5
-- 1.3.6.1.4.1.37950.1.1.5.12.6.3.1.5.5
-- 1.3.6.1.4.1.37950.1.1.5.12.6.3.1.5.5
-- 1.3.6.1.4.1.37950.1.1.5.12.6.3.1.5.5
-- 1.3.6.1.4.1.37950.1.1.5.12.6.3.1.5.5
-- 1.3.6.1.4.1.37950.1.1.5.12.6.3.1.5.5
-- 1.3.6.1.4.1.37950.1.1.5.12.6.3.1.5.5
-- 1.3.6.1.4.1.37950.1.1.5.12.6.3.1.5.5
-- 1.3.6.1.4.1.37950.1.1.5.12.6.3.1.5.5
		-- 1.3.6.1.4.1.37950.1.1.5.12.6.3.1.5.5
		h248ParamMgcComPortNo OBJECT-TYPE
			SYNTAX INTEGER (0..65535)
			MAX-ACCESS read-write
			STATUS current
			DESCRIPTION
				"Description."
			::= { h248ParamCfg 5 }

		
--          1.3.6.1.4.1.37950.1.1.5.12.6.3.1.5.6
-- 1.3.6.1.4.1.37950.1.1.5.12.6.3.1.5.6
-- 1.3.6.1.4.1.37950.1.1.5.12.6.3.1.5.6
-- 1.3.6.1.4.1.37950.1.1.5.12.6.3.1.5.6
-- 1.3.6.1.4.1.37950.1.1.5.12.6.3.1.5.6
-- 1.3.6.1.4.1.37950.1.1.5.12.6.3.1.5.6
-- 1.3.6.1.4.1.37950.1.1.5.12.6.3.1.5.6
-- 1.3.6.1.4.1.37950.1.1.5.12.6.3.1.5.6
-- 1.3.6.1.4.1.37950.1.1.5.12.6.3.1.5.6
		-- 1.3.6.1.4.1.37950.1.1.5.12.6.3.1.5.6
		h248ParamBackupMGCIP OBJECT-TYPE
			SYNTAX IpAddress
			MAX-ACCESS read-write
			STATUS current
			DESCRIPTION
				"Description."
			::= { h248ParamCfg 6 }

		
--          1.3.6.1.4.1.37950.1.1.5.12.6.3.1.5.7
-- 1.3.6.1.4.1.37950.1.1.5.12.6.3.1.5.7
-- 1.3.6.1.4.1.37950.1.1.5.12.6.3.1.5.7
-- 1.3.6.1.4.1.37950.1.1.5.12.6.3.1.5.7
-- 1.3.6.1.4.1.37950.1.1.5.12.6.3.1.5.7
-- 1.3.6.1.4.1.37950.1.1.5.12.6.3.1.5.7
-- 1.3.6.1.4.1.37950.1.1.5.12.6.3.1.5.7
-- 1.3.6.1.4.1.37950.1.1.5.12.6.3.1.5.7
-- 1.3.6.1.4.1.37950.1.1.5.12.6.3.1.5.7
		-- 1.3.6.1.4.1.37950.1.1.5.12.6.3.1.5.7
		h248ParamBackupMgcComPortNo OBJECT-TYPE
			SYNTAX INTEGER (0..65535)
			MAX-ACCESS read-write
			STATUS current
			DESCRIPTION
				"Description."
			::= { h248ParamCfg 7 }

		
--          1.3.6.1.4.1.37950.1.1.5.12.6.3.1.5.8
-- 1.3.6.1.4.1.37950.1.1.5.12.6.3.1.5.8
-- 1.3.6.1.4.1.37950.1.1.5.12.6.3.1.5.8
-- 1.3.6.1.4.1.37950.1.1.5.12.6.3.1.5.8
-- 1.3.6.1.4.1.37950.1.1.5.12.6.3.1.5.8
-- 1.3.6.1.4.1.37950.1.1.5.12.6.3.1.5.8
-- 1.3.6.1.4.1.37950.1.1.5.12.6.3.1.5.8
-- 1.3.6.1.4.1.37950.1.1.5.12.6.3.1.5.8
-- 1.3.6.1.4.1.37950.1.1.5.12.6.3.1.5.8
		-- 1.3.6.1.4.1.37950.1.1.5.12.6.3.1.5.8
		h248ParamRegMode OBJECT-TYPE
			SYNTAX INTEGER
				{
				ipaddr(0),
				domain-name(1),
				device-name(2)
				}
			MAX-ACCESS read-write
			STATUS current
			DESCRIPTION
				"Description."
			::= { h248ParamCfg 8 }

		
--          1.3.6.1.4.1.37950.1.1.5.12.6.3.1.5.9
-- 1.3.6.1.4.1.37950.1.1.5.12.6.3.1.5.9
-- 1.3.6.1.4.1.37950.1.1.5.12.6.3.1.5.9
-- 1.3.6.1.4.1.37950.1.1.5.12.6.3.1.5.9
-- 1.3.6.1.4.1.37950.1.1.5.12.6.3.1.5.9
-- 1.3.6.1.4.1.37950.1.1.5.12.6.3.1.5.9
-- 1.3.6.1.4.1.37950.1.1.5.12.6.3.1.5.9
-- 1.3.6.1.4.1.37950.1.1.5.12.6.3.1.5.9
-- 1.3.6.1.4.1.37950.1.1.5.12.6.3.1.5.9
		-- 1.3.6.1.4.1.37950.1.1.5.12.6.3.1.5.9
		h248ParamMID OBJECT-TYPE
			SYNTAX OCTET STRING (SIZE (0..64))
			MAX-ACCESS read-write
			STATUS current
			DESCRIPTION
				"Description."
			::= { h248ParamCfg 9 }

		
--          1.3.6.1.4.1.37950.1.1.5.12.6.3.1.5.10
-- 1.3.6.1.4.1.37950.1.1.5.12.6.3.1.5.10
-- 1.3.6.1.4.1.37950.1.1.5.12.6.3.1.5.10
-- 1.3.6.1.4.1.37950.1.1.5.12.6.3.1.5.10
-- 1.3.6.1.4.1.37950.1.1.5.12.6.3.1.5.10
-- 1.3.6.1.4.1.37950.1.1.5.12.6.3.1.5.10
-- 1.3.6.1.4.1.37950.1.1.5.12.6.3.1.5.10
-- 1.3.6.1.4.1.37950.1.1.5.12.6.3.1.5.10
-- 1.3.6.1.4.1.37950.1.1.5.12.6.3.1.5.10
		-- 1.3.6.1.4.1.37950.1.1.5.12.6.3.1.5.10
		h248ParamHBMode OBJECT-TYPE
			SYNTAX INTEGER
				{
				disable(0),
				h248(1)
				}
			MAX-ACCESS read-write
			STATUS current
			DESCRIPTION
				"Description."
			::= { h248ParamCfg 10 }

		
--          1.3.6.1.4.1.37950.1.1.5.12.6.3.1.5.11
-- 1.3.6.1.4.1.37950.1.1.5.12.6.3.1.5.11
-- 1.3.6.1.4.1.37950.1.1.5.12.6.3.1.5.11
-- 1.3.6.1.4.1.37950.1.1.5.12.6.3.1.5.11
-- 1.3.6.1.4.1.37950.1.1.5.12.6.3.1.5.11
-- 1.3.6.1.4.1.37950.1.1.5.12.6.3.1.5.11
-- 1.3.6.1.4.1.37950.1.1.5.12.6.3.1.5.11
-- 1.3.6.1.4.1.37950.1.1.5.12.6.3.1.5.11
-- 1.3.6.1.4.1.37950.1.1.5.12.6.3.1.5.11
		-- 1.3.6.1.4.1.37950.1.1.5.12.6.3.1.5.11
		h248ParamHBCycle OBJECT-TYPE
			SYNTAX INTEGER (0..65535)
			MAX-ACCESS read-write
			STATUS current
			DESCRIPTION
				"Description."
			::= { h248ParamCfg 11 }

		
--          1.3.6.1.4.1.37950.1.1.5.12.6.3.1.5.12
-- 1.3.6.1.4.1.37950.1.1.5.12.6.3.1.5.12
-- 1.3.6.1.4.1.37950.1.1.5.12.6.3.1.5.12
-- 1.3.6.1.4.1.37950.1.1.5.12.6.3.1.5.12
-- 1.3.6.1.4.1.37950.1.1.5.12.6.3.1.5.12
-- 1.3.6.1.4.1.37950.1.1.5.12.6.3.1.5.12
-- 1.3.6.1.4.1.37950.1.1.5.12.6.3.1.5.12
-- 1.3.6.1.4.1.37950.1.1.5.12.6.3.1.5.12
-- 1.3.6.1.4.1.37950.1.1.5.12.6.3.1.5.12
		-- 1.3.6.1.4.1.37950.1.1.5.12.6.3.1.5.12
		h248ParamHBCount OBJECT-TYPE
			SYNTAX INTEGER (0..255)
			MAX-ACCESS read-write
			STATUS current
			DESCRIPTION
				"Description."
			::= { h248ParamCfg 12 }

		
--          1.3.6.1.4.1.37950.1.1.5.12.6.3.1.5.13
-- 1.3.6.1.4.1.37950.1.1.5.12.6.3.1.5.13
-- 1.3.6.1.4.1.37950.1.1.5.12.6.3.1.5.13
-- 1.3.6.1.4.1.37950.1.1.5.12.6.3.1.5.13
-- 1.3.6.1.4.1.37950.1.1.5.12.6.3.1.5.13
-- 1.3.6.1.4.1.37950.1.1.5.12.6.3.1.5.13
-- 1.3.6.1.4.1.37950.1.1.5.12.6.3.1.5.13
-- 1.3.6.1.4.1.37950.1.1.5.12.6.3.1.5.13
-- 1.3.6.1.4.1.37950.1.1.5.12.6.3.1.5.13
		-- 1.3.6.1.4.1.37950.1.1.5.12.6.3.1.5.13
		h248ParamAction OBJECT-TYPE
			SYNTAX INTEGER { commit(1) }
			MAX-ACCESS read-write
			STATUS current
			DESCRIPTION
				"Description."
			::= { h248ParamCfg 13 }

		
--          1.3.6.1.4.1.37950.1.1.5.12.6.3.2
-- 1.3.6.1.4.1.37950.1.1.5.12.6.3.2
-- 1.3.6.1.4.1.37950.1.1.5.12.6.3.2
-- 1.3.6.1.4.1.37950.1.1.5.12.6.3.2
-- 1.3.6.1.4.1.37950.1.1.5.12.6.3.2
-- 1.3.6.1.4.1.37950.1.1.5.12.6.3.2
-- 1.3.6.1.4.1.37950.1.1.5.12.6.3.2
-- 1.3.6.1.4.1.37950.1.1.5.12.6.3.2
-- 1.3.6.1.4.1.37950.1.1.5.12.6.3.2
		-- 1.3.6.1.4.1.37950.1.1.5.12.6.3.2
		h248UserTid OBJECT IDENTIFIER ::= { voipH248Cfg 2 }

		
--          1.3.6.1.4.1.37950.1.1.5.12.6.3.2.1
-- 1.3.6.1.4.1.37950.1.1.5.12.6.3.2.1
-- 1.3.6.1.4.1.37950.1.1.5.12.6.3.2.1
-- 1.3.6.1.4.1.37950.1.1.5.12.6.3.2.1
-- 1.3.6.1.4.1.37950.1.1.5.12.6.3.2.1
-- 1.3.6.1.4.1.37950.1.1.5.12.6.3.2.1
-- 1.3.6.1.4.1.37950.1.1.5.12.6.3.2.1
-- 1.3.6.1.4.1.37950.1.1.5.12.6.3.2.1
-- 1.3.6.1.4.1.37950.1.1.5.12.6.3.2.1
		-- 1.3.6.1.4.1.37950.1.1.5.12.6.3.2.1
		userTidPonNo OBJECT-TYPE
			SYNTAX INTEGER (1..16)
			MAX-ACCESS read-write
			STATUS current
			DESCRIPTION
				"Description."
			::= { h248UserTid 1 }

		
--          1.3.6.1.4.1.37950.1.1.5.12.6.3.2.2
-- 1.3.6.1.4.1.37950.1.1.5.12.6.3.2.2
-- 1.3.6.1.4.1.37950.1.1.5.12.6.3.2.2
-- 1.3.6.1.4.1.37950.1.1.5.12.6.3.2.2
-- 1.3.6.1.4.1.37950.1.1.5.12.6.3.2.2
-- 1.3.6.1.4.1.37950.1.1.5.12.6.3.2.2
-- 1.3.6.1.4.1.37950.1.1.5.12.6.3.2.2
-- 1.3.6.1.4.1.37950.1.1.5.12.6.3.2.2
-- 1.3.6.1.4.1.37950.1.1.5.12.6.3.2.2
		-- 1.3.6.1.4.1.37950.1.1.5.12.6.3.2.2
		userTidOnuNo OBJECT-TYPE
			SYNTAX INTEGER (1..65535)
			MAX-ACCESS read-write
			STATUS current
			DESCRIPTION
				"Description."
			::= { h248UserTid 2 }

		
--          1.3.6.1.4.1.37950.1.1.5.12.6.3.2.3
-- 1.3.6.1.4.1.37950.1.1.5.12.6.3.2.3
-- 1.3.6.1.4.1.37950.1.1.5.12.6.3.2.3
-- 1.3.6.1.4.1.37950.1.1.5.12.6.3.2.3
-- 1.3.6.1.4.1.37950.1.1.5.12.6.3.2.3
-- 1.3.6.1.4.1.37950.1.1.5.12.6.3.2.3
-- 1.3.6.1.4.1.37950.1.1.5.12.6.3.2.3
-- 1.3.6.1.4.1.37950.1.1.5.12.6.3.2.3
-- 1.3.6.1.4.1.37950.1.1.5.12.6.3.2.3
		-- 1.3.6.1.4.1.37950.1.1.5.12.6.3.2.3
		userTidPotsNo OBJECT-TYPE
			SYNTAX INTEGER (1..255)
			MAX-ACCESS read-write
			STATUS current
			DESCRIPTION
				"Description."
			::= { h248UserTid 3 }

		
--          1.3.6.1.4.1.37950.1.1.5.12.6.3.2.4
-- 1.3.6.1.4.1.37950.1.1.5.12.6.3.2.4
-- 1.3.6.1.4.1.37950.1.1.5.12.6.3.2.4
-- 1.3.6.1.4.1.37950.1.1.5.12.6.3.2.4
-- 1.3.6.1.4.1.37950.1.1.5.12.6.3.2.4
-- 1.3.6.1.4.1.37950.1.1.5.12.6.3.2.4
-- 1.3.6.1.4.1.37950.1.1.5.12.6.3.2.4
-- 1.3.6.1.4.1.37950.1.1.5.12.6.3.2.4
-- 1.3.6.1.4.1.37950.1.1.5.12.6.3.2.4
		-- 1.3.6.1.4.1.37950.1.1.5.12.6.3.2.4
		userTid OBJECT-TYPE
			SYNTAX OCTET STRING (SIZE (0..32))
			MAX-ACCESS read-write
			STATUS current
			DESCRIPTION
				"Description."
			::= { h248UserTid 4 }

		
--          1.3.6.1.4.1.37950.1.1.5.12.6.3.2.5
-- 1.3.6.1.4.1.37950.1.1.5.12.6.3.2.5
-- 1.3.6.1.4.1.37950.1.1.5.12.6.3.2.5
-- 1.3.6.1.4.1.37950.1.1.5.12.6.3.2.5
-- 1.3.6.1.4.1.37950.1.1.5.12.6.3.2.5
-- 1.3.6.1.4.1.37950.1.1.5.12.6.3.2.5
-- 1.3.6.1.4.1.37950.1.1.5.12.6.3.2.5
-- 1.3.6.1.4.1.37950.1.1.5.12.6.3.2.5
-- 1.3.6.1.4.1.37950.1.1.5.12.6.3.2.5
		-- 1.3.6.1.4.1.37950.1.1.5.12.6.3.2.5
		userTidAction OBJECT-TYPE
			SYNTAX INTEGER { commit(1) }
			MAX-ACCESS read-write
			STATUS current
			DESCRIPTION
				"Description."
			::= { h248UserTid 5 }

		
--          1.3.6.1.4.1.37950.1.1.5.12.6.3.4
-- 1.3.6.1.4.1.37950.1.1.5.12.6.3.4
-- 1.3.6.1.4.1.37950.1.1.5.12.6.3.4
-- 1.3.6.1.4.1.37950.1.1.5.12.6.3.4
-- 1.3.6.1.4.1.37950.1.1.5.12.6.3.4
-- 1.3.6.1.4.1.37950.1.1.5.12.6.3.4
-- 1.3.6.1.4.1.37950.1.1.5.12.6.3.4
-- 1.3.6.1.4.1.37950.1.1.5.12.6.3.4
-- 1.3.6.1.4.1.37950.1.1.5.12.6.3.4
		-- 1.3.6.1.4.1.37950.1.1.5.12.6.3.4
		h248RtpTid OBJECT IDENTIFIER ::= { voipH248Cfg 4 }

		
--          1.3.6.1.4.1.37950.1.1.5.12.6.3.4.1
-- 1.3.6.1.4.1.37950.1.1.5.12.6.3.4.1
-- 1.3.6.1.4.1.37950.1.1.5.12.6.3.4.1
-- 1.3.6.1.4.1.37950.1.1.5.12.6.3.4.1
-- 1.3.6.1.4.1.37950.1.1.5.12.6.3.4.1
-- 1.3.6.1.4.1.37950.1.1.5.12.6.3.4.1
-- 1.3.6.1.4.1.37950.1.1.5.12.6.3.4.1
-- 1.3.6.1.4.1.37950.1.1.5.12.6.3.4.1
-- 1.3.6.1.4.1.37950.1.1.5.12.6.3.4.1
		-- 1.3.6.1.4.1.37950.1.1.5.12.6.3.4.1
		rtpTidPonNo OBJECT-TYPE
			SYNTAX INTEGER (1..16)
			MAX-ACCESS read-write
			STATUS current
			DESCRIPTION
				"Description."
			::= { h248RtpTid 1 }

		
--          1.3.6.1.4.1.37950.1.1.5.12.6.3.4.2
-- 1.3.6.1.4.1.37950.1.1.5.12.6.3.4.2
-- 1.3.6.1.4.1.37950.1.1.5.12.6.3.4.2
-- 1.3.6.1.4.1.37950.1.1.5.12.6.3.4.2
-- 1.3.6.1.4.1.37950.1.1.5.12.6.3.4.2
-- 1.3.6.1.4.1.37950.1.1.5.12.6.3.4.2
-- 1.3.6.1.4.1.37950.1.1.5.12.6.3.4.2
-- 1.3.6.1.4.1.37950.1.1.5.12.6.3.4.2
-- 1.3.6.1.4.1.37950.1.1.5.12.6.3.4.2
		-- 1.3.6.1.4.1.37950.1.1.5.12.6.3.4.2
		rtpTidOnuNo OBJECT-TYPE
			SYNTAX INTEGER (1..255)
			MAX-ACCESS read-write
			STATUS current
			DESCRIPTION
				"Description."
			::= { h248RtpTid 2 }

		
--          1.3.6.1.4.1.37950.1.1.5.12.6.3.4.3
-- 1.3.6.1.4.1.37950.1.1.5.12.6.3.4.3
-- 1.3.6.1.4.1.37950.1.1.5.12.6.3.4.3
-- 1.3.6.1.4.1.37950.1.1.5.12.6.3.4.3
-- 1.3.6.1.4.1.37950.1.1.5.12.6.3.4.3
-- 1.3.6.1.4.1.37950.1.1.5.12.6.3.4.3
-- 1.3.6.1.4.1.37950.1.1.5.12.6.3.4.3
-- 1.3.6.1.4.1.37950.1.1.5.12.6.3.4.3
-- 1.3.6.1.4.1.37950.1.1.5.12.6.3.4.3
		-- 1.3.6.1.4.1.37950.1.1.5.12.6.3.4.3
		rtpTidNumber OBJECT-TYPE
			SYNTAX INTEGER (0..255)
			MAX-ACCESS read-write
			STATUS current
			DESCRIPTION
				"Description."
			::= { h248RtpTid 3 }

		
--          1.3.6.1.4.1.37950.1.1.5.12.6.3.4.4
-- 1.3.6.1.4.1.37950.1.1.5.12.6.3.4.4
-- 1.3.6.1.4.1.37950.1.1.5.12.6.3.4.4
-- 1.3.6.1.4.1.37950.1.1.5.12.6.3.4.4
-- 1.3.6.1.4.1.37950.1.1.5.12.6.3.4.4
-- 1.3.6.1.4.1.37950.1.1.5.12.6.3.4.4
-- 1.3.6.1.4.1.37950.1.1.5.12.6.3.4.4
-- 1.3.6.1.4.1.37950.1.1.5.12.6.3.4.4
-- 1.3.6.1.4.1.37950.1.1.5.12.6.3.4.4
		-- 1.3.6.1.4.1.37950.1.1.5.12.6.3.4.4
		rtpTidPrefix OBJECT-TYPE
			SYNTAX OCTET STRING
			MAX-ACCESS read-write
			STATUS current
			DESCRIPTION
				"Description."
			::= { h248RtpTid 4 }

		
--          1.3.6.1.4.1.37950.1.1.5.12.6.3.4.5
-- 1.3.6.1.4.1.37950.1.1.5.12.6.3.4.5
-- 1.3.6.1.4.1.37950.1.1.5.12.6.3.4.5
-- 1.3.6.1.4.1.37950.1.1.5.12.6.3.4.5
-- 1.3.6.1.4.1.37950.1.1.5.12.6.3.4.5
-- 1.3.6.1.4.1.37950.1.1.5.12.6.3.4.5
-- 1.3.6.1.4.1.37950.1.1.5.12.6.3.4.5
-- 1.3.6.1.4.1.37950.1.1.5.12.6.3.4.5
-- 1.3.6.1.4.1.37950.1.1.5.12.6.3.4.5
		-- 1.3.6.1.4.1.37950.1.1.5.12.6.3.4.5
		digitBegin0 OBJECT-TYPE
			SYNTAX Unsigned32 (0..4294967295)
			MAX-ACCESS read-write
			STATUS current
			DESCRIPTION
				"Description."
			::= { h248RtpTid 5 }

		
--          1.3.6.1.4.1.37950.1.1.5.12.6.3.4.6
-- 1.3.6.1.4.1.37950.1.1.5.12.6.3.4.6
-- 1.3.6.1.4.1.37950.1.1.5.12.6.3.4.6
-- 1.3.6.1.4.1.37950.1.1.5.12.6.3.4.6
-- 1.3.6.1.4.1.37950.1.1.5.12.6.3.4.6
-- 1.3.6.1.4.1.37950.1.1.5.12.6.3.4.6
-- 1.3.6.1.4.1.37950.1.1.5.12.6.3.4.6
-- 1.3.6.1.4.1.37950.1.1.5.12.6.3.4.6
-- 1.3.6.1.4.1.37950.1.1.5.12.6.3.4.6
		-- 1.3.6.1.4.1.37950.1.1.5.12.6.3.4.6
		digitBegin1 OBJECT-TYPE
			SYNTAX Unsigned32 (0..4294967295)
			MAX-ACCESS read-write
			STATUS current
			DESCRIPTION
				"Description."
			::= { h248RtpTid 6 }

		
--          1.3.6.1.4.1.37950.1.1.5.12.6.3.4.7
-- 1.3.6.1.4.1.37950.1.1.5.12.6.3.4.7
-- 1.3.6.1.4.1.37950.1.1.5.12.6.3.4.7
-- 1.3.6.1.4.1.37950.1.1.5.12.6.3.4.7
-- 1.3.6.1.4.1.37950.1.1.5.12.6.3.4.7
-- 1.3.6.1.4.1.37950.1.1.5.12.6.3.4.7
-- 1.3.6.1.4.1.37950.1.1.5.12.6.3.4.7
-- 1.3.6.1.4.1.37950.1.1.5.12.6.3.4.7
-- 1.3.6.1.4.1.37950.1.1.5.12.6.3.4.7
		-- 1.3.6.1.4.1.37950.1.1.5.12.6.3.4.7
		rtpTidMode OBJECT-TYPE
			SYNTAX INTEGER
				{
				align(1),
				unalign(2)
				}
			MAX-ACCESS read-write
			STATUS current
			DESCRIPTION
				"Description."
			::= { h248RtpTid 7 }

		
--          1.3.6.1.4.1.37950.1.1.5.12.6.3.4.8
-- 1.3.6.1.4.1.37950.1.1.5.12.6.3.4.8
-- 1.3.6.1.4.1.37950.1.1.5.12.6.3.4.8
-- 1.3.6.1.4.1.37950.1.1.5.12.6.3.4.8
-- 1.3.6.1.4.1.37950.1.1.5.12.6.3.4.8
-- 1.3.6.1.4.1.37950.1.1.5.12.6.3.4.8
-- 1.3.6.1.4.1.37950.1.1.5.12.6.3.4.8
-- 1.3.6.1.4.1.37950.1.1.5.12.6.3.4.8
-- 1.3.6.1.4.1.37950.1.1.5.12.6.3.4.8
		-- 1.3.6.1.4.1.37950.1.1.5.12.6.3.4.8
		digitLength OBJECT-TYPE
			SYNTAX INTEGER (0..255)
			MAX-ACCESS read-write
			STATUS current
			DESCRIPTION
				"Description."
			::= { h248RtpTid 8 }

		
--          1.3.6.1.4.1.37950.1.1.5.12.6.3.4.9
-- 1.3.6.1.4.1.37950.1.1.5.12.6.3.4.9
-- 1.3.6.1.4.1.37950.1.1.5.12.6.3.4.9
-- 1.3.6.1.4.1.37950.1.1.5.12.6.3.4.9
-- 1.3.6.1.4.1.37950.1.1.5.12.6.3.4.9
-- 1.3.6.1.4.1.37950.1.1.5.12.6.3.4.9
-- 1.3.6.1.4.1.37950.1.1.5.12.6.3.4.9
-- 1.3.6.1.4.1.37950.1.1.5.12.6.3.4.9
-- 1.3.6.1.4.1.37950.1.1.5.12.6.3.4.9
		-- 1.3.6.1.4.1.37950.1.1.5.12.6.3.4.9
		rtpTidAction OBJECT-TYPE
			SYNTAX INTEGER { commit(1) }
			MAX-ACCESS read-write
			STATUS current
			DESCRIPTION
				"Description."
			::= { h248RtpTid 9 }

		
--          1.3.6.1.4.1.37950.1.1.5.12.6.4
-- 1.3.6.1.4.1.37950.1.1.5.12.6.4
-- 1.3.6.1.4.1.37950.1.1.5.12.6.4
-- 1.3.6.1.4.1.37950.1.1.5.12.6.4
-- 1.3.6.1.4.1.37950.1.1.5.12.6.4
-- 1.3.6.1.4.1.37950.1.1.5.12.6.4
-- 1.3.6.1.4.1.37950.1.1.5.12.6.4
-- 1.3.6.1.4.1.37950.1.1.5.12.6.4
-- 1.3.6.1.4.1.37950.1.1.5.12.6.4
		-- 1.3.6.1.4.1.37950.1.1.5.12.6.4
		voipSipCfg OBJECT IDENTIFIER ::= { onuVoipCfg 4 }

		
--          1.3.6.1.4.1.37950.1.1.5.12.6.4.1
-- 1.3.6.1.4.1.37950.1.1.5.12.6.4.1
-- 1.3.6.1.4.1.37950.1.1.5.12.6.4.1
-- 1.3.6.1.4.1.37950.1.1.5.12.6.4.1
-- 1.3.6.1.4.1.37950.1.1.5.12.6.4.1
-- 1.3.6.1.4.1.37950.1.1.5.12.6.4.1
-- 1.3.6.1.4.1.37950.1.1.5.12.6.4.1
-- 1.3.6.1.4.1.37950.1.1.5.12.6.4.1
-- 1.3.6.1.4.1.37950.1.1.5.12.6.4.1
		-- 1.3.6.1.4.1.37950.1.1.5.12.6.4.1
		sipProParam OBJECT IDENTIFIER ::= { voipSipCfg 1 }

		
--          1.3.6.1.4.1.37950.1.1.5.12.6.4.1.1
-- 1.3.6.1.4.1.37950.1.1.5.12.6.4.1.1
-- 1.3.6.1.4.1.37950.1.1.5.12.6.4.1.1
-- 1.3.6.1.4.1.37950.1.1.5.12.6.4.1.1
-- 1.3.6.1.4.1.37950.1.1.5.12.6.4.1.1
-- 1.3.6.1.4.1.37950.1.1.5.12.6.4.1.1
-- 1.3.6.1.4.1.37950.1.1.5.12.6.4.1.1
-- 1.3.6.1.4.1.37950.1.1.5.12.6.4.1.1
-- 1.3.6.1.4.1.37950.1.1.5.12.6.4.1.1
		-- 1.3.6.1.4.1.37950.1.1.5.12.6.4.1.1
		hbeatCfg OBJECT IDENTIFIER ::= { sipProParam 1 }

		
--          1.3.6.1.4.1.37950.1.1.5.12.6.4.1.1.1
-- 1.3.6.1.4.1.37950.1.1.5.12.6.4.1.1.1
-- 1.3.6.1.4.1.37950.1.1.5.12.6.4.1.1.1
-- 1.3.6.1.4.1.37950.1.1.5.12.6.4.1.1.1
-- 1.3.6.1.4.1.37950.1.1.5.12.6.4.1.1.1
-- 1.3.6.1.4.1.37950.1.1.5.12.6.4.1.1.1
-- 1.3.6.1.4.1.37950.1.1.5.12.6.4.1.1.1
-- 1.3.6.1.4.1.37950.1.1.5.12.6.4.1.1.1
-- 1.3.6.1.4.1.37950.1.1.5.12.6.4.1.1.1
		-- 1.3.6.1.4.1.37950.1.1.5.12.6.4.1.1.1
		hbeatPonNo OBJECT-TYPE
			SYNTAX INTEGER (1..16)
			MAX-ACCESS read-write
			STATUS current
			DESCRIPTION
				"Description."
			::= { hbeatCfg 1 }

		
--          1.3.6.1.4.1.37950.1.1.5.12.6.4.1.1.2
-- 1.3.6.1.4.1.37950.1.1.5.12.6.4.1.1.2
-- 1.3.6.1.4.1.37950.1.1.5.12.6.4.1.1.2
-- 1.3.6.1.4.1.37950.1.1.5.12.6.4.1.1.2
-- 1.3.6.1.4.1.37950.1.1.5.12.6.4.1.1.2
-- 1.3.6.1.4.1.37950.1.1.5.12.6.4.1.1.2
-- 1.3.6.1.4.1.37950.1.1.5.12.6.4.1.1.2
-- 1.3.6.1.4.1.37950.1.1.5.12.6.4.1.1.2
-- 1.3.6.1.4.1.37950.1.1.5.12.6.4.1.1.2
		-- 1.3.6.1.4.1.37950.1.1.5.12.6.4.1.1.2
		hbeatOnuNo OBJECT-TYPE
			SYNTAX INTEGER (1..65535)
			MAX-ACCESS read-write
			STATUS current
			DESCRIPTION
				"Description."
			::= { hbeatCfg 2 }

		
--          1.3.6.1.4.1.37950.1.1.5.12.6.4.1.1.3
-- 1.3.6.1.4.1.37950.1.1.5.12.6.4.1.1.3
-- 1.3.6.1.4.1.37950.1.1.5.12.6.4.1.1.3
-- 1.3.6.1.4.1.37950.1.1.5.12.6.4.1.1.3
-- 1.3.6.1.4.1.37950.1.1.5.12.6.4.1.1.3
-- 1.3.6.1.4.1.37950.1.1.5.12.6.4.1.1.3
-- 1.3.6.1.4.1.37950.1.1.5.12.6.4.1.1.3
-- 1.3.6.1.4.1.37950.1.1.5.12.6.4.1.1.3
-- 1.3.6.1.4.1.37950.1.1.5.12.6.4.1.1.3
		-- 1.3.6.1.4.1.37950.1.1.5.12.6.4.1.1.3
		hbeartEn OBJECT-TYPE
			SYNTAX INTEGER
				{
				disable(0),
				enable(1)
				}
			MAX-ACCESS read-write
			STATUS current
			DESCRIPTION
				"Description."
			::= { hbeatCfg 3 }

		
--          1.3.6.1.4.1.37950.1.1.5.12.6.4.1.1.4
-- 1.3.6.1.4.1.37950.1.1.5.12.6.4.1.1.4
-- 1.3.6.1.4.1.37950.1.1.5.12.6.4.1.1.4
-- 1.3.6.1.4.1.37950.1.1.5.12.6.4.1.1.4
-- 1.3.6.1.4.1.37950.1.1.5.12.6.4.1.1.4
-- 1.3.6.1.4.1.37950.1.1.5.12.6.4.1.1.4
-- 1.3.6.1.4.1.37950.1.1.5.12.6.4.1.1.4
-- 1.3.6.1.4.1.37950.1.1.5.12.6.4.1.1.4
-- 1.3.6.1.4.1.37950.1.1.5.12.6.4.1.1.4
		-- 1.3.6.1.4.1.37950.1.1.5.12.6.4.1.1.4
		hbeatCycle OBJECT-TYPE
			SYNTAX INTEGER (1..65535)
			MAX-ACCESS read-write
			STATUS current
			DESCRIPTION
				"Description."
			::= { hbeatCfg 4 }

		
--          1.3.6.1.4.1.37950.1.1.5.12.6.4.1.1.5
-- 1.3.6.1.4.1.37950.1.1.5.12.6.4.1.1.5
-- 1.3.6.1.4.1.37950.1.1.5.12.6.4.1.1.5
-- 1.3.6.1.4.1.37950.1.1.5.12.6.4.1.1.5
-- 1.3.6.1.4.1.37950.1.1.5.12.6.4.1.1.5
-- 1.3.6.1.4.1.37950.1.1.5.12.6.4.1.1.5
-- 1.3.6.1.4.1.37950.1.1.5.12.6.4.1.1.5
-- 1.3.6.1.4.1.37950.1.1.5.12.6.4.1.1.5
-- 1.3.6.1.4.1.37950.1.1.5.12.6.4.1.1.5
		-- 1.3.6.1.4.1.37950.1.1.5.12.6.4.1.1.5
		hbeatCount OBJECT-TYPE
			SYNTAX INTEGER (1..65535)
			MAX-ACCESS read-write
			STATUS current
			DESCRIPTION
				"Description."
			::= { hbeatCfg 5 }

		
--          1.3.6.1.4.1.37950.1.1.5.12.6.4.1.1.6
-- 1.3.6.1.4.1.37950.1.1.5.12.6.4.1.1.6
-- 1.3.6.1.4.1.37950.1.1.5.12.6.4.1.1.6
-- 1.3.6.1.4.1.37950.1.1.5.12.6.4.1.1.6
-- 1.3.6.1.4.1.37950.1.1.5.12.6.4.1.1.6
-- 1.3.6.1.4.1.37950.1.1.5.12.6.4.1.1.6
-- 1.3.6.1.4.1.37950.1.1.5.12.6.4.1.1.6
-- 1.3.6.1.4.1.37950.1.1.5.12.6.4.1.1.6
-- 1.3.6.1.4.1.37950.1.1.5.12.6.4.1.1.6
		-- 1.3.6.1.4.1.37950.1.1.5.12.6.4.1.1.6
		regInterVal OBJECT-TYPE
			SYNTAX INTEGER (0..65535)
			MAX-ACCESS read-write
			STATUS current
			DESCRIPTION
				"Description."
			::= { hbeatCfg 6 }

		
--          1.3.6.1.4.1.37950.1.1.5.12.6.4.1.1.7
-- 1.3.6.1.4.1.37950.1.1.5.12.6.4.1.1.7
-- 1.3.6.1.4.1.37950.1.1.5.12.6.4.1.1.7
-- 1.3.6.1.4.1.37950.1.1.5.12.6.4.1.1.7
-- 1.3.6.1.4.1.37950.1.1.5.12.6.4.1.1.7
-- 1.3.6.1.4.1.37950.1.1.5.12.6.4.1.1.7
-- 1.3.6.1.4.1.37950.1.1.5.12.6.4.1.1.7
-- 1.3.6.1.4.1.37950.1.1.5.12.6.4.1.1.7
-- 1.3.6.1.4.1.37950.1.1.5.12.6.4.1.1.7
		-- 1.3.6.1.4.1.37950.1.1.5.12.6.4.1.1.7
		hbeatAction OBJECT-TYPE
			SYNTAX INTEGER { commit(1) }
			MAX-ACCESS read-write
			STATUS current
			DESCRIPTION
				"Description."
			::= { hbeatCfg 7 }

		
--          1.3.6.1.4.1.37950.1.1.5.12.6.4.1.2
-- 1.3.6.1.4.1.37950.1.1.5.12.6.4.1.2
-- 1.3.6.1.4.1.37950.1.1.5.12.6.4.1.2
-- 1.3.6.1.4.1.37950.1.1.5.12.6.4.1.2
-- 1.3.6.1.4.1.37950.1.1.5.12.6.4.1.2
-- 1.3.6.1.4.1.37950.1.1.5.12.6.4.1.2
-- 1.3.6.1.4.1.37950.1.1.5.12.6.4.1.2
-- 1.3.6.1.4.1.37950.1.1.5.12.6.4.1.2
-- 1.3.6.1.4.1.37950.1.1.5.12.6.4.1.2
		-- 1.3.6.1.4.1.37950.1.1.5.12.6.4.1.2
		servIpCfg OBJECT IDENTIFIER ::= { sipProParam 2 }

		
--          1.3.6.1.4.1.37950.1.1.5.12.6.4.1.2.1
-- 1.3.6.1.4.1.37950.1.1.5.12.6.4.1.2.1
-- 1.3.6.1.4.1.37950.1.1.5.12.6.4.1.2.1
-- 1.3.6.1.4.1.37950.1.1.5.12.6.4.1.2.1
-- 1.3.6.1.4.1.37950.1.1.5.12.6.4.1.2.1
-- 1.3.6.1.4.1.37950.1.1.5.12.6.4.1.2.1
-- 1.3.6.1.4.1.37950.1.1.5.12.6.4.1.2.1
-- 1.3.6.1.4.1.37950.1.1.5.12.6.4.1.2.1
-- 1.3.6.1.4.1.37950.1.1.5.12.6.4.1.2.1
		-- 1.3.6.1.4.1.37950.1.1.5.12.6.4.1.2.1
		servIpPonNo OBJECT-TYPE
			SYNTAX INTEGER (1..16)
			MAX-ACCESS read-write
			STATUS current
			DESCRIPTION
				"Description."
			::= { servIpCfg 1 }

		
--          1.3.6.1.4.1.37950.1.1.5.12.6.4.1.2.2
-- 1.3.6.1.4.1.37950.1.1.5.12.6.4.1.2.2
-- 1.3.6.1.4.1.37950.1.1.5.12.6.4.1.2.2
-- 1.3.6.1.4.1.37950.1.1.5.12.6.4.1.2.2
-- 1.3.6.1.4.1.37950.1.1.5.12.6.4.1.2.2
-- 1.3.6.1.4.1.37950.1.1.5.12.6.4.1.2.2
-- 1.3.6.1.4.1.37950.1.1.5.12.6.4.1.2.2
-- 1.3.6.1.4.1.37950.1.1.5.12.6.4.1.2.2
-- 1.3.6.1.4.1.37950.1.1.5.12.6.4.1.2.2
		-- 1.3.6.1.4.1.37950.1.1.5.12.6.4.1.2.2
		servIpOnuNo OBJECT-TYPE
			SYNTAX INTEGER (1..65535)
			MAX-ACCESS read-write
			STATUS current
			DESCRIPTION
				"Description."
			::= { servIpCfg 2 }

		
--          1.3.6.1.4.1.37950.1.1.5.12.6.4.1.2.3
-- 1.3.6.1.4.1.37950.1.1.5.12.6.4.1.2.3
-- 1.3.6.1.4.1.37950.1.1.5.12.6.4.1.2.3
-- 1.3.6.1.4.1.37950.1.1.5.12.6.4.1.2.3
-- 1.3.6.1.4.1.37950.1.1.5.12.6.4.1.2.3
-- 1.3.6.1.4.1.37950.1.1.5.12.6.4.1.2.3
-- 1.3.6.1.4.1.37950.1.1.5.12.6.4.1.2.3
-- 1.3.6.1.4.1.37950.1.1.5.12.6.4.1.2.3
-- 1.3.6.1.4.1.37950.1.1.5.12.6.4.1.2.3
		-- 1.3.6.1.4.1.37950.1.1.5.12.6.4.1.2.3
		mgPortVal OBJECT-TYPE
			SYNTAX INTEGER (1..65535)
			MAX-ACCESS read-write
			STATUS current
			DESCRIPTION
				"Description."
			::= { servIpCfg 3 }

		
--          1.3.6.1.4.1.37950.1.1.5.12.6.4.1.2.4
-- 1.3.6.1.4.1.37950.1.1.5.12.6.4.1.2.4
-- 1.3.6.1.4.1.37950.1.1.5.12.6.4.1.2.4
-- 1.3.6.1.4.1.37950.1.1.5.12.6.4.1.2.4
-- 1.3.6.1.4.1.37950.1.1.5.12.6.4.1.2.4
-- 1.3.6.1.4.1.37950.1.1.5.12.6.4.1.2.4
-- 1.3.6.1.4.1.37950.1.1.5.12.6.4.1.2.4
-- 1.3.6.1.4.1.37950.1.1.5.12.6.4.1.2.4
-- 1.3.6.1.4.1.37950.1.1.5.12.6.4.1.2.4
		-- 1.3.6.1.4.1.37950.1.1.5.12.6.4.1.2.4
		servIpVal OBJECT-TYPE
			SYNTAX IpAddress
			MAX-ACCESS read-write
			STATUS current
			DESCRIPTION
				"Description."
			::= { servIpCfg 4 }

		
--          1.3.6.1.4.1.37950.1.1.5.12.6.4.1.2.5
-- 1.3.6.1.4.1.37950.1.1.5.12.6.4.1.2.5
-- 1.3.6.1.4.1.37950.1.1.5.12.6.4.1.2.5
-- 1.3.6.1.4.1.37950.1.1.5.12.6.4.1.2.5
-- 1.3.6.1.4.1.37950.1.1.5.12.6.4.1.2.5
-- 1.3.6.1.4.1.37950.1.1.5.12.6.4.1.2.5
-- 1.3.6.1.4.1.37950.1.1.5.12.6.4.1.2.5
-- 1.3.6.1.4.1.37950.1.1.5.12.6.4.1.2.5
-- 1.3.6.1.4.1.37950.1.1.5.12.6.4.1.2.5
		-- 1.3.6.1.4.1.37950.1.1.5.12.6.4.1.2.5
		servPortVal OBJECT-TYPE
			SYNTAX INTEGER (1..65535)
			MAX-ACCESS read-write
			STATUS current
			DESCRIPTION
				"Description."
			::= { servIpCfg 5 }

		
--          1.3.6.1.4.1.37950.1.1.5.12.6.4.1.2.6
-- 1.3.6.1.4.1.37950.1.1.5.12.6.4.1.2.6
-- 1.3.6.1.4.1.37950.1.1.5.12.6.4.1.2.6
-- 1.3.6.1.4.1.37950.1.1.5.12.6.4.1.2.6
-- 1.3.6.1.4.1.37950.1.1.5.12.6.4.1.2.6
-- 1.3.6.1.4.1.37950.1.1.5.12.6.4.1.2.6
-- 1.3.6.1.4.1.37950.1.1.5.12.6.4.1.2.6
-- 1.3.6.1.4.1.37950.1.1.5.12.6.4.1.2.6
-- 1.3.6.1.4.1.37950.1.1.5.12.6.4.1.2.6
		-- 1.3.6.1.4.1.37950.1.1.5.12.6.4.1.2.6
		servIpAction OBJECT-TYPE
			SYNTAX INTEGER { commit(1) }
			MAX-ACCESS read-write
			STATUS current
			DESCRIPTION
				"Description."
			::= { servIpCfg 6 }

		
--          1.3.6.1.4.1.37950.1.1.5.12.6.4.1.3
-- 1.3.6.1.4.1.37950.1.1.5.12.6.4.1.3
-- 1.3.6.1.4.1.37950.1.1.5.12.6.4.1.3
-- 1.3.6.1.4.1.37950.1.1.5.12.6.4.1.3
-- 1.3.6.1.4.1.37950.1.1.5.12.6.4.1.3
-- 1.3.6.1.4.1.37950.1.1.5.12.6.4.1.3
-- 1.3.6.1.4.1.37950.1.1.5.12.6.4.1.3
-- 1.3.6.1.4.1.37950.1.1.5.12.6.4.1.3
-- 1.3.6.1.4.1.37950.1.1.5.12.6.4.1.3
		-- 1.3.6.1.4.1.37950.1.1.5.12.6.4.1.3
		proxyServCfg OBJECT IDENTIFIER ::= { sipProParam 3 }

		
--          1.3.6.1.4.1.37950.1.1.5.12.6.4.1.3.1
-- 1.3.6.1.4.1.37950.1.1.5.12.6.4.1.3.1
-- 1.3.6.1.4.1.37950.1.1.5.12.6.4.1.3.1
-- 1.3.6.1.4.1.37950.1.1.5.12.6.4.1.3.1
-- 1.3.6.1.4.1.37950.1.1.5.12.6.4.1.3.1
-- 1.3.6.1.4.1.37950.1.1.5.12.6.4.1.3.1
-- 1.3.6.1.4.1.37950.1.1.5.12.6.4.1.3.1
-- 1.3.6.1.4.1.37950.1.1.5.12.6.4.1.3.1
-- 1.3.6.1.4.1.37950.1.1.5.12.6.4.1.3.1
		-- 1.3.6.1.4.1.37950.1.1.5.12.6.4.1.3.1
		proxySrvPonNo OBJECT-TYPE
			SYNTAX INTEGER (1..16)
			MAX-ACCESS read-write
			STATUS current
			DESCRIPTION
				"Description."
			::= { proxyServCfg 1 }

		
--          1.3.6.1.4.1.37950.1.1.5.12.6.4.1.3.2
-- 1.3.6.1.4.1.37950.1.1.5.12.6.4.1.3.2
-- 1.3.6.1.4.1.37950.1.1.5.12.6.4.1.3.2
-- 1.3.6.1.4.1.37950.1.1.5.12.6.4.1.3.2
-- 1.3.6.1.4.1.37950.1.1.5.12.6.4.1.3.2
-- 1.3.6.1.4.1.37950.1.1.5.12.6.4.1.3.2
-- 1.3.6.1.4.1.37950.1.1.5.12.6.4.1.3.2
-- 1.3.6.1.4.1.37950.1.1.5.12.6.4.1.3.2
-- 1.3.6.1.4.1.37950.1.1.5.12.6.4.1.3.2
		-- 1.3.6.1.4.1.37950.1.1.5.12.6.4.1.3.2
		proxySrvOnuNo OBJECT-TYPE
			SYNTAX INTEGER (1..65535)
			MAX-ACCESS read-write
			STATUS current
			DESCRIPTION
				"Description."
			::= { proxyServCfg 2 }

		
--          1.3.6.1.4.1.37950.1.1.5.12.6.4.1.3.3
-- 1.3.6.1.4.1.37950.1.1.5.12.6.4.1.3.3
-- 1.3.6.1.4.1.37950.1.1.5.12.6.4.1.3.3
-- 1.3.6.1.4.1.37950.1.1.5.12.6.4.1.3.3
-- 1.3.6.1.4.1.37950.1.1.5.12.6.4.1.3.3
-- 1.3.6.1.4.1.37950.1.1.5.12.6.4.1.3.3
-- 1.3.6.1.4.1.37950.1.1.5.12.6.4.1.3.3
-- 1.3.6.1.4.1.37950.1.1.5.12.6.4.1.3.3
-- 1.3.6.1.4.1.37950.1.1.5.12.6.4.1.3.3
		-- 1.3.6.1.4.1.37950.1.1.5.12.6.4.1.3.3
		proxySrv OBJECT-TYPE
			SYNTAX IpAddress
			MAX-ACCESS read-write
			STATUS current
			DESCRIPTION
				"Description."
			::= { proxyServCfg 3 }

		
--          1.3.6.1.4.1.37950.1.1.5.12.6.4.1.3.4
-- 1.3.6.1.4.1.37950.1.1.5.12.6.4.1.3.4
-- 1.3.6.1.4.1.37950.1.1.5.12.6.4.1.3.4
-- 1.3.6.1.4.1.37950.1.1.5.12.6.4.1.3.4
-- 1.3.6.1.4.1.37950.1.1.5.12.6.4.1.3.4
-- 1.3.6.1.4.1.37950.1.1.5.12.6.4.1.3.4
-- 1.3.6.1.4.1.37950.1.1.5.12.6.4.1.3.4
-- 1.3.6.1.4.1.37950.1.1.5.12.6.4.1.3.4
-- 1.3.6.1.4.1.37950.1.1.5.12.6.4.1.3.4
		-- 1.3.6.1.4.1.37950.1.1.5.12.6.4.1.3.4
		proxySrvPort OBJECT-TYPE
			SYNTAX INTEGER (1..65535)
			MAX-ACCESS read-write
			STATUS current
			DESCRIPTION
				"Description."
			::= { proxyServCfg 4 }

		
--          1.3.6.1.4.1.37950.1.1.5.12.6.4.1.3.5
-- 1.3.6.1.4.1.37950.1.1.5.12.6.4.1.3.5
-- 1.3.6.1.4.1.37950.1.1.5.12.6.4.1.3.5
-- 1.3.6.1.4.1.37950.1.1.5.12.6.4.1.3.5
-- 1.3.6.1.4.1.37950.1.1.5.12.6.4.1.3.5
-- 1.3.6.1.4.1.37950.1.1.5.12.6.4.1.3.5
-- 1.3.6.1.4.1.37950.1.1.5.12.6.4.1.3.5
-- 1.3.6.1.4.1.37950.1.1.5.12.6.4.1.3.5
-- 1.3.6.1.4.1.37950.1.1.5.12.6.4.1.3.5
		-- 1.3.6.1.4.1.37950.1.1.5.12.6.4.1.3.5
		bakProxySrv OBJECT-TYPE
			SYNTAX IpAddress
			MAX-ACCESS read-write
			STATUS current
			DESCRIPTION
				"Description."
			::= { proxyServCfg 5 }

		
--          1.3.6.1.4.1.37950.1.1.5.12.6.4.1.3.6
-- 1.3.6.1.4.1.37950.1.1.5.12.6.4.1.3.6
-- 1.3.6.1.4.1.37950.1.1.5.12.6.4.1.3.6
-- 1.3.6.1.4.1.37950.1.1.5.12.6.4.1.3.6
-- 1.3.6.1.4.1.37950.1.1.5.12.6.4.1.3.6
-- 1.3.6.1.4.1.37950.1.1.5.12.6.4.1.3.6
-- 1.3.6.1.4.1.37950.1.1.5.12.6.4.1.3.6
-- 1.3.6.1.4.1.37950.1.1.5.12.6.4.1.3.6
-- 1.3.6.1.4.1.37950.1.1.5.12.6.4.1.3.6
		-- 1.3.6.1.4.1.37950.1.1.5.12.6.4.1.3.6
		bakProxySrvPort OBJECT-TYPE
			SYNTAX INTEGER (1..65535)
			MAX-ACCESS read-write
			STATUS current
			DESCRIPTION
				"Description."
			::= { proxyServCfg 6 }

		
--          1.3.6.1.4.1.37950.1.1.5.12.6.4.1.3.7
-- 1.3.6.1.4.1.37950.1.1.5.12.6.4.1.3.7
-- 1.3.6.1.4.1.37950.1.1.5.12.6.4.1.3.7
-- 1.3.6.1.4.1.37950.1.1.5.12.6.4.1.3.7
-- 1.3.6.1.4.1.37950.1.1.5.12.6.4.1.3.7
-- 1.3.6.1.4.1.37950.1.1.5.12.6.4.1.3.7
-- 1.3.6.1.4.1.37950.1.1.5.12.6.4.1.3.7
-- 1.3.6.1.4.1.37950.1.1.5.12.6.4.1.3.7
-- 1.3.6.1.4.1.37950.1.1.5.12.6.4.1.3.7
		-- 1.3.6.1.4.1.37950.1.1.5.12.6.4.1.3.7
		proxySrvAction OBJECT-TYPE
			SYNTAX INTEGER { commit(1) }
			MAX-ACCESS read-write
			STATUS current
			DESCRIPTION
				"Description."
			::= { proxyServCfg 7 }

		
--          1.3.6.1.4.1.37950.1.1.5.12.6.4.1.4
-- 1.3.6.1.4.1.37950.1.1.5.12.6.4.1.4
-- 1.3.6.1.4.1.37950.1.1.5.12.6.4.1.4
-- 1.3.6.1.4.1.37950.1.1.5.12.6.4.1.4
-- 1.3.6.1.4.1.37950.1.1.5.12.6.4.1.4
-- 1.3.6.1.4.1.37950.1.1.5.12.6.4.1.4
-- 1.3.6.1.4.1.37950.1.1.5.12.6.4.1.4
-- 1.3.6.1.4.1.37950.1.1.5.12.6.4.1.4
-- 1.3.6.1.4.1.37950.1.1.5.12.6.4.1.4
		-- 1.3.6.1.4.1.37950.1.1.5.12.6.4.1.4
		regServCfg OBJECT IDENTIFIER ::= { sipProParam 4 }

		
--          1.3.6.1.4.1.37950.1.1.5.12.6.4.1.4.1
-- 1.3.6.1.4.1.37950.1.1.5.12.6.4.1.4.1
-- 1.3.6.1.4.1.37950.1.1.5.12.6.4.1.4.1
-- 1.3.6.1.4.1.37950.1.1.5.12.6.4.1.4.1
-- 1.3.6.1.4.1.37950.1.1.5.12.6.4.1.4.1
-- 1.3.6.1.4.1.37950.1.1.5.12.6.4.1.4.1
-- 1.3.6.1.4.1.37950.1.1.5.12.6.4.1.4.1
-- 1.3.6.1.4.1.37950.1.1.5.12.6.4.1.4.1
-- 1.3.6.1.4.1.37950.1.1.5.12.6.4.1.4.1
		-- 1.3.6.1.4.1.37950.1.1.5.12.6.4.1.4.1
		regSrvPonNo OBJECT-TYPE
			SYNTAX INTEGER (1..16)
			MAX-ACCESS read-write
			STATUS current
			DESCRIPTION
				"Description."
			::= { regServCfg 1 }

		
--          1.3.6.1.4.1.37950.1.1.5.12.6.4.1.4.2
-- 1.3.6.1.4.1.37950.1.1.5.12.6.4.1.4.2
-- 1.3.6.1.4.1.37950.1.1.5.12.6.4.1.4.2
-- 1.3.6.1.4.1.37950.1.1.5.12.6.4.1.4.2
-- 1.3.6.1.4.1.37950.1.1.5.12.6.4.1.4.2
-- 1.3.6.1.4.1.37950.1.1.5.12.6.4.1.4.2
-- 1.3.6.1.4.1.37950.1.1.5.12.6.4.1.4.2
-- 1.3.6.1.4.1.37950.1.1.5.12.6.4.1.4.2
-- 1.3.6.1.4.1.37950.1.1.5.12.6.4.1.4.2
		-- 1.3.6.1.4.1.37950.1.1.5.12.6.4.1.4.2
		regSrvOnuNo OBJECT-TYPE
			SYNTAX INTEGER (1..65535)
			MAX-ACCESS read-write
			STATUS current
			DESCRIPTION
				"Description."
			::= { regServCfg 2 }

		
--          1.3.6.1.4.1.37950.1.1.5.12.6.4.1.4.3
-- 1.3.6.1.4.1.37950.1.1.5.12.6.4.1.4.3
-- 1.3.6.1.4.1.37950.1.1.5.12.6.4.1.4.3
-- 1.3.6.1.4.1.37950.1.1.5.12.6.4.1.4.3
-- 1.3.6.1.4.1.37950.1.1.5.12.6.4.1.4.3
-- 1.3.6.1.4.1.37950.1.1.5.12.6.4.1.4.3
-- 1.3.6.1.4.1.37950.1.1.5.12.6.4.1.4.3
-- 1.3.6.1.4.1.37950.1.1.5.12.6.4.1.4.3
-- 1.3.6.1.4.1.37950.1.1.5.12.6.4.1.4.3
		-- 1.3.6.1.4.1.37950.1.1.5.12.6.4.1.4.3
		regSrv OBJECT-TYPE
			SYNTAX IpAddress
			MAX-ACCESS read-write
			STATUS current
			DESCRIPTION
				"Description."
			::= { regServCfg 3 }

		
--          1.3.6.1.4.1.37950.1.1.5.12.6.4.1.4.4
-- 1.3.6.1.4.1.37950.1.1.5.12.6.4.1.4.4
-- 1.3.6.1.4.1.37950.1.1.5.12.6.4.1.4.4
-- 1.3.6.1.4.1.37950.1.1.5.12.6.4.1.4.4
-- 1.3.6.1.4.1.37950.1.1.5.12.6.4.1.4.4
-- 1.3.6.1.4.1.37950.1.1.5.12.6.4.1.4.4
-- 1.3.6.1.4.1.37950.1.1.5.12.6.4.1.4.4
-- 1.3.6.1.4.1.37950.1.1.5.12.6.4.1.4.4
-- 1.3.6.1.4.1.37950.1.1.5.12.6.4.1.4.4
		-- 1.3.6.1.4.1.37950.1.1.5.12.6.4.1.4.4
		regSrvPort OBJECT-TYPE
			SYNTAX INTEGER (1..65535)
			MAX-ACCESS read-write
			STATUS current
			DESCRIPTION
				"Description."
			::= { regServCfg 4 }

		
--          1.3.6.1.4.1.37950.1.1.5.12.6.4.1.4.5
-- 1.3.6.1.4.1.37950.1.1.5.12.6.4.1.4.5
-- 1.3.6.1.4.1.37950.1.1.5.12.6.4.1.4.5
-- 1.3.6.1.4.1.37950.1.1.5.12.6.4.1.4.5
-- 1.3.6.1.4.1.37950.1.1.5.12.6.4.1.4.5
-- 1.3.6.1.4.1.37950.1.1.5.12.6.4.1.4.5
-- 1.3.6.1.4.1.37950.1.1.5.12.6.4.1.4.5
-- 1.3.6.1.4.1.37950.1.1.5.12.6.4.1.4.5
-- 1.3.6.1.4.1.37950.1.1.5.12.6.4.1.4.5
		-- 1.3.6.1.4.1.37950.1.1.5.12.6.4.1.4.5
		bakRegSrv OBJECT-TYPE
			SYNTAX IpAddress
			MAX-ACCESS read-write
			STATUS current
			DESCRIPTION
				"Description."
			::= { regServCfg 5 }

		
--          1.3.6.1.4.1.37950.1.1.5.12.6.4.1.4.6
-- 1.3.6.1.4.1.37950.1.1.5.12.6.4.1.4.6
-- 1.3.6.1.4.1.37950.1.1.5.12.6.4.1.4.6
-- 1.3.6.1.4.1.37950.1.1.5.12.6.4.1.4.6
-- 1.3.6.1.4.1.37950.1.1.5.12.6.4.1.4.6
-- 1.3.6.1.4.1.37950.1.1.5.12.6.4.1.4.6
-- 1.3.6.1.4.1.37950.1.1.5.12.6.4.1.4.6
-- 1.3.6.1.4.1.37950.1.1.5.12.6.4.1.4.6
-- 1.3.6.1.4.1.37950.1.1.5.12.6.4.1.4.6
		-- 1.3.6.1.4.1.37950.1.1.5.12.6.4.1.4.6
		bakRegSrvPort OBJECT-TYPE
			SYNTAX INTEGER (1..65535)
			MAX-ACCESS read-write
			STATUS current
			DESCRIPTION
				"Description."
			::= { regServCfg 6 }

		
--          1.3.6.1.4.1.37950.1.1.5.12.6.4.1.4.7
-- 1.3.6.1.4.1.37950.1.1.5.12.6.4.1.4.7
-- 1.3.6.1.4.1.37950.1.1.5.12.6.4.1.4.7
-- 1.3.6.1.4.1.37950.1.1.5.12.6.4.1.4.7
-- 1.3.6.1.4.1.37950.1.1.5.12.6.4.1.4.7
-- 1.3.6.1.4.1.37950.1.1.5.12.6.4.1.4.7
-- 1.3.6.1.4.1.37950.1.1.5.12.6.4.1.4.7
-- 1.3.6.1.4.1.37950.1.1.5.12.6.4.1.4.7
-- 1.3.6.1.4.1.37950.1.1.5.12.6.4.1.4.7
		-- 1.3.6.1.4.1.37950.1.1.5.12.6.4.1.4.7
		regSrvAction OBJECT-TYPE
			SYNTAX INTEGER { commit(1) }
			MAX-ACCESS read-write
			STATUS current
			DESCRIPTION
				"Description."
			::= { regServCfg 7 }

		
--          1.3.6.1.4.1.37950.1.1.5.12.6.4.1.5
-- 1.3.6.1.4.1.37950.1.1.5.12.6.4.1.5
-- 1.3.6.1.4.1.37950.1.1.5.12.6.4.1.5
-- 1.3.6.1.4.1.37950.1.1.5.12.6.4.1.5
-- 1.3.6.1.4.1.37950.1.1.5.12.6.4.1.5
-- 1.3.6.1.4.1.37950.1.1.5.12.6.4.1.5
-- 1.3.6.1.4.1.37950.1.1.5.12.6.4.1.5
-- 1.3.6.1.4.1.37950.1.1.5.12.6.4.1.5
-- 1.3.6.1.4.1.37950.1.1.5.12.6.4.1.5
		-- 1.3.6.1.4.1.37950.1.1.5.12.6.4.1.5
		sipParamCfg OBJECT IDENTIFIER ::= { sipProParam 5 }

		
--          1.3.6.1.4.1.37950.1.1.5.12.6.4.1.5.1
-- 1.3.6.1.4.1.37950.1.1.5.12.6.4.1.5.1
-- 1.3.6.1.4.1.37950.1.1.5.12.6.4.1.5.1
-- 1.3.6.1.4.1.37950.1.1.5.12.6.4.1.5.1
-- 1.3.6.1.4.1.37950.1.1.5.12.6.4.1.5.1
-- 1.3.6.1.4.1.37950.1.1.5.12.6.4.1.5.1
-- 1.3.6.1.4.1.37950.1.1.5.12.6.4.1.5.1
-- 1.3.6.1.4.1.37950.1.1.5.12.6.4.1.5.1
-- 1.3.6.1.4.1.37950.1.1.5.12.6.4.1.5.1
		-- 1.3.6.1.4.1.37950.1.1.5.12.6.4.1.5.1
		sipParamPonNo OBJECT-TYPE
			SYNTAX Integer32 (1..16)
			MAX-ACCESS read-write
			STATUS current
			DESCRIPTION
				"Description."
			::= { sipParamCfg 1 }

		
--          1.3.6.1.4.1.37950.1.1.5.12.6.4.1.5.2
-- 1.3.6.1.4.1.37950.1.1.5.12.6.4.1.5.2
-- 1.3.6.1.4.1.37950.1.1.5.12.6.4.1.5.2
-- 1.3.6.1.4.1.37950.1.1.5.12.6.4.1.5.2
-- 1.3.6.1.4.1.37950.1.1.5.12.6.4.1.5.2
-- 1.3.6.1.4.1.37950.1.1.5.12.6.4.1.5.2
-- 1.3.6.1.4.1.37950.1.1.5.12.6.4.1.5.2
-- 1.3.6.1.4.1.37950.1.1.5.12.6.4.1.5.2
-- 1.3.6.1.4.1.37950.1.1.5.12.6.4.1.5.2
		-- 1.3.6.1.4.1.37950.1.1.5.12.6.4.1.5.2
		sipParamOnuNo OBJECT-TYPE
			SYNTAX Integer32 (1..65535)
			MAX-ACCESS read-write
			STATUS current
			DESCRIPTION
				"Description."
			::= { sipParamCfg 2 }

		
--          1.3.6.1.4.1.37950.1.1.5.12.6.4.1.5.3
-- 1.3.6.1.4.1.37950.1.1.5.12.6.4.1.5.3
-- 1.3.6.1.4.1.37950.1.1.5.12.6.4.1.5.3
-- 1.3.6.1.4.1.37950.1.1.5.12.6.4.1.5.3
-- 1.3.6.1.4.1.37950.1.1.5.12.6.4.1.5.3
-- 1.3.6.1.4.1.37950.1.1.5.12.6.4.1.5.3
-- 1.3.6.1.4.1.37950.1.1.5.12.6.4.1.5.3
-- 1.3.6.1.4.1.37950.1.1.5.12.6.4.1.5.3
-- 1.3.6.1.4.1.37950.1.1.5.12.6.4.1.5.3
		-- 1.3.6.1.4.1.37950.1.1.5.12.6.4.1.5.3
		sipParamMGPortNo OBJECT-TYPE
			SYNTAX Integer32 (0..65535)
			MAX-ACCESS read-write
			STATUS current
			DESCRIPTION
				"Description."
			::= { sipParamCfg 3 }

		
--          1.3.6.1.4.1.37950.1.1.5.12.6.4.1.5.4
-- 1.3.6.1.4.1.37950.1.1.5.12.6.4.1.5.4
-- 1.3.6.1.4.1.37950.1.1.5.12.6.4.1.5.4
-- 1.3.6.1.4.1.37950.1.1.5.12.6.4.1.5.4
-- 1.3.6.1.4.1.37950.1.1.5.12.6.4.1.5.4
-- 1.3.6.1.4.1.37950.1.1.5.12.6.4.1.5.4
-- 1.3.6.1.4.1.37950.1.1.5.12.6.4.1.5.4
-- 1.3.6.1.4.1.37950.1.1.5.12.6.4.1.5.4
-- 1.3.6.1.4.1.37950.1.1.5.12.6.4.1.5.4
		-- 1.3.6.1.4.1.37950.1.1.5.12.6.4.1.5.4
		sipParamSipProxyServIp OBJECT-TYPE
			SYNTAX IpAddress
			MAX-ACCESS read-write
			STATUS current
			DESCRIPTION
				"Description."
			::= { sipParamCfg 4 }

		
--          1.3.6.1.4.1.37950.1.1.5.12.6.4.1.5.5
-- 1.3.6.1.4.1.37950.1.1.5.12.6.4.1.5.5
-- 1.3.6.1.4.1.37950.1.1.5.12.6.4.1.5.5
-- 1.3.6.1.4.1.37950.1.1.5.12.6.4.1.5.5
-- 1.3.6.1.4.1.37950.1.1.5.12.6.4.1.5.5
-- 1.3.6.1.4.1.37950.1.1.5.12.6.4.1.5.5
-- 1.3.6.1.4.1.37950.1.1.5.12.6.4.1.5.5
-- 1.3.6.1.4.1.37950.1.1.5.12.6.4.1.5.5
-- 1.3.6.1.4.1.37950.1.1.5.12.6.4.1.5.5
		-- 1.3.6.1.4.1.37950.1.1.5.12.6.4.1.5.5
		sipParamSipProxyServPortNo OBJECT-TYPE
			SYNTAX Integer32 (0..65535)
			MAX-ACCESS read-write
			STATUS current
			DESCRIPTION
				"Description."
			::= { sipParamCfg 5 }

		
--          1.3.6.1.4.1.37950.1.1.5.12.6.4.1.5.6
-- 1.3.6.1.4.1.37950.1.1.5.12.6.4.1.5.6
-- 1.3.6.1.4.1.37950.1.1.5.12.6.4.1.5.6
-- 1.3.6.1.4.1.37950.1.1.5.12.6.4.1.5.6
-- 1.3.6.1.4.1.37950.1.1.5.12.6.4.1.5.6
-- 1.3.6.1.4.1.37950.1.1.5.12.6.4.1.5.6
-- 1.3.6.1.4.1.37950.1.1.5.12.6.4.1.5.6
-- 1.3.6.1.4.1.37950.1.1.5.12.6.4.1.5.6
-- 1.3.6.1.4.1.37950.1.1.5.12.6.4.1.5.6
		-- 1.3.6.1.4.1.37950.1.1.5.12.6.4.1.5.6
		sipParamBackupSipProxyServIp OBJECT-TYPE
			SYNTAX IpAddress
			MAX-ACCESS read-write
			STATUS current
			DESCRIPTION
				"Description."
			::= { sipParamCfg 6 }

		
--          1.3.6.1.4.1.37950.1.1.5.12.6.4.1.5.7
-- 1.3.6.1.4.1.37950.1.1.5.12.6.4.1.5.7
-- 1.3.6.1.4.1.37950.1.1.5.12.6.4.1.5.7
-- 1.3.6.1.4.1.37950.1.1.5.12.6.4.1.5.7
-- 1.3.6.1.4.1.37950.1.1.5.12.6.4.1.5.7
-- 1.3.6.1.4.1.37950.1.1.5.12.6.4.1.5.7
-- 1.3.6.1.4.1.37950.1.1.5.12.6.4.1.5.7
-- 1.3.6.1.4.1.37950.1.1.5.12.6.4.1.5.7
-- 1.3.6.1.4.1.37950.1.1.5.12.6.4.1.5.7
		-- 1.3.6.1.4.1.37950.1.1.5.12.6.4.1.5.7
		sipParamBackupSipProxyServPortNo OBJECT-TYPE
			SYNTAX Integer32 (0..65535)
			MAX-ACCESS read-write
			STATUS current
			DESCRIPTION
				"Description."
			::= { sipParamCfg 7 }

		
--          1.3.6.1.4.1.37950.1.1.5.12.6.4.1.5.8
-- 1.3.6.1.4.1.37950.1.1.5.12.6.4.1.5.8
-- 1.3.6.1.4.1.37950.1.1.5.12.6.4.1.5.8
-- 1.3.6.1.4.1.37950.1.1.5.12.6.4.1.5.8
-- 1.3.6.1.4.1.37950.1.1.5.12.6.4.1.5.8
-- 1.3.6.1.4.1.37950.1.1.5.12.6.4.1.5.8
-- 1.3.6.1.4.1.37950.1.1.5.12.6.4.1.5.8
-- 1.3.6.1.4.1.37950.1.1.5.12.6.4.1.5.8
-- 1.3.6.1.4.1.37950.1.1.5.12.6.4.1.5.8
		-- 1.3.6.1.4.1.37950.1.1.5.12.6.4.1.5.8
		sipParamSipRegServIp OBJECT-TYPE
			SYNTAX IpAddress
			MAX-ACCESS read-write
			STATUS current
			DESCRIPTION
				"Description."
			::= { sipParamCfg 8 }

		
--          1.3.6.1.4.1.37950.1.1.5.12.6.4.1.5.9
-- 1.3.6.1.4.1.37950.1.1.5.12.6.4.1.5.9
-- 1.3.6.1.4.1.37950.1.1.5.12.6.4.1.5.9
-- 1.3.6.1.4.1.37950.1.1.5.12.6.4.1.5.9
-- 1.3.6.1.4.1.37950.1.1.5.12.6.4.1.5.9
-- 1.3.6.1.4.1.37950.1.1.5.12.6.4.1.5.9
-- 1.3.6.1.4.1.37950.1.1.5.12.6.4.1.5.9
-- 1.3.6.1.4.1.37950.1.1.5.12.6.4.1.5.9
-- 1.3.6.1.4.1.37950.1.1.5.12.6.4.1.5.9
		-- 1.3.6.1.4.1.37950.1.1.5.12.6.4.1.5.9
		sipParamSipRegServPortNo OBJECT-TYPE
			SYNTAX Integer32 (0..65535)
			MAX-ACCESS read-write
			STATUS current
			DESCRIPTION
				"Description."
			::= { sipParamCfg 9 }

		
--          1.3.6.1.4.1.37950.1.1.5.12.6.4.1.5.10
-- 1.3.6.1.4.1.37950.1.1.5.12.6.4.1.5.10
-- 1.3.6.1.4.1.37950.1.1.5.12.6.4.1.5.10
-- 1.3.6.1.4.1.37950.1.1.5.12.6.4.1.5.10
-- 1.3.6.1.4.1.37950.1.1.5.12.6.4.1.5.10
-- 1.3.6.1.4.1.37950.1.1.5.12.6.4.1.5.10
-- 1.3.6.1.4.1.37950.1.1.5.12.6.4.1.5.10
-- 1.3.6.1.4.1.37950.1.1.5.12.6.4.1.5.10
-- 1.3.6.1.4.1.37950.1.1.5.12.6.4.1.5.10
		-- 1.3.6.1.4.1.37950.1.1.5.12.6.4.1.5.10
		sipParamBackupSipRegServIp OBJECT-TYPE
			SYNTAX IpAddress
			MAX-ACCESS read-write
			STATUS current
			DESCRIPTION
				"Description."
			::= { sipParamCfg 10 }

		
--          1.3.6.1.4.1.37950.1.1.5.12.6.4.1.5.11
-- 1.3.6.1.4.1.37950.1.1.5.12.6.4.1.5.11
-- 1.3.6.1.4.1.37950.1.1.5.12.6.4.1.5.11
-- 1.3.6.1.4.1.37950.1.1.5.12.6.4.1.5.11
-- 1.3.6.1.4.1.37950.1.1.5.12.6.4.1.5.11
-- 1.3.6.1.4.1.37950.1.1.5.12.6.4.1.5.11
-- 1.3.6.1.4.1.37950.1.1.5.12.6.4.1.5.11
-- 1.3.6.1.4.1.37950.1.1.5.12.6.4.1.5.11
-- 1.3.6.1.4.1.37950.1.1.5.12.6.4.1.5.11
		-- 1.3.6.1.4.1.37950.1.1.5.12.6.4.1.5.11
		sipParamBackupSipRegServPortNo OBJECT-TYPE
			SYNTAX Integer32 (0..65535)
			MAX-ACCESS read-write
			STATUS current
			DESCRIPTION
				"Description."
			::= { sipParamCfg 11 }

		
--          1.3.6.1.4.1.37950.1.1.5.12.6.4.1.5.12
-- 1.3.6.1.4.1.37950.1.1.5.12.6.4.1.5.12
-- 1.3.6.1.4.1.37950.1.1.5.12.6.4.1.5.12
-- 1.3.6.1.4.1.37950.1.1.5.12.6.4.1.5.12
-- 1.3.6.1.4.1.37950.1.1.5.12.6.4.1.5.12
-- 1.3.6.1.4.1.37950.1.1.5.12.6.4.1.5.12
-- 1.3.6.1.4.1.37950.1.1.5.12.6.4.1.5.12
-- 1.3.6.1.4.1.37950.1.1.5.12.6.4.1.5.12
-- 1.3.6.1.4.1.37950.1.1.5.12.6.4.1.5.12
		-- 1.3.6.1.4.1.37950.1.1.5.12.6.4.1.5.12
		sipParamOutBoundServIp OBJECT-TYPE
			SYNTAX IpAddress
			MAX-ACCESS read-write
			STATUS current
			DESCRIPTION
				"Description."
			::= { sipParamCfg 12 }

		
--          1.3.6.1.4.1.37950.1.1.5.12.6.4.1.5.13
-- 1.3.6.1.4.1.37950.1.1.5.12.6.4.1.5.13
-- 1.3.6.1.4.1.37950.1.1.5.12.6.4.1.5.13
-- 1.3.6.1.4.1.37950.1.1.5.12.6.4.1.5.13
-- 1.3.6.1.4.1.37950.1.1.5.12.6.4.1.5.13
-- 1.3.6.1.4.1.37950.1.1.5.12.6.4.1.5.13
-- 1.3.6.1.4.1.37950.1.1.5.12.6.4.1.5.13
-- 1.3.6.1.4.1.37950.1.1.5.12.6.4.1.5.13
-- 1.3.6.1.4.1.37950.1.1.5.12.6.4.1.5.13
		-- 1.3.6.1.4.1.37950.1.1.5.12.6.4.1.5.13
		sipParamOutBoundServPortNo OBJECT-TYPE
			SYNTAX Integer32 (0..65535)
			MAX-ACCESS read-write
			STATUS current
			DESCRIPTION
				"Description."
			::= { sipParamCfg 13 }

		
--          1.3.6.1.4.1.37950.1.1.5.12.6.4.1.5.14
-- 1.3.6.1.4.1.37950.1.1.5.12.6.4.1.5.14
-- 1.3.6.1.4.1.37950.1.1.5.12.6.4.1.5.14
-- 1.3.6.1.4.1.37950.1.1.5.12.6.4.1.5.14
-- 1.3.6.1.4.1.37950.1.1.5.12.6.4.1.5.14
-- 1.3.6.1.4.1.37950.1.1.5.12.6.4.1.5.14
-- 1.3.6.1.4.1.37950.1.1.5.12.6.4.1.5.14
-- 1.3.6.1.4.1.37950.1.1.5.12.6.4.1.5.14
-- 1.3.6.1.4.1.37950.1.1.5.12.6.4.1.5.14
		-- 1.3.6.1.4.1.37950.1.1.5.12.6.4.1.5.14
		sipParamRegInterval OBJECT-TYPE
			SYNTAX Integer32
			MAX-ACCESS read-write
			STATUS current
			DESCRIPTION
				"Description."
			::= { sipParamCfg 14 }

		
--          1.3.6.1.4.1.37950.1.1.5.12.6.4.1.5.15
-- 1.3.6.1.4.1.37950.1.1.5.12.6.4.1.5.15
-- 1.3.6.1.4.1.37950.1.1.5.12.6.4.1.5.15
-- 1.3.6.1.4.1.37950.1.1.5.12.6.4.1.5.15
-- 1.3.6.1.4.1.37950.1.1.5.12.6.4.1.5.15
-- 1.3.6.1.4.1.37950.1.1.5.12.6.4.1.5.15
-- 1.3.6.1.4.1.37950.1.1.5.12.6.4.1.5.15
-- 1.3.6.1.4.1.37950.1.1.5.12.6.4.1.5.15
-- 1.3.6.1.4.1.37950.1.1.5.12.6.4.1.5.15
		-- 1.3.6.1.4.1.37950.1.1.5.12.6.4.1.5.15
		sipParamHeartbeatEn OBJECT-TYPE
			SYNTAX INTEGER
				{
				enable(0),
				disable(1)
				}
			MAX-ACCESS read-write
			STATUS current
			DESCRIPTION
				"Description."
			::= { sipParamCfg 15 }

		
--          1.3.6.1.4.1.37950.1.1.5.12.6.4.1.5.16
-- 1.3.6.1.4.1.37950.1.1.5.12.6.4.1.5.16
-- 1.3.6.1.4.1.37950.1.1.5.12.6.4.1.5.16
-- 1.3.6.1.4.1.37950.1.1.5.12.6.4.1.5.16
-- 1.3.6.1.4.1.37950.1.1.5.12.6.4.1.5.16
-- 1.3.6.1.4.1.37950.1.1.5.12.6.4.1.5.16
-- 1.3.6.1.4.1.37950.1.1.5.12.6.4.1.5.16
-- 1.3.6.1.4.1.37950.1.1.5.12.6.4.1.5.16
-- 1.3.6.1.4.1.37950.1.1.5.12.6.4.1.5.16
		-- 1.3.6.1.4.1.37950.1.1.5.12.6.4.1.5.16
		sipParamHeartbeatCycle OBJECT-TYPE
			SYNTAX Integer32 (1..65535)
			MAX-ACCESS read-write
			STATUS current
			DESCRIPTION
				"Description."
			::= { sipParamCfg 16 }

		
--          1.3.6.1.4.1.37950.1.1.5.12.6.4.1.5.17
-- 1.3.6.1.4.1.37950.1.1.5.12.6.4.1.5.17
-- 1.3.6.1.4.1.37950.1.1.5.12.6.4.1.5.17
-- 1.3.6.1.4.1.37950.1.1.5.12.6.4.1.5.17
-- 1.3.6.1.4.1.37950.1.1.5.12.6.4.1.5.17
-- 1.3.6.1.4.1.37950.1.1.5.12.6.4.1.5.17
-- 1.3.6.1.4.1.37950.1.1.5.12.6.4.1.5.17
-- 1.3.6.1.4.1.37950.1.1.5.12.6.4.1.5.17
-- 1.3.6.1.4.1.37950.1.1.5.12.6.4.1.5.17
		-- 1.3.6.1.4.1.37950.1.1.5.12.6.4.1.5.17
		sipParamHeartbeatCount OBJECT-TYPE
			SYNTAX Integer32 (1..65535)
			MAX-ACCESS read-write
			STATUS current
			DESCRIPTION
				"Description."
			::= { sipParamCfg 17 }

		
--          1.3.6.1.4.1.37950.1.1.5.12.6.4.1.5.18
-- 1.3.6.1.4.1.37950.1.1.5.12.6.4.1.5.18
-- 1.3.6.1.4.1.37950.1.1.5.12.6.4.1.5.18
-- 1.3.6.1.4.1.37950.1.1.5.12.6.4.1.5.18
-- 1.3.6.1.4.1.37950.1.1.5.12.6.4.1.5.18
-- 1.3.6.1.4.1.37950.1.1.5.12.6.4.1.5.18
-- 1.3.6.1.4.1.37950.1.1.5.12.6.4.1.5.18
-- 1.3.6.1.4.1.37950.1.1.5.12.6.4.1.5.18
-- 1.3.6.1.4.1.37950.1.1.5.12.6.4.1.5.18
		-- 1.3.6.1.4.1.37950.1.1.5.12.6.4.1.5.18
		sipParamAction OBJECT-TYPE
			SYNTAX INTEGER { commit(1) }
			MAX-ACCESS read-write
			STATUS current
			DESCRIPTION
				"Description."
			::= { sipParamCfg 18 }

		
--          1.3.6.1.4.1.37950.1.1.5.12.6.4.2
-- 1.3.6.1.4.1.37950.1.1.5.12.6.4.2
-- 1.3.6.1.4.1.37950.1.1.5.12.6.4.2
-- 1.3.6.1.4.1.37950.1.1.5.12.6.4.2
-- 1.3.6.1.4.1.37950.1.1.5.12.6.4.2
-- 1.3.6.1.4.1.37950.1.1.5.12.6.4.2
-- 1.3.6.1.4.1.37950.1.1.5.12.6.4.2
-- 1.3.6.1.4.1.37950.1.1.5.12.6.4.2
-- 1.3.6.1.4.1.37950.1.1.5.12.6.4.2
		-- 1.3.6.1.4.1.37950.1.1.5.12.6.4.2
		sipUserParam OBJECT IDENTIFIER ::= { voipSipCfg 2 }

		
--          1.3.6.1.4.1.37950.1.1.5.12.6.4.2.1
-- 1.3.6.1.4.1.37950.1.1.5.12.6.4.2.1
-- 1.3.6.1.4.1.37950.1.1.5.12.6.4.2.1
-- 1.3.6.1.4.1.37950.1.1.5.12.6.4.2.1
-- 1.3.6.1.4.1.37950.1.1.5.12.6.4.2.1
-- 1.3.6.1.4.1.37950.1.1.5.12.6.4.2.1
-- 1.3.6.1.4.1.37950.1.1.5.12.6.4.2.1
-- 1.3.6.1.4.1.37950.1.1.5.12.6.4.2.1
-- 1.3.6.1.4.1.37950.1.1.5.12.6.4.2.1
		-- 1.3.6.1.4.1.37950.1.1.5.12.6.4.2.1
		sipUserPonNo OBJECT-TYPE
			SYNTAX INTEGER (1..16)
			MAX-ACCESS read-write
			STATUS current
			DESCRIPTION
				"Description."
			::= { sipUserParam 1 }

		
--          1.3.6.1.4.1.37950.1.1.5.12.6.4.2.2
-- 1.3.6.1.4.1.37950.1.1.5.12.6.4.2.2
-- 1.3.6.1.4.1.37950.1.1.5.12.6.4.2.2
-- 1.3.6.1.4.1.37950.1.1.5.12.6.4.2.2
-- 1.3.6.1.4.1.37950.1.1.5.12.6.4.2.2
-- 1.3.6.1.4.1.37950.1.1.5.12.6.4.2.2
-- 1.3.6.1.4.1.37950.1.1.5.12.6.4.2.2
-- 1.3.6.1.4.1.37950.1.1.5.12.6.4.2.2
-- 1.3.6.1.4.1.37950.1.1.5.12.6.4.2.2
		-- 1.3.6.1.4.1.37950.1.1.5.12.6.4.2.2
		sipUserOnuNo OBJECT-TYPE
			SYNTAX INTEGER (1..65535)
			MAX-ACCESS read-write
			STATUS current
			DESCRIPTION
				"Description."
			::= { sipUserParam 2 }

		
--          1.3.6.1.4.1.37950.1.1.5.12.6.4.2.3
-- 1.3.6.1.4.1.37950.1.1.5.12.6.4.2.3
-- 1.3.6.1.4.1.37950.1.1.5.12.6.4.2.3
-- 1.3.6.1.4.1.37950.1.1.5.12.6.4.2.3
-- 1.3.6.1.4.1.37950.1.1.5.12.6.4.2.3
-- 1.3.6.1.4.1.37950.1.1.5.12.6.4.2.3
-- 1.3.6.1.4.1.37950.1.1.5.12.6.4.2.3
-- 1.3.6.1.4.1.37950.1.1.5.12.6.4.2.3
-- 1.3.6.1.4.1.37950.1.1.5.12.6.4.2.3
		-- 1.3.6.1.4.1.37950.1.1.5.12.6.4.2.3
		sipUserPotsNo OBJECT-TYPE
			SYNTAX INTEGER (1..255)
			MAX-ACCESS read-write
			STATUS current
			DESCRIPTION
				"Description."
			::= { sipUserParam 3 }

		
--          1.3.6.1.4.1.37950.1.1.5.12.6.4.2.4
-- 1.3.6.1.4.1.37950.1.1.5.12.6.4.2.4
-- 1.3.6.1.4.1.37950.1.1.5.12.6.4.2.4
-- 1.3.6.1.4.1.37950.1.1.5.12.6.4.2.4
-- 1.3.6.1.4.1.37950.1.1.5.12.6.4.2.4
-- 1.3.6.1.4.1.37950.1.1.5.12.6.4.2.4
-- 1.3.6.1.4.1.37950.1.1.5.12.6.4.2.4
-- 1.3.6.1.4.1.37950.1.1.5.12.6.4.2.4
-- 1.3.6.1.4.1.37950.1.1.5.12.6.4.2.4
		-- 1.3.6.1.4.1.37950.1.1.5.12.6.4.2.4
		sipUserAccount OBJECT-TYPE
			SYNTAX OCTET STRING
			MAX-ACCESS read-write
			STATUS current
			DESCRIPTION
				"Description."
			::= { sipUserParam 4 }

		
--          1.3.6.1.4.1.37950.1.1.5.12.6.4.2.5
-- 1.3.6.1.4.1.37950.1.1.5.12.6.4.2.5
-- 1.3.6.1.4.1.37950.1.1.5.12.6.4.2.5
-- 1.3.6.1.4.1.37950.1.1.5.12.6.4.2.5
-- 1.3.6.1.4.1.37950.1.1.5.12.6.4.2.5
-- 1.3.6.1.4.1.37950.1.1.5.12.6.4.2.5
-- 1.3.6.1.4.1.37950.1.1.5.12.6.4.2.5
-- 1.3.6.1.4.1.37950.1.1.5.12.6.4.2.5
-- 1.3.6.1.4.1.37950.1.1.5.12.6.4.2.5
		-- 1.3.6.1.4.1.37950.1.1.5.12.6.4.2.5
		sipUserName OBJECT-TYPE
			SYNTAX OCTET STRING
			MAX-ACCESS read-write
			STATUS current
			DESCRIPTION
				"Description."
			::= { sipUserParam 5 }

		
--          1.3.6.1.4.1.37950.1.1.5.12.6.4.2.6
-- 1.3.6.1.4.1.37950.1.1.5.12.6.4.2.6
-- 1.3.6.1.4.1.37950.1.1.5.12.6.4.2.6
-- 1.3.6.1.4.1.37950.1.1.5.12.6.4.2.6
-- 1.3.6.1.4.1.37950.1.1.5.12.6.4.2.6
-- 1.3.6.1.4.1.37950.1.1.5.12.6.4.2.6
-- 1.3.6.1.4.1.37950.1.1.5.12.6.4.2.6
-- 1.3.6.1.4.1.37950.1.1.5.12.6.4.2.6
-- 1.3.6.1.4.1.37950.1.1.5.12.6.4.2.6
		-- 1.3.6.1.4.1.37950.1.1.5.12.6.4.2.6
		sipUserPw OBJECT-TYPE
			SYNTAX OCTET STRING
			MAX-ACCESS read-write
			STATUS current
			DESCRIPTION
				"Description."
			::= { sipUserParam 6 }

		
--          1.3.6.1.4.1.37950.1.1.5.12.6.4.2.7
-- 1.3.6.1.4.1.37950.1.1.5.12.6.4.2.7
-- 1.3.6.1.4.1.37950.1.1.5.12.6.4.2.7
-- 1.3.6.1.4.1.37950.1.1.5.12.6.4.2.7
-- 1.3.6.1.4.1.37950.1.1.5.12.6.4.2.7
-- 1.3.6.1.4.1.37950.1.1.5.12.6.4.2.7
-- 1.3.6.1.4.1.37950.1.1.5.12.6.4.2.7
-- 1.3.6.1.4.1.37950.1.1.5.12.6.4.2.7
-- 1.3.6.1.4.1.37950.1.1.5.12.6.4.2.7
		-- 1.3.6.1.4.1.37950.1.1.5.12.6.4.2.7
		sipUserAction OBJECT-TYPE
			SYNTAX INTEGER { commit(1) }
			MAX-ACCESS read-write
			STATUS current
			DESCRIPTION
				"Description."
			::= { sipUserParam 7 }

		
--          1.3.6.1.4.1.37950.1.1.5.12.6.4.3
-- 1.3.6.1.4.1.37950.1.1.5.12.6.4.3
-- 1.3.6.1.4.1.37950.1.1.5.12.6.4.3
-- 1.3.6.1.4.1.37950.1.1.5.12.6.4.3
-- 1.3.6.1.4.1.37950.1.1.5.12.6.4.3
-- 1.3.6.1.4.1.37950.1.1.5.12.6.4.3
-- 1.3.6.1.4.1.37950.1.1.5.12.6.4.3
-- 1.3.6.1.4.1.37950.1.1.5.12.6.4.3
-- 1.3.6.1.4.1.37950.1.1.5.12.6.4.3
		-- 1.3.6.1.4.1.37950.1.1.5.12.6.4.3
		faxModemCfg OBJECT IDENTIFIER ::= { voipSipCfg 3 }

		
--          1.3.6.1.4.1.37950.1.1.5.12.6.4.3.1
-- 1.3.6.1.4.1.37950.1.1.5.12.6.4.3.1
-- 1.3.6.1.4.1.37950.1.1.5.12.6.4.3.1
-- 1.3.6.1.4.1.37950.1.1.5.12.6.4.3.1
-- 1.3.6.1.4.1.37950.1.1.5.12.6.4.3.1
-- 1.3.6.1.4.1.37950.1.1.5.12.6.4.3.1
-- 1.3.6.1.4.1.37950.1.1.5.12.6.4.3.1
-- 1.3.6.1.4.1.37950.1.1.5.12.6.4.3.1
-- 1.3.6.1.4.1.37950.1.1.5.12.6.4.3.1
		-- 1.3.6.1.4.1.37950.1.1.5.12.6.4.3.1
		faxPonNo OBJECT-TYPE
			SYNTAX INTEGER (1..16)
			MAX-ACCESS read-write
			STATUS current
			DESCRIPTION
				"Description."
			::= { faxModemCfg 1 }

		
--          1.3.6.1.4.1.37950.1.1.5.12.6.4.3.2
-- 1.3.6.1.4.1.37950.1.1.5.12.6.4.3.2
-- 1.3.6.1.4.1.37950.1.1.5.12.6.4.3.2
-- 1.3.6.1.4.1.37950.1.1.5.12.6.4.3.2
-- 1.3.6.1.4.1.37950.1.1.5.12.6.4.3.2
-- 1.3.6.1.4.1.37950.1.1.5.12.6.4.3.2
-- 1.3.6.1.4.1.37950.1.1.5.12.6.4.3.2
-- 1.3.6.1.4.1.37950.1.1.5.12.6.4.3.2
-- 1.3.6.1.4.1.37950.1.1.5.12.6.4.3.2
		-- 1.3.6.1.4.1.37950.1.1.5.12.6.4.3.2
		faxOnuNo OBJECT-TYPE
			SYNTAX INTEGER (1..65535)
			MAX-ACCESS read-write
			STATUS current
			DESCRIPTION
				"Description."
			::= { faxModemCfg 2 }

		
--          1.3.6.1.4.1.37950.1.1.5.12.6.4.3.3
-- 1.3.6.1.4.1.37950.1.1.5.12.6.4.3.3
-- 1.3.6.1.4.1.37950.1.1.5.12.6.4.3.3
-- 1.3.6.1.4.1.37950.1.1.5.12.6.4.3.3
-- 1.3.6.1.4.1.37950.1.1.5.12.6.4.3.3
-- 1.3.6.1.4.1.37950.1.1.5.12.6.4.3.3
-- 1.3.6.1.4.1.37950.1.1.5.12.6.4.3.3
-- 1.3.6.1.4.1.37950.1.1.5.12.6.4.3.3
-- 1.3.6.1.4.1.37950.1.1.5.12.6.4.3.3
		-- 1.3.6.1.4.1.37950.1.1.5.12.6.4.3.3
		t38En OBJECT-TYPE
			SYNTAX INTEGER
				{
				disable(0),
				enable(1)
				}
			MAX-ACCESS read-write
			STATUS current
			DESCRIPTION
				"Description."
			::= { faxModemCfg 3 }

		
--          1.3.6.1.4.1.37950.1.1.5.12.6.4.3.4
-- 1.3.6.1.4.1.37950.1.1.5.12.6.4.3.4
-- 1.3.6.1.4.1.37950.1.1.5.12.6.4.3.4
-- 1.3.6.1.4.1.37950.1.1.5.12.6.4.3.4
-- 1.3.6.1.4.1.37950.1.1.5.12.6.4.3.4
-- 1.3.6.1.4.1.37950.1.1.5.12.6.4.3.4
-- 1.3.6.1.4.1.37950.1.1.5.12.6.4.3.4
-- 1.3.6.1.4.1.37950.1.1.5.12.6.4.3.4
-- 1.3.6.1.4.1.37950.1.1.5.12.6.4.3.4
		-- 1.3.6.1.4.1.37950.1.1.5.12.6.4.3.4
		control OBJECT-TYPE
			SYNTAX INTEGER
				{
				negotiation(1),
				autovbd(2)
				}
			MAX-ACCESS read-write
			STATUS current
			DESCRIPTION
				"Description."
			::= { faxModemCfg 4 }

		
--          1.3.6.1.4.1.37950.1.1.5.12.6.4.3.5
-- 1.3.6.1.4.1.37950.1.1.5.12.6.4.3.5
-- 1.3.6.1.4.1.37950.1.1.5.12.6.4.3.5
-- 1.3.6.1.4.1.37950.1.1.5.12.6.4.3.5
-- 1.3.6.1.4.1.37950.1.1.5.12.6.4.3.5
-- 1.3.6.1.4.1.37950.1.1.5.12.6.4.3.5
-- 1.3.6.1.4.1.37950.1.1.5.12.6.4.3.5
-- 1.3.6.1.4.1.37950.1.1.5.12.6.4.3.5
-- 1.3.6.1.4.1.37950.1.1.5.12.6.4.3.5
		-- 1.3.6.1.4.1.37950.1.1.5.12.6.4.3.5
		faxModemAction OBJECT-TYPE
			SYNTAX INTEGER { commit(1) }
			MAX-ACCESS read-write
			STATUS current
			DESCRIPTION
				"Description."
			::= { faxModemCfg 5 }

		
--          1.3.6.1.4.1.37950.1.1.5.12.6.4.4
-- 1.3.6.1.4.1.37950.1.1.5.12.6.4.4
-- 1.3.6.1.4.1.37950.1.1.5.12.6.4.4
-- 1.3.6.1.4.1.37950.1.1.5.12.6.4.4
-- 1.3.6.1.4.1.37950.1.1.5.12.6.4.4
-- 1.3.6.1.4.1.37950.1.1.5.12.6.4.4
-- 1.3.6.1.4.1.37950.1.1.5.12.6.4.4
-- 1.3.6.1.4.1.37950.1.1.5.12.6.4.4
-- 1.3.6.1.4.1.37950.1.1.5.12.6.4.4
		-- 1.3.6.1.4.1.37950.1.1.5.12.6.4.4
		iadOperCfg OBJECT IDENTIFIER ::= { voipSipCfg 4 }

		
--          1.3.6.1.4.1.37950.1.1.5.12.6.4.4.1
-- 1.3.6.1.4.1.37950.1.1.5.12.6.4.4.1
-- 1.3.6.1.4.1.37950.1.1.5.12.6.4.4.1
-- 1.3.6.1.4.1.37950.1.1.5.12.6.4.4.1
-- 1.3.6.1.4.1.37950.1.1.5.12.6.4.4.1
-- 1.3.6.1.4.1.37950.1.1.5.12.6.4.4.1
-- 1.3.6.1.4.1.37950.1.1.5.12.6.4.4.1
-- 1.3.6.1.4.1.37950.1.1.5.12.6.4.4.1
-- 1.3.6.1.4.1.37950.1.1.5.12.6.4.4.1
		-- 1.3.6.1.4.1.37950.1.1.5.12.6.4.4.1
		iadOperPonNo OBJECT-TYPE
			SYNTAX INTEGER (1..16)
			MAX-ACCESS read-write
			STATUS current
			DESCRIPTION
				"Description."
			::= { iadOperCfg 1 }

		
--          1.3.6.1.4.1.37950.1.1.5.12.6.4.4.2
-- 1.3.6.1.4.1.37950.1.1.5.12.6.4.4.2
-- 1.3.6.1.4.1.37950.1.1.5.12.6.4.4.2
-- 1.3.6.1.4.1.37950.1.1.5.12.6.4.4.2
-- 1.3.6.1.4.1.37950.1.1.5.12.6.4.4.2
-- 1.3.6.1.4.1.37950.1.1.5.12.6.4.4.2
-- 1.3.6.1.4.1.37950.1.1.5.12.6.4.4.2
-- 1.3.6.1.4.1.37950.1.1.5.12.6.4.4.2
-- 1.3.6.1.4.1.37950.1.1.5.12.6.4.4.2
		-- 1.3.6.1.4.1.37950.1.1.5.12.6.4.4.2
		iadOperOnuNo OBJECT-TYPE
			SYNTAX INTEGER (1..65535)
			MAX-ACCESS read-write
			STATUS current
			DESCRIPTION
				"Description."
			::= { iadOperCfg 2 }

		
--          1.3.6.1.4.1.37950.1.1.5.12.6.4.4.3
-- 1.3.6.1.4.1.37950.1.1.5.12.6.4.4.3
-- 1.3.6.1.4.1.37950.1.1.5.12.6.4.4.3
-- 1.3.6.1.4.1.37950.1.1.5.12.6.4.4.3
-- 1.3.6.1.4.1.37950.1.1.5.12.6.4.4.3
-- 1.3.6.1.4.1.37950.1.1.5.12.6.4.4.3
-- 1.3.6.1.4.1.37950.1.1.5.12.6.4.4.3
-- 1.3.6.1.4.1.37950.1.1.5.12.6.4.4.3
-- 1.3.6.1.4.1.37950.1.1.5.12.6.4.4.3
		-- 1.3.6.1.4.1.37950.1.1.5.12.6.4.4.3
		iadOperation OBJECT-TYPE
			SYNTAX INTEGER
				{
				reregister(1),
				deregister(2),
				reset(3)
				}
			MAX-ACCESS read-write
			STATUS current
			DESCRIPTION
				"Description."
			::= { iadOperCfg 3 }

		
--          1.3.6.1.4.1.37950.1.1.5.12.6.4.4.4
-- 1.3.6.1.4.1.37950.1.1.5.12.6.4.4.4
-- 1.3.6.1.4.1.37950.1.1.5.12.6.4.4.4
-- 1.3.6.1.4.1.37950.1.1.5.12.6.4.4.4
-- 1.3.6.1.4.1.37950.1.1.5.12.6.4.4.4
-- 1.3.6.1.4.1.37950.1.1.5.12.6.4.4.4
-- 1.3.6.1.4.1.37950.1.1.5.12.6.4.4.4
-- 1.3.6.1.4.1.37950.1.1.5.12.6.4.4.4
-- 1.3.6.1.4.1.37950.1.1.5.12.6.4.4.4
		-- 1.3.6.1.4.1.37950.1.1.5.12.6.4.4.4
		iadOperAction OBJECT-TYPE
			SYNTAX INTEGER { commit(1) }
			MAX-ACCESS read-write
			STATUS current
			DESCRIPTION
				"Description."
			::= { iadOperCfg 4 }

		
--          1.3.6.1.4.1.37950.1.1.5.12.6.4.5
-- 1.3.6.1.4.1.37950.1.1.5.12.6.4.5
-- 1.3.6.1.4.1.37950.1.1.5.12.6.4.5
-- 1.3.6.1.4.1.37950.1.1.5.12.6.4.5
-- 1.3.6.1.4.1.37950.1.1.5.12.6.4.5
-- 1.3.6.1.4.1.37950.1.1.5.12.6.4.5
-- 1.3.6.1.4.1.37950.1.1.5.12.6.4.5
-- 1.3.6.1.4.1.37950.1.1.5.12.6.4.5
-- 1.3.6.1.4.1.37950.1.1.5.12.6.4.5
		-- 1.3.6.1.4.1.37950.1.1.5.12.6.4.5
		sipDigitCfg OBJECT IDENTIFIER ::= { voipSipCfg 5 }

		
--          1.3.6.1.4.1.37950.1.1.5.12.6.4.5.1
-- 1.3.6.1.4.1.37950.1.1.5.12.6.4.5.1
-- 1.3.6.1.4.1.37950.1.1.5.12.6.4.5.1
-- 1.3.6.1.4.1.37950.1.1.5.12.6.4.5.1
-- 1.3.6.1.4.1.37950.1.1.5.12.6.4.5.1
-- 1.3.6.1.4.1.37950.1.1.5.12.6.4.5.1
-- 1.3.6.1.4.1.37950.1.1.5.12.6.4.5.1
-- 1.3.6.1.4.1.37950.1.1.5.12.6.4.5.1
-- 1.3.6.1.4.1.37950.1.1.5.12.6.4.5.1
		-- 1.3.6.1.4.1.37950.1.1.5.12.6.4.5.1
		digitPonNo OBJECT-TYPE
			SYNTAX INTEGER (1..16)
			MAX-ACCESS read-write
			STATUS current
			DESCRIPTION
				"Description."
			::= { sipDigitCfg 1 }

		
--          1.3.6.1.4.1.37950.1.1.5.12.6.4.5.2
-- 1.3.6.1.4.1.37950.1.1.5.12.6.4.5.2
-- 1.3.6.1.4.1.37950.1.1.5.12.6.4.5.2
-- 1.3.6.1.4.1.37950.1.1.5.12.6.4.5.2
-- 1.3.6.1.4.1.37950.1.1.5.12.6.4.5.2
-- 1.3.6.1.4.1.37950.1.1.5.12.6.4.5.2
-- 1.3.6.1.4.1.37950.1.1.5.12.6.4.5.2
-- 1.3.6.1.4.1.37950.1.1.5.12.6.4.5.2
-- 1.3.6.1.4.1.37950.1.1.5.12.6.4.5.2
		-- 1.3.6.1.4.1.37950.1.1.5.12.6.4.5.2
		digitOnuNo OBJECT-TYPE
			SYNTAX INTEGER (1..65535)
			MAX-ACCESS read-write
			STATUS current
			DESCRIPTION
				"Description."
			::= { sipDigitCfg 2 }

		
--          1.3.6.1.4.1.37950.1.1.5.12.6.4.5.3
-- 1.3.6.1.4.1.37950.1.1.5.12.6.4.5.3
-- 1.3.6.1.4.1.37950.1.1.5.12.6.4.5.3
-- 1.3.6.1.4.1.37950.1.1.5.12.6.4.5.3
-- 1.3.6.1.4.1.37950.1.1.5.12.6.4.5.3
-- 1.3.6.1.4.1.37950.1.1.5.12.6.4.5.3
-- 1.3.6.1.4.1.37950.1.1.5.12.6.4.5.3
-- 1.3.6.1.4.1.37950.1.1.5.12.6.4.5.3
-- 1.3.6.1.4.1.37950.1.1.5.12.6.4.5.3
		-- 1.3.6.1.4.1.37950.1.1.5.12.6.4.5.3
		digBlockNum OBJECT-TYPE
			SYNTAX Integer32 (1..255)
			MAX-ACCESS read-write
			STATUS current
			DESCRIPTION
				"Description."
			::= { sipDigitCfg 3 }

		
--          1.3.6.1.4.1.37950.1.1.5.12.6.4.5.4
-- 1.3.6.1.4.1.37950.1.1.5.12.6.4.5.4
-- 1.3.6.1.4.1.37950.1.1.5.12.6.4.5.4
-- 1.3.6.1.4.1.37950.1.1.5.12.6.4.5.4
-- 1.3.6.1.4.1.37950.1.1.5.12.6.4.5.4
-- 1.3.6.1.4.1.37950.1.1.5.12.6.4.5.4
-- 1.3.6.1.4.1.37950.1.1.5.12.6.4.5.4
-- 1.3.6.1.4.1.37950.1.1.5.12.6.4.5.4
-- 1.3.6.1.4.1.37950.1.1.5.12.6.4.5.4
		-- 1.3.6.1.4.1.37950.1.1.5.12.6.4.5.4
		digMapId OBJECT-TYPE
			SYNTAX INTEGER (1..255)
			MAX-ACCESS read-write
			STATUS current
			DESCRIPTION
				"Description."
			::= { sipDigitCfg 4 }

		
--          1.3.6.1.4.1.37950.1.1.5.12.6.4.5.5
-- 1.3.6.1.4.1.37950.1.1.5.12.6.4.5.5
-- 1.3.6.1.4.1.37950.1.1.5.12.6.4.5.5
-- 1.3.6.1.4.1.37950.1.1.5.12.6.4.5.5
-- 1.3.6.1.4.1.37950.1.1.5.12.6.4.5.5
-- 1.3.6.1.4.1.37950.1.1.5.12.6.4.5.5
-- 1.3.6.1.4.1.37950.1.1.5.12.6.4.5.5
-- 1.3.6.1.4.1.37950.1.1.5.12.6.4.5.5
-- 1.3.6.1.4.1.37950.1.1.5.12.6.4.5.5
		-- 1.3.6.1.4.1.37950.1.1.5.12.6.4.5.5
		digitMap OBJECT-TYPE
			SYNTAX OCTET STRING
			MAX-ACCESS read-write
			STATUS current
			DESCRIPTION
				"Description."
			::= { sipDigitCfg 5 }

		
--          1.3.6.1.4.1.37950.1.1.5.12.6.4.5.6
-- 1.3.6.1.4.1.37950.1.1.5.12.6.4.5.6
-- 1.3.6.1.4.1.37950.1.1.5.12.6.4.5.6
-- 1.3.6.1.4.1.37950.1.1.5.12.6.4.5.6
-- 1.3.6.1.4.1.37950.1.1.5.12.6.4.5.6
-- 1.3.6.1.4.1.37950.1.1.5.12.6.4.5.6
-- 1.3.6.1.4.1.37950.1.1.5.12.6.4.5.6
-- 1.3.6.1.4.1.37950.1.1.5.12.6.4.5.6
-- 1.3.6.1.4.1.37950.1.1.5.12.6.4.5.6
		-- 1.3.6.1.4.1.37950.1.1.5.12.6.4.5.6
		sipDigitAction OBJECT-TYPE
			SYNTAX INTEGER { commit(1) }
			MAX-ACCESS read-write
			STATUS current
			DESCRIPTION
				"Description."
			::= { sipDigitCfg 6 }

		
--          1.3.6.1.4.1.37950.1.1.5.12.7
-- 1.3.6.1.4.1.37950.1.1.5.12.7
-- 1.3.6.1.4.1.37950.1.1.5.12.7
-- 1.3.6.1.4.1.37950.1.1.5.12.7
-- 1.3.6.1.4.1.37950.1.1.5.12.7
-- 1.3.6.1.4.1.37950.1.1.5.12.7
-- 1.3.6.1.4.1.37950.1.1.5.12.7
-- 1.3.6.1.4.1.37950.1.1.5.12.7
-- 1.3.6.1.4.1.37950.1.1.5.12.7
		-- 1.3.6.1.4.1.37950.1.1.5.12.7
		onuAlarmShow OBJECT IDENTIFIER ::= { v1600dOnuMgmt 7 }

		
--          1.3.6.1.4.1.37950.1.1.5.12.7.1
-- 1.3.6.1.4.1.37950.1.1.5.12.7.1
-- 1.3.6.1.4.1.37950.1.1.5.12.7.1
-- 1.3.6.1.4.1.37950.1.1.5.12.7.1
-- 1.3.6.1.4.1.37950.1.1.5.12.7.1
-- 1.3.6.1.4.1.37950.1.1.5.12.7.1
-- 1.3.6.1.4.1.37950.1.1.5.12.7.1
-- 1.3.6.1.4.1.37950.1.1.5.12.7.1
-- 1.3.6.1.4.1.37950.1.1.5.12.7.1
		-- 1.3.6.1.4.1.37950.1.1.5.12.7.1
		onuAlarmPonTable OBJECT-TYPE
			SYNTAX SEQUENCE OF OnuAlarmPonEntry
			MAX-ACCESS not-accessible
			STATUS current
			DESCRIPTION
				"Description."
			::= { onuAlarmShow 1 }

		
--          1.3.6.1.4.1.37950.1.1.5.12.7.1.1
-- 1.3.6.1.4.1.37950.1.1.5.12.7.1.1
-- 1.3.6.1.4.1.37950.1.1.5.12.7.1.1
-- 1.3.6.1.4.1.37950.1.1.5.12.7.1.1
-- 1.3.6.1.4.1.37950.1.1.5.12.7.1.1
-- 1.3.6.1.4.1.37950.1.1.5.12.7.1.1
-- 1.3.6.1.4.1.37950.1.1.5.12.7.1.1
-- 1.3.6.1.4.1.37950.1.1.5.12.7.1.1
-- 1.3.6.1.4.1.37950.1.1.5.12.7.1.1
		-- 1.3.6.1.4.1.37950.1.1.5.12.7.1.1
		onuAlarmPonEntry OBJECT-TYPE
			SYNTAX OnuAlarmPonEntry
			MAX-ACCESS not-accessible
			STATUS current
			DESCRIPTION
				"Description."
			INDEX { onuAlarmPonIndex, onuAlarmPonOnuIndex, onuAlarmPonType }
			::= { onuAlarmPonTable 1 }

		
		OnuAlarmPonEntry ::=
			SEQUENCE { 
				onuAlarmPonIndex
					Integer32,
				onuAlarmPonOnuIndex
					Integer32,
				onuAlarmPonType
					INTEGER,
				onuAlarmPonEnable
					INTEGER,
				onuAlarmPonAlarmThr
					OCTET STRING,
				onuAlarmPonClearThr
					OCTET STRING
			 }

--          1.3.6.1.4.1.37950.1.1.5.12.7.1.1.1
-- 1.3.6.1.4.1.37950.1.1.5.12.7.1.1.1
-- 1.3.6.1.4.1.37950.1.1.5.12.7.1.1.1
-- 1.3.6.1.4.1.37950.1.1.5.12.7.1.1.1
-- 1.3.6.1.4.1.37950.1.1.5.12.7.1.1.1
-- 1.3.6.1.4.1.37950.1.1.5.12.7.1.1.1
-- 1.3.6.1.4.1.37950.1.1.5.12.7.1.1.1
-- 1.3.6.1.4.1.37950.1.1.5.12.7.1.1.1
-- 1.3.6.1.4.1.37950.1.1.5.12.7.1.1.1
		-- 1.3.6.1.4.1.37950.1.1.5.12.7.1.1.1
		onuAlarmPonIndex OBJECT-TYPE
			SYNTAX Integer32
			MAX-ACCESS read-only
			STATUS current
			DESCRIPTION
				"Description."
			::= { onuAlarmPonEntry 1 }

		
--          1.3.6.1.4.1.37950.1.1.5.12.7.1.1.2
-- 1.3.6.1.4.1.37950.1.1.5.12.7.1.1.2
-- 1.3.6.1.4.1.37950.1.1.5.12.7.1.1.2
-- 1.3.6.1.4.1.37950.1.1.5.12.7.1.1.2
-- 1.3.6.1.4.1.37950.1.1.5.12.7.1.1.2
-- 1.3.6.1.4.1.37950.1.1.5.12.7.1.1.2
-- 1.3.6.1.4.1.37950.1.1.5.12.7.1.1.2
-- 1.3.6.1.4.1.37950.1.1.5.12.7.1.1.2
-- 1.3.6.1.4.1.37950.1.1.5.12.7.1.1.2
		-- 1.3.6.1.4.1.37950.1.1.5.12.7.1.1.2
		onuAlarmPonOnuIndex OBJECT-TYPE
			SYNTAX Integer32
			MAX-ACCESS read-only
			STATUS current
			DESCRIPTION
				"Description."
			::= { onuAlarmPonEntry 2 }

		
--          1.3.6.1.4.1.37950.1.1.5.12.7.1.1.3
-- 1.3.6.1.4.1.37950.1.1.5.12.7.1.1.3
-- 1.3.6.1.4.1.37950.1.1.5.12.7.1.1.3
-- 1.3.6.1.4.1.37950.1.1.5.12.7.1.1.3
-- 1.3.6.1.4.1.37950.1.1.5.12.7.1.1.3
-- 1.3.6.1.4.1.37950.1.1.5.12.7.1.1.3
-- 1.3.6.1.4.1.37950.1.1.5.12.7.1.1.3
-- 1.3.6.1.4.1.37950.1.1.5.12.7.1.1.3
-- 1.3.6.1.4.1.37950.1.1.5.12.7.1.1.3
		-- 1.3.6.1.4.1.37950.1.1.5.12.7.1.1.3
		onuAlarmPonType OBJECT-TYPE
			SYNTAX INTEGER
				{
				rxPowerHighAlarm(1),
				rxPowerLowAlarm(2),
				txPowerHighAlarm(3),
				txPowerLowAlarm(4),
				txBiasHighAlarm(5),
				txBiasLowAlarm(6),
				vccHighAlarm(7),
				vccLowAlarm(8),
				tempHighAlarm(9),
				tempLowAlarm(10),
				rxPowerHighWarn(11),
				rxPowerLowWarn(12),
				txPowerHighWarn(13),
				txPowerLowWarn(14),
				txBiasHighWarn(15),
				txBiasLowWarn(16),
				vccHighWarn(17),
				vccLowWarn(18),
				tempHighWarn(19),
				tempLowWarn(20)
				}
			MAX-ACCESS read-only
			STATUS current
			DESCRIPTION
				"Description."
			::= { onuAlarmPonEntry 3 }

		
--          1.3.6.1.4.1.37950.1.1.5.12.7.1.1.4
-- 1.3.6.1.4.1.37950.1.1.5.12.7.1.1.4
-- 1.3.6.1.4.1.37950.1.1.5.12.7.1.1.4
-- 1.3.6.1.4.1.37950.1.1.5.12.7.1.1.4
-- 1.3.6.1.4.1.37950.1.1.5.12.7.1.1.4
-- 1.3.6.1.4.1.37950.1.1.5.12.7.1.1.4
-- 1.3.6.1.4.1.37950.1.1.5.12.7.1.1.4
-- 1.3.6.1.4.1.37950.1.1.5.12.7.1.1.4
-- 1.3.6.1.4.1.37950.1.1.5.12.7.1.1.4
		-- 1.3.6.1.4.1.37950.1.1.5.12.7.1.1.4
		onuAlarmPonEnable OBJECT-TYPE
			SYNTAX INTEGER
				{
				disable(0),
				enable(1)
				}
			MAX-ACCESS read-only
			STATUS current
			DESCRIPTION
				"Description."
			::= { onuAlarmPonEntry 4 }

		
--          1.3.6.1.4.1.37950.1.1.5.12.7.1.1.5
-- 1.3.6.1.4.1.37950.1.1.5.12.7.1.1.5
-- 1.3.6.1.4.1.37950.1.1.5.12.7.1.1.5
-- 1.3.6.1.4.1.37950.1.1.5.12.7.1.1.5
-- 1.3.6.1.4.1.37950.1.1.5.12.7.1.1.5
-- 1.3.6.1.4.1.37950.1.1.5.12.7.1.1.5
-- 1.3.6.1.4.1.37950.1.1.5.12.7.1.1.5
-- 1.3.6.1.4.1.37950.1.1.5.12.7.1.1.5
-- 1.3.6.1.4.1.37950.1.1.5.12.7.1.1.5
		-- 1.3.6.1.4.1.37950.1.1.5.12.7.1.1.5
		onuAlarmPonAlarmThr OBJECT-TYPE
			SYNTAX OCTET STRING
			MAX-ACCESS read-only
			STATUS current
			DESCRIPTION
				"Description."
			::= { onuAlarmPonEntry 5 }

		
--          1.3.6.1.4.1.37950.1.1.5.12.7.1.1.6
-- 1.3.6.1.4.1.37950.1.1.5.12.7.1.1.6
-- 1.3.6.1.4.1.37950.1.1.5.12.7.1.1.6
-- 1.3.6.1.4.1.37950.1.1.5.12.7.1.1.6
-- 1.3.6.1.4.1.37950.1.1.5.12.7.1.1.6
-- 1.3.6.1.4.1.37950.1.1.5.12.7.1.1.6
-- 1.3.6.1.4.1.37950.1.1.5.12.7.1.1.6
-- 1.3.6.1.4.1.37950.1.1.5.12.7.1.1.6
-- 1.3.6.1.4.1.37950.1.1.5.12.7.1.1.6
		-- 1.3.6.1.4.1.37950.1.1.5.12.7.1.1.6
		onuAlarmPonClearThr OBJECT-TYPE
			SYNTAX OCTET STRING
			MAX-ACCESS read-only
			STATUS current
			DESCRIPTION
				"Description."
			::= { onuAlarmPonEntry 6 }

		
--          1.3.6.1.4.1.37950.1.1.5.12.7.2
-- 1.3.6.1.4.1.37950.1.1.5.12.7.2
-- 1.3.6.1.4.1.37950.1.1.5.12.7.2
-- 1.3.6.1.4.1.37950.1.1.5.12.7.2
-- 1.3.6.1.4.1.37950.1.1.5.12.7.2
-- 1.3.6.1.4.1.37950.1.1.5.12.7.2
-- 1.3.6.1.4.1.37950.1.1.5.12.7.2
-- 1.3.6.1.4.1.37950.1.1.5.12.7.2
-- 1.3.6.1.4.1.37950.1.1.5.12.7.2
		-- 1.3.6.1.4.1.37950.1.1.5.12.7.2
		onuAlarmPortTable OBJECT-TYPE
			SYNTAX SEQUENCE OF OnuAlarmPortEntry
			MAX-ACCESS not-accessible
			STATUS current
			DESCRIPTION
				"Description."
			::= { onuAlarmShow 2 }

		
--          1.3.6.1.4.1.37950.1.1.5.12.7.2.1
-- 1.3.6.1.4.1.37950.1.1.5.12.7.2.1
-- 1.3.6.1.4.1.37950.1.1.5.12.7.2.1
-- 1.3.6.1.4.1.37950.1.1.5.12.7.2.1
-- 1.3.6.1.4.1.37950.1.1.5.12.7.2.1
-- 1.3.6.1.4.1.37950.1.1.5.12.7.2.1
-- 1.3.6.1.4.1.37950.1.1.5.12.7.2.1
-- 1.3.6.1.4.1.37950.1.1.5.12.7.2.1
-- 1.3.6.1.4.1.37950.1.1.5.12.7.2.1
		-- 1.3.6.1.4.1.37950.1.1.5.12.7.2.1
		onuAlarmPortEntry OBJECT-TYPE
			SYNTAX OnuAlarmPortEntry
			MAX-ACCESS not-accessible
			STATUS current
			DESCRIPTION
				"Description."
			INDEX { onuAlarmPortPon, onuAlarmPortOnu, onuAlarmPortPort }
			::= { onuAlarmPortTable 1 }

		
		OnuAlarmPortEntry ::=
			SEQUENCE { 
				onuAlarmPortPon
					Integer32,
				onuAlarmPortOnu
					Integer32,
				onuAlarmPortPort
					Integer32,
				onuAlarmPortAutoEnable
					INTEGER,
				onuAlarmPortLosEnable
					INTEGER,
				onuAlarmPortFailureEnable
					INTEGER,
				onuAlarmPortLoopbackEnable
					INTEGER,
				onuAlarmPortCongestEnable
					INTEGER
			 }

--          1.3.6.1.4.1.37950.1.1.5.12.7.2.1.1
-- 1.3.6.1.4.1.37950.1.1.5.12.7.2.1.1
-- 1.3.6.1.4.1.37950.1.1.5.12.7.2.1.1
-- 1.3.6.1.4.1.37950.1.1.5.12.7.2.1.1
-- 1.3.6.1.4.1.37950.1.1.5.12.7.2.1.1
-- 1.3.6.1.4.1.37950.1.1.5.12.7.2.1.1
-- 1.3.6.1.4.1.37950.1.1.5.12.7.2.1.1
-- 1.3.6.1.4.1.37950.1.1.5.12.7.2.1.1
-- 1.3.6.1.4.1.37950.1.1.5.12.7.2.1.1
		-- 1.3.6.1.4.1.37950.1.1.5.12.7.2.1.1
		onuAlarmPortPon OBJECT-TYPE
			SYNTAX Integer32
			MAX-ACCESS read-only
			STATUS current
			DESCRIPTION
				"Description."
			::= { onuAlarmPortEntry 1 }

		
--          1.3.6.1.4.1.37950.1.1.5.12.7.2.1.2
-- 1.3.6.1.4.1.37950.1.1.5.12.7.2.1.2
-- 1.3.6.1.4.1.37950.1.1.5.12.7.2.1.2
-- 1.3.6.1.4.1.37950.1.1.5.12.7.2.1.2
-- 1.3.6.1.4.1.37950.1.1.5.12.7.2.1.2
-- 1.3.6.1.4.1.37950.1.1.5.12.7.2.1.2
-- 1.3.6.1.4.1.37950.1.1.5.12.7.2.1.2
-- 1.3.6.1.4.1.37950.1.1.5.12.7.2.1.2
-- 1.3.6.1.4.1.37950.1.1.5.12.7.2.1.2
		-- 1.3.6.1.4.1.37950.1.1.5.12.7.2.1.2
		onuAlarmPortOnu OBJECT-TYPE
			SYNTAX Integer32
			MAX-ACCESS read-only
			STATUS current
			DESCRIPTION
				"Description."
			::= { onuAlarmPortEntry 2 }

		
--          1.3.6.1.4.1.37950.1.1.5.12.7.2.1.3
-- 1.3.6.1.4.1.37950.1.1.5.12.7.2.1.3
-- 1.3.6.1.4.1.37950.1.1.5.12.7.2.1.3
-- 1.3.6.1.4.1.37950.1.1.5.12.7.2.1.3
-- 1.3.6.1.4.1.37950.1.1.5.12.7.2.1.3
-- 1.3.6.1.4.1.37950.1.1.5.12.7.2.1.3
-- 1.3.6.1.4.1.37950.1.1.5.12.7.2.1.3
-- 1.3.6.1.4.1.37950.1.1.5.12.7.2.1.3
-- 1.3.6.1.4.1.37950.1.1.5.12.7.2.1.3
		-- 1.3.6.1.4.1.37950.1.1.5.12.7.2.1.3
		onuAlarmPortPort OBJECT-TYPE
			SYNTAX Integer32
			MAX-ACCESS read-only
			STATUS current
			DESCRIPTION
				"Description."
			::= { onuAlarmPortEntry 3 }

		
--          1.3.6.1.4.1.37950.1.1.5.12.7.2.1.4
-- 1.3.6.1.4.1.37950.1.1.5.12.7.2.1.4
-- 1.3.6.1.4.1.37950.1.1.5.12.7.2.1.4
-- 1.3.6.1.4.1.37950.1.1.5.12.7.2.1.4
-- 1.3.6.1.4.1.37950.1.1.5.12.7.2.1.4
-- 1.3.6.1.4.1.37950.1.1.5.12.7.2.1.4
-- 1.3.6.1.4.1.37950.1.1.5.12.7.2.1.4
-- 1.3.6.1.4.1.37950.1.1.5.12.7.2.1.4
-- 1.3.6.1.4.1.37950.1.1.5.12.7.2.1.4
		-- 1.3.6.1.4.1.37950.1.1.5.12.7.2.1.4
		onuAlarmPortAutoEnable OBJECT-TYPE
			SYNTAX INTEGER
				{
				disable(0),
				enable(1)
				}
			MAX-ACCESS read-only
			STATUS current
			DESCRIPTION
				"Description."
			::= { onuAlarmPortEntry 4 }

		
--          1.3.6.1.4.1.37950.1.1.5.12.7.2.1.5
-- 1.3.6.1.4.1.37950.1.1.5.12.7.2.1.5
-- 1.3.6.1.4.1.37950.1.1.5.12.7.2.1.5
-- 1.3.6.1.4.1.37950.1.1.5.12.7.2.1.5
-- 1.3.6.1.4.1.37950.1.1.5.12.7.2.1.5
-- 1.3.6.1.4.1.37950.1.1.5.12.7.2.1.5
-- 1.3.6.1.4.1.37950.1.1.5.12.7.2.1.5
-- 1.3.6.1.4.1.37950.1.1.5.12.7.2.1.5
-- 1.3.6.1.4.1.37950.1.1.5.12.7.2.1.5
		-- 1.3.6.1.4.1.37950.1.1.5.12.7.2.1.5
		onuAlarmPortLosEnable OBJECT-TYPE
			SYNTAX INTEGER
				{
				disable(0),
				enable(1)
				}
			MAX-ACCESS read-only
			STATUS current
			DESCRIPTION
				"Description."
			::= { onuAlarmPortEntry 5 }

		
--          1.3.6.1.4.1.37950.1.1.5.12.7.2.1.6
-- 1.3.6.1.4.1.37950.1.1.5.12.7.2.1.6
-- 1.3.6.1.4.1.37950.1.1.5.12.7.2.1.6
-- 1.3.6.1.4.1.37950.1.1.5.12.7.2.1.6
-- 1.3.6.1.4.1.37950.1.1.5.12.7.2.1.6
-- 1.3.6.1.4.1.37950.1.1.5.12.7.2.1.6
-- 1.3.6.1.4.1.37950.1.1.5.12.7.2.1.6
-- 1.3.6.1.4.1.37950.1.1.5.12.7.2.1.6
-- 1.3.6.1.4.1.37950.1.1.5.12.7.2.1.6
		-- 1.3.6.1.4.1.37950.1.1.5.12.7.2.1.6
		onuAlarmPortFailureEnable OBJECT-TYPE
			SYNTAX INTEGER
				{
				disable(0),
				enable(1)
				}
			MAX-ACCESS read-only
			STATUS current
			DESCRIPTION
				"Description."
			::= { onuAlarmPortEntry 6 }

		
--          1.3.6.1.4.1.37950.1.1.5.12.7.2.1.7
-- 1.3.6.1.4.1.37950.1.1.5.12.7.2.1.7
-- 1.3.6.1.4.1.37950.1.1.5.12.7.2.1.7
-- 1.3.6.1.4.1.37950.1.1.5.12.7.2.1.7
-- 1.3.6.1.4.1.37950.1.1.5.12.7.2.1.7
-- 1.3.6.1.4.1.37950.1.1.5.12.7.2.1.7
-- 1.3.6.1.4.1.37950.1.1.5.12.7.2.1.7
-- 1.3.6.1.4.1.37950.1.1.5.12.7.2.1.7
-- 1.3.6.1.4.1.37950.1.1.5.12.7.2.1.7
		-- 1.3.6.1.4.1.37950.1.1.5.12.7.2.1.7
		onuAlarmPortLoopbackEnable OBJECT-TYPE
			SYNTAX INTEGER
				{
				disable(0),
				enable(1)
				}
			MAX-ACCESS read-only
			STATUS current
			DESCRIPTION
				"Description."
			::= { onuAlarmPortEntry 7 }

		
--          1.3.6.1.4.1.37950.1.1.5.12.7.2.1.8
-- 1.3.6.1.4.1.37950.1.1.5.12.7.2.1.8
-- 1.3.6.1.4.1.37950.1.1.5.12.7.2.1.8
-- 1.3.6.1.4.1.37950.1.1.5.12.7.2.1.8
-- 1.3.6.1.4.1.37950.1.1.5.12.7.2.1.8
-- 1.3.6.1.4.1.37950.1.1.5.12.7.2.1.8
-- 1.3.6.1.4.1.37950.1.1.5.12.7.2.1.8
-- 1.3.6.1.4.1.37950.1.1.5.12.7.2.1.8
-- 1.3.6.1.4.1.37950.1.1.5.12.7.2.1.8
		-- 1.3.6.1.4.1.37950.1.1.5.12.7.2.1.8
		onuAlarmPortCongestEnable OBJECT-TYPE
			SYNTAX INTEGER
				{
				disable(0),
				enable(1)
				}
			MAX-ACCESS read-only
			STATUS current
			DESCRIPTION
				"Description."
			::= { onuAlarmPortEntry 8 }

		
--          1.3.6.1.4.1.37950.1.1.5.12.8
-- 1.3.6.1.4.1.37950.1.1.5.12.8
-- 1.3.6.1.4.1.37950.1.1.5.12.8
-- 1.3.6.1.4.1.37950.1.1.5.12.8
-- 1.3.6.1.4.1.37950.1.1.5.12.8
-- 1.3.6.1.4.1.37950.1.1.5.12.8
-- 1.3.6.1.4.1.37950.1.1.5.12.8
-- 1.3.6.1.4.1.37950.1.1.5.12.8
-- 1.3.6.1.4.1.37950.1.1.5.12.8
		-- 1.3.6.1.4.1.37950.1.1.5.12.8
		onuProfileCfg OBJECT IDENTIFIER ::= { v1600dOnuMgmt 8 }

		
--          1.3.6.1.4.1.37950.1.1.5.12.8.1
-- 1.3.6.1.4.1.37950.1.1.5.12.8.1
-- 1.3.6.1.4.1.37950.1.1.5.12.8.1
-- 1.3.6.1.4.1.37950.1.1.5.12.8.1
-- 1.3.6.1.4.1.37950.1.1.5.12.8.1
-- 1.3.6.1.4.1.37950.1.1.5.12.8.1
-- 1.3.6.1.4.1.37950.1.1.5.12.8.1
-- 1.3.6.1.4.1.37950.1.1.5.12.8.1
-- 1.3.6.1.4.1.37950.1.1.5.12.8.1
		-- 1.3.6.1.4.1.37950.1.1.5.12.8.1
		profileEdit OBJECT IDENTIFIER ::= { onuProfileCfg 1 }

		
--          1.3.6.1.4.1.37950.1.1.5.12.8.1.1
-- 1.3.6.1.4.1.37950.1.1.5.12.8.1.1
-- 1.3.6.1.4.1.37950.1.1.5.12.8.1.1
-- 1.3.6.1.4.1.37950.1.1.5.12.8.1.1
-- 1.3.6.1.4.1.37950.1.1.5.12.8.1.1
-- 1.3.6.1.4.1.37950.1.1.5.12.8.1.1
-- 1.3.6.1.4.1.37950.1.1.5.12.8.1.1
-- 1.3.6.1.4.1.37950.1.1.5.12.8.1.1
-- 1.3.6.1.4.1.37950.1.1.5.12.8.1.1
		-- 1.3.6.1.4.1.37950.1.1.5.12.8.1.1
		profileTpye OBJECT-TYPE
			SYNTAX INTEGER
				{
				dba(1),
				srv(2),
				voip(3),
				alarm(4)
				}
			MAX-ACCESS read-write
			STATUS current
			DESCRIPTION
				"Description."
			::= { profileEdit 1 }

		
--          1.3.6.1.4.1.37950.1.1.5.12.8.1.2
-- 1.3.6.1.4.1.37950.1.1.5.12.8.1.2
-- 1.3.6.1.4.1.37950.1.1.5.12.8.1.2
-- 1.3.6.1.4.1.37950.1.1.5.12.8.1.2
-- 1.3.6.1.4.1.37950.1.1.5.12.8.1.2
-- 1.3.6.1.4.1.37950.1.1.5.12.8.1.2
-- 1.3.6.1.4.1.37950.1.1.5.12.8.1.2
-- 1.3.6.1.4.1.37950.1.1.5.12.8.1.2
-- 1.3.6.1.4.1.37950.1.1.5.12.8.1.2
		-- 1.3.6.1.4.1.37950.1.1.5.12.8.1.2
		profileId OBJECT-TYPE
			SYNTAX INTEGER (1..32767)
			MAX-ACCESS read-write
			STATUS current
			DESCRIPTION
				"Description."
			::= { profileEdit 2 }

		
--          1.3.6.1.4.1.37950.1.1.5.12.8.1.3
-- 1.3.6.1.4.1.37950.1.1.5.12.8.1.3
-- 1.3.6.1.4.1.37950.1.1.5.12.8.1.3
-- 1.3.6.1.4.1.37950.1.1.5.12.8.1.3
-- 1.3.6.1.4.1.37950.1.1.5.12.8.1.3
-- 1.3.6.1.4.1.37950.1.1.5.12.8.1.3
-- 1.3.6.1.4.1.37950.1.1.5.12.8.1.3
-- 1.3.6.1.4.1.37950.1.1.5.12.8.1.3
-- 1.3.6.1.4.1.37950.1.1.5.12.8.1.3
		-- 1.3.6.1.4.1.37950.1.1.5.12.8.1.3
		profileAction OBJECT-TYPE
			SYNTAX INTEGER
				{
				add(1),
				delete(2),
				commit(3)
				}
			MAX-ACCESS read-write
			STATUS current
			DESCRIPTION
				"Description."
			::= { profileEdit 3 }

		
--          1.3.6.1.4.1.37950.1.1.5.12.8.2
-- 1.3.6.1.4.1.37950.1.1.5.12.8.2
-- 1.3.6.1.4.1.37950.1.1.5.12.8.2
-- 1.3.6.1.4.1.37950.1.1.5.12.8.2
-- 1.3.6.1.4.1.37950.1.1.5.12.8.2
-- 1.3.6.1.4.1.37950.1.1.5.12.8.2
-- 1.3.6.1.4.1.37950.1.1.5.12.8.2
-- 1.3.6.1.4.1.37950.1.1.5.12.8.2
-- 1.3.6.1.4.1.37950.1.1.5.12.8.2
		-- 1.3.6.1.4.1.37950.1.1.5.12.8.2
		dbaProfileEdit OBJECT IDENTIFIER ::= { onuProfileCfg 2 }

		
--          1.3.6.1.4.1.37950.1.1.5.12.8.2.1
-- 1.3.6.1.4.1.37950.1.1.5.12.8.2.1
-- 1.3.6.1.4.1.37950.1.1.5.12.8.2.1
-- 1.3.6.1.4.1.37950.1.1.5.12.8.2.1
-- 1.3.6.1.4.1.37950.1.1.5.12.8.2.1
-- 1.3.6.1.4.1.37950.1.1.5.12.8.2.1
-- 1.3.6.1.4.1.37950.1.1.5.12.8.2.1
-- 1.3.6.1.4.1.37950.1.1.5.12.8.2.1
-- 1.3.6.1.4.1.37950.1.1.5.12.8.2.1
		-- 1.3.6.1.4.1.37950.1.1.5.12.8.2.1
		dbaProfileNo OBJECT-TYPE
			SYNTAX INTEGER (1..32767)
			MAX-ACCESS read-write
			STATUS current
			DESCRIPTION
				"Description."
			::= { dbaProfileEdit 1 }

		
--          1.3.6.1.4.1.37950.1.1.5.12.8.2.2
-- 1.3.6.1.4.1.37950.1.1.5.12.8.2.2
-- 1.3.6.1.4.1.37950.1.1.5.12.8.2.2
-- 1.3.6.1.4.1.37950.1.1.5.12.8.2.2
-- 1.3.6.1.4.1.37950.1.1.5.12.8.2.2
-- 1.3.6.1.4.1.37950.1.1.5.12.8.2.2
-- 1.3.6.1.4.1.37950.1.1.5.12.8.2.2
-- 1.3.6.1.4.1.37950.1.1.5.12.8.2.2
-- 1.3.6.1.4.1.37950.1.1.5.12.8.2.2
		-- 1.3.6.1.4.1.37950.1.1.5.12.8.2.2
		upstreamCfg OBJECT IDENTIFIER ::= { dbaProfileEdit 2 }

		
--          1.3.6.1.4.1.37950.1.1.5.12.8.2.2.1
-- 1.3.6.1.4.1.37950.1.1.5.12.8.2.2.1
-- 1.3.6.1.4.1.37950.1.1.5.12.8.2.2.1
-- 1.3.6.1.4.1.37950.1.1.5.12.8.2.2.1
-- 1.3.6.1.4.1.37950.1.1.5.12.8.2.2.1
-- 1.3.6.1.4.1.37950.1.1.5.12.8.2.2.1
-- 1.3.6.1.4.1.37950.1.1.5.12.8.2.2.1
-- 1.3.6.1.4.1.37950.1.1.5.12.8.2.2.1
-- 1.3.6.1.4.1.37950.1.1.5.12.8.2.2.1
		-- 1.3.6.1.4.1.37950.1.1.5.12.8.2.2.1
		upstreamFir OBJECT-TYPE
			SYNTAX INTEGER (0..950000)
			MAX-ACCESS read-write
			STATUS current
			DESCRIPTION
				"Description."
			::= { upstreamCfg 1 }

		
--          1.3.6.1.4.1.37950.1.1.5.12.8.2.2.2
-- 1.3.6.1.4.1.37950.1.1.5.12.8.2.2.2
-- 1.3.6.1.4.1.37950.1.1.5.12.8.2.2.2
-- 1.3.6.1.4.1.37950.1.1.5.12.8.2.2.2
-- 1.3.6.1.4.1.37950.1.1.5.12.8.2.2.2
-- 1.3.6.1.4.1.37950.1.1.5.12.8.2.2.2
-- 1.3.6.1.4.1.37950.1.1.5.12.8.2.2.2
-- 1.3.6.1.4.1.37950.1.1.5.12.8.2.2.2
-- 1.3.6.1.4.1.37950.1.1.5.12.8.2.2.2
		-- 1.3.6.1.4.1.37950.1.1.5.12.8.2.2.2
		upstreamCir OBJECT-TYPE
			SYNTAX INTEGER (1..950000)
			MAX-ACCESS read-write
			STATUS current
			DESCRIPTION
				"Description."
			::= { upstreamCfg 2 }

		
--          1.3.6.1.4.1.37950.1.1.5.12.8.2.2.3
-- 1.3.6.1.4.1.37950.1.1.5.12.8.2.2.3
-- 1.3.6.1.4.1.37950.1.1.5.12.8.2.2.3
-- 1.3.6.1.4.1.37950.1.1.5.12.8.2.2.3
-- 1.3.6.1.4.1.37950.1.1.5.12.8.2.2.3
-- 1.3.6.1.4.1.37950.1.1.5.12.8.2.2.3
-- 1.3.6.1.4.1.37950.1.1.5.12.8.2.2.3
-- 1.3.6.1.4.1.37950.1.1.5.12.8.2.2.3
-- 1.3.6.1.4.1.37950.1.1.5.12.8.2.2.3
		-- 1.3.6.1.4.1.37950.1.1.5.12.8.2.2.3
		upstreamPir OBJECT-TYPE
			SYNTAX INTEGER (512..1000000)
			MAX-ACCESS read-write
			STATUS current
			DESCRIPTION
				"Description."
			::= { upstreamCfg 3 }

		
--          1.3.6.1.4.1.37950.1.1.5.12.8.2.2.4
-- 1.3.6.1.4.1.37950.1.1.5.12.8.2.2.4
-- 1.3.6.1.4.1.37950.1.1.5.12.8.2.2.4
-- 1.3.6.1.4.1.37950.1.1.5.12.8.2.2.4
-- 1.3.6.1.4.1.37950.1.1.5.12.8.2.2.4
-- 1.3.6.1.4.1.37950.1.1.5.12.8.2.2.4
-- 1.3.6.1.4.1.37950.1.1.5.12.8.2.2.4
-- 1.3.6.1.4.1.37950.1.1.5.12.8.2.2.4
-- 1.3.6.1.4.1.37950.1.1.5.12.8.2.2.4
		-- 1.3.6.1.4.1.37950.1.1.5.12.8.2.2.4
		upstreamWeight OBJECT-TYPE
			SYNTAX INTEGER (1..20)
			MAX-ACCESS read-write
			STATUS current
			DESCRIPTION
				"Description."
			::= { upstreamCfg 4 }

		
--          1.3.6.1.4.1.37950.1.1.5.12.8.2.2.5
-- 1.3.6.1.4.1.37950.1.1.5.12.8.2.2.5
-- 1.3.6.1.4.1.37950.1.1.5.12.8.2.2.5
-- 1.3.6.1.4.1.37950.1.1.5.12.8.2.2.5
-- 1.3.6.1.4.1.37950.1.1.5.12.8.2.2.5
-- 1.3.6.1.4.1.37950.1.1.5.12.8.2.2.5
-- 1.3.6.1.4.1.37950.1.1.5.12.8.2.2.5
-- 1.3.6.1.4.1.37950.1.1.5.12.8.2.2.5
-- 1.3.6.1.4.1.37950.1.1.5.12.8.2.2.5
		-- 1.3.6.1.4.1.37950.1.1.5.12.8.2.2.5
		upstreamAction OBJECT-TYPE
			SYNTAX INTEGER
				{
				add(1),
				delete(2)
				}
			MAX-ACCESS read-write
			STATUS current
			DESCRIPTION
				"Description."
			::= { upstreamCfg 5 }

		
--          1.3.6.1.4.1.37950.1.1.5.12.8.2.3
-- 1.3.6.1.4.1.37950.1.1.5.12.8.2.3
-- 1.3.6.1.4.1.37950.1.1.5.12.8.2.3
-- 1.3.6.1.4.1.37950.1.1.5.12.8.2.3
-- 1.3.6.1.4.1.37950.1.1.5.12.8.2.3
-- 1.3.6.1.4.1.37950.1.1.5.12.8.2.3
-- 1.3.6.1.4.1.37950.1.1.5.12.8.2.3
-- 1.3.6.1.4.1.37950.1.1.5.12.8.2.3
-- 1.3.6.1.4.1.37950.1.1.5.12.8.2.3
		-- 1.3.6.1.4.1.37950.1.1.5.12.8.2.3
		dnstreamCfg OBJECT IDENTIFIER ::= { dbaProfileEdit 3 }

		
--          1.3.6.1.4.1.37950.1.1.5.12.8.2.3.1
-- 1.3.6.1.4.1.37950.1.1.5.12.8.2.3.1
-- 1.3.6.1.4.1.37950.1.1.5.12.8.2.3.1
-- 1.3.6.1.4.1.37950.1.1.5.12.8.2.3.1
-- 1.3.6.1.4.1.37950.1.1.5.12.8.2.3.1
-- 1.3.6.1.4.1.37950.1.1.5.12.8.2.3.1
-- 1.3.6.1.4.1.37950.1.1.5.12.8.2.3.1
-- 1.3.6.1.4.1.37950.1.1.5.12.8.2.3.1
-- 1.3.6.1.4.1.37950.1.1.5.12.8.2.3.1
		-- 1.3.6.1.4.1.37950.1.1.5.12.8.2.3.1
		dnstreamPir OBJECT-TYPE
			SYNTAX INTEGER (0..1000000)
			MAX-ACCESS read-write
			STATUS current
			DESCRIPTION
				"Description."
			::= { dnstreamCfg 1 }

		
--          1.3.6.1.4.1.37950.1.1.5.12.8.2.3.2
-- 1.3.6.1.4.1.37950.1.1.5.12.8.2.3.2
-- 1.3.6.1.4.1.37950.1.1.5.12.8.2.3.2
-- 1.3.6.1.4.1.37950.1.1.5.12.8.2.3.2
-- 1.3.6.1.4.1.37950.1.1.5.12.8.2.3.2
-- 1.3.6.1.4.1.37950.1.1.5.12.8.2.3.2
-- 1.3.6.1.4.1.37950.1.1.5.12.8.2.3.2
-- 1.3.6.1.4.1.37950.1.1.5.12.8.2.3.2
-- 1.3.6.1.4.1.37950.1.1.5.12.8.2.3.2
		-- 1.3.6.1.4.1.37950.1.1.5.12.8.2.3.2
		dnstreamWeight OBJECT-TYPE
			SYNTAX INTEGER (1..16)
			MAX-ACCESS read-write
			STATUS current
			DESCRIPTION
				"Description."
			::= { dnstreamCfg 2 }

		
--          1.3.6.1.4.1.37950.1.1.5.12.8.2.3.3
-- 1.3.6.1.4.1.37950.1.1.5.12.8.2.3.3
-- 1.3.6.1.4.1.37950.1.1.5.12.8.2.3.3
-- 1.3.6.1.4.1.37950.1.1.5.12.8.2.3.3
-- 1.3.6.1.4.1.37950.1.1.5.12.8.2.3.3
-- 1.3.6.1.4.1.37950.1.1.5.12.8.2.3.3
-- 1.3.6.1.4.1.37950.1.1.5.12.8.2.3.3
-- 1.3.6.1.4.1.37950.1.1.5.12.8.2.3.3
-- 1.3.6.1.4.1.37950.1.1.5.12.8.2.3.3
		-- 1.3.6.1.4.1.37950.1.1.5.12.8.2.3.3
		dnstreamAction OBJECT-TYPE
			SYNTAX INTEGER
				{
				add(1),
				delete(2)
				}
			MAX-ACCESS read-write
			STATUS current
			DESCRIPTION
				"Description."
			::= { dnstreamCfg 3 }

		
--          1.3.6.1.4.1.37950.1.1.5.12.8.3
-- 1.3.6.1.4.1.37950.1.1.5.12.8.3
-- 1.3.6.1.4.1.37950.1.1.5.12.8.3
-- 1.3.6.1.4.1.37950.1.1.5.12.8.3
-- 1.3.6.1.4.1.37950.1.1.5.12.8.3
-- 1.3.6.1.4.1.37950.1.1.5.12.8.3
-- 1.3.6.1.4.1.37950.1.1.5.12.8.3
-- 1.3.6.1.4.1.37950.1.1.5.12.8.3
-- 1.3.6.1.4.1.37950.1.1.5.12.8.3
		-- 1.3.6.1.4.1.37950.1.1.5.12.8.3
		srvProfileEdit OBJECT IDENTIFIER ::= { onuProfileCfg 3 }

		
--          1.3.6.1.4.1.37950.1.1.5.12.8.3.1
-- 1.3.6.1.4.1.37950.1.1.5.12.8.3.1
-- 1.3.6.1.4.1.37950.1.1.5.12.8.3.1
-- 1.3.6.1.4.1.37950.1.1.5.12.8.3.1
-- 1.3.6.1.4.1.37950.1.1.5.12.8.3.1
-- 1.3.6.1.4.1.37950.1.1.5.12.8.3.1
-- 1.3.6.1.4.1.37950.1.1.5.12.8.3.1
-- 1.3.6.1.4.1.37950.1.1.5.12.8.3.1
-- 1.3.6.1.4.1.37950.1.1.5.12.8.3.1
		-- 1.3.6.1.4.1.37950.1.1.5.12.8.3.1
		srvProfileNo OBJECT-TYPE
			SYNTAX INTEGER (1..32767)
			MAX-ACCESS read-write
			STATUS current
			DESCRIPTION
				"Description."
			::= { srvProfileEdit 1 }

		
--          1.3.6.1.4.1.37950.1.1.5.12.8.3.2
-- 1.3.6.1.4.1.37950.1.1.5.12.8.3.2
-- 1.3.6.1.4.1.37950.1.1.5.12.8.3.2
-- 1.3.6.1.4.1.37950.1.1.5.12.8.3.2
-- 1.3.6.1.4.1.37950.1.1.5.12.8.3.2
-- 1.3.6.1.4.1.37950.1.1.5.12.8.3.2
-- 1.3.6.1.4.1.37950.1.1.5.12.8.3.2
-- 1.3.6.1.4.1.37950.1.1.5.12.8.3.2
-- 1.3.6.1.4.1.37950.1.1.5.12.8.3.2
		-- 1.3.6.1.4.1.37950.1.1.5.12.8.3.2
		onuLanCountConfig OBJECT IDENTIFIER ::= { srvProfileEdit 2 }

		
--          1.3.6.1.4.1.37950.1.1.5.12.8.3.2.1
-- 1.3.6.1.4.1.37950.1.1.5.12.8.3.2.1
-- 1.3.6.1.4.1.37950.1.1.5.12.8.3.2.1
-- 1.3.6.1.4.1.37950.1.1.5.12.8.3.2.1
-- 1.3.6.1.4.1.37950.1.1.5.12.8.3.2.1
-- 1.3.6.1.4.1.37950.1.1.5.12.8.3.2.1
-- 1.3.6.1.4.1.37950.1.1.5.12.8.3.2.1
-- 1.3.6.1.4.1.37950.1.1.5.12.8.3.2.1
-- 1.3.6.1.4.1.37950.1.1.5.12.8.3.2.1
		-- 1.3.6.1.4.1.37950.1.1.5.12.8.3.2.1
		lanCount OBJECT-TYPE
			SYNTAX INTEGER (0..255)
			MAX-ACCESS read-write
			STATUS current
			DESCRIPTION
				"Description."
			::= { onuLanCountConfig 1 }

		
--          1.3.6.1.4.1.37950.1.1.5.12.8.3.2.2
-- 1.3.6.1.4.1.37950.1.1.5.12.8.3.2.2
-- 1.3.6.1.4.1.37950.1.1.5.12.8.3.2.2
-- 1.3.6.1.4.1.37950.1.1.5.12.8.3.2.2
-- 1.3.6.1.4.1.37950.1.1.5.12.8.3.2.2
-- 1.3.6.1.4.1.37950.1.1.5.12.8.3.2.2
-- 1.3.6.1.4.1.37950.1.1.5.12.8.3.2.2
-- 1.3.6.1.4.1.37950.1.1.5.12.8.3.2.2
-- 1.3.6.1.4.1.37950.1.1.5.12.8.3.2.2
		-- 1.3.6.1.4.1.37950.1.1.5.12.8.3.2.2
		lanCountAction OBJECT-TYPE
			SYNTAX INTEGER
				{
				add(1),
				remove(2)
				}
			MAX-ACCESS read-write
			STATUS current
			DESCRIPTION
				"Description."
			::= { onuLanCountConfig 2 }

		
--          1.3.6.1.4.1.37950.1.1.5.12.8.3.3
-- 1.3.6.1.4.1.37950.1.1.5.12.8.3.3
-- 1.3.6.1.4.1.37950.1.1.5.12.8.3.3
-- 1.3.6.1.4.1.37950.1.1.5.12.8.3.3
-- 1.3.6.1.4.1.37950.1.1.5.12.8.3.3
-- 1.3.6.1.4.1.37950.1.1.5.12.8.3.3
-- 1.3.6.1.4.1.37950.1.1.5.12.8.3.3
-- 1.3.6.1.4.1.37950.1.1.5.12.8.3.3
-- 1.3.6.1.4.1.37950.1.1.5.12.8.3.3
		-- 1.3.6.1.4.1.37950.1.1.5.12.8.3.3
		onuFastLeaveConfig OBJECT IDENTIFIER ::= { srvProfileEdit 3 }

		
--          1.3.6.1.4.1.37950.1.1.5.12.8.3.3.1
-- 1.3.6.1.4.1.37950.1.1.5.12.8.3.3.1
-- 1.3.6.1.4.1.37950.1.1.5.12.8.3.3.1
-- 1.3.6.1.4.1.37950.1.1.5.12.8.3.3.1
-- 1.3.6.1.4.1.37950.1.1.5.12.8.3.3.1
-- 1.3.6.1.4.1.37950.1.1.5.12.8.3.3.1
-- 1.3.6.1.4.1.37950.1.1.5.12.8.3.3.1
-- 1.3.6.1.4.1.37950.1.1.5.12.8.3.3.1
-- 1.3.6.1.4.1.37950.1.1.5.12.8.3.3.1
		-- 1.3.6.1.4.1.37950.1.1.5.12.8.3.3.1
		ctcFastLeave OBJECT-TYPE
			SYNTAX INTEGER
				{
				disable(0),
				enable(1)
				}
			MAX-ACCESS read-write
			STATUS current
			DESCRIPTION
				"Description."
			::= { onuFastLeaveConfig 1 }

		
--          1.3.6.1.4.1.37950.1.1.5.12.8.3.3.2
-- 1.3.6.1.4.1.37950.1.1.5.12.8.3.3.2
-- 1.3.6.1.4.1.37950.1.1.5.12.8.3.3.2
-- 1.3.6.1.4.1.37950.1.1.5.12.8.3.3.2
-- 1.3.6.1.4.1.37950.1.1.5.12.8.3.3.2
-- 1.3.6.1.4.1.37950.1.1.5.12.8.3.3.2
-- 1.3.6.1.4.1.37950.1.1.5.12.8.3.3.2
-- 1.3.6.1.4.1.37950.1.1.5.12.8.3.3.2
-- 1.3.6.1.4.1.37950.1.1.5.12.8.3.3.2
		-- 1.3.6.1.4.1.37950.1.1.5.12.8.3.3.2
		ctcFastLeaveAction OBJECT-TYPE
			SYNTAX INTEGER
				{
				add(1),
				remove(2)
				}
			MAX-ACCESS read-write
			STATUS current
			DESCRIPTION
				"Description."
			::= { onuFastLeaveConfig 2 }

		
--          1.3.6.1.4.1.37950.1.1.5.12.8.3.4
-- 1.3.6.1.4.1.37950.1.1.5.12.8.3.4
-- 1.3.6.1.4.1.37950.1.1.5.12.8.3.4
-- 1.3.6.1.4.1.37950.1.1.5.12.8.3.4
-- 1.3.6.1.4.1.37950.1.1.5.12.8.3.4
-- 1.3.6.1.4.1.37950.1.1.5.12.8.3.4
-- 1.3.6.1.4.1.37950.1.1.5.12.8.3.4
-- 1.3.6.1.4.1.37950.1.1.5.12.8.3.4
-- 1.3.6.1.4.1.37950.1.1.5.12.8.3.4
		-- 1.3.6.1.4.1.37950.1.1.5.12.8.3.4
		onuFecModeConfig OBJECT IDENTIFIER ::= { srvProfileEdit 4 }

		
--          1.3.6.1.4.1.37950.1.1.5.12.8.3.4.1
-- 1.3.6.1.4.1.37950.1.1.5.12.8.3.4.1
-- 1.3.6.1.4.1.37950.1.1.5.12.8.3.4.1
-- 1.3.6.1.4.1.37950.1.1.5.12.8.3.4.1
-- 1.3.6.1.4.1.37950.1.1.5.12.8.3.4.1
-- 1.3.6.1.4.1.37950.1.1.5.12.8.3.4.1
-- 1.3.6.1.4.1.37950.1.1.5.12.8.3.4.1
-- 1.3.6.1.4.1.37950.1.1.5.12.8.3.4.1
-- 1.3.6.1.4.1.37950.1.1.5.12.8.3.4.1
		-- 1.3.6.1.4.1.37950.1.1.5.12.8.3.4.1
		ctcFecMode OBJECT-TYPE
			SYNTAX INTEGER
				{
				disable(0),
				enable(1)
				}
			MAX-ACCESS read-write
			STATUS current
			DESCRIPTION
				"Description."
			::= { onuFecModeConfig 1 }

		
--          1.3.6.1.4.1.37950.1.1.5.12.8.3.4.2
-- 1.3.6.1.4.1.37950.1.1.5.12.8.3.4.2
-- 1.3.6.1.4.1.37950.1.1.5.12.8.3.4.2
-- 1.3.6.1.4.1.37950.1.1.5.12.8.3.4.2
-- 1.3.6.1.4.1.37950.1.1.5.12.8.3.4.2
-- 1.3.6.1.4.1.37950.1.1.5.12.8.3.4.2
-- 1.3.6.1.4.1.37950.1.1.5.12.8.3.4.2
-- 1.3.6.1.4.1.37950.1.1.5.12.8.3.4.2
-- 1.3.6.1.4.1.37950.1.1.5.12.8.3.4.2
		-- 1.3.6.1.4.1.37950.1.1.5.12.8.3.4.2
		ctcFecModeAction OBJECT-TYPE
			SYNTAX INTEGER
				{
				add(1),
				remove(2)
				}
			MAX-ACCESS read-write
			STATUS current
			DESCRIPTION
				"Description."
			::= { onuFecModeConfig 2 }

		
--          1.3.6.1.4.1.37950.1.1.5.12.8.3.5
-- 1.3.6.1.4.1.37950.1.1.5.12.8.3.5
-- 1.3.6.1.4.1.37950.1.1.5.12.8.3.5
-- 1.3.6.1.4.1.37950.1.1.5.12.8.3.5
-- 1.3.6.1.4.1.37950.1.1.5.12.8.3.5
-- 1.3.6.1.4.1.37950.1.1.5.12.8.3.5
-- 1.3.6.1.4.1.37950.1.1.5.12.8.3.5
-- 1.3.6.1.4.1.37950.1.1.5.12.8.3.5
-- 1.3.6.1.4.1.37950.1.1.5.12.8.3.5
		-- 1.3.6.1.4.1.37950.1.1.5.12.8.3.5
		ctcMcModeConfig OBJECT IDENTIFIER ::= { srvProfileEdit 5 }

		
--          1.3.6.1.4.1.37950.1.1.5.12.8.3.5.1
-- 1.3.6.1.4.1.37950.1.1.5.12.8.3.5.1
-- 1.3.6.1.4.1.37950.1.1.5.12.8.3.5.1
-- 1.3.6.1.4.1.37950.1.1.5.12.8.3.5.1
-- 1.3.6.1.4.1.37950.1.1.5.12.8.3.5.1
-- 1.3.6.1.4.1.37950.1.1.5.12.8.3.5.1
-- 1.3.6.1.4.1.37950.1.1.5.12.8.3.5.1
-- 1.3.6.1.4.1.37950.1.1.5.12.8.3.5.1
-- 1.3.6.1.4.1.37950.1.1.5.12.8.3.5.1
		-- 1.3.6.1.4.1.37950.1.1.5.12.8.3.5.1
		ctcMcMode OBJECT-TYPE
			SYNTAX INTEGER
				{
				snooping(1),
				control(2)
				}
			MAX-ACCESS read-write
			STATUS current
			DESCRIPTION
				"Description."
			::= { ctcMcModeConfig 1 }

		
--          1.3.6.1.4.1.37950.1.1.5.12.8.3.5.2
-- 1.3.6.1.4.1.37950.1.1.5.12.8.3.5.2
-- 1.3.6.1.4.1.37950.1.1.5.12.8.3.5.2
-- 1.3.6.1.4.1.37950.1.1.5.12.8.3.5.2
-- 1.3.6.1.4.1.37950.1.1.5.12.8.3.5.2
-- 1.3.6.1.4.1.37950.1.1.5.12.8.3.5.2
-- 1.3.6.1.4.1.37950.1.1.5.12.8.3.5.2
-- 1.3.6.1.4.1.37950.1.1.5.12.8.3.5.2
-- 1.3.6.1.4.1.37950.1.1.5.12.8.3.5.2
		-- 1.3.6.1.4.1.37950.1.1.5.12.8.3.5.2
		ctcMcModeAction OBJECT-TYPE
			SYNTAX INTEGER
				{
				add(1),
				remove(2)
				}
			MAX-ACCESS read-write
			STATUS current
			DESCRIPTION
				"Description."
			::= { ctcMcModeConfig 2 }

		
--          1.3.6.1.4.1.37950.1.1.5.12.8.3.6
-- 1.3.6.1.4.1.37950.1.1.5.12.8.3.6
-- 1.3.6.1.4.1.37950.1.1.5.12.8.3.6
-- 1.3.6.1.4.1.37950.1.1.5.12.8.3.6
-- 1.3.6.1.4.1.37950.1.1.5.12.8.3.6
-- 1.3.6.1.4.1.37950.1.1.5.12.8.3.6
-- 1.3.6.1.4.1.37950.1.1.5.12.8.3.6
-- 1.3.6.1.4.1.37950.1.1.5.12.8.3.6
-- 1.3.6.1.4.1.37950.1.1.5.12.8.3.6
		-- 1.3.6.1.4.1.37950.1.1.5.12.8.3.6
		ctcMultiLlidConfig OBJECT IDENTIFIER ::= { srvProfileEdit 6 }

		
--          1.3.6.1.4.1.37950.1.1.5.12.8.3.6.1
-- 1.3.6.1.4.1.37950.1.1.5.12.8.3.6.1
-- 1.3.6.1.4.1.37950.1.1.5.12.8.3.6.1
-- 1.3.6.1.4.1.37950.1.1.5.12.8.3.6.1
-- 1.3.6.1.4.1.37950.1.1.5.12.8.3.6.1
-- 1.3.6.1.4.1.37950.1.1.5.12.8.3.6.1
-- 1.3.6.1.4.1.37950.1.1.5.12.8.3.6.1
-- 1.3.6.1.4.1.37950.1.1.5.12.8.3.6.1
-- 1.3.6.1.4.1.37950.1.1.5.12.8.3.6.1
		-- 1.3.6.1.4.1.37950.1.1.5.12.8.3.6.1
		ctcMultiLlid OBJECT-TYPE
			SYNTAX INTEGER (0..8)
			MAX-ACCESS read-write
			STATUS current
			DESCRIPTION
				"Description."
			::= { ctcMultiLlidConfig 1 }

		
--          1.3.6.1.4.1.37950.1.1.5.12.8.3.6.2
-- 1.3.6.1.4.1.37950.1.1.5.12.8.3.6.2
-- 1.3.6.1.4.1.37950.1.1.5.12.8.3.6.2
-- 1.3.6.1.4.1.37950.1.1.5.12.8.3.6.2
-- 1.3.6.1.4.1.37950.1.1.5.12.8.3.6.2
-- 1.3.6.1.4.1.37950.1.1.5.12.8.3.6.2
-- 1.3.6.1.4.1.37950.1.1.5.12.8.3.6.2
-- 1.3.6.1.4.1.37950.1.1.5.12.8.3.6.2
-- 1.3.6.1.4.1.37950.1.1.5.12.8.3.6.2
		-- 1.3.6.1.4.1.37950.1.1.5.12.8.3.6.2
		ctcMultiLlidAction OBJECT-TYPE
			SYNTAX INTEGER
				{
				add(1),
				remove(2)
				}
			MAX-ACCESS read-write
			STATUS current
			DESCRIPTION
				"Description."
			::= { ctcMultiLlidConfig 2 }

		
--          1.3.6.1.4.1.37950.1.1.5.12.8.3.7
-- 1.3.6.1.4.1.37950.1.1.5.12.8.3.7
-- 1.3.6.1.4.1.37950.1.1.5.12.8.3.7
-- 1.3.6.1.4.1.37950.1.1.5.12.8.3.7
-- 1.3.6.1.4.1.37950.1.1.5.12.8.3.7
-- 1.3.6.1.4.1.37950.1.1.5.12.8.3.7
-- 1.3.6.1.4.1.37950.1.1.5.12.8.3.7
-- 1.3.6.1.4.1.37950.1.1.5.12.8.3.7
-- 1.3.6.1.4.1.37950.1.1.5.12.8.3.7
		-- 1.3.6.1.4.1.37950.1.1.5.12.8.3.7
		ctcActivePonConfig OBJECT IDENTIFIER ::= { srvProfileEdit 7 }

		
--          1.3.6.1.4.1.37950.1.1.5.12.8.3.7.1
-- 1.3.6.1.4.1.37950.1.1.5.12.8.3.7.1
-- 1.3.6.1.4.1.37950.1.1.5.12.8.3.7.1
-- 1.3.6.1.4.1.37950.1.1.5.12.8.3.7.1
-- 1.3.6.1.4.1.37950.1.1.5.12.8.3.7.1
-- 1.3.6.1.4.1.37950.1.1.5.12.8.3.7.1
-- 1.3.6.1.4.1.37950.1.1.5.12.8.3.7.1
-- 1.3.6.1.4.1.37950.1.1.5.12.8.3.7.1
-- 1.3.6.1.4.1.37950.1.1.5.12.8.3.7.1
		-- 1.3.6.1.4.1.37950.1.1.5.12.8.3.7.1
		ctcActivePon OBJECT-TYPE
			SYNTAX INTEGER (0..8)
			MAX-ACCESS read-write
			STATUS current
			DESCRIPTION
				"Description."
			::= { ctcActivePonConfig 1 }

		
--          1.3.6.1.4.1.37950.1.1.5.12.8.3.7.2
-- 1.3.6.1.4.1.37950.1.1.5.12.8.3.7.2
-- 1.3.6.1.4.1.37950.1.1.5.12.8.3.7.2
-- 1.3.6.1.4.1.37950.1.1.5.12.8.3.7.2
-- 1.3.6.1.4.1.37950.1.1.5.12.8.3.7.2
-- 1.3.6.1.4.1.37950.1.1.5.12.8.3.7.2
-- 1.3.6.1.4.1.37950.1.1.5.12.8.3.7.2
-- 1.3.6.1.4.1.37950.1.1.5.12.8.3.7.2
-- 1.3.6.1.4.1.37950.1.1.5.12.8.3.7.2
		-- 1.3.6.1.4.1.37950.1.1.5.12.8.3.7.2
		ctcActivePonAction OBJECT-TYPE
			SYNTAX INTEGER
				{
				add(1),
				remove(2)
				}
			MAX-ACCESS read-write
			STATUS current
			DESCRIPTION
				"Description."
			::= { ctcActivePonConfig 2 }

		
--          1.3.6.1.4.1.37950.1.1.5.12.8.3.8
-- 1.3.6.1.4.1.37950.1.1.5.12.8.3.8
-- 1.3.6.1.4.1.37950.1.1.5.12.8.3.8
-- 1.3.6.1.4.1.37950.1.1.5.12.8.3.8
-- 1.3.6.1.4.1.37950.1.1.5.12.8.3.8
-- 1.3.6.1.4.1.37950.1.1.5.12.8.3.8
-- 1.3.6.1.4.1.37950.1.1.5.12.8.3.8
-- 1.3.6.1.4.1.37950.1.1.5.12.8.3.8
-- 1.3.6.1.4.1.37950.1.1.5.12.8.3.8
		-- 1.3.6.1.4.1.37950.1.1.5.12.8.3.8
		ctcHoldoverConfig OBJECT IDENTIFIER ::= { srvProfileEdit 8 }

		
--          1.3.6.1.4.1.37950.1.1.5.12.8.3.8.1
-- 1.3.6.1.4.1.37950.1.1.5.12.8.3.8.1
-- 1.3.6.1.4.1.37950.1.1.5.12.8.3.8.1
-- 1.3.6.1.4.1.37950.1.1.5.12.8.3.8.1
-- 1.3.6.1.4.1.37950.1.1.5.12.8.3.8.1
-- 1.3.6.1.4.1.37950.1.1.5.12.8.3.8.1
-- 1.3.6.1.4.1.37950.1.1.5.12.8.3.8.1
-- 1.3.6.1.4.1.37950.1.1.5.12.8.3.8.1
-- 1.3.6.1.4.1.37950.1.1.5.12.8.3.8.1
		-- 1.3.6.1.4.1.37950.1.1.5.12.8.3.8.1
		ctcHoldover OBJECT-TYPE
			SYNTAX INTEGER (0..65535)
			MAX-ACCESS read-write
			STATUS current
			DESCRIPTION
				"Description."
			::= { ctcHoldoverConfig 1 }

		
--          1.3.6.1.4.1.37950.1.1.5.12.8.3.8.2
-- 1.3.6.1.4.1.37950.1.1.5.12.8.3.8.2
-- 1.3.6.1.4.1.37950.1.1.5.12.8.3.8.2
-- 1.3.6.1.4.1.37950.1.1.5.12.8.3.8.2
-- 1.3.6.1.4.1.37950.1.1.5.12.8.3.8.2
-- 1.3.6.1.4.1.37950.1.1.5.12.8.3.8.2
-- 1.3.6.1.4.1.37950.1.1.5.12.8.3.8.2
-- 1.3.6.1.4.1.37950.1.1.5.12.8.3.8.2
-- 1.3.6.1.4.1.37950.1.1.5.12.8.3.8.2
		-- 1.3.6.1.4.1.37950.1.1.5.12.8.3.8.2
		ctcHoldoverAction OBJECT-TYPE
			SYNTAX INTEGER
				{
				add(1),
				remove(2)
				}
			MAX-ACCESS read-write
			STATUS current
			DESCRIPTION
				"Description."
			::= { ctcHoldoverConfig 2 }

		
--          1.3.6.1.4.1.37950.1.1.5.12.8.3.9
-- 1.3.6.1.4.1.37950.1.1.5.12.8.3.9
-- 1.3.6.1.4.1.37950.1.1.5.12.8.3.9
-- 1.3.6.1.4.1.37950.1.1.5.12.8.3.9
-- 1.3.6.1.4.1.37950.1.1.5.12.8.3.9
-- 1.3.6.1.4.1.37950.1.1.5.12.8.3.9
-- 1.3.6.1.4.1.37950.1.1.5.12.8.3.9
-- 1.3.6.1.4.1.37950.1.1.5.12.8.3.9
-- 1.3.6.1.4.1.37950.1.1.5.12.8.3.9
		-- 1.3.6.1.4.1.37950.1.1.5.12.8.3.9
		onuMgmtIpCfg OBJECT IDENTIFIER ::= { srvProfileEdit 9 }

		
--          1.3.6.1.4.1.37950.1.1.5.12.8.3.9.1
-- 1.3.6.1.4.1.37950.1.1.5.12.8.3.9.1
-- 1.3.6.1.4.1.37950.1.1.5.12.8.3.9.1
-- 1.3.6.1.4.1.37950.1.1.5.12.8.3.9.1
-- 1.3.6.1.4.1.37950.1.1.5.12.8.3.9.1
-- 1.3.6.1.4.1.37950.1.1.5.12.8.3.9.1
-- 1.3.6.1.4.1.37950.1.1.5.12.8.3.9.1
-- 1.3.6.1.4.1.37950.1.1.5.12.8.3.9.1
-- 1.3.6.1.4.1.37950.1.1.5.12.8.3.9.1
		-- 1.3.6.1.4.1.37950.1.1.5.12.8.3.9.1
		onuMgmtIpAddr OBJECT-TYPE
			SYNTAX IpAddress
			MAX-ACCESS read-write
			STATUS current
			DESCRIPTION
				"Description."
			::= { onuMgmtIpCfg 1 }

		
--          1.3.6.1.4.1.37950.1.1.5.12.8.3.9.2
-- 1.3.6.1.4.1.37950.1.1.5.12.8.3.9.2
-- 1.3.6.1.4.1.37950.1.1.5.12.8.3.9.2
-- 1.3.6.1.4.1.37950.1.1.5.12.8.3.9.2
-- 1.3.6.1.4.1.37950.1.1.5.12.8.3.9.2
-- 1.3.6.1.4.1.37950.1.1.5.12.8.3.9.2
-- 1.3.6.1.4.1.37950.1.1.5.12.8.3.9.2
-- 1.3.6.1.4.1.37950.1.1.5.12.8.3.9.2
-- 1.3.6.1.4.1.37950.1.1.5.12.8.3.9.2
		-- 1.3.6.1.4.1.37950.1.1.5.12.8.3.9.2
		onuMgmtIpMask OBJECT-TYPE
			SYNTAX IpAddress
			MAX-ACCESS read-write
			STATUS current
			DESCRIPTION
				"Description."
			::= { onuMgmtIpCfg 2 }

		
--          1.3.6.1.4.1.37950.1.1.5.12.8.3.9.3
-- 1.3.6.1.4.1.37950.1.1.5.12.8.3.9.3
-- 1.3.6.1.4.1.37950.1.1.5.12.8.3.9.3
-- 1.3.6.1.4.1.37950.1.1.5.12.8.3.9.3
-- 1.3.6.1.4.1.37950.1.1.5.12.8.3.9.3
-- 1.3.6.1.4.1.37950.1.1.5.12.8.3.9.3
-- 1.3.6.1.4.1.37950.1.1.5.12.8.3.9.3
-- 1.3.6.1.4.1.37950.1.1.5.12.8.3.9.3
-- 1.3.6.1.4.1.37950.1.1.5.12.8.3.9.3
		-- 1.3.6.1.4.1.37950.1.1.5.12.8.3.9.3
		onuMgmtIpGw OBJECT-TYPE
			SYNTAX IpAddress
			MAX-ACCESS read-write
			STATUS current
			DESCRIPTION
				"Description."
			::= { onuMgmtIpCfg 3 }

		
--          1.3.6.1.4.1.37950.1.1.5.12.8.3.9.4
-- 1.3.6.1.4.1.37950.1.1.5.12.8.3.9.4
-- 1.3.6.1.4.1.37950.1.1.5.12.8.3.9.4
-- 1.3.6.1.4.1.37950.1.1.5.12.8.3.9.4
-- 1.3.6.1.4.1.37950.1.1.5.12.8.3.9.4
-- 1.3.6.1.4.1.37950.1.1.5.12.8.3.9.4
-- 1.3.6.1.4.1.37950.1.1.5.12.8.3.9.4
-- 1.3.6.1.4.1.37950.1.1.5.12.8.3.9.4
-- 1.3.6.1.4.1.37950.1.1.5.12.8.3.9.4
		-- 1.3.6.1.4.1.37950.1.1.5.12.8.3.9.4
		onuMgmtCvlan OBJECT-TYPE
			SYNTAX INTEGER (1..4095)
			MAX-ACCESS read-write
			STATUS current
			DESCRIPTION
				"Description."
			::= { onuMgmtIpCfg 4 }

		
--          1.3.6.1.4.1.37950.1.1.5.12.8.3.9.5
-- 1.3.6.1.4.1.37950.1.1.5.12.8.3.9.5
-- 1.3.6.1.4.1.37950.1.1.5.12.8.3.9.5
-- 1.3.6.1.4.1.37950.1.1.5.12.8.3.9.5
-- 1.3.6.1.4.1.37950.1.1.5.12.8.3.9.5
-- 1.3.6.1.4.1.37950.1.1.5.12.8.3.9.5
-- 1.3.6.1.4.1.37950.1.1.5.12.8.3.9.5
-- 1.3.6.1.4.1.37950.1.1.5.12.8.3.9.5
-- 1.3.6.1.4.1.37950.1.1.5.12.8.3.9.5
		-- 1.3.6.1.4.1.37950.1.1.5.12.8.3.9.5
		onuMgmtSvlan OBJECT-TYPE
			SYNTAX INTEGER (1..4095)
			MAX-ACCESS read-write
			STATUS current
			DESCRIPTION
				"Description."
			DEFVAL { 0 }
			::= { onuMgmtIpCfg 5 }

		
--          1.3.6.1.4.1.37950.1.1.5.12.8.3.9.6
-- 1.3.6.1.4.1.37950.1.1.5.12.8.3.9.6
-- 1.3.6.1.4.1.37950.1.1.5.12.8.3.9.6
-- 1.3.6.1.4.1.37950.1.1.5.12.8.3.9.6
-- 1.3.6.1.4.1.37950.1.1.5.12.8.3.9.6
-- 1.3.6.1.4.1.37950.1.1.5.12.8.3.9.6
-- 1.3.6.1.4.1.37950.1.1.5.12.8.3.9.6
-- 1.3.6.1.4.1.37950.1.1.5.12.8.3.9.6
-- 1.3.6.1.4.1.37950.1.1.5.12.8.3.9.6
		-- 1.3.6.1.4.1.37950.1.1.5.12.8.3.9.6
		onuMgmtPri OBJECT-TYPE
			SYNTAX INTEGER (0..7)
			MAX-ACCESS read-write
			STATUS current
			DESCRIPTION
				"Description."
			::= { onuMgmtIpCfg 6 }

		
--          1.3.6.1.4.1.37950.1.1.5.12.8.3.9.7
-- 1.3.6.1.4.1.37950.1.1.5.12.8.3.9.7
-- 1.3.6.1.4.1.37950.1.1.5.12.8.3.9.7
-- 1.3.6.1.4.1.37950.1.1.5.12.8.3.9.7
-- 1.3.6.1.4.1.37950.1.1.5.12.8.3.9.7
-- 1.3.6.1.4.1.37950.1.1.5.12.8.3.9.7
-- 1.3.6.1.4.1.37950.1.1.5.12.8.3.9.7
-- 1.3.6.1.4.1.37950.1.1.5.12.8.3.9.7
-- 1.3.6.1.4.1.37950.1.1.5.12.8.3.9.7
		-- 1.3.6.1.4.1.37950.1.1.5.12.8.3.9.7
		onuMgmtAction OBJECT-TYPE
			SYNTAX INTEGER
				{
				add(1),
				remove(2)
				}
			MAX-ACCESS read-write
			STATUS current
			DESCRIPTION
				"Description."
			::= { onuMgmtIpCfg 7 }

		
--          1.3.6.1.4.1.37950.1.1.5.12.8.3.10
-- 1.3.6.1.4.1.37950.1.1.5.12.8.3.10
-- 1.3.6.1.4.1.37950.1.1.5.12.8.3.10
-- 1.3.6.1.4.1.37950.1.1.5.12.8.3.10
-- 1.3.6.1.4.1.37950.1.1.5.12.8.3.10
-- 1.3.6.1.4.1.37950.1.1.5.12.8.3.10
-- 1.3.6.1.4.1.37950.1.1.5.12.8.3.10
-- 1.3.6.1.4.1.37950.1.1.5.12.8.3.10
-- 1.3.6.1.4.1.37950.1.1.5.12.8.3.10
		-- 1.3.6.1.4.1.37950.1.1.5.12.8.3.10
		onuSnmpProParam OBJECT IDENTIFIER ::= { srvProfileEdit 10 }

		
--          1.3.6.1.4.1.37950.1.1.5.12.8.3.10.1
-- 1.3.6.1.4.1.37950.1.1.5.12.8.3.10.1
-- 1.3.6.1.4.1.37950.1.1.5.12.8.3.10.1
-- 1.3.6.1.4.1.37950.1.1.5.12.8.3.10.1
-- 1.3.6.1.4.1.37950.1.1.5.12.8.3.10.1
-- 1.3.6.1.4.1.37950.1.1.5.12.8.3.10.1
-- 1.3.6.1.4.1.37950.1.1.5.12.8.3.10.1
-- 1.3.6.1.4.1.37950.1.1.5.12.8.3.10.1
-- 1.3.6.1.4.1.37950.1.1.5.12.8.3.10.1
		-- 1.3.6.1.4.1.37950.1.1.5.12.8.3.10.1
		ctcSnmpHost OBJECT-TYPE
			SYNTAX IpAddress
			MAX-ACCESS read-write
			STATUS current
			DESCRIPTION
				"Description."
			::= { onuSnmpProParam 1 }

		
--          1.3.6.1.4.1.37950.1.1.5.12.8.3.10.2
-- 1.3.6.1.4.1.37950.1.1.5.12.8.3.10.2
-- 1.3.6.1.4.1.37950.1.1.5.12.8.3.10.2
-- 1.3.6.1.4.1.37950.1.1.5.12.8.3.10.2
-- 1.3.6.1.4.1.37950.1.1.5.12.8.3.10.2
-- 1.3.6.1.4.1.37950.1.1.5.12.8.3.10.2
-- 1.3.6.1.4.1.37950.1.1.5.12.8.3.10.2
-- 1.3.6.1.4.1.37950.1.1.5.12.8.3.10.2
-- 1.3.6.1.4.1.37950.1.1.5.12.8.3.10.2
		-- 1.3.6.1.4.1.37950.1.1.5.12.8.3.10.2
		ctcSnmpTrapPort OBJECT-TYPE
			SYNTAX INTEGER (1..65535)
			MAX-ACCESS read-write
			STATUS current
			DESCRIPTION
				"Description."
			::= { onuSnmpProParam 2 }

		
--          1.3.6.1.4.1.37950.1.1.5.12.8.3.10.3
-- 1.3.6.1.4.1.37950.1.1.5.12.8.3.10.3
-- 1.3.6.1.4.1.37950.1.1.5.12.8.3.10.3
-- 1.3.6.1.4.1.37950.1.1.5.12.8.3.10.3
-- 1.3.6.1.4.1.37950.1.1.5.12.8.3.10.3
-- 1.3.6.1.4.1.37950.1.1.5.12.8.3.10.3
-- 1.3.6.1.4.1.37950.1.1.5.12.8.3.10.3
-- 1.3.6.1.4.1.37950.1.1.5.12.8.3.10.3
-- 1.3.6.1.4.1.37950.1.1.5.12.8.3.10.3
		-- 1.3.6.1.4.1.37950.1.1.5.12.8.3.10.3
		ctcSnmpPort OBJECT-TYPE
			SYNTAX INTEGER (1..65535)
			MAX-ACCESS read-write
			STATUS current
			DESCRIPTION
				"Description."
			::= { onuSnmpProParam 3 }

		
--          1.3.6.1.4.1.37950.1.1.5.12.8.3.10.4
-- 1.3.6.1.4.1.37950.1.1.5.12.8.3.10.4
-- 1.3.6.1.4.1.37950.1.1.5.12.8.3.10.4
-- 1.3.6.1.4.1.37950.1.1.5.12.8.3.10.4
-- 1.3.6.1.4.1.37950.1.1.5.12.8.3.10.4
-- 1.3.6.1.4.1.37950.1.1.5.12.8.3.10.4
-- 1.3.6.1.4.1.37950.1.1.5.12.8.3.10.4
-- 1.3.6.1.4.1.37950.1.1.5.12.8.3.10.4
-- 1.3.6.1.4.1.37950.1.1.5.12.8.3.10.4
		-- 1.3.6.1.4.1.37950.1.1.5.12.8.3.10.4
		ctcCommunityName OBJECT-TYPE
			SYNTAX OCTET STRING
			MAX-ACCESS read-write
			STATUS current
			DESCRIPTION
				"Description."
			::= { onuSnmpProParam 4 }

		
--          1.3.6.1.4.1.37950.1.1.5.12.8.3.10.5
-- 1.3.6.1.4.1.37950.1.1.5.12.8.3.10.5
-- 1.3.6.1.4.1.37950.1.1.5.12.8.3.10.5
-- 1.3.6.1.4.1.37950.1.1.5.12.8.3.10.5
-- 1.3.6.1.4.1.37950.1.1.5.12.8.3.10.5
-- 1.3.6.1.4.1.37950.1.1.5.12.8.3.10.5
-- 1.3.6.1.4.1.37950.1.1.5.12.8.3.10.5
-- 1.3.6.1.4.1.37950.1.1.5.12.8.3.10.5
-- 1.3.6.1.4.1.37950.1.1.5.12.8.3.10.5
		-- 1.3.6.1.4.1.37950.1.1.5.12.8.3.10.5
		ctcRoCommunityName OBJECT-TYPE
			SYNTAX OCTET STRING
			MAX-ACCESS read-write
			STATUS current
			DESCRIPTION
				"Description."
			::= { onuSnmpProParam 5 }

		
--          1.3.6.1.4.1.37950.1.1.5.12.8.3.10.6
-- 1.3.6.1.4.1.37950.1.1.5.12.8.3.10.6
-- 1.3.6.1.4.1.37950.1.1.5.12.8.3.10.6
-- 1.3.6.1.4.1.37950.1.1.5.12.8.3.10.6
-- 1.3.6.1.4.1.37950.1.1.5.12.8.3.10.6
-- 1.3.6.1.4.1.37950.1.1.5.12.8.3.10.6
-- 1.3.6.1.4.1.37950.1.1.5.12.8.3.10.6
-- 1.3.6.1.4.1.37950.1.1.5.12.8.3.10.6
-- 1.3.6.1.4.1.37950.1.1.5.12.8.3.10.6
		-- 1.3.6.1.4.1.37950.1.1.5.12.8.3.10.6
		ctcRwCommunityName OBJECT-TYPE
			SYNTAX OCTET STRING
			MAX-ACCESS read-write
			STATUS current
			DESCRIPTION
				"Description."
			::= { onuSnmpProParam 6 }

		
--          1.3.6.1.4.1.37950.1.1.5.12.8.3.10.7
-- 1.3.6.1.4.1.37950.1.1.5.12.8.3.10.7
-- 1.3.6.1.4.1.37950.1.1.5.12.8.3.10.7
-- 1.3.6.1.4.1.37950.1.1.5.12.8.3.10.7
-- 1.3.6.1.4.1.37950.1.1.5.12.8.3.10.7
-- 1.3.6.1.4.1.37950.1.1.5.12.8.3.10.7
-- 1.3.6.1.4.1.37950.1.1.5.12.8.3.10.7
-- 1.3.6.1.4.1.37950.1.1.5.12.8.3.10.7
-- 1.3.6.1.4.1.37950.1.1.5.12.8.3.10.7
		-- 1.3.6.1.4.1.37950.1.1.5.12.8.3.10.7
		ctcSnmpAction OBJECT-TYPE
			SYNTAX INTEGER
				{
				add(1),
				remove(2)
				}
			MAX-ACCESS read-write
			STATUS current
			DESCRIPTION
				"Description."
			::= { onuSnmpProParam 7 }

		
--          1.3.6.1.4.1.37950.1.1.5.12.8.3.11
-- 1.3.6.1.4.1.37950.1.1.5.12.8.3.11
-- 1.3.6.1.4.1.37950.1.1.5.12.8.3.11
-- 1.3.6.1.4.1.37950.1.1.5.12.8.3.11
-- 1.3.6.1.4.1.37950.1.1.5.12.8.3.11
-- 1.3.6.1.4.1.37950.1.1.5.12.8.3.11
-- 1.3.6.1.4.1.37950.1.1.5.12.8.3.11
-- 1.3.6.1.4.1.37950.1.1.5.12.8.3.11
-- 1.3.6.1.4.1.37950.1.1.5.12.8.3.11
		-- 1.3.6.1.4.1.37950.1.1.5.12.8.3.11
		onuSlaConfig OBJECT IDENTIFIER ::= { srvProfileEdit 11 }

		
--          1.3.6.1.4.1.37950.1.1.5.12.8.3.11.1
-- 1.3.6.1.4.1.37950.1.1.5.12.8.3.11.1
-- 1.3.6.1.4.1.37950.1.1.5.12.8.3.11.1
-- 1.3.6.1.4.1.37950.1.1.5.12.8.3.11.1
-- 1.3.6.1.4.1.37950.1.1.5.12.8.3.11.1
-- 1.3.6.1.4.1.37950.1.1.5.12.8.3.11.1
-- 1.3.6.1.4.1.37950.1.1.5.12.8.3.11.1
-- 1.3.6.1.4.1.37950.1.1.5.12.8.3.11.1
-- 1.3.6.1.4.1.37950.1.1.5.12.8.3.11.1
		-- 1.3.6.1.4.1.37950.1.1.5.12.8.3.11.1
		ctcSlaEn OBJECT-TYPE
			SYNTAX INTEGER
				{
				disable(0),
				enable(1)
				}
			MAX-ACCESS read-write
			STATUS current
			DESCRIPTION
				"Description."
			::= { onuSlaConfig 1 }

		
--          1.3.6.1.4.1.37950.1.1.5.12.8.3.11.2
-- 1.3.6.1.4.1.37950.1.1.5.12.8.3.11.2
-- 1.3.6.1.4.1.37950.1.1.5.12.8.3.11.2
-- 1.3.6.1.4.1.37950.1.1.5.12.8.3.11.2
-- 1.3.6.1.4.1.37950.1.1.5.12.8.3.11.2
-- 1.3.6.1.4.1.37950.1.1.5.12.8.3.11.2
-- 1.3.6.1.4.1.37950.1.1.5.12.8.3.11.2
-- 1.3.6.1.4.1.37950.1.1.5.12.8.3.11.2
-- 1.3.6.1.4.1.37950.1.1.5.12.8.3.11.2
		-- 1.3.6.1.4.1.37950.1.1.5.12.8.3.11.2
		ctcSlaMode OBJECT-TYPE
			SYNTAX INTEGER
				{
				sp-basic(1),
				wrr(2),
				sp-wrr(3)
				}
			MAX-ACCESS read-write
			STATUS current
			DESCRIPTION
				"Description."
			::= { onuSlaConfig 2 }

		
--          1.3.6.1.4.1.37950.1.1.5.12.8.3.11.3
-- 1.3.6.1.4.1.37950.1.1.5.12.8.3.11.3
-- 1.3.6.1.4.1.37950.1.1.5.12.8.3.11.3
-- 1.3.6.1.4.1.37950.1.1.5.12.8.3.11.3
-- 1.3.6.1.4.1.37950.1.1.5.12.8.3.11.3
-- 1.3.6.1.4.1.37950.1.1.5.12.8.3.11.3
-- 1.3.6.1.4.1.37950.1.1.5.12.8.3.11.3
-- 1.3.6.1.4.1.37950.1.1.5.12.8.3.11.3
-- 1.3.6.1.4.1.37950.1.1.5.12.8.3.11.3
		-- 1.3.6.1.4.1.37950.1.1.5.12.8.3.11.3
		ctcQueueId OBJECT-TYPE
			SYNTAX INTEGER (0..7)
			MAX-ACCESS read-write
			STATUS current
			DESCRIPTION
				"Description."
			::= { onuSlaConfig 3 }

		
--          1.3.6.1.4.1.37950.1.1.5.12.8.3.11.4
-- 1.3.6.1.4.1.37950.1.1.5.12.8.3.11.4
-- 1.3.6.1.4.1.37950.1.1.5.12.8.3.11.4
-- 1.3.6.1.4.1.37950.1.1.5.12.8.3.11.4
-- 1.3.6.1.4.1.37950.1.1.5.12.8.3.11.4
-- 1.3.6.1.4.1.37950.1.1.5.12.8.3.11.4
-- 1.3.6.1.4.1.37950.1.1.5.12.8.3.11.4
-- 1.3.6.1.4.1.37950.1.1.5.12.8.3.11.4
-- 1.3.6.1.4.1.37950.1.1.5.12.8.3.11.4
		-- 1.3.6.1.4.1.37950.1.1.5.12.8.3.11.4
		ctcQueweight OBJECT-TYPE
			SYNTAX INTEGER (0..100)
			MAX-ACCESS read-write
			STATUS current
			DESCRIPTION
				"Description."
			::= { onuSlaConfig 4 }

		
--          1.3.6.1.4.1.37950.1.1.5.12.8.3.11.5
-- 1.3.6.1.4.1.37950.1.1.5.12.8.3.11.5
-- 1.3.6.1.4.1.37950.1.1.5.12.8.3.11.5
-- 1.3.6.1.4.1.37950.1.1.5.12.8.3.11.5
-- 1.3.6.1.4.1.37950.1.1.5.12.8.3.11.5
-- 1.3.6.1.4.1.37950.1.1.5.12.8.3.11.5
-- 1.3.6.1.4.1.37950.1.1.5.12.8.3.11.5
-- 1.3.6.1.4.1.37950.1.1.5.12.8.3.11.5
-- 1.3.6.1.4.1.37950.1.1.5.12.8.3.11.5
		-- 1.3.6.1.4.1.37950.1.1.5.12.8.3.11.5
		ctcGuaranteedBandwidth OBJECT-TYPE
			SYNTAX INTEGER (1..1024)
			MAX-ACCESS read-write
			STATUS current
			DESCRIPTION
				"Description."
			::= { onuSlaConfig 5 }

		
--          1.3.6.1.4.1.37950.1.1.5.12.8.3.11.6
-- 1.3.6.1.4.1.37950.1.1.5.12.8.3.11.6
-- 1.3.6.1.4.1.37950.1.1.5.12.8.3.11.6
-- 1.3.6.1.4.1.37950.1.1.5.12.8.3.11.6
-- 1.3.6.1.4.1.37950.1.1.5.12.8.3.11.6
-- 1.3.6.1.4.1.37950.1.1.5.12.8.3.11.6
-- 1.3.6.1.4.1.37950.1.1.5.12.8.3.11.6
-- 1.3.6.1.4.1.37950.1.1.5.12.8.3.11.6
-- 1.3.6.1.4.1.37950.1.1.5.12.8.3.11.6
		-- 1.3.6.1.4.1.37950.1.1.5.12.8.3.11.6
		ctcBesteffortBandwith OBJECT-TYPE
			SYNTAX INTEGER (1..1024)
			MAX-ACCESS read-write
			STATUS current
			DESCRIPTION
				"Description."
			::= { onuSlaConfig 6 }

		
--          1.3.6.1.4.1.37950.1.1.5.12.8.3.11.7
-- 1.3.6.1.4.1.37950.1.1.5.12.8.3.11.7
-- 1.3.6.1.4.1.37950.1.1.5.12.8.3.11.7
-- 1.3.6.1.4.1.37950.1.1.5.12.8.3.11.7
-- 1.3.6.1.4.1.37950.1.1.5.12.8.3.11.7
-- 1.3.6.1.4.1.37950.1.1.5.12.8.3.11.7
-- 1.3.6.1.4.1.37950.1.1.5.12.8.3.11.7
-- 1.3.6.1.4.1.37950.1.1.5.12.8.3.11.7
-- 1.3.6.1.4.1.37950.1.1.5.12.8.3.11.7
		-- 1.3.6.1.4.1.37950.1.1.5.12.8.3.11.7
		ctcSlaAction OBJECT-TYPE
			SYNTAX INTEGER
				{
				add(1),
				remove(2)
				}
			MAX-ACCESS read-write
			STATUS current
			DESCRIPTION
				"Description."
			::= { onuSlaConfig 7 }

		
--          1.3.6.1.4.1.37950.1.1.5.12.8.3.12
-- 1.3.6.1.4.1.37950.1.1.5.12.8.3.12
-- 1.3.6.1.4.1.37950.1.1.5.12.8.3.12
-- 1.3.6.1.4.1.37950.1.1.5.12.8.3.12
-- 1.3.6.1.4.1.37950.1.1.5.12.8.3.12
-- 1.3.6.1.4.1.37950.1.1.5.12.8.3.12
-- 1.3.6.1.4.1.37950.1.1.5.12.8.3.12
-- 1.3.6.1.4.1.37950.1.1.5.12.8.3.12
-- 1.3.6.1.4.1.37950.1.1.5.12.8.3.12
		-- 1.3.6.1.4.1.37950.1.1.5.12.8.3.12
		onuCtcPause OBJECT IDENTIFIER ::= { srvProfileEdit 12 }

		
--          1.3.6.1.4.1.37950.1.1.5.12.8.3.12.1
-- 1.3.6.1.4.1.37950.1.1.5.12.8.3.12.1
-- 1.3.6.1.4.1.37950.1.1.5.12.8.3.12.1
-- 1.3.6.1.4.1.37950.1.1.5.12.8.3.12.1
-- 1.3.6.1.4.1.37950.1.1.5.12.8.3.12.1
-- 1.3.6.1.4.1.37950.1.1.5.12.8.3.12.1
-- 1.3.6.1.4.1.37950.1.1.5.12.8.3.12.1
-- 1.3.6.1.4.1.37950.1.1.5.12.8.3.12.1
-- 1.3.6.1.4.1.37950.1.1.5.12.8.3.12.1
		-- 1.3.6.1.4.1.37950.1.1.5.12.8.3.12.1
		pauseEthNo OBJECT-TYPE
			SYNTAX INTEGER (1..255)
			MAX-ACCESS read-write
			STATUS current
			DESCRIPTION
				"Description."
			::= { onuCtcPause 1 }

		
--          1.3.6.1.4.1.37950.1.1.5.12.8.3.12.2
-- 1.3.6.1.4.1.37950.1.1.5.12.8.3.12.2
-- 1.3.6.1.4.1.37950.1.1.5.12.8.3.12.2
-- 1.3.6.1.4.1.37950.1.1.5.12.8.3.12.2
-- 1.3.6.1.4.1.37950.1.1.5.12.8.3.12.2
-- 1.3.6.1.4.1.37950.1.1.5.12.8.3.12.2
-- 1.3.6.1.4.1.37950.1.1.5.12.8.3.12.2
-- 1.3.6.1.4.1.37950.1.1.5.12.8.3.12.2
-- 1.3.6.1.4.1.37950.1.1.5.12.8.3.12.2
		-- 1.3.6.1.4.1.37950.1.1.5.12.8.3.12.2
		ctcPauseEn OBJECT-TYPE
			SYNTAX INTEGER
				{
				disable(0),
				enable(1)
				}
			MAX-ACCESS read-write
			STATUS current
			DESCRIPTION
				"Description."
			::= { onuCtcPause 2 }

		
--          1.3.6.1.4.1.37950.1.1.5.12.8.3.12.3
-- 1.3.6.1.4.1.37950.1.1.5.12.8.3.12.3
-- 1.3.6.1.4.1.37950.1.1.5.12.8.3.12.3
-- 1.3.6.1.4.1.37950.1.1.5.12.8.3.12.3
-- 1.3.6.1.4.1.37950.1.1.5.12.8.3.12.3
-- 1.3.6.1.4.1.37950.1.1.5.12.8.3.12.3
-- 1.3.6.1.4.1.37950.1.1.5.12.8.3.12.3
-- 1.3.6.1.4.1.37950.1.1.5.12.8.3.12.3
-- 1.3.6.1.4.1.37950.1.1.5.12.8.3.12.3
		-- 1.3.6.1.4.1.37950.1.1.5.12.8.3.12.3
		ctcPauseAction OBJECT-TYPE
			SYNTAX INTEGER
				{
				add(1),
				remove(2)
				}
			MAX-ACCESS read-write
			STATUS current
			DESCRIPTION
				"Description."
			::= { onuCtcPause 3 }

		
--          1.3.6.1.4.1.37950.1.1.5.12.8.3.13
-- 1.3.6.1.4.1.37950.1.1.5.12.8.3.13
-- 1.3.6.1.4.1.37950.1.1.5.12.8.3.13
-- 1.3.6.1.4.1.37950.1.1.5.12.8.3.13
-- 1.3.6.1.4.1.37950.1.1.5.12.8.3.13
-- 1.3.6.1.4.1.37950.1.1.5.12.8.3.13
-- 1.3.6.1.4.1.37950.1.1.5.12.8.3.13
-- 1.3.6.1.4.1.37950.1.1.5.12.8.3.13
-- 1.3.6.1.4.1.37950.1.1.5.12.8.3.13
		-- 1.3.6.1.4.1.37950.1.1.5.12.8.3.13
		onuCtcLoopdetect OBJECT IDENTIFIER ::= { srvProfileEdit 13 }

		
--          1.3.6.1.4.1.37950.1.1.5.12.8.3.13.1
-- 1.3.6.1.4.1.37950.1.1.5.12.8.3.13.1
-- 1.3.6.1.4.1.37950.1.1.5.12.8.3.13.1
-- 1.3.6.1.4.1.37950.1.1.5.12.8.3.13.1
-- 1.3.6.1.4.1.37950.1.1.5.12.8.3.13.1
-- 1.3.6.1.4.1.37950.1.1.5.12.8.3.13.1
-- 1.3.6.1.4.1.37950.1.1.5.12.8.3.13.1
-- 1.3.6.1.4.1.37950.1.1.5.12.8.3.13.1
-- 1.3.6.1.4.1.37950.1.1.5.12.8.3.13.1
		-- 1.3.6.1.4.1.37950.1.1.5.12.8.3.13.1
		loopEthNo OBJECT-TYPE
			SYNTAX INTEGER (1..255)
			MAX-ACCESS read-write
			STATUS current
			DESCRIPTION
				"Description."
			::= { onuCtcLoopdetect 1 }

		
--          1.3.6.1.4.1.37950.1.1.5.12.8.3.13.2
-- 1.3.6.1.4.1.37950.1.1.5.12.8.3.13.2
-- 1.3.6.1.4.1.37950.1.1.5.12.8.3.13.2
-- 1.3.6.1.4.1.37950.1.1.5.12.8.3.13.2
-- 1.3.6.1.4.1.37950.1.1.5.12.8.3.13.2
-- 1.3.6.1.4.1.37950.1.1.5.12.8.3.13.2
-- 1.3.6.1.4.1.37950.1.1.5.12.8.3.13.2
-- 1.3.6.1.4.1.37950.1.1.5.12.8.3.13.2
-- 1.3.6.1.4.1.37950.1.1.5.12.8.3.13.2
		-- 1.3.6.1.4.1.37950.1.1.5.12.8.3.13.2
		ctcLoopdetectEn OBJECT-TYPE
			SYNTAX INTEGER
				{
				disable(0),
				enable(1)
				}
			MAX-ACCESS read-write
			STATUS current
			DESCRIPTION
				"Description."
			::= { onuCtcLoopdetect 2 }

		
--          1.3.6.1.4.1.37950.1.1.5.12.8.3.13.3
-- 1.3.6.1.4.1.37950.1.1.5.12.8.3.13.3
-- 1.3.6.1.4.1.37950.1.1.5.12.8.3.13.3
-- 1.3.6.1.4.1.37950.1.1.5.12.8.3.13.3
-- 1.3.6.1.4.1.37950.1.1.5.12.8.3.13.3
-- 1.3.6.1.4.1.37950.1.1.5.12.8.3.13.3
-- 1.3.6.1.4.1.37950.1.1.5.12.8.3.13.3
-- 1.3.6.1.4.1.37950.1.1.5.12.8.3.13.3
-- 1.3.6.1.4.1.37950.1.1.5.12.8.3.13.3
		-- 1.3.6.1.4.1.37950.1.1.5.12.8.3.13.3
		ctcLoopdetectAction OBJECT-TYPE
			SYNTAX INTEGER
				{
				add(1),
				remove(2)
				}
			MAX-ACCESS read-write
			STATUS current
			DESCRIPTION
				"Description."
			::= { onuCtcLoopdetect 3 }

		
--          1.3.6.1.4.1.37950.1.1.5.12.8.3.14
-- 1.3.6.1.4.1.37950.1.1.5.12.8.3.14
-- 1.3.6.1.4.1.37950.1.1.5.12.8.3.14
-- 1.3.6.1.4.1.37950.1.1.5.12.8.3.14
-- 1.3.6.1.4.1.37950.1.1.5.12.8.3.14
-- 1.3.6.1.4.1.37950.1.1.5.12.8.3.14
-- 1.3.6.1.4.1.37950.1.1.5.12.8.3.14
-- 1.3.6.1.4.1.37950.1.1.5.12.8.3.14
-- 1.3.6.1.4.1.37950.1.1.5.12.8.3.14
		-- 1.3.6.1.4.1.37950.1.1.5.12.8.3.14
		onuMcTagstrip OBJECT IDENTIFIER ::= { srvProfileEdit 14 }

		
--          1.3.6.1.4.1.37950.1.1.5.12.8.3.14.1
-- 1.3.6.1.4.1.37950.1.1.5.12.8.3.14.1
-- 1.3.6.1.4.1.37950.1.1.5.12.8.3.14.1
-- 1.3.6.1.4.1.37950.1.1.5.12.8.3.14.1
-- 1.3.6.1.4.1.37950.1.1.5.12.8.3.14.1
-- 1.3.6.1.4.1.37950.1.1.5.12.8.3.14.1
-- 1.3.6.1.4.1.37950.1.1.5.12.8.3.14.1
-- 1.3.6.1.4.1.37950.1.1.5.12.8.3.14.1
-- 1.3.6.1.4.1.37950.1.1.5.12.8.3.14.1
		-- 1.3.6.1.4.1.37950.1.1.5.12.8.3.14.1
		tagstripEthNo OBJECT-TYPE
			SYNTAX INTEGER (1..255)
			MAX-ACCESS read-write
			STATUS current
			DESCRIPTION
				"Description."
			::= { onuMcTagstrip 1 }

		
--          1.3.6.1.4.1.37950.1.1.5.12.8.3.14.2
-- 1.3.6.1.4.1.37950.1.1.5.12.8.3.14.2
-- 1.3.6.1.4.1.37950.1.1.5.12.8.3.14.2
-- 1.3.6.1.4.1.37950.1.1.5.12.8.3.14.2
-- 1.3.6.1.4.1.37950.1.1.5.12.8.3.14.2
-- 1.3.6.1.4.1.37950.1.1.5.12.8.3.14.2
-- 1.3.6.1.4.1.37950.1.1.5.12.8.3.14.2
-- 1.3.6.1.4.1.37950.1.1.5.12.8.3.14.2
-- 1.3.6.1.4.1.37950.1.1.5.12.8.3.14.2
		-- 1.3.6.1.4.1.37950.1.1.5.12.8.3.14.2
		ctcTagstripEn OBJECT-TYPE
			SYNTAX INTEGER
				{
				disable(0),
				enable(1)
				}
			MAX-ACCESS read-write
			STATUS current
			DESCRIPTION
				"Description."
			::= { onuMcTagstrip 2 }

		
--          1.3.6.1.4.1.37950.1.1.5.12.8.3.14.3
-- 1.3.6.1.4.1.37950.1.1.5.12.8.3.14.3
-- 1.3.6.1.4.1.37950.1.1.5.12.8.3.14.3
-- 1.3.6.1.4.1.37950.1.1.5.12.8.3.14.3
-- 1.3.6.1.4.1.37950.1.1.5.12.8.3.14.3
-- 1.3.6.1.4.1.37950.1.1.5.12.8.3.14.3
-- 1.3.6.1.4.1.37950.1.1.5.12.8.3.14.3
-- 1.3.6.1.4.1.37950.1.1.5.12.8.3.14.3
-- 1.3.6.1.4.1.37950.1.1.5.12.8.3.14.3
		-- 1.3.6.1.4.1.37950.1.1.5.12.8.3.14.3
		tagstripAction OBJECT-TYPE
			SYNTAX INTEGER
				{
				add(1),
				remove(2)
				}
			MAX-ACCESS read-write
			STATUS current
			DESCRIPTION
				"Description."
			::= { onuMcTagstrip 3 }

		
--          1.3.6.1.4.1.37950.1.1.5.12.8.3.15
-- 1.3.6.1.4.1.37950.1.1.5.12.8.3.15
-- 1.3.6.1.4.1.37950.1.1.5.12.8.3.15
-- 1.3.6.1.4.1.37950.1.1.5.12.8.3.15
-- 1.3.6.1.4.1.37950.1.1.5.12.8.3.15
-- 1.3.6.1.4.1.37950.1.1.5.12.8.3.15
-- 1.3.6.1.4.1.37950.1.1.5.12.8.3.15
-- 1.3.6.1.4.1.37950.1.1.5.12.8.3.15
-- 1.3.6.1.4.1.37950.1.1.5.12.8.3.15
		-- 1.3.6.1.4.1.37950.1.1.5.12.8.3.15
		onuMcVlanTrans OBJECT IDENTIFIER ::= { srvProfileEdit 15 }

		
--          1.3.6.1.4.1.37950.1.1.5.12.8.3.15.1
-- 1.3.6.1.4.1.37950.1.1.5.12.8.3.15.1
-- 1.3.6.1.4.1.37950.1.1.5.12.8.3.15.1
-- 1.3.6.1.4.1.37950.1.1.5.12.8.3.15.1
-- 1.3.6.1.4.1.37950.1.1.5.12.8.3.15.1
-- 1.3.6.1.4.1.37950.1.1.5.12.8.3.15.1
-- 1.3.6.1.4.1.37950.1.1.5.12.8.3.15.1
-- 1.3.6.1.4.1.37950.1.1.5.12.8.3.15.1
-- 1.3.6.1.4.1.37950.1.1.5.12.8.3.15.1
		-- 1.3.6.1.4.1.37950.1.1.5.12.8.3.15.1
		mcVlanTransEthNo OBJECT-TYPE
			SYNTAX INTEGER (1..255)
			MAX-ACCESS read-write
			STATUS current
			DESCRIPTION
				"Description."
			::= { onuMcVlanTrans 1 }

		
--          1.3.6.1.4.1.37950.1.1.5.12.8.3.15.2
-- 1.3.6.1.4.1.37950.1.1.5.12.8.3.15.2
-- 1.3.6.1.4.1.37950.1.1.5.12.8.3.15.2
-- 1.3.6.1.4.1.37950.1.1.5.12.8.3.15.2
-- 1.3.6.1.4.1.37950.1.1.5.12.8.3.15.2
-- 1.3.6.1.4.1.37950.1.1.5.12.8.3.15.2
-- 1.3.6.1.4.1.37950.1.1.5.12.8.3.15.2
-- 1.3.6.1.4.1.37950.1.1.5.12.8.3.15.2
-- 1.3.6.1.4.1.37950.1.1.5.12.8.3.15.2
		-- 1.3.6.1.4.1.37950.1.1.5.12.8.3.15.2
		ctcMcTransVlanStr OBJECT-TYPE
			SYNTAX OCTET STRING
			MAX-ACCESS read-write
			STATUS current
			DESCRIPTION
				"Description."
			::= { onuMcVlanTrans 2 }

		
--          1.3.6.1.4.1.37950.1.1.5.12.8.3.15.10
-- 1.3.6.1.4.1.37950.1.1.5.12.8.3.15.10
-- 1.3.6.1.4.1.37950.1.1.5.12.8.3.15.10
-- 1.3.6.1.4.1.37950.1.1.5.12.8.3.15.10
-- 1.3.6.1.4.1.37950.1.1.5.12.8.3.15.10
-- 1.3.6.1.4.1.37950.1.1.5.12.8.3.15.10
-- 1.3.6.1.4.1.37950.1.1.5.12.8.3.15.10
-- 1.3.6.1.4.1.37950.1.1.5.12.8.3.15.10
-- 1.3.6.1.4.1.37950.1.1.5.12.8.3.15.10
		-- 1.3.6.1.4.1.37950.1.1.5.12.8.3.15.10
		ctcMcTransAction OBJECT-TYPE
			SYNTAX INTEGER
				{
				add(1),
				remove(2)
				}
			MAX-ACCESS read-write
			STATUS current
			DESCRIPTION
				"Description."
			::= { onuMcVlanTrans 10 }

		
--          1.3.6.1.4.1.37950.1.1.5.12.8.3.16
-- 1.3.6.1.4.1.37950.1.1.5.12.8.3.16
-- 1.3.6.1.4.1.37950.1.1.5.12.8.3.16
-- 1.3.6.1.4.1.37950.1.1.5.12.8.3.16
-- 1.3.6.1.4.1.37950.1.1.5.12.8.3.16
-- 1.3.6.1.4.1.37950.1.1.5.12.8.3.16
-- 1.3.6.1.4.1.37950.1.1.5.12.8.3.16
-- 1.3.6.1.4.1.37950.1.1.5.12.8.3.16
-- 1.3.6.1.4.1.37950.1.1.5.12.8.3.16
		-- 1.3.6.1.4.1.37950.1.1.5.12.8.3.16
		onuPortPhyAdmin OBJECT IDENTIFIER ::= { srvProfileEdit 16 }

		
--          1.3.6.1.4.1.37950.1.1.5.12.8.3.16.1
-- 1.3.6.1.4.1.37950.1.1.5.12.8.3.16.1
-- 1.3.6.1.4.1.37950.1.1.5.12.8.3.16.1
-- 1.3.6.1.4.1.37950.1.1.5.12.8.3.16.1
-- 1.3.6.1.4.1.37950.1.1.5.12.8.3.16.1
-- 1.3.6.1.4.1.37950.1.1.5.12.8.3.16.1
-- 1.3.6.1.4.1.37950.1.1.5.12.8.3.16.1
-- 1.3.6.1.4.1.37950.1.1.5.12.8.3.16.1
-- 1.3.6.1.4.1.37950.1.1.5.12.8.3.16.1
		-- 1.3.6.1.4.1.37950.1.1.5.12.8.3.16.1
		adminEthNo OBJECT-TYPE
			SYNTAX INTEGER (1..255)
			MAX-ACCESS read-write
			STATUS current
			DESCRIPTION
				"Description."
			::= { onuPortPhyAdmin 1 }

		
--          1.3.6.1.4.1.37950.1.1.5.12.8.3.16.2
-- 1.3.6.1.4.1.37950.1.1.5.12.8.3.16.2
-- 1.3.6.1.4.1.37950.1.1.5.12.8.3.16.2
-- 1.3.6.1.4.1.37950.1.1.5.12.8.3.16.2
-- 1.3.6.1.4.1.37950.1.1.5.12.8.3.16.2
-- 1.3.6.1.4.1.37950.1.1.5.12.8.3.16.2
-- 1.3.6.1.4.1.37950.1.1.5.12.8.3.16.2
-- 1.3.6.1.4.1.37950.1.1.5.12.8.3.16.2
-- 1.3.6.1.4.1.37950.1.1.5.12.8.3.16.2
		-- 1.3.6.1.4.1.37950.1.1.5.12.8.3.16.2
		ctcPortAdmin OBJECT-TYPE
			SYNTAX INTEGER
				{
				disable(0),
				enable(1)
				}
			MAX-ACCESS read-write
			STATUS current
			DESCRIPTION
				"Description."
			::= { onuPortPhyAdmin 2 }

		
--          1.3.6.1.4.1.37950.1.1.5.12.8.3.16.3
-- 1.3.6.1.4.1.37950.1.1.5.12.8.3.16.3
-- 1.3.6.1.4.1.37950.1.1.5.12.8.3.16.3
-- 1.3.6.1.4.1.37950.1.1.5.12.8.3.16.3
-- 1.3.6.1.4.1.37950.1.1.5.12.8.3.16.3
-- 1.3.6.1.4.1.37950.1.1.5.12.8.3.16.3
-- 1.3.6.1.4.1.37950.1.1.5.12.8.3.16.3
-- 1.3.6.1.4.1.37950.1.1.5.12.8.3.16.3
-- 1.3.6.1.4.1.37950.1.1.5.12.8.3.16.3
		-- 1.3.6.1.4.1.37950.1.1.5.12.8.3.16.3
		ctcPortAdminAction OBJECT-TYPE
			SYNTAX INTEGER
				{
				commit(1),
				remove(2)
				}
			MAX-ACCESS read-write
			STATUS current
			DESCRIPTION
				"Description."
			::= { onuPortPhyAdmin 3 }

		
--          1.3.6.1.4.1.37950.1.1.5.12.8.3.17
-- 1.3.6.1.4.1.37950.1.1.5.12.8.3.17
-- 1.3.6.1.4.1.37950.1.1.5.12.8.3.17
-- 1.3.6.1.4.1.37950.1.1.5.12.8.3.17
-- 1.3.6.1.4.1.37950.1.1.5.12.8.3.17
-- 1.3.6.1.4.1.37950.1.1.5.12.8.3.17
-- 1.3.6.1.4.1.37950.1.1.5.12.8.3.17
-- 1.3.6.1.4.1.37950.1.1.5.12.8.3.17
-- 1.3.6.1.4.1.37950.1.1.5.12.8.3.17
		-- 1.3.6.1.4.1.37950.1.1.5.12.8.3.17
		onuPortAutoNegConfig OBJECT IDENTIFIER ::= { srvProfileEdit 17 }

		
--          1.3.6.1.4.1.37950.1.1.5.12.8.3.17.1
-- 1.3.6.1.4.1.37950.1.1.5.12.8.3.17.1
-- 1.3.6.1.4.1.37950.1.1.5.12.8.3.17.1
-- 1.3.6.1.4.1.37950.1.1.5.12.8.3.17.1
-- 1.3.6.1.4.1.37950.1.1.5.12.8.3.17.1
-- 1.3.6.1.4.1.37950.1.1.5.12.8.3.17.1
-- 1.3.6.1.4.1.37950.1.1.5.12.8.3.17.1
-- 1.3.6.1.4.1.37950.1.1.5.12.8.3.17.1
-- 1.3.6.1.4.1.37950.1.1.5.12.8.3.17.1
		-- 1.3.6.1.4.1.37950.1.1.5.12.8.3.17.1
		autoNegEthNo OBJECT-TYPE
			SYNTAX INTEGER (1..255)
			MAX-ACCESS read-write
			STATUS current
			DESCRIPTION
				"Description."
			::= { onuPortAutoNegConfig 1 }

		
--          1.3.6.1.4.1.37950.1.1.5.12.8.3.17.2
-- 1.3.6.1.4.1.37950.1.1.5.12.8.3.17.2
-- 1.3.6.1.4.1.37950.1.1.5.12.8.3.17.2
-- 1.3.6.1.4.1.37950.1.1.5.12.8.3.17.2
-- 1.3.6.1.4.1.37950.1.1.5.12.8.3.17.2
-- 1.3.6.1.4.1.37950.1.1.5.12.8.3.17.2
-- 1.3.6.1.4.1.37950.1.1.5.12.8.3.17.2
-- 1.3.6.1.4.1.37950.1.1.5.12.8.3.17.2
-- 1.3.6.1.4.1.37950.1.1.5.12.8.3.17.2
		-- 1.3.6.1.4.1.37950.1.1.5.12.8.3.17.2
		ctcAutoNeg OBJECT-TYPE
			SYNTAX INTEGER
				{
				disable(0),
				enable(1)
				}
			MAX-ACCESS read-write
			STATUS current
			DESCRIPTION
				"Description."
			::= { onuPortAutoNegConfig 2 }

		
--          1.3.6.1.4.1.37950.1.1.5.12.8.3.17.3
-- 1.3.6.1.4.1.37950.1.1.5.12.8.3.17.3
-- 1.3.6.1.4.1.37950.1.1.5.12.8.3.17.3
-- 1.3.6.1.4.1.37950.1.1.5.12.8.3.17.3
-- 1.3.6.1.4.1.37950.1.1.5.12.8.3.17.3
-- 1.3.6.1.4.1.37950.1.1.5.12.8.3.17.3
-- 1.3.6.1.4.1.37950.1.1.5.12.8.3.17.3
-- 1.3.6.1.4.1.37950.1.1.5.12.8.3.17.3
-- 1.3.6.1.4.1.37950.1.1.5.12.8.3.17.3
		-- 1.3.6.1.4.1.37950.1.1.5.12.8.3.17.3
		ctcAutoNegAction OBJECT-TYPE
			SYNTAX INTEGER
				{
				commit(1),
				remove(2)
				}
			MAX-ACCESS read-write
			STATUS current
			DESCRIPTION
				"Description."
			::= { onuPortAutoNegConfig 3 }

		
--          1.3.6.1.4.1.37950.1.1.5.12.8.3.18
-- 1.3.6.1.4.1.37950.1.1.5.12.8.3.18
-- 1.3.6.1.4.1.37950.1.1.5.12.8.3.18
-- 1.3.6.1.4.1.37950.1.1.5.12.8.3.18
-- 1.3.6.1.4.1.37950.1.1.5.12.8.3.18
-- 1.3.6.1.4.1.37950.1.1.5.12.8.3.18
-- 1.3.6.1.4.1.37950.1.1.5.12.8.3.18
-- 1.3.6.1.4.1.37950.1.1.5.12.8.3.18
-- 1.3.6.1.4.1.37950.1.1.5.12.8.3.18
		-- 1.3.6.1.4.1.37950.1.1.5.12.8.3.18
		onuPortMaxIgmpGrp OBJECT IDENTIFIER ::= { srvProfileEdit 18 }

		
--          1.3.6.1.4.1.37950.1.1.5.12.8.3.18.1
-- 1.3.6.1.4.1.37950.1.1.5.12.8.3.18.1
-- 1.3.6.1.4.1.37950.1.1.5.12.8.3.18.1
-- 1.3.6.1.4.1.37950.1.1.5.12.8.3.18.1
-- 1.3.6.1.4.1.37950.1.1.5.12.8.3.18.1
-- 1.3.6.1.4.1.37950.1.1.5.12.8.3.18.1
-- 1.3.6.1.4.1.37950.1.1.5.12.8.3.18.1
-- 1.3.6.1.4.1.37950.1.1.5.12.8.3.18.1
-- 1.3.6.1.4.1.37950.1.1.5.12.8.3.18.1
		-- 1.3.6.1.4.1.37950.1.1.5.12.8.3.18.1
		grpEthNo OBJECT-TYPE
			SYNTAX INTEGER (1..255)
			MAX-ACCESS read-write
			STATUS current
			DESCRIPTION
				"Description."
			::= { onuPortMaxIgmpGrp 1 }

		
--          1.3.6.1.4.1.37950.1.1.5.12.8.3.18.2
-- 1.3.6.1.4.1.37950.1.1.5.12.8.3.18.2
-- 1.3.6.1.4.1.37950.1.1.5.12.8.3.18.2
-- 1.3.6.1.4.1.37950.1.1.5.12.8.3.18.2
-- 1.3.6.1.4.1.37950.1.1.5.12.8.3.18.2
-- 1.3.6.1.4.1.37950.1.1.5.12.8.3.18.2
-- 1.3.6.1.4.1.37950.1.1.5.12.8.3.18.2
-- 1.3.6.1.4.1.37950.1.1.5.12.8.3.18.2
-- 1.3.6.1.4.1.37950.1.1.5.12.8.3.18.2
		-- 1.3.6.1.4.1.37950.1.1.5.12.8.3.18.2
		ctcMcMaxGrp OBJECT-TYPE
			SYNTAX INTEGER (1..255)
			MAX-ACCESS read-write
			STATUS current
			DESCRIPTION
				"Description."
			::= { onuPortMaxIgmpGrp 2 }

		
--          1.3.6.1.4.1.37950.1.1.5.12.8.3.18.3
-- 1.3.6.1.4.1.37950.1.1.5.12.8.3.18.3
-- 1.3.6.1.4.1.37950.1.1.5.12.8.3.18.3
-- 1.3.6.1.4.1.37950.1.1.5.12.8.3.18.3
-- 1.3.6.1.4.1.37950.1.1.5.12.8.3.18.3
-- 1.3.6.1.4.1.37950.1.1.5.12.8.3.18.3
-- 1.3.6.1.4.1.37950.1.1.5.12.8.3.18.3
-- 1.3.6.1.4.1.37950.1.1.5.12.8.3.18.3
-- 1.3.6.1.4.1.37950.1.1.5.12.8.3.18.3
		-- 1.3.6.1.4.1.37950.1.1.5.12.8.3.18.3
		mcMaxGrpAction OBJECT-TYPE
			SYNTAX INTEGER
				{
				commit(1),
				remove(2)
				}
			MAX-ACCESS read-write
			STATUS current
			DESCRIPTION
				"Description."
			::= { onuPortMaxIgmpGrp 3 }

		
--          1.3.6.1.4.1.37950.1.1.5.12.8.3.19
-- 1.3.6.1.4.1.37950.1.1.5.12.8.3.19
-- 1.3.6.1.4.1.37950.1.1.5.12.8.3.19
-- 1.3.6.1.4.1.37950.1.1.5.12.8.3.19
-- 1.3.6.1.4.1.37950.1.1.5.12.8.3.19
-- 1.3.6.1.4.1.37950.1.1.5.12.8.3.19
-- 1.3.6.1.4.1.37950.1.1.5.12.8.3.19
-- 1.3.6.1.4.1.37950.1.1.5.12.8.3.19
-- 1.3.6.1.4.1.37950.1.1.5.12.8.3.19
		-- 1.3.6.1.4.1.37950.1.1.5.12.8.3.19
		onuPortUpLimit OBJECT IDENTIFIER ::= { srvProfileEdit 19 }

		
--          1.3.6.1.4.1.37950.1.1.5.12.8.3.19.1
-- 1.3.6.1.4.1.37950.1.1.5.12.8.3.19.1
-- 1.3.6.1.4.1.37950.1.1.5.12.8.3.19.1
-- 1.3.6.1.4.1.37950.1.1.5.12.8.3.19.1
-- 1.3.6.1.4.1.37950.1.1.5.12.8.3.19.1
-- 1.3.6.1.4.1.37950.1.1.5.12.8.3.19.1
-- 1.3.6.1.4.1.37950.1.1.5.12.8.3.19.1
-- 1.3.6.1.4.1.37950.1.1.5.12.8.3.19.1
-- 1.3.6.1.4.1.37950.1.1.5.12.8.3.19.1
		-- 1.3.6.1.4.1.37950.1.1.5.12.8.3.19.1
		upLimitEthNo OBJECT-TYPE
			SYNTAX INTEGER (1..255)
			MAX-ACCESS read-write
			STATUS current
			DESCRIPTION
				"Description."
			::= { onuPortUpLimit 1 }

		
--          1.3.6.1.4.1.37950.1.1.5.12.8.3.19.2
-- 1.3.6.1.4.1.37950.1.1.5.12.8.3.19.2
-- 1.3.6.1.4.1.37950.1.1.5.12.8.3.19.2
-- 1.3.6.1.4.1.37950.1.1.5.12.8.3.19.2
-- 1.3.6.1.4.1.37950.1.1.5.12.8.3.19.2
-- 1.3.6.1.4.1.37950.1.1.5.12.8.3.19.2
-- 1.3.6.1.4.1.37950.1.1.5.12.8.3.19.2
-- 1.3.6.1.4.1.37950.1.1.5.12.8.3.19.2
-- 1.3.6.1.4.1.37950.1.1.5.12.8.3.19.2
		-- 1.3.6.1.4.1.37950.1.1.5.12.8.3.19.2
		ctcUpLimitCir OBJECT-TYPE
			SYNTAX INTEGER (0..1048576)
			MAX-ACCESS read-write
			STATUS current
			DESCRIPTION
				"Description."
			::= { onuPortUpLimit 2 }

		
--          1.3.6.1.4.1.37950.1.1.5.12.8.3.19.3
-- 1.3.6.1.4.1.37950.1.1.5.12.8.3.19.3
-- 1.3.6.1.4.1.37950.1.1.5.12.8.3.19.3
-- 1.3.6.1.4.1.37950.1.1.5.12.8.3.19.3
-- 1.3.6.1.4.1.37950.1.1.5.12.8.3.19.3
-- 1.3.6.1.4.1.37950.1.1.5.12.8.3.19.3
-- 1.3.6.1.4.1.37950.1.1.5.12.8.3.19.3
-- 1.3.6.1.4.1.37950.1.1.5.12.8.3.19.3
-- 1.3.6.1.4.1.37950.1.1.5.12.8.3.19.3
		-- 1.3.6.1.4.1.37950.1.1.5.12.8.3.19.3
		ctcUpLimitCbs OBJECT-TYPE
			SYNTAX INTEGER (1..10240)
			MAX-ACCESS read-write
			STATUS current
			DESCRIPTION
				"Description."
			::= { onuPortUpLimit 3 }

		
--          1.3.6.1.4.1.37950.1.1.5.12.8.3.19.4
-- 1.3.6.1.4.1.37950.1.1.5.12.8.3.19.4
-- 1.3.6.1.4.1.37950.1.1.5.12.8.3.19.4
-- 1.3.6.1.4.1.37950.1.1.5.12.8.3.19.4
-- 1.3.6.1.4.1.37950.1.1.5.12.8.3.19.4
-- 1.3.6.1.4.1.37950.1.1.5.12.8.3.19.4
-- 1.3.6.1.4.1.37950.1.1.5.12.8.3.19.4
-- 1.3.6.1.4.1.37950.1.1.5.12.8.3.19.4
-- 1.3.6.1.4.1.37950.1.1.5.12.8.3.19.4
		-- 1.3.6.1.4.1.37950.1.1.5.12.8.3.19.4
		ctcUpLimitEbs OBJECT-TYPE
			SYNTAX INTEGER (1..10240)
			MAX-ACCESS read-write
			STATUS current
			DESCRIPTION
				"Description."
			::= { onuPortUpLimit 4 }

		
--          1.3.6.1.4.1.37950.1.1.5.12.8.3.19.5
-- 1.3.6.1.4.1.37950.1.1.5.12.8.3.19.5
-- 1.3.6.1.4.1.37950.1.1.5.12.8.3.19.5
-- 1.3.6.1.4.1.37950.1.1.5.12.8.3.19.5
-- 1.3.6.1.4.1.37950.1.1.5.12.8.3.19.5
-- 1.3.6.1.4.1.37950.1.1.5.12.8.3.19.5
-- 1.3.6.1.4.1.37950.1.1.5.12.8.3.19.5
-- 1.3.6.1.4.1.37950.1.1.5.12.8.3.19.5
-- 1.3.6.1.4.1.37950.1.1.5.12.8.3.19.5
		-- 1.3.6.1.4.1.37950.1.1.5.12.8.3.19.5
		ctcUpLimitAction OBJECT-TYPE
			SYNTAX INTEGER
				{
				commit(1),
				delete(2)
				}
			MAX-ACCESS read-write
			STATUS current
			DESCRIPTION
				"Description."
			::= { onuPortUpLimit 5 }

		
--          1.3.6.1.4.1.37950.1.1.5.12.8.3.20
-- 1.3.6.1.4.1.37950.1.1.5.12.8.3.20
-- 1.3.6.1.4.1.37950.1.1.5.12.8.3.20
-- 1.3.6.1.4.1.37950.1.1.5.12.8.3.20
-- 1.3.6.1.4.1.37950.1.1.5.12.8.3.20
-- 1.3.6.1.4.1.37950.1.1.5.12.8.3.20
-- 1.3.6.1.4.1.37950.1.1.5.12.8.3.20
-- 1.3.6.1.4.1.37950.1.1.5.12.8.3.20
-- 1.3.6.1.4.1.37950.1.1.5.12.8.3.20
		-- 1.3.6.1.4.1.37950.1.1.5.12.8.3.20
		onuPortDownLimit OBJECT IDENTIFIER ::= { srvProfileEdit 20 }

		
--          1.3.6.1.4.1.37950.1.1.5.12.8.3.20.1
-- 1.3.6.1.4.1.37950.1.1.5.12.8.3.20.1
-- 1.3.6.1.4.1.37950.1.1.5.12.8.3.20.1
-- 1.3.6.1.4.1.37950.1.1.5.12.8.3.20.1
-- 1.3.6.1.4.1.37950.1.1.5.12.8.3.20.1
-- 1.3.6.1.4.1.37950.1.1.5.12.8.3.20.1
-- 1.3.6.1.4.1.37950.1.1.5.12.8.3.20.1
-- 1.3.6.1.4.1.37950.1.1.5.12.8.3.20.1
-- 1.3.6.1.4.1.37950.1.1.5.12.8.3.20.1
		-- 1.3.6.1.4.1.37950.1.1.5.12.8.3.20.1
		downLimitEthNo OBJECT-TYPE
			SYNTAX INTEGER (1..255)
			MAX-ACCESS read-write
			STATUS current
			DESCRIPTION
				"Description."
			::= { onuPortDownLimit 1 }

		
--          1.3.6.1.4.1.37950.1.1.5.12.8.3.20.2
-- 1.3.6.1.4.1.37950.1.1.5.12.8.3.20.2
-- 1.3.6.1.4.1.37950.1.1.5.12.8.3.20.2
-- 1.3.6.1.4.1.37950.1.1.5.12.8.3.20.2
-- 1.3.6.1.4.1.37950.1.1.5.12.8.3.20.2
-- 1.3.6.1.4.1.37950.1.1.5.12.8.3.20.2
-- 1.3.6.1.4.1.37950.1.1.5.12.8.3.20.2
-- 1.3.6.1.4.1.37950.1.1.5.12.8.3.20.2
-- 1.3.6.1.4.1.37950.1.1.5.12.8.3.20.2
		-- 1.3.6.1.4.1.37950.1.1.5.12.8.3.20.2
		ctcDownLimitCir OBJECT-TYPE
			SYNTAX INTEGER (0..1048576)
			MAX-ACCESS read-write
			STATUS current
			DESCRIPTION
				"Description."
			::= { onuPortDownLimit 2 }

		
--          1.3.6.1.4.1.37950.1.1.5.12.8.3.20.3
-- 1.3.6.1.4.1.37950.1.1.5.12.8.3.20.3
-- 1.3.6.1.4.1.37950.1.1.5.12.8.3.20.3
-- 1.3.6.1.4.1.37950.1.1.5.12.8.3.20.3
-- 1.3.6.1.4.1.37950.1.1.5.12.8.3.20.3
-- 1.3.6.1.4.1.37950.1.1.5.12.8.3.20.3
-- 1.3.6.1.4.1.37950.1.1.5.12.8.3.20.3
-- 1.3.6.1.4.1.37950.1.1.5.12.8.3.20.3
-- 1.3.6.1.4.1.37950.1.1.5.12.8.3.20.3
		-- 1.3.6.1.4.1.37950.1.1.5.12.8.3.20.3
		ctcDownLimitPir OBJECT-TYPE
			SYNTAX INTEGER (1..1048576)
			MAX-ACCESS read-write
			STATUS current
			DESCRIPTION
				"Description."
			::= { onuPortDownLimit 3 }

		
--          1.3.6.1.4.1.37950.1.1.5.12.8.3.20.4
-- 1.3.6.1.4.1.37950.1.1.5.12.8.3.20.4
-- 1.3.6.1.4.1.37950.1.1.5.12.8.3.20.4
-- 1.3.6.1.4.1.37950.1.1.5.12.8.3.20.4
-- 1.3.6.1.4.1.37950.1.1.5.12.8.3.20.4
-- 1.3.6.1.4.1.37950.1.1.5.12.8.3.20.4
-- 1.3.6.1.4.1.37950.1.1.5.12.8.3.20.4
-- 1.3.6.1.4.1.37950.1.1.5.12.8.3.20.4
-- 1.3.6.1.4.1.37950.1.1.5.12.8.3.20.4
		-- 1.3.6.1.4.1.37950.1.1.5.12.8.3.20.4
		ctcDownLimitAction OBJECT-TYPE
			SYNTAX INTEGER
				{
				commit(1),
				delete(2)
				}
			MAX-ACCESS read-write
			STATUS current
			DESCRIPTION
				"Description."
			::= { onuPortDownLimit 4 }

		
--          1.3.6.1.4.1.37950.1.1.5.12.8.3.21
-- 1.3.6.1.4.1.37950.1.1.5.12.8.3.21
-- 1.3.6.1.4.1.37950.1.1.5.12.8.3.21
-- 1.3.6.1.4.1.37950.1.1.5.12.8.3.21
-- 1.3.6.1.4.1.37950.1.1.5.12.8.3.21
-- 1.3.6.1.4.1.37950.1.1.5.12.8.3.21
-- 1.3.6.1.4.1.37950.1.1.5.12.8.3.21
-- 1.3.6.1.4.1.37950.1.1.5.12.8.3.21
-- 1.3.6.1.4.1.37950.1.1.5.12.8.3.21
		-- 1.3.6.1.4.1.37950.1.1.5.12.8.3.21
		onuPortVlanConfig OBJECT IDENTIFIER ::= { srvProfileEdit 21 }

		
--          1.3.6.1.4.1.37950.1.1.5.12.8.3.21.1
-- 1.3.6.1.4.1.37950.1.1.5.12.8.3.21.1
-- 1.3.6.1.4.1.37950.1.1.5.12.8.3.21.1
-- 1.3.6.1.4.1.37950.1.1.5.12.8.3.21.1
-- 1.3.6.1.4.1.37950.1.1.5.12.8.3.21.1
-- 1.3.6.1.4.1.37950.1.1.5.12.8.3.21.1
-- 1.3.6.1.4.1.37950.1.1.5.12.8.3.21.1
-- 1.3.6.1.4.1.37950.1.1.5.12.8.3.21.1
-- 1.3.6.1.4.1.37950.1.1.5.12.8.3.21.1
		-- 1.3.6.1.4.1.37950.1.1.5.12.8.3.21.1
		portVlanMode OBJECT IDENTIFIER ::= { onuPortVlanConfig 1 }

		
--          1.3.6.1.4.1.37950.1.1.5.12.8.3.21.1.1
-- 1.3.6.1.4.1.37950.1.1.5.12.8.3.21.1.1
-- 1.3.6.1.4.1.37950.1.1.5.12.8.3.21.1.1
-- 1.3.6.1.4.1.37950.1.1.5.12.8.3.21.1.1
-- 1.3.6.1.4.1.37950.1.1.5.12.8.3.21.1.1
-- 1.3.6.1.4.1.37950.1.1.5.12.8.3.21.1.1
-- 1.3.6.1.4.1.37950.1.1.5.12.8.3.21.1.1
-- 1.3.6.1.4.1.37950.1.1.5.12.8.3.21.1.1
-- 1.3.6.1.4.1.37950.1.1.5.12.8.3.21.1.1
		-- 1.3.6.1.4.1.37950.1.1.5.12.8.3.21.1.1
		vlanModeEthNo OBJECT-TYPE
			SYNTAX INTEGER (1..255)
			MAX-ACCESS read-write
			STATUS current
			DESCRIPTION
				"Description."
			::= { portVlanMode 1 }

		
--          1.3.6.1.4.1.37950.1.1.5.12.8.3.21.1.2
-- 1.3.6.1.4.1.37950.1.1.5.12.8.3.21.1.2
-- 1.3.6.1.4.1.37950.1.1.5.12.8.3.21.1.2
-- 1.3.6.1.4.1.37950.1.1.5.12.8.3.21.1.2
-- 1.3.6.1.4.1.37950.1.1.5.12.8.3.21.1.2
-- 1.3.6.1.4.1.37950.1.1.5.12.8.3.21.1.2
-- 1.3.6.1.4.1.37950.1.1.5.12.8.3.21.1.2
-- 1.3.6.1.4.1.37950.1.1.5.12.8.3.21.1.2
-- 1.3.6.1.4.1.37950.1.1.5.12.8.3.21.1.2
		-- 1.3.6.1.4.1.37950.1.1.5.12.8.3.21.1.2
		ctcVlanMode OBJECT-TYPE
			SYNTAX INTEGER
				{
				transparent(1),
				tag(2),
				translation(3),
				aggregation(4),
				trunk(5)
				}
			MAX-ACCESS read-write
			STATUS current
			DESCRIPTION
				"Description."
			::= { portVlanMode 2 }

		
--          1.3.6.1.4.1.37950.1.1.5.12.8.3.21.1.3
-- 1.3.6.1.4.1.37950.1.1.5.12.8.3.21.1.3
-- 1.3.6.1.4.1.37950.1.1.5.12.8.3.21.1.3
-- 1.3.6.1.4.1.37950.1.1.5.12.8.3.21.1.3
-- 1.3.6.1.4.1.37950.1.1.5.12.8.3.21.1.3
-- 1.3.6.1.4.1.37950.1.1.5.12.8.3.21.1.3
-- 1.3.6.1.4.1.37950.1.1.5.12.8.3.21.1.3
-- 1.3.6.1.4.1.37950.1.1.5.12.8.3.21.1.3
-- 1.3.6.1.4.1.37950.1.1.5.12.8.3.21.1.3
		-- 1.3.6.1.4.1.37950.1.1.5.12.8.3.21.1.3
		vlanModeAction OBJECT-TYPE
			SYNTAX INTEGER
				{
				commit(1),
				remove(2)
				}
			MAX-ACCESS read-write
			STATUS current
			DESCRIPTION
				"Description."
			::= { portVlanMode 3 }

		
--          1.3.6.1.4.1.37950.1.1.5.12.8.3.21.2
-- 1.3.6.1.4.1.37950.1.1.5.12.8.3.21.2
-- 1.3.6.1.4.1.37950.1.1.5.12.8.3.21.2
-- 1.3.6.1.4.1.37950.1.1.5.12.8.3.21.2
-- 1.3.6.1.4.1.37950.1.1.5.12.8.3.21.2
-- 1.3.6.1.4.1.37950.1.1.5.12.8.3.21.2
-- 1.3.6.1.4.1.37950.1.1.5.12.8.3.21.2
-- 1.3.6.1.4.1.37950.1.1.5.12.8.3.21.2
-- 1.3.6.1.4.1.37950.1.1.5.12.8.3.21.2
		-- 1.3.6.1.4.1.37950.1.1.5.12.8.3.21.2
		portVlanPvid OBJECT IDENTIFIER ::= { onuPortVlanConfig 2 }

		
--          1.3.6.1.4.1.37950.1.1.5.12.8.3.21.2.1
-- 1.3.6.1.4.1.37950.1.1.5.12.8.3.21.2.1
-- 1.3.6.1.4.1.37950.1.1.5.12.8.3.21.2.1
-- 1.3.6.1.4.1.37950.1.1.5.12.8.3.21.2.1
-- 1.3.6.1.4.1.37950.1.1.5.12.8.3.21.2.1
-- 1.3.6.1.4.1.37950.1.1.5.12.8.3.21.2.1
-- 1.3.6.1.4.1.37950.1.1.5.12.8.3.21.2.1
-- 1.3.6.1.4.1.37950.1.1.5.12.8.3.21.2.1
-- 1.3.6.1.4.1.37950.1.1.5.12.8.3.21.2.1
		-- 1.3.6.1.4.1.37950.1.1.5.12.8.3.21.2.1
		pvidEthNo OBJECT-TYPE
			SYNTAX INTEGER (1..255)
			MAX-ACCESS read-write
			STATUS current
			DESCRIPTION
				"Description."
			::= { portVlanPvid 1 }

		
--          1.3.6.1.4.1.37950.1.1.5.12.8.3.21.2.2
-- 1.3.6.1.4.1.37950.1.1.5.12.8.3.21.2.2
-- 1.3.6.1.4.1.37950.1.1.5.12.8.3.21.2.2
-- 1.3.6.1.4.1.37950.1.1.5.12.8.3.21.2.2
-- 1.3.6.1.4.1.37950.1.1.5.12.8.3.21.2.2
-- 1.3.6.1.4.1.37950.1.1.5.12.8.3.21.2.2
-- 1.3.6.1.4.1.37950.1.1.5.12.8.3.21.2.2
-- 1.3.6.1.4.1.37950.1.1.5.12.8.3.21.2.2
-- 1.3.6.1.4.1.37950.1.1.5.12.8.3.21.2.2
		-- 1.3.6.1.4.1.37950.1.1.5.12.8.3.21.2.2
		ctcPvidVal OBJECT-TYPE
			SYNTAX INTEGER (1..4095)
			MAX-ACCESS read-write
			STATUS current
			DESCRIPTION
				"Description."
			::= { portVlanPvid 2 }

		
--          1.3.6.1.4.1.37950.1.1.5.12.8.3.21.2.3
-- 1.3.6.1.4.1.37950.1.1.5.12.8.3.21.2.3
-- 1.3.6.1.4.1.37950.1.1.5.12.8.3.21.2.3
-- 1.3.6.1.4.1.37950.1.1.5.12.8.3.21.2.3
-- 1.3.6.1.4.1.37950.1.1.5.12.8.3.21.2.3
-- 1.3.6.1.4.1.37950.1.1.5.12.8.3.21.2.3
-- 1.3.6.1.4.1.37950.1.1.5.12.8.3.21.2.3
-- 1.3.6.1.4.1.37950.1.1.5.12.8.3.21.2.3
-- 1.3.6.1.4.1.37950.1.1.5.12.8.3.21.2.3
		-- 1.3.6.1.4.1.37950.1.1.5.12.8.3.21.2.3
		ctcTpidVal OBJECT-TYPE
			SYNTAX OCTET STRING
			MAX-ACCESS read-write
			STATUS current
			DESCRIPTION
				"Description."
			DEFVAL { '0'b }
			::= { portVlanPvid 3 }

		
--          1.3.6.1.4.1.37950.1.1.5.12.8.3.21.2.4
-- 1.3.6.1.4.1.37950.1.1.5.12.8.3.21.2.4
-- 1.3.6.1.4.1.37950.1.1.5.12.8.3.21.2.4
-- 1.3.6.1.4.1.37950.1.1.5.12.8.3.21.2.4
-- 1.3.6.1.4.1.37950.1.1.5.12.8.3.21.2.4
-- 1.3.6.1.4.1.37950.1.1.5.12.8.3.21.2.4
-- 1.3.6.1.4.1.37950.1.1.5.12.8.3.21.2.4
-- 1.3.6.1.4.1.37950.1.1.5.12.8.3.21.2.4
-- 1.3.6.1.4.1.37950.1.1.5.12.8.3.21.2.4
		-- 1.3.6.1.4.1.37950.1.1.5.12.8.3.21.2.4
		ctcPvidAction OBJECT-TYPE
			SYNTAX INTEGER
				{
				commit(1),
				remove(2)
				}
			MAX-ACCESS read-write
			STATUS current
			DESCRIPTION
				"Description."
			::= { portVlanPvid 4 }

		
--           1.3.6.1.4.1.37950.1.1.5.12.5.2.10.2.5
-- 1.3.6.1.4.1.37950.1.1.5.12.8.3.21.2.5
-- 1.3.6.1.4.1.37950.1.1.5.12.8.3.21.2.5
-- 1.3.6.1.4.1.37950.1.1.5.12.8.3.21.2.5
-- 1.3.6.1.4.1.37950.1.1.5.12.8.3.21.2.5
-- 1.3.6.1.4.1.37950.1.1.5.12.8.3.21.2.5
-- 1.3.6.1.4.1.37950.1.1.5.12.8.3.21.2.5
-- 1.3.6.1.4.1.37950.1.1.5.12.8.3.21.2.5
-- 1.3.6.1.4.1.37950.1.1.5.12.8.3.21.2.5
		-- 1.3.6.1.4.1.37950.1.1.5.12.8.3.21.2.5
		ctcPvidPriVal OBJECT-TYPE
			SYNTAX INTEGER (0..7)
			MAX-ACCESS read-write
			STATUS current
			DESCRIPTION
				"Description."
			::= { portVlanPvid 5 }

		
--          1.3.6.1.4.1.37950.1.1.5.12.8.3.21.3
-- 1.3.6.1.4.1.37950.1.1.5.12.8.3.21.3
-- 1.3.6.1.4.1.37950.1.1.5.12.8.3.21.3
-- 1.3.6.1.4.1.37950.1.1.5.12.8.3.21.3
-- 1.3.6.1.4.1.37950.1.1.5.12.8.3.21.3
-- 1.3.6.1.4.1.37950.1.1.5.12.8.3.21.3
-- 1.3.6.1.4.1.37950.1.1.5.12.8.3.21.3
-- 1.3.6.1.4.1.37950.1.1.5.12.8.3.21.3
-- 1.3.6.1.4.1.37950.1.1.5.12.8.3.21.3
		-- 1.3.6.1.4.1.37950.1.1.5.12.8.3.21.3
		portVlanTranslate OBJECT IDENTIFIER ::= { onuPortVlanConfig 3 }

		
--          1.3.6.1.4.1.37950.1.1.5.12.8.3.21.3.1
-- 1.3.6.1.4.1.37950.1.1.5.12.8.3.21.3.1
-- 1.3.6.1.4.1.37950.1.1.5.12.8.3.21.3.1
-- 1.3.6.1.4.1.37950.1.1.5.12.8.3.21.3.1
-- 1.3.6.1.4.1.37950.1.1.5.12.8.3.21.3.1
-- 1.3.6.1.4.1.37950.1.1.5.12.8.3.21.3.1
-- 1.3.6.1.4.1.37950.1.1.5.12.8.3.21.3.1
-- 1.3.6.1.4.1.37950.1.1.5.12.8.3.21.3.1
-- 1.3.6.1.4.1.37950.1.1.5.12.8.3.21.3.1
		-- 1.3.6.1.4.1.37950.1.1.5.12.8.3.21.3.1
		vlanTransEthNo OBJECT-TYPE
			SYNTAX INTEGER (1..255)
			MAX-ACCESS read-write
			STATUS current
			DESCRIPTION
				"Description."
			::= { portVlanTranslate 1 }

		
--          1.3.6.1.4.1.37950.1.1.5.12.8.3.21.3.2
-- 1.3.6.1.4.1.37950.1.1.5.12.8.3.21.3.2
-- 1.3.6.1.4.1.37950.1.1.5.12.8.3.21.3.2
-- 1.3.6.1.4.1.37950.1.1.5.12.8.3.21.3.2
-- 1.3.6.1.4.1.37950.1.1.5.12.8.3.21.3.2
-- 1.3.6.1.4.1.37950.1.1.5.12.8.3.21.3.2
-- 1.3.6.1.4.1.37950.1.1.5.12.8.3.21.3.2
-- 1.3.6.1.4.1.37950.1.1.5.12.8.3.21.3.2
-- 1.3.6.1.4.1.37950.1.1.5.12.8.3.21.3.2
		-- 1.3.6.1.4.1.37950.1.1.5.12.8.3.21.3.2
		ctcTransVlanStr OBJECT-TYPE
			SYNTAX OCTET STRING
			MAX-ACCESS read-write
			STATUS current
			DESCRIPTION
				"Description."
			DEFVAL { '0'b }
			::= { portVlanTranslate 2 }

		
--          1.3.6.1.4.1.37950.1.1.5.12.8.3.21.3.8
-- 1.3.6.1.4.1.37950.1.1.5.12.8.3.21.3.8
-- 1.3.6.1.4.1.37950.1.1.5.12.8.3.21.3.8
-- 1.3.6.1.4.1.37950.1.1.5.12.8.3.21.3.8
-- 1.3.6.1.4.1.37950.1.1.5.12.8.3.21.3.8
-- 1.3.6.1.4.1.37950.1.1.5.12.8.3.21.3.8
-- 1.3.6.1.4.1.37950.1.1.5.12.8.3.21.3.8
-- 1.3.6.1.4.1.37950.1.1.5.12.8.3.21.3.8
-- 1.3.6.1.4.1.37950.1.1.5.12.8.3.21.3.8
		-- 1.3.6.1.4.1.37950.1.1.5.12.8.3.21.3.8
		ctcTransAction OBJECT-TYPE
			SYNTAX INTEGER
				{
				add(1),
				remove(2)
				}
			MAX-ACCESS read-write
			STATUS current
			DESCRIPTION
				"Description."
			::= { portVlanTranslate 8 }

		
--          1.3.6.1.4.1.37950.1.1.5.12.8.3.21.4
-- 1.3.6.1.4.1.37950.1.1.5.12.8.3.21.4
-- 1.3.6.1.4.1.37950.1.1.5.12.8.3.21.4
-- 1.3.6.1.4.1.37950.1.1.5.12.8.3.21.4
-- 1.3.6.1.4.1.37950.1.1.5.12.8.3.21.4
-- 1.3.6.1.4.1.37950.1.1.5.12.8.3.21.4
-- 1.3.6.1.4.1.37950.1.1.5.12.8.3.21.4
-- 1.3.6.1.4.1.37950.1.1.5.12.8.3.21.4
-- 1.3.6.1.4.1.37950.1.1.5.12.8.3.21.4
		-- 1.3.6.1.4.1.37950.1.1.5.12.8.3.21.4
		portVlanTrunk OBJECT IDENTIFIER ::= { onuPortVlanConfig 4 }

		
--          1.3.6.1.4.1.37950.1.1.5.12.8.3.21.4.1
-- 1.3.6.1.4.1.37950.1.1.5.12.8.3.21.4.1
-- 1.3.6.1.4.1.37950.1.1.5.12.8.3.21.4.1
-- 1.3.6.1.4.1.37950.1.1.5.12.8.3.21.4.1
-- 1.3.6.1.4.1.37950.1.1.5.12.8.3.21.4.1
-- 1.3.6.1.4.1.37950.1.1.5.12.8.3.21.4.1
-- 1.3.6.1.4.1.37950.1.1.5.12.8.3.21.4.1
-- 1.3.6.1.4.1.37950.1.1.5.12.8.3.21.4.1
-- 1.3.6.1.4.1.37950.1.1.5.12.8.3.21.4.1
		-- 1.3.6.1.4.1.37950.1.1.5.12.8.3.21.4.1
		trunkEthNo OBJECT-TYPE
			SYNTAX INTEGER (1..255)
			MAX-ACCESS read-write
			STATUS current
			DESCRIPTION
				"Description."
			::= { portVlanTrunk 1 }

		
--          1.3.6.1.4.1.37950.1.1.5.12.8.3.21.4.2
-- 1.3.6.1.4.1.37950.1.1.5.12.8.3.21.4.2
-- 1.3.6.1.4.1.37950.1.1.5.12.8.3.21.4.2
-- 1.3.6.1.4.1.37950.1.1.5.12.8.3.21.4.2
-- 1.3.6.1.4.1.37950.1.1.5.12.8.3.21.4.2
-- 1.3.6.1.4.1.37950.1.1.5.12.8.3.21.4.2
-- 1.3.6.1.4.1.37950.1.1.5.12.8.3.21.4.2
-- 1.3.6.1.4.1.37950.1.1.5.12.8.3.21.4.2
-- 1.3.6.1.4.1.37950.1.1.5.12.8.3.21.4.2
		-- 1.3.6.1.4.1.37950.1.1.5.12.8.3.21.4.2
		ctcTrunkVidStr OBJECT-TYPE
			SYNTAX OCTET STRING
			MAX-ACCESS read-write
			STATUS current
			DESCRIPTION
				"Description."
			DEFVAL { '0'b }
			::= { portVlanTrunk 2 }

		
--          1.3.6.1.4.1.37950.1.1.5.12.8.3.21.4.3
-- 1.3.6.1.4.1.37950.1.1.5.12.8.3.21.4.3
-- 1.3.6.1.4.1.37950.1.1.5.12.8.3.21.4.3
-- 1.3.6.1.4.1.37950.1.1.5.12.8.3.21.4.3
-- 1.3.6.1.4.1.37950.1.1.5.12.8.3.21.4.3
-- 1.3.6.1.4.1.37950.1.1.5.12.8.3.21.4.3
-- 1.3.6.1.4.1.37950.1.1.5.12.8.3.21.4.3
-- 1.3.6.1.4.1.37950.1.1.5.12.8.3.21.4.3
-- 1.3.6.1.4.1.37950.1.1.5.12.8.3.21.4.3
		-- 1.3.6.1.4.1.37950.1.1.5.12.8.3.21.4.3
		ctcTrunkVidAction OBJECT-TYPE
			SYNTAX INTEGER
				{
				add(1),
				remove(2)
				}
			MAX-ACCESS read-write
			STATUS current
			DESCRIPTION
				"Description."
			::= { portVlanTrunk 3 }

		
--          1.3.6.1.4.1.37950.1.1.5.12.8.3.21.5
-- 1.3.6.1.4.1.37950.1.1.5.12.8.3.21.5
-- 1.3.6.1.4.1.37950.1.1.5.12.8.3.21.5
-- 1.3.6.1.4.1.37950.1.1.5.12.8.3.21.5
-- 1.3.6.1.4.1.37950.1.1.5.12.8.3.21.5
-- 1.3.6.1.4.1.37950.1.1.5.12.8.3.21.5
-- 1.3.6.1.4.1.37950.1.1.5.12.8.3.21.5
-- 1.3.6.1.4.1.37950.1.1.5.12.8.3.21.5
-- 1.3.6.1.4.1.37950.1.1.5.12.8.3.21.5
		-- 1.3.6.1.4.1.37950.1.1.5.12.8.3.21.5
		portVlanAgg OBJECT IDENTIFIER ::= { onuPortVlanConfig 5 }

		
--          1.3.6.1.4.1.37950.1.1.5.12.8.3.21.5.1
-- 1.3.6.1.4.1.37950.1.1.5.12.8.3.21.5.1
-- 1.3.6.1.4.1.37950.1.1.5.12.8.3.21.5.1
-- 1.3.6.1.4.1.37950.1.1.5.12.8.3.21.5.1
-- 1.3.6.1.4.1.37950.1.1.5.12.8.3.21.5.1
-- 1.3.6.1.4.1.37950.1.1.5.12.8.3.21.5.1
-- 1.3.6.1.4.1.37950.1.1.5.12.8.3.21.5.1
-- 1.3.6.1.4.1.37950.1.1.5.12.8.3.21.5.1
-- 1.3.6.1.4.1.37950.1.1.5.12.8.3.21.5.1
		-- 1.3.6.1.4.1.37950.1.1.5.12.8.3.21.5.1
		aggEthNo OBJECT-TYPE
			SYNTAX INTEGER (1..255)
			MAX-ACCESS read-write
			STATUS current
			DESCRIPTION
				"Description."
			::= { portVlanAgg 1 }

		
--          1.3.6.1.4.1.37950.1.1.5.12.8.3.21.5.2
-- 1.3.6.1.4.1.37950.1.1.5.12.8.3.21.5.2
-- 1.3.6.1.4.1.37950.1.1.5.12.8.3.21.5.2
-- 1.3.6.1.4.1.37950.1.1.5.12.8.3.21.5.2
-- 1.3.6.1.4.1.37950.1.1.5.12.8.3.21.5.2
-- 1.3.6.1.4.1.37950.1.1.5.12.8.3.21.5.2
-- 1.3.6.1.4.1.37950.1.1.5.12.8.3.21.5.2
-- 1.3.6.1.4.1.37950.1.1.5.12.8.3.21.5.2
-- 1.3.6.1.4.1.37950.1.1.5.12.8.3.21.5.2
		-- 1.3.6.1.4.1.37950.1.1.5.12.8.3.21.5.2
		ctcAggNewVlan OBJECT-TYPE
			SYNTAX INTEGER (1..4095)
			MAX-ACCESS read-write
			STATUS current
			DESCRIPTION
				"Description."
			::= { portVlanAgg 2 }

		
--          1.3.6.1.4.1.37950.1.1.5.12.8.3.21.5.10
-- 1.3.6.1.4.1.37950.1.1.5.12.8.3.21.5.10
-- 1.3.6.1.4.1.37950.1.1.5.12.8.3.21.5.10
-- 1.3.6.1.4.1.37950.1.1.5.12.8.3.21.5.10
-- 1.3.6.1.4.1.37950.1.1.5.12.8.3.21.5.10
-- 1.3.6.1.4.1.37950.1.1.5.12.8.3.21.5.10
-- 1.3.6.1.4.1.37950.1.1.5.12.8.3.21.5.10
-- 1.3.6.1.4.1.37950.1.1.5.12.8.3.21.5.10
-- 1.3.6.1.4.1.37950.1.1.5.12.8.3.21.5.10
		-- 1.3.6.1.4.1.37950.1.1.5.12.8.3.21.5.10
		ctcAggVlanStr OBJECT-TYPE
			SYNTAX OCTET STRING
			MAX-ACCESS read-write
			STATUS current
			DESCRIPTION
				"Description."
			DEFVAL { '0'b }
			::= { portVlanAgg 10 }

		
--          1.3.6.1.4.1.37950.1.1.5.12.8.3.21.5.11
-- 1.3.6.1.4.1.37950.1.1.5.12.8.3.21.5.11
-- 1.3.6.1.4.1.37950.1.1.5.12.8.3.21.5.11
-- 1.3.6.1.4.1.37950.1.1.5.12.8.3.21.5.11
-- 1.3.6.1.4.1.37950.1.1.5.12.8.3.21.5.11
-- 1.3.6.1.4.1.37950.1.1.5.12.8.3.21.5.11
-- 1.3.6.1.4.1.37950.1.1.5.12.8.3.21.5.11
-- 1.3.6.1.4.1.37950.1.1.5.12.8.3.21.5.11
-- 1.3.6.1.4.1.37950.1.1.5.12.8.3.21.5.11
		-- 1.3.6.1.4.1.37950.1.1.5.12.8.3.21.5.11
		ctcAggAction OBJECT-TYPE
			SYNTAX INTEGER
				{
				add(1),
				remove(2)
				}
			MAX-ACCESS read-write
			STATUS current
			DESCRIPTION
				"Description."
			::= { portVlanAgg 11 }

		
--          1.3.6.1.4.1.37950.1.1.5.12.8.3.22
-- 1.3.6.1.4.1.37950.1.1.5.12.8.3.22
-- 1.3.6.1.4.1.37950.1.1.5.12.8.3.22
-- 1.3.6.1.4.1.37950.1.1.5.12.8.3.22
-- 1.3.6.1.4.1.37950.1.1.5.12.8.3.22
-- 1.3.6.1.4.1.37950.1.1.5.12.8.3.22
-- 1.3.6.1.4.1.37950.1.1.5.12.8.3.22
-- 1.3.6.1.4.1.37950.1.1.5.12.8.3.22
-- 1.3.6.1.4.1.37950.1.1.5.12.8.3.22
		-- 1.3.6.1.4.1.37950.1.1.5.12.8.3.22
		onuIgmpVlanConfig OBJECT IDENTIFIER ::= { srvProfileEdit 22 }

		
--          1.3.6.1.4.1.37950.1.1.5.12.8.3.22.2
-- 1.3.6.1.4.1.37950.1.1.5.12.8.3.22.2
-- 1.3.6.1.4.1.37950.1.1.5.12.8.3.22.2
-- 1.3.6.1.4.1.37950.1.1.5.12.8.3.22.2
-- 1.3.6.1.4.1.37950.1.1.5.12.8.3.22.2
-- 1.3.6.1.4.1.37950.1.1.5.12.8.3.22.2
-- 1.3.6.1.4.1.37950.1.1.5.12.8.3.22.2
-- 1.3.6.1.4.1.37950.1.1.5.12.8.3.22.2
-- 1.3.6.1.4.1.37950.1.1.5.12.8.3.22.2
		-- 1.3.6.1.4.1.37950.1.1.5.12.8.3.22.2
		mcVlanEthNo OBJECT-TYPE
			SYNTAX INTEGER (1..255)
			MAX-ACCESS read-write
			STATUS current
			DESCRIPTION
				"Description."
			::= { onuIgmpVlanConfig 2 }

		
--          1.3.6.1.4.1.37950.1.1.5.12.8.3.22.3
-- 1.3.6.1.4.1.37950.1.1.5.12.8.3.22.3
-- 1.3.6.1.4.1.37950.1.1.5.12.8.3.22.3
-- 1.3.6.1.4.1.37950.1.1.5.12.8.3.22.3
-- 1.3.6.1.4.1.37950.1.1.5.12.8.3.22.3
-- 1.3.6.1.4.1.37950.1.1.5.12.8.3.22.3
-- 1.3.6.1.4.1.37950.1.1.5.12.8.3.22.3
-- 1.3.6.1.4.1.37950.1.1.5.12.8.3.22.3
-- 1.3.6.1.4.1.37950.1.1.5.12.8.3.22.3
		-- 1.3.6.1.4.1.37950.1.1.5.12.8.3.22.3
		ctcMcVlanStr OBJECT-TYPE
			SYNTAX OCTET STRING
			MAX-ACCESS read-write
			STATUS current
			DESCRIPTION
				"Description."
			DEFVAL { '0'b }
			::= { onuIgmpVlanConfig 3 }

		
--          1.3.6.1.4.1.37950.1.1.5.12.8.3.22.4
-- 1.3.6.1.4.1.37950.1.1.5.12.8.3.22.4
-- 1.3.6.1.4.1.37950.1.1.5.12.8.3.22.4
-- 1.3.6.1.4.1.37950.1.1.5.12.8.3.22.4
-- 1.3.6.1.4.1.37950.1.1.5.12.8.3.22.4
-- 1.3.6.1.4.1.37950.1.1.5.12.8.3.22.4
-- 1.3.6.1.4.1.37950.1.1.5.12.8.3.22.4
-- 1.3.6.1.4.1.37950.1.1.5.12.8.3.22.4
-- 1.3.6.1.4.1.37950.1.1.5.12.8.3.22.4
		-- 1.3.6.1.4.1.37950.1.1.5.12.8.3.22.4
		ctcMcValnAction OBJECT-TYPE
			SYNTAX INTEGER
				{
				add(1),
				remove(2)
				}
			MAX-ACCESS read-write
			STATUS current
			DESCRIPTION
				"Description."
			::= { onuIgmpVlanConfig 4 }

		
--          1.3.6.1.4.1.37950.1.1.5.12.8.3.23
-- 1.3.6.1.4.1.37950.1.1.5.12.8.3.23
-- 1.3.6.1.4.1.37950.1.1.5.12.8.3.23
-- 1.3.6.1.4.1.37950.1.1.5.12.8.3.23
-- 1.3.6.1.4.1.37950.1.1.5.12.8.3.23
-- 1.3.6.1.4.1.37950.1.1.5.12.8.3.23
-- 1.3.6.1.4.1.37950.1.1.5.12.8.3.23
-- 1.3.6.1.4.1.37950.1.1.5.12.8.3.23
-- 1.3.6.1.4.1.37950.1.1.5.12.8.3.23
		-- 1.3.6.1.4.1.37950.1.1.5.12.8.3.23
		onuClassifyConfig OBJECT IDENTIFIER ::= { srvProfileEdit 23 }

		
--          1.3.6.1.4.1.37950.1.1.5.12.8.3.23.1
-- 1.3.6.1.4.1.37950.1.1.5.12.8.3.23.1
-- 1.3.6.1.4.1.37950.1.1.5.12.8.3.23.1
-- 1.3.6.1.4.1.37950.1.1.5.12.8.3.23.1
-- 1.3.6.1.4.1.37950.1.1.5.12.8.3.23.1
-- 1.3.6.1.4.1.37950.1.1.5.12.8.3.23.1
-- 1.3.6.1.4.1.37950.1.1.5.12.8.3.23.1
-- 1.3.6.1.4.1.37950.1.1.5.12.8.3.23.1
-- 1.3.6.1.4.1.37950.1.1.5.12.8.3.23.1
		-- 1.3.6.1.4.1.37950.1.1.5.12.8.3.23.1
		onuClassifyAdd OBJECT IDENTIFIER ::= { onuClassifyConfig 1 }

		
--          1.3.6.1.4.1.37950.1.1.5.12.8.3.23.1.1
-- 1.3.6.1.4.1.37950.1.1.5.12.8.3.23.1.1
-- 1.3.6.1.4.1.37950.1.1.5.12.8.3.23.1.1
-- 1.3.6.1.4.1.37950.1.1.5.12.8.3.23.1.1
-- 1.3.6.1.4.1.37950.1.1.5.12.8.3.23.1.1
-- 1.3.6.1.4.1.37950.1.1.5.12.8.3.23.1.1
-- 1.3.6.1.4.1.37950.1.1.5.12.8.3.23.1.1
-- 1.3.6.1.4.1.37950.1.1.5.12.8.3.23.1.1
-- 1.3.6.1.4.1.37950.1.1.5.12.8.3.23.1.1
		-- 1.3.6.1.4.1.37950.1.1.5.12.8.3.23.1.1
		cfyEthNo OBJECT-TYPE
			SYNTAX INTEGER (1..255)
			MAX-ACCESS read-write
			STATUS current
			DESCRIPTION
				"Description."
			::= { onuClassifyAdd 1 }

		
--          1.3.6.1.4.1.37950.1.1.5.12.8.3.23.1.2
-- 1.3.6.1.4.1.37950.1.1.5.12.8.3.23.1.2
-- 1.3.6.1.4.1.37950.1.1.5.12.8.3.23.1.2
-- 1.3.6.1.4.1.37950.1.1.5.12.8.3.23.1.2
-- 1.3.6.1.4.1.37950.1.1.5.12.8.3.23.1.2
-- 1.3.6.1.4.1.37950.1.1.5.12.8.3.23.1.2
-- 1.3.6.1.4.1.37950.1.1.5.12.8.3.23.1.2
-- 1.3.6.1.4.1.37950.1.1.5.12.8.3.23.1.2
-- 1.3.6.1.4.1.37950.1.1.5.12.8.3.23.1.2
		-- 1.3.6.1.4.1.37950.1.1.5.12.8.3.23.1.2
		ctcPrecedence OBJECT-TYPE
			SYNTAX INTEGER (1..8)
			MAX-ACCESS read-write
			STATUS current
			DESCRIPTION
				"Description."
			::= { onuClassifyAdd 2 }

		
--          1.3.6.1.4.1.37950.1.1.5.12.8.3.23.1.3
-- 1.3.6.1.4.1.37950.1.1.5.12.8.3.23.1.3
-- 1.3.6.1.4.1.37950.1.1.5.12.8.3.23.1.3
-- 1.3.6.1.4.1.37950.1.1.5.12.8.3.23.1.3
-- 1.3.6.1.4.1.37950.1.1.5.12.8.3.23.1.3
-- 1.3.6.1.4.1.37950.1.1.5.12.8.3.23.1.3
-- 1.3.6.1.4.1.37950.1.1.5.12.8.3.23.1.3
-- 1.3.6.1.4.1.37950.1.1.5.12.8.3.23.1.3
-- 1.3.6.1.4.1.37950.1.1.5.12.8.3.23.1.3
		-- 1.3.6.1.4.1.37950.1.1.5.12.8.3.23.1.3
		ctcPri OBJECT-TYPE
			SYNTAX INTEGER (0..7)
			MAX-ACCESS read-write
			STATUS current
			DESCRIPTION
				"Description."
			::= { onuClassifyAdd 3 }

		
--          1.3.6.1.4.1.37950.1.1.5.12.8.3.23.1.4
-- 1.3.6.1.4.1.37950.1.1.5.12.8.3.23.1.4
-- 1.3.6.1.4.1.37950.1.1.5.12.8.3.23.1.4
-- 1.3.6.1.4.1.37950.1.1.5.12.8.3.23.1.4
-- 1.3.6.1.4.1.37950.1.1.5.12.8.3.23.1.4
-- 1.3.6.1.4.1.37950.1.1.5.12.8.3.23.1.4
-- 1.3.6.1.4.1.37950.1.1.5.12.8.3.23.1.4
-- 1.3.6.1.4.1.37950.1.1.5.12.8.3.23.1.4
-- 1.3.6.1.4.1.37950.1.1.5.12.8.3.23.1.4
		-- 1.3.6.1.4.1.37950.1.1.5.12.8.3.23.1.4
		ctcDstMacEqualSel OBJECT-TYPE
			SYNTAX INTEGER
				{
				init(0),
				equal(1),
				unequal(2)
				}
			MAX-ACCESS read-write
			STATUS current
			DESCRIPTION
				"Description."
			::= { onuClassifyAdd 4 }

		
--          1.3.6.1.4.1.37950.1.1.5.12.8.3.23.1.5
-- 1.3.6.1.4.1.37950.1.1.5.12.8.3.23.1.5
-- 1.3.6.1.4.1.37950.1.1.5.12.8.3.23.1.5
-- 1.3.6.1.4.1.37950.1.1.5.12.8.3.23.1.5
-- 1.3.6.1.4.1.37950.1.1.5.12.8.3.23.1.5
-- 1.3.6.1.4.1.37950.1.1.5.12.8.3.23.1.5
-- 1.3.6.1.4.1.37950.1.1.5.12.8.3.23.1.5
-- 1.3.6.1.4.1.37950.1.1.5.12.8.3.23.1.5
-- 1.3.6.1.4.1.37950.1.1.5.12.8.3.23.1.5
		-- 1.3.6.1.4.1.37950.1.1.5.12.8.3.23.1.5
		ctcDstMacValue OBJECT-TYPE
			SYNTAX OCTET STRING
			MAX-ACCESS read-write
			STATUS current
			DESCRIPTION
				"Description."
			::= { onuClassifyAdd 5 }

		
--          1.3.6.1.4.1.37950.1.1.5.12.8.3.23.1.6
-- 1.3.6.1.4.1.37950.1.1.5.12.8.3.23.1.6
-- 1.3.6.1.4.1.37950.1.1.5.12.8.3.23.1.6
-- 1.3.6.1.4.1.37950.1.1.5.12.8.3.23.1.6
-- 1.3.6.1.4.1.37950.1.1.5.12.8.3.23.1.6
-- 1.3.6.1.4.1.37950.1.1.5.12.8.3.23.1.6
-- 1.3.6.1.4.1.37950.1.1.5.12.8.3.23.1.6
-- 1.3.6.1.4.1.37950.1.1.5.12.8.3.23.1.6
-- 1.3.6.1.4.1.37950.1.1.5.12.8.3.23.1.6
		-- 1.3.6.1.4.1.37950.1.1.5.12.8.3.23.1.6
		ctcSrcMacEqualSel OBJECT-TYPE
			SYNTAX INTEGER
				{
				init(0),
				equal(1),
				unequal(2)
				}
			MAX-ACCESS read-write
			STATUS current
			DESCRIPTION
				"Description."
			::= { onuClassifyAdd 6 }

		
--          1.3.6.1.4.1.37950.1.1.5.12.8.3.23.1.7
-- 1.3.6.1.4.1.37950.1.1.5.12.8.3.23.1.7
-- 1.3.6.1.4.1.37950.1.1.5.12.8.3.23.1.7
-- 1.3.6.1.4.1.37950.1.1.5.12.8.3.23.1.7
-- 1.3.6.1.4.1.37950.1.1.5.12.8.3.23.1.7
-- 1.3.6.1.4.1.37950.1.1.5.12.8.3.23.1.7
-- 1.3.6.1.4.1.37950.1.1.5.12.8.3.23.1.7
-- 1.3.6.1.4.1.37950.1.1.5.12.8.3.23.1.7
-- 1.3.6.1.4.1.37950.1.1.5.12.8.3.23.1.7
		-- 1.3.6.1.4.1.37950.1.1.5.12.8.3.23.1.7
		ctcSrcMacValue OBJECT-TYPE
			SYNTAX OCTET STRING
			MAX-ACCESS read-write
			STATUS current
			DESCRIPTION
				"Description."
			::= { onuClassifyAdd 7 }

		
--          1.3.6.1.4.1.37950.1.1.5.12.8.3.23.1.8
-- 1.3.6.1.4.1.37950.1.1.5.12.8.3.23.1.8
-- 1.3.6.1.4.1.37950.1.1.5.12.8.3.23.1.8
-- 1.3.6.1.4.1.37950.1.1.5.12.8.3.23.1.8
-- 1.3.6.1.4.1.37950.1.1.5.12.8.3.23.1.8
-- 1.3.6.1.4.1.37950.1.1.5.12.8.3.23.1.8
-- 1.3.6.1.4.1.37950.1.1.5.12.8.3.23.1.8
-- 1.3.6.1.4.1.37950.1.1.5.12.8.3.23.1.8
-- 1.3.6.1.4.1.37950.1.1.5.12.8.3.23.1.8
		-- 1.3.6.1.4.1.37950.1.1.5.12.8.3.23.1.8
		ctcVlanEqualSel OBJECT-TYPE
			SYNTAX INTEGER
				{
				init(0),
				equal(1),
				unequal(2)
				}
			MAX-ACCESS read-write
			STATUS current
			DESCRIPTION
				"Description."
			::= { onuClassifyAdd 8 }

		
--          1.3.6.1.4.1.37950.1.1.5.12.8.3.23.1.9
-- 1.3.6.1.4.1.37950.1.1.5.12.8.3.23.1.9
-- 1.3.6.1.4.1.37950.1.1.5.12.8.3.23.1.9
-- 1.3.6.1.4.1.37950.1.1.5.12.8.3.23.1.9
-- 1.3.6.1.4.1.37950.1.1.5.12.8.3.23.1.9
-- 1.3.6.1.4.1.37950.1.1.5.12.8.3.23.1.9
-- 1.3.6.1.4.1.37950.1.1.5.12.8.3.23.1.9
-- 1.3.6.1.4.1.37950.1.1.5.12.8.3.23.1.9
-- 1.3.6.1.4.1.37950.1.1.5.12.8.3.23.1.9
		-- 1.3.6.1.4.1.37950.1.1.5.12.8.3.23.1.9
		ctcVlanValue OBJECT-TYPE
			SYNTAX INTEGER (0..4094)
			MAX-ACCESS read-write
			STATUS current
			DESCRIPTION
				"Description."
			::= { onuClassifyAdd 9 }

		
--          1.3.6.1.4.1.37950.1.1.5.12.8.3.23.1.10
-- 1.3.6.1.4.1.37950.1.1.5.12.8.3.23.1.10
-- 1.3.6.1.4.1.37950.1.1.5.12.8.3.23.1.10
-- 1.3.6.1.4.1.37950.1.1.5.12.8.3.23.1.10
-- 1.3.6.1.4.1.37950.1.1.5.12.8.3.23.1.10
-- 1.3.6.1.4.1.37950.1.1.5.12.8.3.23.1.10
-- 1.3.6.1.4.1.37950.1.1.5.12.8.3.23.1.10
-- 1.3.6.1.4.1.37950.1.1.5.12.8.3.23.1.10
-- 1.3.6.1.4.1.37950.1.1.5.12.8.3.23.1.10
		-- 1.3.6.1.4.1.37950.1.1.5.12.8.3.23.1.10
		ctcCosEqualSel OBJECT-TYPE
			SYNTAX INTEGER
				{
				init(0),
				equal(1),
				unequal(2)
				}
			MAX-ACCESS read-write
			STATUS current
			DESCRIPTION
				"Description."
			::= { onuClassifyAdd 10 }

		
--          1.3.6.1.4.1.37950.1.1.5.12.8.3.23.1.11
-- 1.3.6.1.4.1.37950.1.1.5.12.8.3.23.1.11
-- 1.3.6.1.4.1.37950.1.1.5.12.8.3.23.1.11
-- 1.3.6.1.4.1.37950.1.1.5.12.8.3.23.1.11
-- 1.3.6.1.4.1.37950.1.1.5.12.8.3.23.1.11
-- 1.3.6.1.4.1.37950.1.1.5.12.8.3.23.1.11
-- 1.3.6.1.4.1.37950.1.1.5.12.8.3.23.1.11
-- 1.3.6.1.4.1.37950.1.1.5.12.8.3.23.1.11
-- 1.3.6.1.4.1.37950.1.1.5.12.8.3.23.1.11
		-- 1.3.6.1.4.1.37950.1.1.5.12.8.3.23.1.11
		ctcCosValue OBJECT-TYPE
			SYNTAX INTEGER (-1..7)
			MAX-ACCESS read-write
			STATUS current
			DESCRIPTION
				"Description."
			::= { onuClassifyAdd 11 }

		
--          1.3.6.1.4.1.37950.1.1.5.12.8.3.23.1.12
-- 1.3.6.1.4.1.37950.1.1.5.12.8.3.23.1.12
-- 1.3.6.1.4.1.37950.1.1.5.12.8.3.23.1.12
-- 1.3.6.1.4.1.37950.1.1.5.12.8.3.23.1.12
-- 1.3.6.1.4.1.37950.1.1.5.12.8.3.23.1.12
-- 1.3.6.1.4.1.37950.1.1.5.12.8.3.23.1.12
-- 1.3.6.1.4.1.37950.1.1.5.12.8.3.23.1.12
-- 1.3.6.1.4.1.37950.1.1.5.12.8.3.23.1.12
-- 1.3.6.1.4.1.37950.1.1.5.12.8.3.23.1.12
		-- 1.3.6.1.4.1.37950.1.1.5.12.8.3.23.1.12
		ctcEthTypeEqualSel OBJECT-TYPE
			SYNTAX INTEGER
				{
				init(0),
				equal(1),
				unequal(2)
				}
			MAX-ACCESS read-write
			STATUS current
			DESCRIPTION
				"Description."
			::= { onuClassifyAdd 12 }

		
--          1.3.6.1.4.1.37950.1.1.5.12.8.3.23.1.13
-- 1.3.6.1.4.1.37950.1.1.5.12.8.3.23.1.13
-- 1.3.6.1.4.1.37950.1.1.5.12.8.3.23.1.13
-- 1.3.6.1.4.1.37950.1.1.5.12.8.3.23.1.13
-- 1.3.6.1.4.1.37950.1.1.5.12.8.3.23.1.13
-- 1.3.6.1.4.1.37950.1.1.5.12.8.3.23.1.13
-- 1.3.6.1.4.1.37950.1.1.5.12.8.3.23.1.13
-- 1.3.6.1.4.1.37950.1.1.5.12.8.3.23.1.13
-- 1.3.6.1.4.1.37950.1.1.5.12.8.3.23.1.13
		-- 1.3.6.1.4.1.37950.1.1.5.12.8.3.23.1.13
		ctcEthTypeValue OBJECT-TYPE
			SYNTAX OCTET STRING
			MAX-ACCESS read-write
			STATUS current
			DESCRIPTION
				"Description."
			::= { onuClassifyAdd 13 }

		
--          1.3.6.1.4.1.37950.1.1.5.12.8.3.23.1.14
-- 1.3.6.1.4.1.37950.1.1.5.12.8.3.23.1.14
-- 1.3.6.1.4.1.37950.1.1.5.12.8.3.23.1.14
-- 1.3.6.1.4.1.37950.1.1.5.12.8.3.23.1.14
-- 1.3.6.1.4.1.37950.1.1.5.12.8.3.23.1.14
-- 1.3.6.1.4.1.37950.1.1.5.12.8.3.23.1.14
-- 1.3.6.1.4.1.37950.1.1.5.12.8.3.23.1.14
-- 1.3.6.1.4.1.37950.1.1.5.12.8.3.23.1.14
-- 1.3.6.1.4.1.37950.1.1.5.12.8.3.23.1.14
		-- 1.3.6.1.4.1.37950.1.1.5.12.8.3.23.1.14
		ctcSrcIpEqualSel OBJECT-TYPE
			SYNTAX INTEGER
				{
				init(0),
				equal(1),
				unequal(2)
				}
			MAX-ACCESS read-write
			STATUS current
			DESCRIPTION
				"Description."
			::= { onuClassifyAdd 14 }

		
--          1.3.6.1.4.1.37950.1.1.5.12.8.3.23.1.15
-- 1.3.6.1.4.1.37950.1.1.5.12.8.3.23.1.15
-- 1.3.6.1.4.1.37950.1.1.5.12.8.3.23.1.15
-- 1.3.6.1.4.1.37950.1.1.5.12.8.3.23.1.15
-- 1.3.6.1.4.1.37950.1.1.5.12.8.3.23.1.15
-- 1.3.6.1.4.1.37950.1.1.5.12.8.3.23.1.15
-- 1.3.6.1.4.1.37950.1.1.5.12.8.3.23.1.15
-- 1.3.6.1.4.1.37950.1.1.5.12.8.3.23.1.15
-- 1.3.6.1.4.1.37950.1.1.5.12.8.3.23.1.15
		-- 1.3.6.1.4.1.37950.1.1.5.12.8.3.23.1.15
		ctcSrcIpValue OBJECT-TYPE
			SYNTAX IpAddress
			MAX-ACCESS read-write
			STATUS current
			DESCRIPTION
				"Description."
			::= { onuClassifyAdd 15 }

		
--          1.3.6.1.4.1.37950.1.1.5.12.8.3.23.1.16
-- 1.3.6.1.4.1.37950.1.1.5.12.8.3.23.1.16
-- 1.3.6.1.4.1.37950.1.1.5.12.8.3.23.1.16
-- 1.3.6.1.4.1.37950.1.1.5.12.8.3.23.1.16
-- 1.3.6.1.4.1.37950.1.1.5.12.8.3.23.1.16
-- 1.3.6.1.4.1.37950.1.1.5.12.8.3.23.1.16
-- 1.3.6.1.4.1.37950.1.1.5.12.8.3.23.1.16
-- 1.3.6.1.4.1.37950.1.1.5.12.8.3.23.1.16
-- 1.3.6.1.4.1.37950.1.1.5.12.8.3.23.1.16
		-- 1.3.6.1.4.1.37950.1.1.5.12.8.3.23.1.16
		ctcDestIpEqualSel OBJECT-TYPE
			SYNTAX INTEGER
				{
				init(0),
				equal(1),
				unequal(2)
				}
			MAX-ACCESS read-write
			STATUS current
			DESCRIPTION
				"Description."
			::= { onuClassifyAdd 16 }

		
--          1.3.6.1.4.1.37950.1.1.5.12.8.3.23.1.17
-- 1.3.6.1.4.1.37950.1.1.5.12.8.3.23.1.17
-- 1.3.6.1.4.1.37950.1.1.5.12.8.3.23.1.17
-- 1.3.6.1.4.1.37950.1.1.5.12.8.3.23.1.17
-- 1.3.6.1.4.1.37950.1.1.5.12.8.3.23.1.17
-- 1.3.6.1.4.1.37950.1.1.5.12.8.3.23.1.17
-- 1.3.6.1.4.1.37950.1.1.5.12.8.3.23.1.17
-- 1.3.6.1.4.1.37950.1.1.5.12.8.3.23.1.17
-- 1.3.6.1.4.1.37950.1.1.5.12.8.3.23.1.17
		-- 1.3.6.1.4.1.37950.1.1.5.12.8.3.23.1.17
		ctcDestIpValue OBJECT-TYPE
			SYNTAX IpAddress
			MAX-ACCESS read-write
			STATUS current
			DESCRIPTION
				"Description."
			::= { onuClassifyAdd 17 }

		
--          1.3.6.1.4.1.37950.1.1.5.12.8.3.23.1.18
-- 1.3.6.1.4.1.37950.1.1.5.12.8.3.23.1.18
-- 1.3.6.1.4.1.37950.1.1.5.12.8.3.23.1.18
-- 1.3.6.1.4.1.37950.1.1.5.12.8.3.23.1.18
-- 1.3.6.1.4.1.37950.1.1.5.12.8.3.23.1.18
-- 1.3.6.1.4.1.37950.1.1.5.12.8.3.23.1.18
-- 1.3.6.1.4.1.37950.1.1.5.12.8.3.23.1.18
-- 1.3.6.1.4.1.37950.1.1.5.12.8.3.23.1.18
-- 1.3.6.1.4.1.37950.1.1.5.12.8.3.23.1.18
		-- 1.3.6.1.4.1.37950.1.1.5.12.8.3.23.1.18
		ctcProEqualSel OBJECT-TYPE
			SYNTAX INTEGER
				{
				init(0),
				equal(1),
				unequal(2)
				}
			MAX-ACCESS read-write
			STATUS current
			DESCRIPTION
				"Description."
			::= { onuClassifyAdd 18 }

		
--          1.3.6.1.4.1.37950.1.1.5.12.8.3.23.1.19
-- 1.3.6.1.4.1.37950.1.1.5.12.8.3.23.1.19
-- 1.3.6.1.4.1.37950.1.1.5.12.8.3.23.1.19
-- 1.3.6.1.4.1.37950.1.1.5.12.8.3.23.1.19
-- 1.3.6.1.4.1.37950.1.1.5.12.8.3.23.1.19
-- 1.3.6.1.4.1.37950.1.1.5.12.8.3.23.1.19
-- 1.3.6.1.4.1.37950.1.1.5.12.8.3.23.1.19
-- 1.3.6.1.4.1.37950.1.1.5.12.8.3.23.1.19
-- 1.3.6.1.4.1.37950.1.1.5.12.8.3.23.1.19
		-- 1.3.6.1.4.1.37950.1.1.5.12.8.3.23.1.19
		ctcProValue OBJECT-TYPE
			SYNTAX INTEGER (-1..255)
			MAX-ACCESS read-write
			STATUS current
			DESCRIPTION
				"Description."
			::= { onuClassifyAdd 19 }

		
--          1.3.6.1.4.1.37950.1.1.5.12.8.3.23.1.20
-- 1.3.6.1.4.1.37950.1.1.5.12.8.3.23.1.20
-- 1.3.6.1.4.1.37950.1.1.5.12.8.3.23.1.20
-- 1.3.6.1.4.1.37950.1.1.5.12.8.3.23.1.20
-- 1.3.6.1.4.1.37950.1.1.5.12.8.3.23.1.20
-- 1.3.6.1.4.1.37950.1.1.5.12.8.3.23.1.20
-- 1.3.6.1.4.1.37950.1.1.5.12.8.3.23.1.20
-- 1.3.6.1.4.1.37950.1.1.5.12.8.3.23.1.20
-- 1.3.6.1.4.1.37950.1.1.5.12.8.3.23.1.20
		-- 1.3.6.1.4.1.37950.1.1.5.12.8.3.23.1.20
		ctcTosDscpEuqalSel OBJECT-TYPE
			SYNTAX INTEGER
				{
				init(0),
				equal(1),
				unequal(2)
				}
			MAX-ACCESS read-write
			STATUS current
			DESCRIPTION
				"Description."
			::= { onuClassifyAdd 20 }

		
--          1.3.6.1.4.1.37950.1.1.5.12.8.3.23.1.21
-- 1.3.6.1.4.1.37950.1.1.5.12.8.3.23.1.21
-- 1.3.6.1.4.1.37950.1.1.5.12.8.3.23.1.21
-- 1.3.6.1.4.1.37950.1.1.5.12.8.3.23.1.21
-- 1.3.6.1.4.1.37950.1.1.5.12.8.3.23.1.21
-- 1.3.6.1.4.1.37950.1.1.5.12.8.3.23.1.21
-- 1.3.6.1.4.1.37950.1.1.5.12.8.3.23.1.21
-- 1.3.6.1.4.1.37950.1.1.5.12.8.3.23.1.21
-- 1.3.6.1.4.1.37950.1.1.5.12.8.3.23.1.21
		-- 1.3.6.1.4.1.37950.1.1.5.12.8.3.23.1.21
		ctcTosDscpValue OBJECT-TYPE
			SYNTAX INTEGER (-1..255)
			MAX-ACCESS read-write
			STATUS current
			DESCRIPTION
				"Description."
			::= { onuClassifyAdd 21 }

		
--          1.3.6.1.4.1.37950.1.1.5.12.8.3.23.1.22
-- 1.3.6.1.4.1.37950.1.1.5.12.8.3.23.1.22
-- 1.3.6.1.4.1.37950.1.1.5.12.8.3.23.1.22
-- 1.3.6.1.4.1.37950.1.1.5.12.8.3.23.1.22
-- 1.3.6.1.4.1.37950.1.1.5.12.8.3.23.1.22
-- 1.3.6.1.4.1.37950.1.1.5.12.8.3.23.1.22
-- 1.3.6.1.4.1.37950.1.1.5.12.8.3.23.1.22
-- 1.3.6.1.4.1.37950.1.1.5.12.8.3.23.1.22
-- 1.3.6.1.4.1.37950.1.1.5.12.8.3.23.1.22
		-- 1.3.6.1.4.1.37950.1.1.5.12.8.3.23.1.22
		ctcSrcPortEqualSel OBJECT-TYPE
			SYNTAX INTEGER
				{
				init(0),
				equal(1),
				unequal(2)
				}
			MAX-ACCESS read-write
			STATUS current
			DESCRIPTION
				"Description."
			::= { onuClassifyAdd 22 }

		
--          1.3.6.1.4.1.37950.1.1.5.12.8.3.23.1.23
-- 1.3.6.1.4.1.37950.1.1.5.12.8.3.23.1.23
-- 1.3.6.1.4.1.37950.1.1.5.12.8.3.23.1.23
-- 1.3.6.1.4.1.37950.1.1.5.12.8.3.23.1.23
-- 1.3.6.1.4.1.37950.1.1.5.12.8.3.23.1.23
-- 1.3.6.1.4.1.37950.1.1.5.12.8.3.23.1.23
-- 1.3.6.1.4.1.37950.1.1.5.12.8.3.23.1.23
-- 1.3.6.1.4.1.37950.1.1.5.12.8.3.23.1.23
-- 1.3.6.1.4.1.37950.1.1.5.12.8.3.23.1.23
		-- 1.3.6.1.4.1.37950.1.1.5.12.8.3.23.1.23
		ctcSrcPortValue OBJECT-TYPE
			SYNTAX INTEGER (-1..65535)
			MAX-ACCESS read-write
			STATUS current
			DESCRIPTION
				"Description."
			::= { onuClassifyAdd 23 }

		
--          1.3.6.1.4.1.37950.1.1.5.12.8.3.23.1.24
-- 1.3.6.1.4.1.37950.1.1.5.12.8.3.23.1.24
-- 1.3.6.1.4.1.37950.1.1.5.12.8.3.23.1.24
-- 1.3.6.1.4.1.37950.1.1.5.12.8.3.23.1.24
-- 1.3.6.1.4.1.37950.1.1.5.12.8.3.23.1.24
-- 1.3.6.1.4.1.37950.1.1.5.12.8.3.23.1.24
-- 1.3.6.1.4.1.37950.1.1.5.12.8.3.23.1.24
-- 1.3.6.1.4.1.37950.1.1.5.12.8.3.23.1.24
-- 1.3.6.1.4.1.37950.1.1.5.12.8.3.23.1.24
		-- 1.3.6.1.4.1.37950.1.1.5.12.8.3.23.1.24
		ctcDestPortEqualSel OBJECT-TYPE
			SYNTAX INTEGER
				{
				init(0),
				equal(1),
				unequal(2)
				}
			MAX-ACCESS read-write
			STATUS current
			DESCRIPTION
				"Description."
			::= { onuClassifyAdd 24 }

		
--          1.3.6.1.4.1.37950.1.1.5.12.8.3.23.1.25
-- 1.3.6.1.4.1.37950.1.1.5.12.8.3.23.1.25
-- 1.3.6.1.4.1.37950.1.1.5.12.8.3.23.1.25
-- 1.3.6.1.4.1.37950.1.1.5.12.8.3.23.1.25
-- 1.3.6.1.4.1.37950.1.1.5.12.8.3.23.1.25
-- 1.3.6.1.4.1.37950.1.1.5.12.8.3.23.1.25
-- 1.3.6.1.4.1.37950.1.1.5.12.8.3.23.1.25
-- 1.3.6.1.4.1.37950.1.1.5.12.8.3.23.1.25
-- 1.3.6.1.4.1.37950.1.1.5.12.8.3.23.1.25
		-- 1.3.6.1.4.1.37950.1.1.5.12.8.3.23.1.25
		ctcDestPortValue OBJECT-TYPE
			SYNTAX INTEGER (-1..65535)
			MAX-ACCESS read-write
			STATUS current
			DESCRIPTION
				"Description."
			::= { onuClassifyAdd 25 }

		
--          1.3.6.1.4.1.37950.1.1.5.12.8.3.23.1.26
-- 1.3.6.1.4.1.37950.1.1.5.12.8.3.23.1.26
-- 1.3.6.1.4.1.37950.1.1.5.12.8.3.23.1.26
-- 1.3.6.1.4.1.37950.1.1.5.12.8.3.23.1.26
-- 1.3.6.1.4.1.37950.1.1.5.12.8.3.23.1.26
-- 1.3.6.1.4.1.37950.1.1.5.12.8.3.23.1.26
-- 1.3.6.1.4.1.37950.1.1.5.12.8.3.23.1.26
-- 1.3.6.1.4.1.37950.1.1.5.12.8.3.23.1.26
-- 1.3.6.1.4.1.37950.1.1.5.12.8.3.23.1.26
		-- 1.3.6.1.4.1.37950.1.1.5.12.8.3.23.1.26
		ctcCfyAction OBJECT-TYPE
			SYNTAX INTEGER { add(1) }
			MAX-ACCESS read-write
			STATUS current
			DESCRIPTION
				"Description."
			::= { onuClassifyAdd 26 }

		
--          1.3.6.1.4.1.37950.1.1.5.12.8.3.23.1.27
-- 1.3.6.1.4.1.37950.1.1.5.12.8.3.23.1.27
-- 1.3.6.1.4.1.37950.1.1.5.12.8.3.23.1.27
-- 1.3.6.1.4.1.37950.1.1.5.12.8.3.23.1.27
-- 1.3.6.1.4.1.37950.1.1.5.12.8.3.23.1.27
-- 1.3.6.1.4.1.37950.1.1.5.12.8.3.23.1.27
-- 1.3.6.1.4.1.37950.1.1.5.12.8.3.23.1.27
-- 1.3.6.1.4.1.37950.1.1.5.12.8.3.23.1.27
-- 1.3.6.1.4.1.37950.1.1.5.12.8.3.23.1.27
		-- 1.3.6.1.4.1.37950.1.1.5.12.8.3.23.1.27
		ctcQueue OBJECT-TYPE
			SYNTAX Integer32 (0..7)
			MAX-ACCESS read-write
			STATUS current
			DESCRIPTION
				"Description."
			::= { onuClassifyAdd 27 }

		
--          1.3.6.1.4.1.37950.1.1.5.12.8.3.23.2
-- 1.3.6.1.4.1.37950.1.1.5.12.8.3.23.2
-- 1.3.6.1.4.1.37950.1.1.5.12.8.3.23.2
-- 1.3.6.1.4.1.37950.1.1.5.12.8.3.23.2
-- 1.3.6.1.4.1.37950.1.1.5.12.8.3.23.2
-- 1.3.6.1.4.1.37950.1.1.5.12.8.3.23.2
-- 1.3.6.1.4.1.37950.1.1.5.12.8.3.23.2
-- 1.3.6.1.4.1.37950.1.1.5.12.8.3.23.2
-- 1.3.6.1.4.1.37950.1.1.5.12.8.3.23.2
		-- 1.3.6.1.4.1.37950.1.1.5.12.8.3.23.2
		onuClassifyDel OBJECT IDENTIFIER ::= { onuClassifyConfig 2 }

		
--          1.3.6.1.4.1.37950.1.1.5.12.8.3.23.2.1
-- 1.3.6.1.4.1.37950.1.1.5.12.8.3.23.2.1
-- 1.3.6.1.4.1.37950.1.1.5.12.8.3.23.2.1
-- 1.3.6.1.4.1.37950.1.1.5.12.8.3.23.2.1
-- 1.3.6.1.4.1.37950.1.1.5.12.8.3.23.2.1
-- 1.3.6.1.4.1.37950.1.1.5.12.8.3.23.2.1
-- 1.3.6.1.4.1.37950.1.1.5.12.8.3.23.2.1
-- 1.3.6.1.4.1.37950.1.1.5.12.8.3.23.2.1
-- 1.3.6.1.4.1.37950.1.1.5.12.8.3.23.2.1
		-- 1.3.6.1.4.1.37950.1.1.5.12.8.3.23.2.1
		cfyDelEthNo OBJECT-TYPE
			SYNTAX INTEGER (1..255)
			MAX-ACCESS read-write
			STATUS current
			DESCRIPTION
				"Description."
			::= { onuClassifyDel 1 }

		
--          1.3.6.1.4.1.37950.1.1.5.12.8.3.23.2.2
-- 1.3.6.1.4.1.37950.1.1.5.12.8.3.23.2.2
-- 1.3.6.1.4.1.37950.1.1.5.12.8.3.23.2.2
-- 1.3.6.1.4.1.37950.1.1.5.12.8.3.23.2.2
-- 1.3.6.1.4.1.37950.1.1.5.12.8.3.23.2.2
-- 1.3.6.1.4.1.37950.1.1.5.12.8.3.23.2.2
-- 1.3.6.1.4.1.37950.1.1.5.12.8.3.23.2.2
-- 1.3.6.1.4.1.37950.1.1.5.12.8.3.23.2.2
-- 1.3.6.1.4.1.37950.1.1.5.12.8.3.23.2.2
		-- 1.3.6.1.4.1.37950.1.1.5.12.8.3.23.2.2
		ctcDelPrecedence OBJECT-TYPE
			SYNTAX INTEGER (1..8)
			MAX-ACCESS read-write
			STATUS current
			DESCRIPTION
				"Description."
			::= { onuClassifyDel 2 }

		
--          1.3.6.1.4.1.37950.1.1.5.12.8.3.23.2.3
-- 1.3.6.1.4.1.37950.1.1.5.12.8.3.23.2.3
-- 1.3.6.1.4.1.37950.1.1.5.12.8.3.23.2.3
-- 1.3.6.1.4.1.37950.1.1.5.12.8.3.23.2.3
-- 1.3.6.1.4.1.37950.1.1.5.12.8.3.23.2.3
-- 1.3.6.1.4.1.37950.1.1.5.12.8.3.23.2.3
-- 1.3.6.1.4.1.37950.1.1.5.12.8.3.23.2.3
-- 1.3.6.1.4.1.37950.1.1.5.12.8.3.23.2.3
-- 1.3.6.1.4.1.37950.1.1.5.12.8.3.23.2.3
		-- 1.3.6.1.4.1.37950.1.1.5.12.8.3.23.2.3
		ctcCfyDelAction OBJECT-TYPE
			SYNTAX INTEGER
				{
				delete(1),
				clearAll(2)
				}
			MAX-ACCESS read-write
			STATUS current
			DESCRIPTION
				"Description."
			::= { onuClassifyDel 3 }

		
--          1.3.6.1.4.1.37950.1.1.5.12.8.3.24
-- 1.3.6.1.4.1.37950.1.1.5.12.8.3.24
-- 1.3.6.1.4.1.37950.1.1.5.12.8.3.24
-- 1.3.6.1.4.1.37950.1.1.5.12.8.3.24
-- 1.3.6.1.4.1.37950.1.1.5.12.8.3.24
-- 1.3.6.1.4.1.37950.1.1.5.12.8.3.24
-- 1.3.6.1.4.1.37950.1.1.5.12.8.3.24
-- 1.3.6.1.4.1.37950.1.1.5.12.8.3.24
-- 1.3.6.1.4.1.37950.1.1.5.12.8.3.24
		-- 1.3.6.1.4.1.37950.1.1.5.12.8.3.24
		onuMacAgetime OBJECT IDENTIFIER ::= { srvProfileEdit 24 }

		
--          1.3.6.1.4.1.37950.1.1.5.12.8.3.24.1
-- 1.3.6.1.4.1.37950.1.1.5.12.8.3.24.1
-- 1.3.6.1.4.1.37950.1.1.5.12.8.3.24.1
-- 1.3.6.1.4.1.37950.1.1.5.12.8.3.24.1
-- 1.3.6.1.4.1.37950.1.1.5.12.8.3.24.1
-- 1.3.6.1.4.1.37950.1.1.5.12.8.3.24.1
-- 1.3.6.1.4.1.37950.1.1.5.12.8.3.24.1
-- 1.3.6.1.4.1.37950.1.1.5.12.8.3.24.1
-- 1.3.6.1.4.1.37950.1.1.5.12.8.3.24.1
		-- 1.3.6.1.4.1.37950.1.1.5.12.8.3.24.1
		ctcAgetime OBJECT-TYPE
			SYNTAX Gauge32 (0..4294967295)
			MAX-ACCESS read-write
			STATUS current
			DESCRIPTION
				"Description."
			::= { onuMacAgetime 1 }

		
--          1.3.6.1.4.1.37950.1.1.5.12.8.3.24.2
-- 1.3.6.1.4.1.37950.1.1.5.12.8.3.24.2
-- 1.3.6.1.4.1.37950.1.1.5.12.8.3.24.2
-- 1.3.6.1.4.1.37950.1.1.5.12.8.3.24.2
-- 1.3.6.1.4.1.37950.1.1.5.12.8.3.24.2
-- 1.3.6.1.4.1.37950.1.1.5.12.8.3.24.2
-- 1.3.6.1.4.1.37950.1.1.5.12.8.3.24.2
-- 1.3.6.1.4.1.37950.1.1.5.12.8.3.24.2
-- 1.3.6.1.4.1.37950.1.1.5.12.8.3.24.2
		-- 1.3.6.1.4.1.37950.1.1.5.12.8.3.24.2
		agetimeAction OBJECT-TYPE
			SYNTAX INTEGER
				{
				commit(1),
				remove(2)
				}
			MAX-ACCESS read-write
			STATUS current
			DESCRIPTION
				"Description."
			::= { onuMacAgetime 2 }

		
--          1.3.6.1.4.1.37950.1.1.5.12.8.3.25
-- 1.3.6.1.4.1.37950.1.1.5.12.8.3.25
-- 1.3.6.1.4.1.37950.1.1.5.12.8.3.25
-- 1.3.6.1.4.1.37950.1.1.5.12.8.3.25
-- 1.3.6.1.4.1.37950.1.1.5.12.8.3.25
-- 1.3.6.1.4.1.37950.1.1.5.12.8.3.25
-- 1.3.6.1.4.1.37950.1.1.5.12.8.3.25
-- 1.3.6.1.4.1.37950.1.1.5.12.8.3.25
-- 1.3.6.1.4.1.37950.1.1.5.12.8.3.25
		-- 1.3.6.1.4.1.37950.1.1.5.12.8.3.25
		onuPonProtect OBJECT IDENTIFIER ::= { srvProfileEdit 25 }

		
--          1.3.6.1.4.1.37950.1.1.5.12.8.3.25.1
-- 1.3.6.1.4.1.37950.1.1.5.12.8.3.25.1
-- 1.3.6.1.4.1.37950.1.1.5.12.8.3.25.1
-- 1.3.6.1.4.1.37950.1.1.5.12.8.3.25.1
-- 1.3.6.1.4.1.37950.1.1.5.12.8.3.25.1
-- 1.3.6.1.4.1.37950.1.1.5.12.8.3.25.1
-- 1.3.6.1.4.1.37950.1.1.5.12.8.3.25.1
-- 1.3.6.1.4.1.37950.1.1.5.12.8.3.25.1
-- 1.3.6.1.4.1.37950.1.1.5.12.8.3.25.1
		-- 1.3.6.1.4.1.37950.1.1.5.12.8.3.25.1
		ctcLosOptical OBJECT-TYPE
			SYNTAX INTEGER (0..65535)
			MAX-ACCESS read-write
			STATUS current
			DESCRIPTION
				"Description."
			::= { onuPonProtect 1 }

		
--          1.3.6.1.4.1.37950.1.1.5.12.8.3.25.2
-- 1.3.6.1.4.1.37950.1.1.5.12.8.3.25.2
-- 1.3.6.1.4.1.37950.1.1.5.12.8.3.25.2
-- 1.3.6.1.4.1.37950.1.1.5.12.8.3.25.2
-- 1.3.6.1.4.1.37950.1.1.5.12.8.3.25.2
-- 1.3.6.1.4.1.37950.1.1.5.12.8.3.25.2
-- 1.3.6.1.4.1.37950.1.1.5.12.8.3.25.2
-- 1.3.6.1.4.1.37950.1.1.5.12.8.3.25.2
-- 1.3.6.1.4.1.37950.1.1.5.12.8.3.25.2
		-- 1.3.6.1.4.1.37950.1.1.5.12.8.3.25.2
		ctcLosMpcp OBJECT-TYPE
			SYNTAX INTEGER (0..65535)
			MAX-ACCESS read-write
			STATUS current
			DESCRIPTION
				"Description."
			::= { onuPonProtect 2 }

		
--          1.3.6.1.4.1.37950.1.1.5.12.8.3.25.3
-- 1.3.6.1.4.1.37950.1.1.5.12.8.3.25.3
-- 1.3.6.1.4.1.37950.1.1.5.12.8.3.25.3
-- 1.3.6.1.4.1.37950.1.1.5.12.8.3.25.3
-- 1.3.6.1.4.1.37950.1.1.5.12.8.3.25.3
-- 1.3.6.1.4.1.37950.1.1.5.12.8.3.25.3
-- 1.3.6.1.4.1.37950.1.1.5.12.8.3.25.3
-- 1.3.6.1.4.1.37950.1.1.5.12.8.3.25.3
-- 1.3.6.1.4.1.37950.1.1.5.12.8.3.25.3
		-- 1.3.6.1.4.1.37950.1.1.5.12.8.3.25.3
		ctcPonProtectAction OBJECT-TYPE
			SYNTAX INTEGER
				{
				commit(1),
				remove(2)
				}
			MAX-ACCESS read-write
			STATUS current
			DESCRIPTION
				"Description."
			::= { onuPonProtect 3 }

		
--          1.3.6.1.4.1.37950.1.1.5.12.8.3.26
-- 1.3.6.1.4.1.37950.1.1.5.12.8.3.26
-- 1.3.6.1.4.1.37950.1.1.5.12.8.3.26
-- 1.3.6.1.4.1.37950.1.1.5.12.8.3.26
-- 1.3.6.1.4.1.37950.1.1.5.12.8.3.26
-- 1.3.6.1.4.1.37950.1.1.5.12.8.3.26
-- 1.3.6.1.4.1.37950.1.1.5.12.8.3.26
-- 1.3.6.1.4.1.37950.1.1.5.12.8.3.26
-- 1.3.6.1.4.1.37950.1.1.5.12.8.3.26
		-- 1.3.6.1.4.1.37950.1.1.5.12.8.3.26
		onuPowerSaveConfig OBJECT IDENTIFIER ::= { srvProfileEdit 26 }

		
--          1.3.6.1.4.1.37950.1.1.5.12.8.3.26.1
-- 1.3.6.1.4.1.37950.1.1.5.12.8.3.26.1
-- 1.3.6.1.4.1.37950.1.1.5.12.8.3.26.1
-- 1.3.6.1.4.1.37950.1.1.5.12.8.3.26.1
-- 1.3.6.1.4.1.37950.1.1.5.12.8.3.26.1
-- 1.3.6.1.4.1.37950.1.1.5.12.8.3.26.1
-- 1.3.6.1.4.1.37950.1.1.5.12.8.3.26.1
-- 1.3.6.1.4.1.37950.1.1.5.12.8.3.26.1
-- 1.3.6.1.4.1.37950.1.1.5.12.8.3.26.1
		-- 1.3.6.1.4.1.37950.1.1.5.12.8.3.26.1
		ctcEarlyWakeupEn OBJECT-TYPE
			SYNTAX INTEGER
				{
				disable(0),
				enable(1)
				}
			MAX-ACCESS read-write
			STATUS current
			DESCRIPTION
				"Description."
			::= { onuPowerSaveConfig 1 }

		
--          1.3.6.1.4.1.37950.1.1.5.12.8.3.26.2
-- 1.3.6.1.4.1.37950.1.1.5.12.8.3.26.2
-- 1.3.6.1.4.1.37950.1.1.5.12.8.3.26.2
-- 1.3.6.1.4.1.37950.1.1.5.12.8.3.26.2
-- 1.3.6.1.4.1.37950.1.1.5.12.8.3.26.2
-- 1.3.6.1.4.1.37950.1.1.5.12.8.3.26.2
-- 1.3.6.1.4.1.37950.1.1.5.12.8.3.26.2
-- 1.3.6.1.4.1.37950.1.1.5.12.8.3.26.2
-- 1.3.6.1.4.1.37950.1.1.5.12.8.3.26.2
		-- 1.3.6.1.4.1.37950.1.1.5.12.8.3.26.2
		ctcSleepDurationMax OBJECT-TYPE
			SYNTAX INTEGER (0..65535)
			MAX-ACCESS read-write
			STATUS current
			DESCRIPTION
				"Description."
			::= { onuPowerSaveConfig 2 }

		
--          1.3.6.1.4.1.37950.1.1.5.12.8.3.26.3
-- 1.3.6.1.4.1.37950.1.1.5.12.8.3.26.3
-- 1.3.6.1.4.1.37950.1.1.5.12.8.3.26.3
-- 1.3.6.1.4.1.37950.1.1.5.12.8.3.26.3
-- 1.3.6.1.4.1.37950.1.1.5.12.8.3.26.3
-- 1.3.6.1.4.1.37950.1.1.5.12.8.3.26.3
-- 1.3.6.1.4.1.37950.1.1.5.12.8.3.26.3
-- 1.3.6.1.4.1.37950.1.1.5.12.8.3.26.3
-- 1.3.6.1.4.1.37950.1.1.5.12.8.3.26.3
		-- 1.3.6.1.4.1.37950.1.1.5.12.8.3.26.3
		onuPowerSaveAction OBJECT-TYPE
			SYNTAX INTEGER
				{
				commit(1),
				remove(2)
				}
			MAX-ACCESS read-write
			STATUS current
			DESCRIPTION
				"Description."
			::= { onuPowerSaveConfig 3 }

		
--          1.3.6.1.4.1.37950.1.1.5.12.8.3.27
-- 1.3.6.1.4.1.37950.1.1.5.12.8.3.27
-- 1.3.6.1.4.1.37950.1.1.5.12.8.3.27
-- 1.3.6.1.4.1.37950.1.1.5.12.8.3.27
-- 1.3.6.1.4.1.37950.1.1.5.12.8.3.27
-- 1.3.6.1.4.1.37950.1.1.5.12.8.3.27
-- 1.3.6.1.4.1.37950.1.1.5.12.8.3.27
-- 1.3.6.1.4.1.37950.1.1.5.12.8.3.27
-- 1.3.6.1.4.1.37950.1.1.5.12.8.3.27
		-- 1.3.6.1.4.1.37950.1.1.5.12.8.3.27
		onuPwSavParameter OBJECT IDENTIFIER ::= { srvProfileEdit 27 }

		
--          1.3.6.1.4.1.37950.1.1.5.12.8.3.27.1
-- 1.3.6.1.4.1.37950.1.1.5.12.8.3.27.1
-- 1.3.6.1.4.1.37950.1.1.5.12.8.3.27.1
-- 1.3.6.1.4.1.37950.1.1.5.12.8.3.27.1
-- 1.3.6.1.4.1.37950.1.1.5.12.8.3.27.1
-- 1.3.6.1.4.1.37950.1.1.5.12.8.3.27.1
-- 1.3.6.1.4.1.37950.1.1.5.12.8.3.27.1
-- 1.3.6.1.4.1.37950.1.1.5.12.8.3.27.1
-- 1.3.6.1.4.1.37950.1.1.5.12.8.3.27.1
		-- 1.3.6.1.4.1.37950.1.1.5.12.8.3.27.1
		ctcSleepDuration OBJECT-TYPE
			SYNTAX INTEGER (0..65535)
			MAX-ACCESS read-write
			STATUS current
			DESCRIPTION
				"Description."
			::= { onuPwSavParameter 1 }

		
--          1.3.6.1.4.1.37950.1.1.5.12.8.3.27.2
-- 1.3.6.1.4.1.37950.1.1.5.12.8.3.27.2
-- 1.3.6.1.4.1.37950.1.1.5.12.8.3.27.2
-- 1.3.6.1.4.1.37950.1.1.5.12.8.3.27.2
-- 1.3.6.1.4.1.37950.1.1.5.12.8.3.27.2
-- 1.3.6.1.4.1.37950.1.1.5.12.8.3.27.2
-- 1.3.6.1.4.1.37950.1.1.5.12.8.3.27.2
-- 1.3.6.1.4.1.37950.1.1.5.12.8.3.27.2
-- 1.3.6.1.4.1.37950.1.1.5.12.8.3.27.2
		-- 1.3.6.1.4.1.37950.1.1.5.12.8.3.27.2
		ctcWakeDuration OBJECT-TYPE
			SYNTAX INTEGER (0..65535)
			MAX-ACCESS read-write
			STATUS current
			DESCRIPTION
				"Description."
			::= { onuPwSavParameter 2 }

		
--          1.3.6.1.4.1.37950.1.1.5.12.8.3.27.3
-- 1.3.6.1.4.1.37950.1.1.5.12.8.3.27.3
-- 1.3.6.1.4.1.37950.1.1.5.12.8.3.27.3
-- 1.3.6.1.4.1.37950.1.1.5.12.8.3.27.3
-- 1.3.6.1.4.1.37950.1.1.5.12.8.3.27.3
-- 1.3.6.1.4.1.37950.1.1.5.12.8.3.27.3
-- 1.3.6.1.4.1.37950.1.1.5.12.8.3.27.3
-- 1.3.6.1.4.1.37950.1.1.5.12.8.3.27.3
-- 1.3.6.1.4.1.37950.1.1.5.12.8.3.27.3
		-- 1.3.6.1.4.1.37950.1.1.5.12.8.3.27.3
		ctcSleepFlag OBJECT-TYPE
			SYNTAX INTEGER
				{
				off(1),
				on(2),
				change(3)
				}
			MAX-ACCESS read-write
			STATUS current
			DESCRIPTION
				"Description."
			::= { onuPwSavParameter 3 }

		
--          1.3.6.1.4.1.37950.1.1.5.12.8.3.27.4
-- 1.3.6.1.4.1.37950.1.1.5.12.8.3.27.4
-- 1.3.6.1.4.1.37950.1.1.5.12.8.3.27.4
-- 1.3.6.1.4.1.37950.1.1.5.12.8.3.27.4
-- 1.3.6.1.4.1.37950.1.1.5.12.8.3.27.4
-- 1.3.6.1.4.1.37950.1.1.5.12.8.3.27.4
-- 1.3.6.1.4.1.37950.1.1.5.12.8.3.27.4
-- 1.3.6.1.4.1.37950.1.1.5.12.8.3.27.4
-- 1.3.6.1.4.1.37950.1.1.5.12.8.3.27.4
		-- 1.3.6.1.4.1.37950.1.1.5.12.8.3.27.4
		ctcSleepMode OBJECT-TYPE
			SYNTAX INTEGER
				{
				none(1),
				txSleepOnly(2),
				txAndRxSleep(3)
				}
			MAX-ACCESS read-write
			STATUS current
			DESCRIPTION
				"Description."
			::= { onuPwSavParameter 4 }

		
--          1.3.6.1.4.1.37950.1.1.5.12.8.3.27.5
-- 1.3.6.1.4.1.37950.1.1.5.12.8.3.27.5
-- 1.3.6.1.4.1.37950.1.1.5.12.8.3.27.5
-- 1.3.6.1.4.1.37950.1.1.5.12.8.3.27.5
-- 1.3.6.1.4.1.37950.1.1.5.12.8.3.27.5
-- 1.3.6.1.4.1.37950.1.1.5.12.8.3.27.5
-- 1.3.6.1.4.1.37950.1.1.5.12.8.3.27.5
-- 1.3.6.1.4.1.37950.1.1.5.12.8.3.27.5
-- 1.3.6.1.4.1.37950.1.1.5.12.8.3.27.5
		-- 1.3.6.1.4.1.37950.1.1.5.12.8.3.27.5
		onuPwSavAction OBJECT-TYPE
			SYNTAX INTEGER
				{
				commit(1),
				remove(2)
				}
			MAX-ACCESS read-write
			STATUS current
			DESCRIPTION
				"Description."
			::= { onuPwSavParameter 5 }

		
--          1.3.6.1.4.1.37950.1.1.5.12.8.3.28
-- 1.3.6.1.4.1.37950.1.1.5.12.8.3.28
-- 1.3.6.1.4.1.37950.1.1.5.12.8.3.28
-- 1.3.6.1.4.1.37950.1.1.5.12.8.3.28
-- 1.3.6.1.4.1.37950.1.1.5.12.8.3.28
-- 1.3.6.1.4.1.37950.1.1.5.12.8.3.28
-- 1.3.6.1.4.1.37950.1.1.5.12.8.3.28
-- 1.3.6.1.4.1.37950.1.1.5.12.8.3.28
-- 1.3.6.1.4.1.37950.1.1.5.12.8.3.28
		-- 1.3.6.1.4.1.37950.1.1.5.12.8.3.28
		onuDisableLoopConfig OBJECT IDENTIFIER ::= { srvProfileEdit 28 }

		
--          1.3.6.1.4.1.37950.1.1.5.12.8.3.28.1
-- 1.3.6.1.4.1.37950.1.1.5.12.8.3.28.1
-- 1.3.6.1.4.1.37950.1.1.5.12.8.3.28.1
-- 1.3.6.1.4.1.37950.1.1.5.12.8.3.28.1
-- 1.3.6.1.4.1.37950.1.1.5.12.8.3.28.1
-- 1.3.6.1.4.1.37950.1.1.5.12.8.3.28.1
-- 1.3.6.1.4.1.37950.1.1.5.12.8.3.28.1
-- 1.3.6.1.4.1.37950.1.1.5.12.8.3.28.1
-- 1.3.6.1.4.1.37950.1.1.5.12.8.3.28.1
		-- 1.3.6.1.4.1.37950.1.1.5.12.8.3.28.1
		disLoopEthNo OBJECT-TYPE
			SYNTAX INTEGER (1..255)
			MAX-ACCESS read-write
			STATUS current
			DESCRIPTION
				"Description."
			::= { onuDisableLoopConfig 1 }

		
--          1.3.6.1.4.1.37950.1.1.5.12.8.3.28.2
-- 1.3.6.1.4.1.37950.1.1.5.12.8.3.28.2
-- 1.3.6.1.4.1.37950.1.1.5.12.8.3.28.2
-- 1.3.6.1.4.1.37950.1.1.5.12.8.3.28.2
-- 1.3.6.1.4.1.37950.1.1.5.12.8.3.28.2
-- 1.3.6.1.4.1.37950.1.1.5.12.8.3.28.2
-- 1.3.6.1.4.1.37950.1.1.5.12.8.3.28.2
-- 1.3.6.1.4.1.37950.1.1.5.12.8.3.28.2
-- 1.3.6.1.4.1.37950.1.1.5.12.8.3.28.2
		-- 1.3.6.1.4.1.37950.1.1.5.12.8.3.28.2
		disableLoopEn OBJECT-TYPE
			SYNTAX INTEGER
				{
				disable(0),
				enable(1)
				}
			MAX-ACCESS read-write
			STATUS current
			DESCRIPTION
				"Description."
			::= { onuDisableLoopConfig 2 }

		
--          1.3.6.1.4.1.37950.1.1.5.12.8.3.28.3
-- 1.3.6.1.4.1.37950.1.1.5.12.8.3.28.3
-- 1.3.6.1.4.1.37950.1.1.5.12.8.3.28.3
-- 1.3.6.1.4.1.37950.1.1.5.12.8.3.28.3
-- 1.3.6.1.4.1.37950.1.1.5.12.8.3.28.3
-- 1.3.6.1.4.1.37950.1.1.5.12.8.3.28.3
-- 1.3.6.1.4.1.37950.1.1.5.12.8.3.28.3
-- 1.3.6.1.4.1.37950.1.1.5.12.8.3.28.3
-- 1.3.6.1.4.1.37950.1.1.5.12.8.3.28.3
		-- 1.3.6.1.4.1.37950.1.1.5.12.8.3.28.3
		disLoopEthAction OBJECT-TYPE
			SYNTAX INTEGER
				{
				add(1),
				delete(2)
				}
			MAX-ACCESS read-write
			STATUS current
			DESCRIPTION
				"Description."
			::= { onuDisableLoopConfig 3 }

		
--          1.3.6.1.4.1.37950.1.1.5.12.8.3.29
-- 1.3.6.1.4.1.37950.1.1.5.12.8.3.29
-- 1.3.6.1.4.1.37950.1.1.5.12.8.3.29
-- 1.3.6.1.4.1.37950.1.1.5.12.8.3.29
-- 1.3.6.1.4.1.37950.1.1.5.12.8.3.29
-- 1.3.6.1.4.1.37950.1.1.5.12.8.3.29
-- 1.3.6.1.4.1.37950.1.1.5.12.8.3.29
-- 1.3.6.1.4.1.37950.1.1.5.12.8.3.29
-- 1.3.6.1.4.1.37950.1.1.5.12.8.3.29
		-- 1.3.6.1.4.1.37950.1.1.5.12.8.3.29
		onuPortStatConfig OBJECT IDENTIFIER ::= { srvProfileEdit 29 }

		
--          1.3.6.1.4.1.37950.1.1.5.12.8.3.29.1
-- 1.3.6.1.4.1.37950.1.1.5.12.8.3.29.1
-- 1.3.6.1.4.1.37950.1.1.5.12.8.3.29.1
-- 1.3.6.1.4.1.37950.1.1.5.12.8.3.29.1
-- 1.3.6.1.4.1.37950.1.1.5.12.8.3.29.1
-- 1.3.6.1.4.1.37950.1.1.5.12.8.3.29.1
-- 1.3.6.1.4.1.37950.1.1.5.12.8.3.29.1
-- 1.3.6.1.4.1.37950.1.1.5.12.8.3.29.1
-- 1.3.6.1.4.1.37950.1.1.5.12.8.3.29.1
		-- 1.3.6.1.4.1.37950.1.1.5.12.8.3.29.1
		portStatEthNo OBJECT-TYPE
			SYNTAX INTEGER (1..255)
			MAX-ACCESS read-write
			STATUS current
			DESCRIPTION
				"Description."
			::= { onuPortStatConfig 1 }

		
--          1.3.6.1.4.1.37950.1.1.5.12.8.3.29.2
-- 1.3.6.1.4.1.37950.1.1.5.12.8.3.29.2
-- 1.3.6.1.4.1.37950.1.1.5.12.8.3.29.2
-- 1.3.6.1.4.1.37950.1.1.5.12.8.3.29.2
-- 1.3.6.1.4.1.37950.1.1.5.12.8.3.29.2
-- 1.3.6.1.4.1.37950.1.1.5.12.8.3.29.2
-- 1.3.6.1.4.1.37950.1.1.5.12.8.3.29.2
-- 1.3.6.1.4.1.37950.1.1.5.12.8.3.29.2
-- 1.3.6.1.4.1.37950.1.1.5.12.8.3.29.2
		-- 1.3.6.1.4.1.37950.1.1.5.12.8.3.29.2
		ctcMonitorStatus OBJECT-TYPE
			SYNTAX INTEGER
				{
				disable(0),
				enable(1)
				}
			MAX-ACCESS read-write
			STATUS current
			DESCRIPTION
				"Description."
			::= { onuPortStatConfig 2 }

		
--          1.3.6.1.4.1.37950.1.1.5.12.8.3.29.3
-- 1.3.6.1.4.1.37950.1.1.5.12.8.3.29.3
-- 1.3.6.1.4.1.37950.1.1.5.12.8.3.29.3
-- 1.3.6.1.4.1.37950.1.1.5.12.8.3.29.3
-- 1.3.6.1.4.1.37950.1.1.5.12.8.3.29.3
-- 1.3.6.1.4.1.37950.1.1.5.12.8.3.29.3
-- 1.3.6.1.4.1.37950.1.1.5.12.8.3.29.3
-- 1.3.6.1.4.1.37950.1.1.5.12.8.3.29.3
-- 1.3.6.1.4.1.37950.1.1.5.12.8.3.29.3
		-- 1.3.6.1.4.1.37950.1.1.5.12.8.3.29.3
		ctcStatCycle OBJECT-TYPE
			SYNTAX INTEGER (0..65535)
			MAX-ACCESS read-write
			STATUS current
			DESCRIPTION
				"Description."
			::= { onuPortStatConfig 3 }

		
--          1.3.6.1.4.1.37950.1.1.5.12.8.3.29.4
-- 1.3.6.1.4.1.37950.1.1.5.12.8.3.29.4
-- 1.3.6.1.4.1.37950.1.1.5.12.8.3.29.4
-- 1.3.6.1.4.1.37950.1.1.5.12.8.3.29.4
-- 1.3.6.1.4.1.37950.1.1.5.12.8.3.29.4
-- 1.3.6.1.4.1.37950.1.1.5.12.8.3.29.4
-- 1.3.6.1.4.1.37950.1.1.5.12.8.3.29.4
-- 1.3.6.1.4.1.37950.1.1.5.12.8.3.29.4
-- 1.3.6.1.4.1.37950.1.1.5.12.8.3.29.4
		-- 1.3.6.1.4.1.37950.1.1.5.12.8.3.29.4
		portStatAction OBJECT-TYPE
			SYNTAX INTEGER
				{
				add(1),
				remove(2)
				}
			MAX-ACCESS read-write
			STATUS current
			DESCRIPTION
				"Description."
			::= { onuPortStatConfig 4 }

		
--          1.3.6.1.4.1.37950.1.1.5.12.8.3.30
-- 1.3.6.1.4.1.37950.1.1.5.12.8.3.30
-- 1.3.6.1.4.1.37950.1.1.5.12.8.3.30
-- 1.3.6.1.4.1.37950.1.1.5.12.8.3.30
-- 1.3.6.1.4.1.37950.1.1.5.12.8.3.30
-- 1.3.6.1.4.1.37950.1.1.5.12.8.3.30
-- 1.3.6.1.4.1.37950.1.1.5.12.8.3.30
-- 1.3.6.1.4.1.37950.1.1.5.12.8.3.30
-- 1.3.6.1.4.1.37950.1.1.5.12.8.3.30
		-- 1.3.6.1.4.1.37950.1.1.5.12.8.3.30
		onuPortStatClear OBJECT IDENTIFIER ::= { srvProfileEdit 30 }

		
--          1.3.6.1.4.1.37950.1.1.5.12.8.3.30.1
-- 1.3.6.1.4.1.37950.1.1.5.12.8.3.30.1
-- 1.3.6.1.4.1.37950.1.1.5.12.8.3.30.1
-- 1.3.6.1.4.1.37950.1.1.5.12.8.3.30.1
-- 1.3.6.1.4.1.37950.1.1.5.12.8.3.30.1
-- 1.3.6.1.4.1.37950.1.1.5.12.8.3.30.1
-- 1.3.6.1.4.1.37950.1.1.5.12.8.3.30.1
-- 1.3.6.1.4.1.37950.1.1.5.12.8.3.30.1
-- 1.3.6.1.4.1.37950.1.1.5.12.8.3.30.1
		-- 1.3.6.1.4.1.37950.1.1.5.12.8.3.30.1
		ctcClearEthNo OBJECT-TYPE
			SYNTAX INTEGER (1..255)
			MAX-ACCESS read-write
			STATUS current
			DESCRIPTION
				"Description."
			::= { onuPortStatClear 1 }

		
--          1.3.6.1.4.1.37950.1.1.5.12.8.3.30.2
-- 1.3.6.1.4.1.37950.1.1.5.12.8.3.30.2
-- 1.3.6.1.4.1.37950.1.1.5.12.8.3.30.2
-- 1.3.6.1.4.1.37950.1.1.5.12.8.3.30.2
-- 1.3.6.1.4.1.37950.1.1.5.12.8.3.30.2
-- 1.3.6.1.4.1.37950.1.1.5.12.8.3.30.2
-- 1.3.6.1.4.1.37950.1.1.5.12.8.3.30.2
-- 1.3.6.1.4.1.37950.1.1.5.12.8.3.30.2
-- 1.3.6.1.4.1.37950.1.1.5.12.8.3.30.2
		-- 1.3.6.1.4.1.37950.1.1.5.12.8.3.30.2
		ctcClearAction OBJECT-TYPE
			SYNTAX INTEGER
				{
				add(1),
				remove(2)
				}
			MAX-ACCESS read-write
			STATUS current
			DESCRIPTION
				"Description."
			::= { onuPortStatClear 2 }

		
--          1.3.6.1.4.1.37950.1.1.5.12.8.3.31
-- 1.3.6.1.4.1.37950.1.1.5.12.8.3.31
-- 1.3.6.1.4.1.37950.1.1.5.12.8.3.31
-- 1.3.6.1.4.1.37950.1.1.5.12.8.3.31
-- 1.3.6.1.4.1.37950.1.1.5.12.8.3.31
-- 1.3.6.1.4.1.37950.1.1.5.12.8.3.31
-- 1.3.6.1.4.1.37950.1.1.5.12.8.3.31
-- 1.3.6.1.4.1.37950.1.1.5.12.8.3.31
-- 1.3.6.1.4.1.37950.1.1.5.12.8.3.31
		-- 1.3.6.1.4.1.37950.1.1.5.12.8.3.31
		onuIgmpAdmin OBJECT IDENTIFIER ::= { srvProfileEdit 31 }

		
--          1.3.6.1.4.1.37950.1.1.5.12.8.3.31.1
-- 1.3.6.1.4.1.37950.1.1.5.12.8.3.31.1
-- 1.3.6.1.4.1.37950.1.1.5.12.8.3.31.1
-- 1.3.6.1.4.1.37950.1.1.5.12.8.3.31.1
-- 1.3.6.1.4.1.37950.1.1.5.12.8.3.31.1
-- 1.3.6.1.4.1.37950.1.1.5.12.8.3.31.1
-- 1.3.6.1.4.1.37950.1.1.5.12.8.3.31.1
-- 1.3.6.1.4.1.37950.1.1.5.12.8.3.31.1
-- 1.3.6.1.4.1.37950.1.1.5.12.8.3.31.1
		-- 1.3.6.1.4.1.37950.1.1.5.12.8.3.31.1
		igmpAdmin OBJECT-TYPE
			SYNTAX INTEGER
				{
				disable(0),
				enable(1)
				}
			MAX-ACCESS read-write
			STATUS current
			DESCRIPTION
				"Description."
			::= { onuIgmpAdmin 1 }

		
--          1.3.6.1.4.1.37950.1.1.5.12.8.3.31.2
-- 1.3.6.1.4.1.37950.1.1.5.12.8.3.31.2
-- 1.3.6.1.4.1.37950.1.1.5.12.8.3.31.2
-- 1.3.6.1.4.1.37950.1.1.5.12.8.3.31.2
-- 1.3.6.1.4.1.37950.1.1.5.12.8.3.31.2
-- 1.3.6.1.4.1.37950.1.1.5.12.8.3.31.2
-- 1.3.6.1.4.1.37950.1.1.5.12.8.3.31.2
-- 1.3.6.1.4.1.37950.1.1.5.12.8.3.31.2
-- 1.3.6.1.4.1.37950.1.1.5.12.8.3.31.2
		-- 1.3.6.1.4.1.37950.1.1.5.12.8.3.31.2
		igmpAdminAction OBJECT-TYPE
			SYNTAX INTEGER
				{
				add(1),
				remove(2)
				}
			MAX-ACCESS read-write
			STATUS current
			DESCRIPTION
				"Description."
			::= { onuIgmpAdmin 2 }

		
--          1.3.6.1.4.1.37950.1.1.5.12.8.3.32
-- 1.3.6.1.4.1.37950.1.1.5.12.8.3.32
-- 1.3.6.1.4.1.37950.1.1.5.12.8.3.32
-- 1.3.6.1.4.1.37950.1.1.5.12.8.3.32
-- 1.3.6.1.4.1.37950.1.1.5.12.8.3.32
-- 1.3.6.1.4.1.37950.1.1.5.12.8.3.32
-- 1.3.6.1.4.1.37950.1.1.5.12.8.3.32
-- 1.3.6.1.4.1.37950.1.1.5.12.8.3.32
-- 1.3.6.1.4.1.37950.1.1.5.12.8.3.32
		-- 1.3.6.1.4.1.37950.1.1.5.12.8.3.32
		onuCatvEnable OBJECT IDENTIFIER ::= { srvProfileEdit 32 }

		
--          1.3.6.1.4.1.37950.1.1.5.12.8.3.32.1
-- 1.3.6.1.4.1.37950.1.1.5.12.8.3.32.1
-- 1.3.6.1.4.1.37950.1.1.5.12.8.3.32.1
-- 1.3.6.1.4.1.37950.1.1.5.12.8.3.32.1
-- 1.3.6.1.4.1.37950.1.1.5.12.8.3.32.1
-- 1.3.6.1.4.1.37950.1.1.5.12.8.3.32.1
-- 1.3.6.1.4.1.37950.1.1.5.12.8.3.32.1
-- 1.3.6.1.4.1.37950.1.1.5.12.8.3.32.1
-- 1.3.6.1.4.1.37950.1.1.5.12.8.3.32.1
		-- 1.3.6.1.4.1.37950.1.1.5.12.8.3.32.1
		catvEnable OBJECT-TYPE
			SYNTAX INTEGER
				{
				disable(0),
				enable(1)
				}
			MAX-ACCESS read-write
			STATUS current
			DESCRIPTION
				"Description."
			::= { onuCatvEnable 1 }

		
--          1.3.6.1.4.1.37950.1.1.5.12.8.3.32.2
-- 1.3.6.1.4.1.37950.1.1.5.12.8.3.32.2
-- 1.3.6.1.4.1.37950.1.1.5.12.8.3.32.2
-- 1.3.6.1.4.1.37950.1.1.5.12.8.3.32.2
-- 1.3.6.1.4.1.37950.1.1.5.12.8.3.32.2
-- 1.3.6.1.4.1.37950.1.1.5.12.8.3.32.2
-- 1.3.6.1.4.1.37950.1.1.5.12.8.3.32.2
-- 1.3.6.1.4.1.37950.1.1.5.12.8.3.32.2
-- 1.3.6.1.4.1.37950.1.1.5.12.8.3.32.2
		-- 1.3.6.1.4.1.37950.1.1.5.12.8.3.32.2
		catvEnableAction OBJECT-TYPE
			SYNTAX INTEGER
				{
				add(1),
				remove(2)
				}
			MAX-ACCESS read-write
			STATUS current
			DESCRIPTION
				"Description."
			::= { onuCatvEnable 2 }

		
--          1.3.6.1.4.1.37950.1.1.5.12.8.3.33
-- 1.3.6.1.4.1.37950.1.1.5.12.8.3.33
-- 1.3.6.1.4.1.37950.1.1.5.12.8.3.33
-- 1.3.6.1.4.1.37950.1.1.5.12.8.3.33
-- 1.3.6.1.4.1.37950.1.1.5.12.8.3.33
-- 1.3.6.1.4.1.37950.1.1.5.12.8.3.33
-- 1.3.6.1.4.1.37950.1.1.5.12.8.3.33
-- 1.3.6.1.4.1.37950.1.1.5.12.8.3.33
-- 1.3.6.1.4.1.37950.1.1.5.12.8.3.33
		-- 1.3.6.1.4.1.37950.1.1.5.12.8.3.33
		onuCtcoamSkip OBJECT IDENTIFIER ::= { srvProfileEdit 33 }

		
--          1.3.6.1.4.1.37950.1.1.5.12.8.3.33.1
-- 1.3.6.1.4.1.37950.1.1.5.12.8.3.33.1
-- 1.3.6.1.4.1.37950.1.1.5.12.8.3.33.1
-- 1.3.6.1.4.1.37950.1.1.5.12.8.3.33.1
-- 1.3.6.1.4.1.37950.1.1.5.12.8.3.33.1
-- 1.3.6.1.4.1.37950.1.1.5.12.8.3.33.1
-- 1.3.6.1.4.1.37950.1.1.5.12.8.3.33.1
-- 1.3.6.1.4.1.37950.1.1.5.12.8.3.33.1
-- 1.3.6.1.4.1.37950.1.1.5.12.8.3.33.1
		-- 1.3.6.1.4.1.37950.1.1.5.12.8.3.33.1
		ctcoamSkip OBJECT-TYPE
			SYNTAX INTEGER
				{
				disable(0),
				enable(1)
				}
			MAX-ACCESS read-write
			STATUS current
			DESCRIPTION
				"Description."
			::= { onuCtcoamSkip 1 }

		
--          1.3.6.1.4.1.37950.1.1.5.12.8.3.33.2
-- 1.3.6.1.4.1.37950.1.1.5.12.8.3.33.2
-- 1.3.6.1.4.1.37950.1.1.5.12.8.3.33.2
-- 1.3.6.1.4.1.37950.1.1.5.12.8.3.33.2
-- 1.3.6.1.4.1.37950.1.1.5.12.8.3.33.2
-- 1.3.6.1.4.1.37950.1.1.5.12.8.3.33.2
-- 1.3.6.1.4.1.37950.1.1.5.12.8.3.33.2
-- 1.3.6.1.4.1.37950.1.1.5.12.8.3.33.2
-- 1.3.6.1.4.1.37950.1.1.5.12.8.3.33.2
		-- 1.3.6.1.4.1.37950.1.1.5.12.8.3.33.2
		ctcoamSkipAction OBJECT-TYPE
			SYNTAX INTEGER
				{
				disable(0),
				enable(1)
				}
			MAX-ACCESS read-write
			STATUS current
			DESCRIPTION
				"Description."
			::= { onuCtcoamSkip 2 }

		
--          1.3.6.1.4.1.37950.1.1.5.12.8.3.34
-- 1.3.6.1.4.1.37950.1.1.5.12.8.3.34
-- 1.3.6.1.4.1.37950.1.1.5.12.8.3.34
-- 1.3.6.1.4.1.37950.1.1.5.12.8.3.34
-- 1.3.6.1.4.1.37950.1.1.5.12.8.3.34
-- 1.3.6.1.4.1.37950.1.1.5.12.8.3.34
-- 1.3.6.1.4.1.37950.1.1.5.12.8.3.34
-- 1.3.6.1.4.1.37950.1.1.5.12.8.3.34
-- 1.3.6.1.4.1.37950.1.1.5.12.8.3.34
		-- 1.3.6.1.4.1.37950.1.1.5.12.8.3.34
		onuWifiSwich OBJECT IDENTIFIER ::= { srvProfileEdit 34 }

		
--          1.3.6.1.4.1.37950.1.1.5.12.8.3.34.1
-- 1.3.6.1.4.1.37950.1.1.5.12.8.3.34.1
-- 1.3.6.1.4.1.37950.1.1.5.12.8.3.34.1
-- 1.3.6.1.4.1.37950.1.1.5.12.8.3.34.1
-- 1.3.6.1.4.1.37950.1.1.5.12.8.3.34.1
-- 1.3.6.1.4.1.37950.1.1.5.12.8.3.34.1
-- 1.3.6.1.4.1.37950.1.1.5.12.8.3.34.1
-- 1.3.6.1.4.1.37950.1.1.5.12.8.3.34.1
-- 1.3.6.1.4.1.37950.1.1.5.12.8.3.34.1
		-- 1.3.6.1.4.1.37950.1.1.5.12.8.3.34.1
		wlanApmoduleEnable OBJECT-TYPE
			SYNTAX INTEGER
				{
				disable(0),
				enable(1)
				}
			MAX-ACCESS read-write
			STATUS current
			DESCRIPTION
				"Description."
			::= { onuWifiSwich 1 }

		
--          1.3.6.1.4.1.37950.1.1.5.12.8.3.34.2
-- 1.3.6.1.4.1.37950.1.1.5.12.8.3.34.2
-- 1.3.6.1.4.1.37950.1.1.5.12.8.3.34.2
-- 1.3.6.1.4.1.37950.1.1.5.12.8.3.34.2
-- 1.3.6.1.4.1.37950.1.1.5.12.8.3.34.2
-- 1.3.6.1.4.1.37950.1.1.5.12.8.3.34.2
-- 1.3.6.1.4.1.37950.1.1.5.12.8.3.34.2
-- 1.3.6.1.4.1.37950.1.1.5.12.8.3.34.2
-- 1.3.6.1.4.1.37950.1.1.5.12.8.3.34.2
		-- 1.3.6.1.4.1.37950.1.1.5.12.8.3.34.2
		wlanCountry OBJECT-TYPE
			SYNTAX INTEGER
				{
				etsi(0),
				fcc(1),
				ic(2),
				spain(3),
				france(4),
				mkk(5),
				isreal(6),
				mkk2(7),
				mkk3(8),
				russian(9),
				cn(10),
				global(11),
				world-wide(12),
				mkk1(13),
				ncc(14)
				}
			MAX-ACCESS read-write
			STATUS current
			DESCRIPTION
				"Description."
			::= { onuWifiSwich 2 }

		
--          1.3.6.1.4.1.37950.1.1.5.12.8.3.34.3
-- 1.3.6.1.4.1.37950.1.1.5.12.8.3.34.3
-- 1.3.6.1.4.1.37950.1.1.5.12.8.3.34.3
-- 1.3.6.1.4.1.37950.1.1.5.12.8.3.34.3
-- 1.3.6.1.4.1.37950.1.1.5.12.8.3.34.3
-- 1.3.6.1.4.1.37950.1.1.5.12.8.3.34.3
-- 1.3.6.1.4.1.37950.1.1.5.12.8.3.34.3
-- 1.3.6.1.4.1.37950.1.1.5.12.8.3.34.3
-- 1.3.6.1.4.1.37950.1.1.5.12.8.3.34.3
		-- 1.3.6.1.4.1.37950.1.1.5.12.8.3.34.3
		wlanChannel OBJECT-TYPE
			SYNTAX INTEGER (0..13)
			MAX-ACCESS read-write
			STATUS current
			DESCRIPTION
				"Description."
			::= { onuWifiSwich 3 }

		
--          1.3.6.1.4.1.37950.1.1.5.12.8.3.34.4
-- 1.3.6.1.4.1.37950.1.1.5.12.8.3.34.4
-- 1.3.6.1.4.1.37950.1.1.5.12.8.3.34.4
-- 1.3.6.1.4.1.37950.1.1.5.12.8.3.34.4
-- 1.3.6.1.4.1.37950.1.1.5.12.8.3.34.4
-- 1.3.6.1.4.1.37950.1.1.5.12.8.3.34.4
-- 1.3.6.1.4.1.37950.1.1.5.12.8.3.34.4
-- 1.3.6.1.4.1.37950.1.1.5.12.8.3.34.4
-- 1.3.6.1.4.1.37950.1.1.5.12.8.3.34.4
		-- 1.3.6.1.4.1.37950.1.1.5.12.8.3.34.4
		wlanStandard OBJECT-TYPE
			SYNTAX INTEGER
				{
				s80211b(0),
				s80211g(1),
				s80211bg(2),
				s80211n(3),
				s80211bgn(4),
				s80211ax(5),
				s80211bgnax(6)
				}
			MAX-ACCESS read-write
			STATUS current
			DESCRIPTION
				"Description."
			::= { onuWifiSwich 4 }

		
--          1.3.6.1.4.1.37950.1.1.5.12.8.3.34.5
-- 1.3.6.1.4.1.37950.1.1.5.12.8.3.34.5
-- 1.3.6.1.4.1.37950.1.1.5.12.8.3.34.5
-- 1.3.6.1.4.1.37950.1.1.5.12.8.3.34.5
-- 1.3.6.1.4.1.37950.1.1.5.12.8.3.34.5
-- 1.3.6.1.4.1.37950.1.1.5.12.8.3.34.5
-- 1.3.6.1.4.1.37950.1.1.5.12.8.3.34.5
-- 1.3.6.1.4.1.37950.1.1.5.12.8.3.34.5
-- 1.3.6.1.4.1.37950.1.1.5.12.8.3.34.5
		-- 1.3.6.1.4.1.37950.1.1.5.12.8.3.34.5
		wlanPower OBJECT-TYPE
			SYNTAX INTEGER (0..20)
			MAX-ACCESS read-write
			STATUS current
			DESCRIPTION
				"Description."
			::= { onuWifiSwich 5 }

		
--          1.3.6.1.4.1.37950.1.1.5.12.8.3.34.6
-- 1.3.6.1.4.1.37950.1.1.5.12.8.3.34.6
-- 1.3.6.1.4.1.37950.1.1.5.12.8.3.34.6
-- 1.3.6.1.4.1.37950.1.1.5.12.8.3.34.6
-- 1.3.6.1.4.1.37950.1.1.5.12.8.3.34.6
-- 1.3.6.1.4.1.37950.1.1.5.12.8.3.34.6
-- 1.3.6.1.4.1.37950.1.1.5.12.8.3.34.6
-- 1.3.6.1.4.1.37950.1.1.5.12.8.3.34.6
-- 1.3.6.1.4.1.37950.1.1.5.12.8.3.34.6
		-- 1.3.6.1.4.1.37950.1.1.5.12.8.3.34.6
		wlanSwichAction OBJECT-TYPE
			SYNTAX INTEGER
				{
				add(1),
				remove(2)
				}
			MAX-ACCESS read-write
			STATUS current
			DESCRIPTION
				"Description."
			::= { onuWifiSwich 6 }

		
--         1.3.6.1.4.1.37950.1.1.5.12.8.3.34.7
-- 1.3.6.1.4.1.37950.1.1.5.12.8.3.34.7
-- 1.3.6.1.4.1.37950.1.1.5.12.8.3.34.7
-- 1.3.6.1.4.1.37950.1.1.5.12.8.3.34.7
-- 1.3.6.1.4.1.37950.1.1.5.12.8.3.34.7
-- 1.3.6.1.4.1.37950.1.1.5.12.8.3.34.7
-- 1.3.6.1.4.1.37950.1.1.5.12.8.3.34.7
-- 1.3.6.1.4.1.37950.1.1.5.12.8.3.34.7
		-- 1.3.6.1.4.1.37950.1.1.5.12.8.3.34.7
		wlanChannelWidth OBJECT-TYPE
			SYNTAX INTEGER
				{
				s20(0),
				s40(1),
				s20-40(3)
				}
			MAX-ACCESS read-write
			STATUS current
			DESCRIPTION
				"Description."
			::= { onuWifiSwich 7 }

		
--          1.3.6.1.4.1.37950.1.1.5.12.8.3.35
-- 1.3.6.1.4.1.37950.1.1.5.12.8.3.35
-- 1.3.6.1.4.1.37950.1.1.5.12.8.3.35
-- 1.3.6.1.4.1.37950.1.1.5.12.8.3.35
-- 1.3.6.1.4.1.37950.1.1.5.12.8.3.35
-- 1.3.6.1.4.1.37950.1.1.5.12.8.3.35
-- 1.3.6.1.4.1.37950.1.1.5.12.8.3.35
-- 1.3.6.1.4.1.37950.1.1.5.12.8.3.35
-- 1.3.6.1.4.1.37950.1.1.5.12.8.3.35
		-- 1.3.6.1.4.1.37950.1.1.5.12.8.3.35
		onuWifiSsid OBJECT IDENTIFIER ::= { srvProfileEdit 35 }

		
--          1.3.6.1.4.1.37950.1.1.5.12.8.3.35.1
-- 1.3.6.1.4.1.37950.1.1.5.12.8.3.35.1
-- 1.3.6.1.4.1.37950.1.1.5.12.8.3.35.1
-- 1.3.6.1.4.1.37950.1.1.5.12.8.3.35.1
-- 1.3.6.1.4.1.37950.1.1.5.12.8.3.35.1
-- 1.3.6.1.4.1.37950.1.1.5.12.8.3.35.1
-- 1.3.6.1.4.1.37950.1.1.5.12.8.3.35.1
-- 1.3.6.1.4.1.37950.1.1.5.12.8.3.35.1
-- 1.3.6.1.4.1.37950.1.1.5.12.8.3.35.1
		-- 1.3.6.1.4.1.37950.1.1.5.12.8.3.35.1
		ssidId OBJECT-TYPE
			SYNTAX Integer32 (1..10)
			MAX-ACCESS read-write
			STATUS current
			DESCRIPTION
				"Description."
			::= { onuWifiSsid 1 }

		
--          1.3.6.1.4.1.37950.1.1.5.12.8.3.35.2
-- 1.3.6.1.4.1.37950.1.1.5.12.8.3.35.2
-- 1.3.6.1.4.1.37950.1.1.5.12.8.3.35.2
-- 1.3.6.1.4.1.37950.1.1.5.12.8.3.35.2
-- 1.3.6.1.4.1.37950.1.1.5.12.8.3.35.2
-- 1.3.6.1.4.1.37950.1.1.5.12.8.3.35.2
-- 1.3.6.1.4.1.37950.1.1.5.12.8.3.35.2
-- 1.3.6.1.4.1.37950.1.1.5.12.8.3.35.2
-- 1.3.6.1.4.1.37950.1.1.5.12.8.3.35.2
		-- 1.3.6.1.4.1.37950.1.1.5.12.8.3.35.2
		ssidName OBJECT-TYPE
			SYNTAX OCTET STRING
			MAX-ACCESS read-write
			STATUS current
			DESCRIPTION
				"Description."
			::= { onuWifiSsid 2 }

		
--          1.3.6.1.4.1.37950.1.1.5.12.8.3.35.3
-- 1.3.6.1.4.1.37950.1.1.5.12.8.3.35.3
-- 1.3.6.1.4.1.37950.1.1.5.12.8.3.35.3
-- 1.3.6.1.4.1.37950.1.1.5.12.8.3.35.3
-- 1.3.6.1.4.1.37950.1.1.5.12.8.3.35.3
-- 1.3.6.1.4.1.37950.1.1.5.12.8.3.35.3
-- 1.3.6.1.4.1.37950.1.1.5.12.8.3.35.3
-- 1.3.6.1.4.1.37950.1.1.5.12.8.3.35.3
-- 1.3.6.1.4.1.37950.1.1.5.12.8.3.35.3
		-- 1.3.6.1.4.1.37950.1.1.5.12.8.3.35.3
		ssidEnable OBJECT-TYPE
			SYNTAX INTEGER
				{
				disable(0),
				enable(1)
				}
			MAX-ACCESS read-write
			STATUS current
			DESCRIPTION
				"Description."
			::= { onuWifiSsid 3 }

		
--          1.3.6.1.4.1.37950.1.1.5.12.8.3.35.4
-- 1.3.6.1.4.1.37950.1.1.5.12.8.3.35.4
-- 1.3.6.1.4.1.37950.1.1.5.12.8.3.35.4
-- 1.3.6.1.4.1.37950.1.1.5.12.8.3.35.4
-- 1.3.6.1.4.1.37950.1.1.5.12.8.3.35.4
-- 1.3.6.1.4.1.37950.1.1.5.12.8.3.35.4
-- 1.3.6.1.4.1.37950.1.1.5.12.8.3.35.4
-- 1.3.6.1.4.1.37950.1.1.5.12.8.3.35.4
-- 1.3.6.1.4.1.37950.1.1.5.12.8.3.35.4
		-- 1.3.6.1.4.1.37950.1.1.5.12.8.3.35.4
		ssidHide OBJECT-TYPE
			SYNTAX INTEGER
				{
				disable(0),
				enable(1)
				}
			MAX-ACCESS read-write
			STATUS current
			DESCRIPTION
				"Description."
			::= { onuWifiSsid 4 }

		
--          1.3.6.1.4.1.37950.1.1.5.12.8.3.35.5
-- 1.3.6.1.4.1.37950.1.1.5.12.8.3.35.5
-- 1.3.6.1.4.1.37950.1.1.5.12.8.3.35.5
-- 1.3.6.1.4.1.37950.1.1.5.12.8.3.35.5
-- 1.3.6.1.4.1.37950.1.1.5.12.8.3.35.5
-- 1.3.6.1.4.1.37950.1.1.5.12.8.3.35.5
-- 1.3.6.1.4.1.37950.1.1.5.12.8.3.35.5
-- 1.3.6.1.4.1.37950.1.1.5.12.8.3.35.5
-- 1.3.6.1.4.1.37950.1.1.5.12.8.3.35.5
		-- 1.3.6.1.4.1.37950.1.1.5.12.8.3.35.5
		ssidAuthMode OBJECT-TYPE
			SYNTAX INTEGER
				{
				open(1),
				shared(2),
				wepauto(3),
				wpapsk(4),
				wpa(5),
				wpa2psk(6),
				wpa2(7),
				wpa-wpa2(8),
				wpapsk-wpa2psk(9),
				wpa3psk(10),
				wpa2psk-wpa3psk(11)
				}
			MAX-ACCESS read-write
			STATUS current
			DESCRIPTION
				"Description."
			::= { onuWifiSsid 5 }

		
--          1.3.6.1.4.1.37950.1.1.5.12.8.3.35.6
-- 1.3.6.1.4.1.37950.1.1.5.12.8.3.35.6
-- 1.3.6.1.4.1.37950.1.1.5.12.8.3.35.6
-- 1.3.6.1.4.1.37950.1.1.5.12.8.3.35.6
-- 1.3.6.1.4.1.37950.1.1.5.12.8.3.35.6
-- 1.3.6.1.4.1.37950.1.1.5.12.8.3.35.6
-- 1.3.6.1.4.1.37950.1.1.5.12.8.3.35.6
-- 1.3.6.1.4.1.37950.1.1.5.12.8.3.35.6
-- 1.3.6.1.4.1.37950.1.1.5.12.8.3.35.6
		-- 1.3.6.1.4.1.37950.1.1.5.12.8.3.35.6
		ssidEncrypTpye OBJECT-TYPE
			SYNTAX INTEGER
				{
				none(1),
				wep(2),
				tkip(3),
				aes(4),
				tkipaes(5)
				}
			MAX-ACCESS read-write
			STATUS current
			DESCRIPTION
				"Description."
			::= { onuWifiSsid 6 }

		
--          1.3.6.1.4.1.37950.1.1.5.12.8.3.35.7
-- 1.3.6.1.4.1.37950.1.1.5.12.8.3.35.7
-- 1.3.6.1.4.1.37950.1.1.5.12.8.3.35.7
-- 1.3.6.1.4.1.37950.1.1.5.12.8.3.35.7
-- 1.3.6.1.4.1.37950.1.1.5.12.8.3.35.7
-- 1.3.6.1.4.1.37950.1.1.5.12.8.3.35.7
-- 1.3.6.1.4.1.37950.1.1.5.12.8.3.35.7
-- 1.3.6.1.4.1.37950.1.1.5.12.8.3.35.7
-- 1.3.6.1.4.1.37950.1.1.5.12.8.3.35.7
		-- 1.3.6.1.4.1.37950.1.1.5.12.8.3.35.7
		ssidPresharedKey OBJECT-TYPE
			SYNTAX OCTET STRING
			MAX-ACCESS read-write
			STATUS current
			DESCRIPTION
				"Description."
			::= { onuWifiSsid 7 }

		
--          1.3.6.1.4.1.37950.1.1.5.12.8.3.35.8
-- 1.3.6.1.4.1.37950.1.1.5.12.8.3.35.8
-- 1.3.6.1.4.1.37950.1.1.5.12.8.3.35.8
-- 1.3.6.1.4.1.37950.1.1.5.12.8.3.35.8
-- 1.3.6.1.4.1.37950.1.1.5.12.8.3.35.8
-- 1.3.6.1.4.1.37950.1.1.5.12.8.3.35.8
-- 1.3.6.1.4.1.37950.1.1.5.12.8.3.35.8
-- 1.3.6.1.4.1.37950.1.1.5.12.8.3.35.8
-- 1.3.6.1.4.1.37950.1.1.5.12.8.3.35.8
		-- 1.3.6.1.4.1.37950.1.1.5.12.8.3.35.8
		ssidRekeyInterval OBJECT-TYPE
			SYNTAX Integer32 (0..4194303)
			MAX-ACCESS read-write
			STATUS current
			DESCRIPTION
				"Description."
			::= { onuWifiSsid 8 }

		
--          1.3.6.1.4.1.37950.1.1.5.12.8.3.35.9
-- 1.3.6.1.4.1.37950.1.1.5.12.8.3.35.9
-- 1.3.6.1.4.1.37950.1.1.5.12.8.3.35.9
-- 1.3.6.1.4.1.37950.1.1.5.12.8.3.35.9
-- 1.3.6.1.4.1.37950.1.1.5.12.8.3.35.9
-- 1.3.6.1.4.1.37950.1.1.5.12.8.3.35.9
-- 1.3.6.1.4.1.37950.1.1.5.12.8.3.35.9
-- 1.3.6.1.4.1.37950.1.1.5.12.8.3.35.9
-- 1.3.6.1.4.1.37950.1.1.5.12.8.3.35.9
		-- 1.3.6.1.4.1.37950.1.1.5.12.8.3.35.9
		ssidRadiusServIpType OBJECT-TYPE
			SYNTAX INTEGER
				{
				ipv4(1),
				ipv6(2),
				ipv4z(3),
				ipv6z(4),
				dns(16)
				}
			MAX-ACCESS read-write
			STATUS current
			DESCRIPTION
				"Description."
			::= { onuWifiSsid 9 }

		
--          1.3.6.1.4.1.37950.1.1.5.12.8.3.35.10
-- 1.3.6.1.4.1.37950.1.1.5.12.8.3.35.10
-- 1.3.6.1.4.1.37950.1.1.5.12.8.3.35.10
-- 1.3.6.1.4.1.37950.1.1.5.12.8.3.35.10
-- 1.3.6.1.4.1.37950.1.1.5.12.8.3.35.10
-- 1.3.6.1.4.1.37950.1.1.5.12.8.3.35.10
-- 1.3.6.1.4.1.37950.1.1.5.12.8.3.35.10
-- 1.3.6.1.4.1.37950.1.1.5.12.8.3.35.10
-- 1.3.6.1.4.1.37950.1.1.5.12.8.3.35.10
		-- 1.3.6.1.4.1.37950.1.1.5.12.8.3.35.10
		ssidRadiusSerIp OBJECT-TYPE
			SYNTAX OCTET STRING
			MAX-ACCESS read-write
			STATUS current
			DESCRIPTION
				"Description."
			::= { onuWifiSsid 10 }

		
--          1.3.6.1.4.1.37950.1.1.5.12.8.3.35.11
-- 1.3.6.1.4.1.37950.1.1.5.12.8.3.35.11
-- 1.3.6.1.4.1.37950.1.1.5.12.8.3.35.11
-- 1.3.6.1.4.1.37950.1.1.5.12.8.3.35.11
-- 1.3.6.1.4.1.37950.1.1.5.12.8.3.35.11
-- 1.3.6.1.4.1.37950.1.1.5.12.8.3.35.11
-- 1.3.6.1.4.1.37950.1.1.5.12.8.3.35.11
-- 1.3.6.1.4.1.37950.1.1.5.12.8.3.35.11
-- 1.3.6.1.4.1.37950.1.1.5.12.8.3.35.11
		-- 1.3.6.1.4.1.37950.1.1.5.12.8.3.35.11
		ssidRadiusServIpPrefixLen OBJECT-TYPE
			SYNTAX Integer32 (0..255)
			MAX-ACCESS read-write
			STATUS current
			DESCRIPTION
				"Description."
			::= { onuWifiSsid 11 }

		
--          1.3.6.1.4.1.37950.1.1.5.12.8.3.35.12
-- 1.3.6.1.4.1.37950.1.1.5.12.8.3.35.12
-- 1.3.6.1.4.1.37950.1.1.5.12.8.3.35.12
-- 1.3.6.1.4.1.37950.1.1.5.12.8.3.35.12
-- 1.3.6.1.4.1.37950.1.1.5.12.8.3.35.12
-- 1.3.6.1.4.1.37950.1.1.5.12.8.3.35.12
-- 1.3.6.1.4.1.37950.1.1.5.12.8.3.35.12
-- 1.3.6.1.4.1.37950.1.1.5.12.8.3.35.12
-- 1.3.6.1.4.1.37950.1.1.5.12.8.3.35.12
		-- 1.3.6.1.4.1.37950.1.1.5.12.8.3.35.12
		ssidRadiusPort OBJECT-TYPE
			SYNTAX Integer32 (0..65535)
			MAX-ACCESS read-write
			STATUS current
			DESCRIPTION
				"Description."
			::= { onuWifiSsid 12 }

		
--          1.3.6.1.4.1.37950.1.1.5.12.8.3.35.13
-- 1.3.6.1.4.1.37950.1.1.5.12.8.3.35.13
-- 1.3.6.1.4.1.37950.1.1.5.12.8.3.35.13
-- 1.3.6.1.4.1.37950.1.1.5.12.8.3.35.13
-- 1.3.6.1.4.1.37950.1.1.5.12.8.3.35.13
-- 1.3.6.1.4.1.37950.1.1.5.12.8.3.35.13
-- 1.3.6.1.4.1.37950.1.1.5.12.8.3.35.13
-- 1.3.6.1.4.1.37950.1.1.5.12.8.3.35.13
-- 1.3.6.1.4.1.37950.1.1.5.12.8.3.35.13
		-- 1.3.6.1.4.1.37950.1.1.5.12.8.3.35.13
		ssidRadiusKey OBJECT-TYPE
			SYNTAX OCTET STRING (SIZE (0..32))
			MAX-ACCESS read-write
			STATUS current
			DESCRIPTION
				"Description."
			::= { onuWifiSsid 13 }

		
--          1.3.6.1.4.1.37950.1.1.5.12.8.3.35.14
-- 1.3.6.1.4.1.37950.1.1.5.12.8.3.35.14
-- 1.3.6.1.4.1.37950.1.1.5.12.8.3.35.14
-- 1.3.6.1.4.1.37950.1.1.5.12.8.3.35.14
-- 1.3.6.1.4.1.37950.1.1.5.12.8.3.35.14
-- 1.3.6.1.4.1.37950.1.1.5.12.8.3.35.14
-- 1.3.6.1.4.1.37950.1.1.5.12.8.3.35.14
-- 1.3.6.1.4.1.37950.1.1.5.12.8.3.35.14
-- 1.3.6.1.4.1.37950.1.1.5.12.8.3.35.14
		-- 1.3.6.1.4.1.37950.1.1.5.12.8.3.35.14
		ssidWepEncryptionLevel OBJECT-TYPE
			SYNTAX INTEGER
				{
				s64bit(1),
				s128bit(2)
				}
			MAX-ACCESS read-write
			STATUS current
			DESCRIPTION
				"Description."
			::= { onuWifiSsid 14 }

		
--          1.3.6.1.4.1.37950.1.1.5.12.8.3.35.15
-- 1.3.6.1.4.1.37950.1.1.5.12.8.3.35.15
-- 1.3.6.1.4.1.37950.1.1.5.12.8.3.35.15
-- 1.3.6.1.4.1.37950.1.1.5.12.8.3.35.15
-- 1.3.6.1.4.1.37950.1.1.5.12.8.3.35.15
-- 1.3.6.1.4.1.37950.1.1.5.12.8.3.35.15
-- 1.3.6.1.4.1.37950.1.1.5.12.8.3.35.15
-- 1.3.6.1.4.1.37950.1.1.5.12.8.3.35.15
-- 1.3.6.1.4.1.37950.1.1.5.12.8.3.35.15
		-- 1.3.6.1.4.1.37950.1.1.5.12.8.3.35.15
		ssidWepKeyIndex OBJECT-TYPE
			SYNTAX Integer32 (1..4)
			MAX-ACCESS read-write
			STATUS current
			DESCRIPTION
				"Description."
			::= { onuWifiSsid 15 }

		
--          1.3.6.1.4.1.37950.1.1.5.12.8.3.35.16
-- 1.3.6.1.4.1.37950.1.1.5.12.8.3.35.16
-- 1.3.6.1.4.1.37950.1.1.5.12.8.3.35.16
-- 1.3.6.1.4.1.37950.1.1.5.12.8.3.35.16
-- 1.3.6.1.4.1.37950.1.1.5.12.8.3.35.16
-- 1.3.6.1.4.1.37950.1.1.5.12.8.3.35.16
-- 1.3.6.1.4.1.37950.1.1.5.12.8.3.35.16
-- 1.3.6.1.4.1.37950.1.1.5.12.8.3.35.16
-- 1.3.6.1.4.1.37950.1.1.5.12.8.3.35.16
		-- 1.3.6.1.4.1.37950.1.1.5.12.8.3.35.16
		ssidWepKey1 OBJECT-TYPE
			SYNTAX OCTET STRING (SIZE (0..32))
			MAX-ACCESS read-write
			STATUS current
			DESCRIPTION
				"Description."
			::= { onuWifiSsid 16 }

		
--          1.3.6.1.4.1.37950.1.1.5.12.8.3.35.17
-- 1.3.6.1.4.1.37950.1.1.5.12.8.3.35.17
-- 1.3.6.1.4.1.37950.1.1.5.12.8.3.35.17
-- 1.3.6.1.4.1.37950.1.1.5.12.8.3.35.17
-- 1.3.6.1.4.1.37950.1.1.5.12.8.3.35.17
-- 1.3.6.1.4.1.37950.1.1.5.12.8.3.35.17
-- 1.3.6.1.4.1.37950.1.1.5.12.8.3.35.17
-- 1.3.6.1.4.1.37950.1.1.5.12.8.3.35.17
-- 1.3.6.1.4.1.37950.1.1.5.12.8.3.35.17
		-- 1.3.6.1.4.1.37950.1.1.5.12.8.3.35.17
		ssidWepKey2 OBJECT-TYPE
			SYNTAX OCTET STRING (SIZE (0..32))
			MAX-ACCESS read-write
			STATUS current
			DESCRIPTION
				"Description."
			::= { onuWifiSsid 17 }

		
--          1.3.6.1.4.1.37950.1.1.5.12.8.3.35.18
-- 1.3.6.1.4.1.37950.1.1.5.12.8.3.35.18
-- 1.3.6.1.4.1.37950.1.1.5.12.8.3.35.18
-- 1.3.6.1.4.1.37950.1.1.5.12.8.3.35.18
-- 1.3.6.1.4.1.37950.1.1.5.12.8.3.35.18
-- 1.3.6.1.4.1.37950.1.1.5.12.8.3.35.18
-- 1.3.6.1.4.1.37950.1.1.5.12.8.3.35.18
-- 1.3.6.1.4.1.37950.1.1.5.12.8.3.35.18
-- 1.3.6.1.4.1.37950.1.1.5.12.8.3.35.18
		-- 1.3.6.1.4.1.37950.1.1.5.12.8.3.35.18
		ssidWepKey3 OBJECT-TYPE
			SYNTAX OCTET STRING (SIZE (0..32))
			MAX-ACCESS read-write
			STATUS current
			DESCRIPTION
				"Description."
			::= { onuWifiSsid 18 }

		
--          1.3.6.1.4.1.37950.1.1.5.12.8.3.35.19
-- 1.3.6.1.4.1.37950.1.1.5.12.8.3.35.19
-- 1.3.6.1.4.1.37950.1.1.5.12.8.3.35.19
-- 1.3.6.1.4.1.37950.1.1.5.12.8.3.35.19
-- 1.3.6.1.4.1.37950.1.1.5.12.8.3.35.19
-- 1.3.6.1.4.1.37950.1.1.5.12.8.3.35.19
-- 1.3.6.1.4.1.37950.1.1.5.12.8.3.35.19
-- 1.3.6.1.4.1.37950.1.1.5.12.8.3.35.19
-- 1.3.6.1.4.1.37950.1.1.5.12.8.3.35.19
		-- 1.3.6.1.4.1.37950.1.1.5.12.8.3.35.19
		ssidWepKey4 OBJECT-TYPE
			SYNTAX OCTET STRING (SIZE (0..32))
			MAX-ACCESS read-write
			STATUS current
			DESCRIPTION
				"Description."
			::= { onuWifiSsid 19 }

		
--          1.3.6.1.4.1.37950.1.1.5.12.8.3.35.20
-- 1.3.6.1.4.1.37950.1.1.5.12.8.3.35.20
-- 1.3.6.1.4.1.37950.1.1.5.12.8.3.35.20
-- 1.3.6.1.4.1.37950.1.1.5.12.8.3.35.20
-- 1.3.6.1.4.1.37950.1.1.5.12.8.3.35.20
-- 1.3.6.1.4.1.37950.1.1.5.12.8.3.35.20
-- 1.3.6.1.4.1.37950.1.1.5.12.8.3.35.20
-- 1.3.6.1.4.1.37950.1.1.5.12.8.3.35.20
-- 1.3.6.1.4.1.37950.1.1.5.12.8.3.35.20
		-- 1.3.6.1.4.1.37950.1.1.5.12.8.3.35.20
		ssidAction OBJECT-TYPE
			SYNTAX INTEGER
				{
				add(1),
				remove(2)
				}
			MAX-ACCESS read-write
			STATUS current
			DESCRIPTION
				"Description."
			::= { onuWifiSsid 20 }

		
--          1.3.6.1.4.1.37950.1.1.5.12.8.3.36
-- 1.3.6.1.4.1.37950.1.1.5.12.8.3.36
-- 1.3.6.1.4.1.37950.1.1.5.12.8.3.36
-- 1.3.6.1.4.1.37950.1.1.5.12.8.3.36
-- 1.3.6.1.4.1.37950.1.1.5.12.8.3.36
-- 1.3.6.1.4.1.37950.1.1.5.12.8.3.36
-- 1.3.6.1.4.1.37950.1.1.5.12.8.3.36
-- 1.3.6.1.4.1.37950.1.1.5.12.8.3.36
-- 1.3.6.1.4.1.37950.1.1.5.12.8.3.36
		-- 1.3.6.1.4.1.37950.1.1.5.12.8.3.36
		onuWanConn OBJECT IDENTIFIER ::= { srvProfileEdit 36 }

		
--          1.3.6.1.4.1.37950.1.1.5.12.8.3.36.1
-- 1.3.6.1.4.1.37950.1.1.5.12.8.3.36.1
-- 1.3.6.1.4.1.37950.1.1.5.12.8.3.36.1
-- 1.3.6.1.4.1.37950.1.1.5.12.8.3.36.1
-- 1.3.6.1.4.1.37950.1.1.5.12.8.3.36.1
-- 1.3.6.1.4.1.37950.1.1.5.12.8.3.36.1
-- 1.3.6.1.4.1.37950.1.1.5.12.8.3.36.1
-- 1.3.6.1.4.1.37950.1.1.5.12.8.3.36.1
-- 1.3.6.1.4.1.37950.1.1.5.12.8.3.36.1
		-- 1.3.6.1.4.1.37950.1.1.5.12.8.3.36.1
		wanConnAdd OBJECT IDENTIFIER ::= { onuWanConn 1 }

		
--          1.3.6.1.4.1.37950.1.1.5.12.8.3.36.1.1
-- 1.3.6.1.4.1.37950.1.1.5.12.8.3.36.1.1
-- 1.3.6.1.4.1.37950.1.1.5.12.8.3.36.1.1
-- 1.3.6.1.4.1.37950.1.1.5.12.8.3.36.1.1
-- 1.3.6.1.4.1.37950.1.1.5.12.8.3.36.1.1
-- 1.3.6.1.4.1.37950.1.1.5.12.8.3.36.1.1
-- 1.3.6.1.4.1.37950.1.1.5.12.8.3.36.1.1
-- 1.3.6.1.4.1.37950.1.1.5.12.8.3.36.1.1
-- 1.3.6.1.4.1.37950.1.1.5.12.8.3.36.1.1
		-- 1.3.6.1.4.1.37950.1.1.5.12.8.3.36.1.1
		connType OBJECT-TYPE
			SYNTAX INTEGER
				{
				bridge(0),
				route(1)
				}
			MAX-ACCESS read-write
			STATUS current
			DESCRIPTION
				"Description."
			::= { wanConnAdd 1 }

		
--          1.3.6.1.4.1.37950.1.1.5.12.8.3.36.1.2
-- 1.3.6.1.4.1.37950.1.1.5.12.8.3.36.1.2
-- 1.3.6.1.4.1.37950.1.1.5.12.8.3.36.1.2
-- 1.3.6.1.4.1.37950.1.1.5.12.8.3.36.1.2
-- 1.3.6.1.4.1.37950.1.1.5.12.8.3.36.1.2
-- 1.3.6.1.4.1.37950.1.1.5.12.8.3.36.1.2
-- 1.3.6.1.4.1.37950.1.1.5.12.8.3.36.1.2
-- 1.3.6.1.4.1.37950.1.1.5.12.8.3.36.1.2
-- 1.3.6.1.4.1.37950.1.1.5.12.8.3.36.1.2
		-- 1.3.6.1.4.1.37950.1.1.5.12.8.3.36.1.2
		connAddAction OBJECT-TYPE
			SYNTAX INTEGER { add(1) }
			MAX-ACCESS read-write
			STATUS current
			DESCRIPTION
				"Description."
			::= { wanConnAdd 2 }

		
--          1.3.6.1.4.1.37950.1.1.5.12.8.3.36.2
-- 1.3.6.1.4.1.37950.1.1.5.12.8.3.36.2
-- 1.3.6.1.4.1.37950.1.1.5.12.8.3.36.2
-- 1.3.6.1.4.1.37950.1.1.5.12.8.3.36.2
-- 1.3.6.1.4.1.37950.1.1.5.12.8.3.36.2
-- 1.3.6.1.4.1.37950.1.1.5.12.8.3.36.2
-- 1.3.6.1.4.1.37950.1.1.5.12.8.3.36.2
-- 1.3.6.1.4.1.37950.1.1.5.12.8.3.36.2
-- 1.3.6.1.4.1.37950.1.1.5.12.8.3.36.2
		-- 1.3.6.1.4.1.37950.1.1.5.12.8.3.36.2
		wanConnDelete OBJECT IDENTIFIER ::= { onuWanConn 2 }

		
--          1.3.6.1.4.1.37950.1.1.5.12.8.3.36.2.1
-- 1.3.6.1.4.1.37950.1.1.5.12.8.3.36.2.1
-- 1.3.6.1.4.1.37950.1.1.5.12.8.3.36.2.1
-- 1.3.6.1.4.1.37950.1.1.5.12.8.3.36.2.1
-- 1.3.6.1.4.1.37950.1.1.5.12.8.3.36.2.1
-- 1.3.6.1.4.1.37950.1.1.5.12.8.3.36.2.1
-- 1.3.6.1.4.1.37950.1.1.5.12.8.3.36.2.1
-- 1.3.6.1.4.1.37950.1.1.5.12.8.3.36.2.1
-- 1.3.6.1.4.1.37950.1.1.5.12.8.3.36.2.1
		-- 1.3.6.1.4.1.37950.1.1.5.12.8.3.36.2.1
		connIndexD OBJECT-TYPE
			SYNTAX Integer32 (1..8)
			MAX-ACCESS read-write
			STATUS current
			DESCRIPTION
				"Description."
			::= { wanConnDelete 1 }

		
--          1.3.6.1.4.1.37950.1.1.5.12.8.3.36.2.2
-- 1.3.6.1.4.1.37950.1.1.5.12.8.3.36.2.2
-- 1.3.6.1.4.1.37950.1.1.5.12.8.3.36.2.2
-- 1.3.6.1.4.1.37950.1.1.5.12.8.3.36.2.2
-- 1.3.6.1.4.1.37950.1.1.5.12.8.3.36.2.2
-- 1.3.6.1.4.1.37950.1.1.5.12.8.3.36.2.2
-- 1.3.6.1.4.1.37950.1.1.5.12.8.3.36.2.2
-- 1.3.6.1.4.1.37950.1.1.5.12.8.3.36.2.2
-- 1.3.6.1.4.1.37950.1.1.5.12.8.3.36.2.2
		-- 1.3.6.1.4.1.37950.1.1.5.12.8.3.36.2.2
		connDeleteAction OBJECT-TYPE
			SYNTAX INTEGER { delete(1) }
			MAX-ACCESS read-write
			STATUS current
			DESCRIPTION
				"Description."
			::= { wanConnDelete 2 }

		
--          1.3.6.1.4.1.37950.1.1.5.12.8.3.36.3
-- 1.3.6.1.4.1.37950.1.1.5.12.8.3.36.3
-- 1.3.6.1.4.1.37950.1.1.5.12.8.3.36.3
-- 1.3.6.1.4.1.37950.1.1.5.12.8.3.36.3
-- 1.3.6.1.4.1.37950.1.1.5.12.8.3.36.3
-- 1.3.6.1.4.1.37950.1.1.5.12.8.3.36.3
-- 1.3.6.1.4.1.37950.1.1.5.12.8.3.36.3
-- 1.3.6.1.4.1.37950.1.1.5.12.8.3.36.3
-- 1.3.6.1.4.1.37950.1.1.5.12.8.3.36.3
		-- 1.3.6.1.4.1.37950.1.1.5.12.8.3.36.3
		wanConnCfg OBJECT IDENTIFIER ::= { onuWanConn 3 }

		
--          1.3.6.1.4.1.37950.1.1.5.12.8.3.36.3.1
-- 1.3.6.1.4.1.37950.1.1.5.12.8.3.36.3.1
-- 1.3.6.1.4.1.37950.1.1.5.12.8.3.36.3.1
-- 1.3.6.1.4.1.37950.1.1.5.12.8.3.36.3.1
-- 1.3.6.1.4.1.37950.1.1.5.12.8.3.36.3.1
-- 1.3.6.1.4.1.37950.1.1.5.12.8.3.36.3.1
-- 1.3.6.1.4.1.37950.1.1.5.12.8.3.36.3.1
-- 1.3.6.1.4.1.37950.1.1.5.12.8.3.36.3.1
-- 1.3.6.1.4.1.37950.1.1.5.12.8.3.36.3.1
		-- 1.3.6.1.4.1.37950.1.1.5.12.8.3.36.3.1
		connIndex OBJECT-TYPE
			SYNTAX INTEGER (1..8)
			MAX-ACCESS read-write
			STATUS current
			DESCRIPTION
				"Description."
			::= { wanConnCfg 1 }

		
--          1.3.6.1.4.1.37950.1.1.5.12.8.3.36.3.2
-- 1.3.6.1.4.1.37950.1.1.5.12.8.3.36.3.2
-- 1.3.6.1.4.1.37950.1.1.5.12.8.3.36.3.2
-- 1.3.6.1.4.1.37950.1.1.5.12.8.3.36.3.2
-- 1.3.6.1.4.1.37950.1.1.5.12.8.3.36.3.2
-- 1.3.6.1.4.1.37950.1.1.5.12.8.3.36.3.2
-- 1.3.6.1.4.1.37950.1.1.5.12.8.3.36.3.2
-- 1.3.6.1.4.1.37950.1.1.5.12.8.3.36.3.2
-- 1.3.6.1.4.1.37950.1.1.5.12.8.3.36.3.2
		-- 1.3.6.1.4.1.37950.1.1.5.12.8.3.36.3.2
		connBindLan OBJECT-TYPE
			SYNTAX INTEGER (0..15)
			MAX-ACCESS read-write
			STATUS current
			DESCRIPTION
				"Description."
			::= { wanConnCfg 2 }

		
--          1.3.6.1.4.1.37950.1.1.5.12.8.3.36.3.3
-- 1.3.6.1.4.1.37950.1.1.5.12.8.3.36.3.3
-- 1.3.6.1.4.1.37950.1.1.5.12.8.3.36.3.3
-- 1.3.6.1.4.1.37950.1.1.5.12.8.3.36.3.3
-- 1.3.6.1.4.1.37950.1.1.5.12.8.3.36.3.3
-- 1.3.6.1.4.1.37950.1.1.5.12.8.3.36.3.3
-- 1.3.6.1.4.1.37950.1.1.5.12.8.3.36.3.3
-- 1.3.6.1.4.1.37950.1.1.5.12.8.3.36.3.3
-- 1.3.6.1.4.1.37950.1.1.5.12.8.3.36.3.3
		-- 1.3.6.1.4.1.37950.1.1.5.12.8.3.36.3.3
		connBindSsid OBJECT-TYPE
			SYNTAX INTEGER (0..1023)
			MAX-ACCESS read-write
			STATUS current
			DESCRIPTION
				"Description."
			::= { wanConnCfg 3 }

		
--          1.3.6.1.4.1.37950.1.1.5.12.8.3.36.3.4
-- 1.3.6.1.4.1.37950.1.1.5.12.8.3.36.3.4
-- 1.3.6.1.4.1.37950.1.1.5.12.8.3.36.3.4
-- 1.3.6.1.4.1.37950.1.1.5.12.8.3.36.3.4
-- 1.3.6.1.4.1.37950.1.1.5.12.8.3.36.3.4
-- 1.3.6.1.4.1.37950.1.1.5.12.8.3.36.3.4
-- 1.3.6.1.4.1.37950.1.1.5.12.8.3.36.3.4
-- 1.3.6.1.4.1.37950.1.1.5.12.8.3.36.3.4
-- 1.3.6.1.4.1.37950.1.1.5.12.8.3.36.3.4
		-- 1.3.6.1.4.1.37950.1.1.5.12.8.3.36.3.4
		wanMode OBJECT-TYPE
			SYNTAX INTEGER
				{
				internet(0),
				multicast(1),
				tr069(2),
				tr069-internet(3),
				tr069-voip(4),
				voip-internet(5),
				tr069-voip-internet(6),
				other(100)
				}
			MAX-ACCESS read-write
			STATUS current
			DESCRIPTION
				"Description."
			::= { wanConnCfg 4 }

		
--          1.3.6.1.4.1.37950.1.1.5.12.8.3.36.3.5
-- 1.3.6.1.4.1.37950.1.1.5.12.8.3.36.3.5
-- 1.3.6.1.4.1.37950.1.1.5.12.8.3.36.3.5
-- 1.3.6.1.4.1.37950.1.1.5.12.8.3.36.3.5
-- 1.3.6.1.4.1.37950.1.1.5.12.8.3.36.3.5
-- 1.3.6.1.4.1.37950.1.1.5.12.8.3.36.3.5
-- 1.3.6.1.4.1.37950.1.1.5.12.8.3.36.3.5
-- 1.3.6.1.4.1.37950.1.1.5.12.8.3.36.3.5
-- 1.3.6.1.4.1.37950.1.1.5.12.8.3.36.3.5
		-- 1.3.6.1.4.1.37950.1.1.5.12.8.3.36.3.5
		connTypeCfg OBJECT-TYPE
			SYNTAX INTEGER
				{
				bridge(0),
				route(1)
				}
			MAX-ACCESS read-write
			STATUS current
			DESCRIPTION
				"Description."
			::= { wanConnCfg 5 }

		
--          1.3.6.1.4.1.37950.1.1.5.12.8.3.36.3.6
-- 1.3.6.1.4.1.37950.1.1.5.12.8.3.36.3.6
-- 1.3.6.1.4.1.37950.1.1.5.12.8.3.36.3.6
-- 1.3.6.1.4.1.37950.1.1.5.12.8.3.36.3.6
-- 1.3.6.1.4.1.37950.1.1.5.12.8.3.36.3.6
-- 1.3.6.1.4.1.37950.1.1.5.12.8.3.36.3.6
-- 1.3.6.1.4.1.37950.1.1.5.12.8.3.36.3.6
-- 1.3.6.1.4.1.37950.1.1.5.12.8.3.36.3.6
-- 1.3.6.1.4.1.37950.1.1.5.12.8.3.36.3.6
		-- 1.3.6.1.4.1.37950.1.1.5.12.8.3.36.3.6
		connVlanId OBJECT-TYPE
			SYNTAX Integer32 (0..4095)
			MAX-ACCESS read-write
			STATUS current
			DESCRIPTION
				"Description."
			::= { wanConnCfg 6 }

		
--          1.3.6.1.4.1.37950.1.1.5.12.8.3.36.3.7
-- 1.3.6.1.4.1.37950.1.1.5.12.8.3.36.3.7
-- 1.3.6.1.4.1.37950.1.1.5.12.8.3.36.3.7
-- 1.3.6.1.4.1.37950.1.1.5.12.8.3.36.3.7
-- 1.3.6.1.4.1.37950.1.1.5.12.8.3.36.3.7
-- 1.3.6.1.4.1.37950.1.1.5.12.8.3.36.3.7
-- 1.3.6.1.4.1.37950.1.1.5.12.8.3.36.3.7
-- 1.3.6.1.4.1.37950.1.1.5.12.8.3.36.3.7
-- 1.3.6.1.4.1.37950.1.1.5.12.8.3.36.3.7
		-- 1.3.6.1.4.1.37950.1.1.5.12.8.3.36.3.7
		connCos OBJECT-TYPE
			SYNTAX INTEGER (0..7)
			MAX-ACCESS read-write
			STATUS current
			DESCRIPTION
				"Description."
			::= { wanConnCfg 7 }

		
--          1.3.6.1.4.1.37950.1.1.5.12.8.3.36.3.8
-- 1.3.6.1.4.1.37950.1.1.5.12.8.3.36.3.8
-- 1.3.6.1.4.1.37950.1.1.5.12.8.3.36.3.8
-- 1.3.6.1.4.1.37950.1.1.5.12.8.3.36.3.8
-- 1.3.6.1.4.1.37950.1.1.5.12.8.3.36.3.8
-- 1.3.6.1.4.1.37950.1.1.5.12.8.3.36.3.8
-- 1.3.6.1.4.1.37950.1.1.5.12.8.3.36.3.8
-- 1.3.6.1.4.1.37950.1.1.5.12.8.3.36.3.8
-- 1.3.6.1.4.1.37950.1.1.5.12.8.3.36.3.8
		-- 1.3.6.1.4.1.37950.1.1.5.12.8.3.36.3.8
		connNatEnable OBJECT-TYPE
			SYNTAX INTEGER
				{
				disable(0),
				enable(1)
				}
			MAX-ACCESS read-write
			STATUS current
			DESCRIPTION
				"Description."
			::= { wanConnCfg 8 }

		
--          1.3.6.1.4.1.37950.1.1.5.12.8.3.36.3.9
-- 1.3.6.1.4.1.37950.1.1.5.12.8.3.36.3.9
-- 1.3.6.1.4.1.37950.1.1.5.12.8.3.36.3.9
-- 1.3.6.1.4.1.37950.1.1.5.12.8.3.36.3.9
-- 1.3.6.1.4.1.37950.1.1.5.12.8.3.36.3.9
-- 1.3.6.1.4.1.37950.1.1.5.12.8.3.36.3.9
-- 1.3.6.1.4.1.37950.1.1.5.12.8.3.36.3.9
-- 1.3.6.1.4.1.37950.1.1.5.12.8.3.36.3.9
-- 1.3.6.1.4.1.37950.1.1.5.12.8.3.36.3.9
		-- 1.3.6.1.4.1.37950.1.1.5.12.8.3.36.3.9
		connModeCfg OBJECT-TYPE
			SYNTAX INTEGER
				{
				dhcp(0),
				static(1),
				pppoe(2)
				}
			MAX-ACCESS read-write
			STATUS current
			DESCRIPTION
				"Description."
			::= { wanConnCfg 9 }

		
--          1.3.6.1.4.1.37950.1.1.5.12.8.3.36.3.10
-- 1.3.6.1.4.1.37950.1.1.5.12.8.3.36.3.10
-- 1.3.6.1.4.1.37950.1.1.5.12.8.3.36.3.10
-- 1.3.6.1.4.1.37950.1.1.5.12.8.3.36.3.10
-- 1.3.6.1.4.1.37950.1.1.5.12.8.3.36.3.10
-- 1.3.6.1.4.1.37950.1.1.5.12.8.3.36.3.10
-- 1.3.6.1.4.1.37950.1.1.5.12.8.3.36.3.10
-- 1.3.6.1.4.1.37950.1.1.5.12.8.3.36.3.10
-- 1.3.6.1.4.1.37950.1.1.5.12.8.3.36.3.10
		-- 1.3.6.1.4.1.37950.1.1.5.12.8.3.36.3.10
		connIpAddress OBJECT-TYPE
			SYNTAX IpAddress
			MAX-ACCESS read-write
			STATUS current
			DESCRIPTION
				"Description."
			::= { wanConnCfg 10 }

		
--          1.3.6.1.4.1.37950.1.1.5.12.8.3.36.3.11
-- 1.3.6.1.4.1.37950.1.1.5.12.8.3.36.3.11
-- 1.3.6.1.4.1.37950.1.1.5.12.8.3.36.3.11
-- 1.3.6.1.4.1.37950.1.1.5.12.8.3.36.3.11
-- 1.3.6.1.4.1.37950.1.1.5.12.8.3.36.3.11
-- 1.3.6.1.4.1.37950.1.1.5.12.8.3.36.3.11
-- 1.3.6.1.4.1.37950.1.1.5.12.8.3.36.3.11
-- 1.3.6.1.4.1.37950.1.1.5.12.8.3.36.3.11
-- 1.3.6.1.4.1.37950.1.1.5.12.8.3.36.3.11
		-- 1.3.6.1.4.1.37950.1.1.5.12.8.3.36.3.11
		connIpMask OBJECT-TYPE
			SYNTAX IpAddress
			MAX-ACCESS read-write
			STATUS current
			DESCRIPTION
				"Description."
			::= { wanConnCfg 11 }

		
--          1.3.6.1.4.1.37950.1.1.5.12.8.3.36.3.12
-- 1.3.6.1.4.1.37950.1.1.5.12.8.3.36.3.12
-- 1.3.6.1.4.1.37950.1.1.5.12.8.3.36.3.12
-- 1.3.6.1.4.1.37950.1.1.5.12.8.3.36.3.12
-- 1.3.6.1.4.1.37950.1.1.5.12.8.3.36.3.12
-- 1.3.6.1.4.1.37950.1.1.5.12.8.3.36.3.12
-- 1.3.6.1.4.1.37950.1.1.5.12.8.3.36.3.12
-- 1.3.6.1.4.1.37950.1.1.5.12.8.3.36.3.12
-- 1.3.6.1.4.1.37950.1.1.5.12.8.3.36.3.12
		-- 1.3.6.1.4.1.37950.1.1.5.12.8.3.36.3.12
		connGateway OBJECT-TYPE
			SYNTAX IpAddress
			MAX-ACCESS read-write
			STATUS current
			DESCRIPTION
				"Description."
			::= { wanConnCfg 12 }

		
--          1.3.6.1.4.1.37950.1.1.5.12.8.3.36.3.13
-- 1.3.6.1.4.1.37950.1.1.5.12.8.3.36.3.13
-- 1.3.6.1.4.1.37950.1.1.5.12.8.3.36.3.13
-- 1.3.6.1.4.1.37950.1.1.5.12.8.3.36.3.13
-- 1.3.6.1.4.1.37950.1.1.5.12.8.3.36.3.13
-- 1.3.6.1.4.1.37950.1.1.5.12.8.3.36.3.13
-- 1.3.6.1.4.1.37950.1.1.5.12.8.3.36.3.13
-- 1.3.6.1.4.1.37950.1.1.5.12.8.3.36.3.13
-- 1.3.6.1.4.1.37950.1.1.5.12.8.3.36.3.13
		-- 1.3.6.1.4.1.37950.1.1.5.12.8.3.36.3.13
		connMasterDns OBJECT-TYPE
			SYNTAX IpAddress
			MAX-ACCESS read-write
			STATUS current
			DESCRIPTION
				"Description."
			::= { wanConnCfg 13 }

		
--          1.3.6.1.4.1.37950.1.1.5.12.8.3.36.3.14
-- 1.3.6.1.4.1.37950.1.1.5.12.8.3.36.3.14
-- 1.3.6.1.4.1.37950.1.1.5.12.8.3.36.3.14
-- 1.3.6.1.4.1.37950.1.1.5.12.8.3.36.3.14
-- 1.3.6.1.4.1.37950.1.1.5.12.8.3.36.3.14
-- 1.3.6.1.4.1.37950.1.1.5.12.8.3.36.3.14
-- 1.3.6.1.4.1.37950.1.1.5.12.8.3.36.3.14
-- 1.3.6.1.4.1.37950.1.1.5.12.8.3.36.3.14
-- 1.3.6.1.4.1.37950.1.1.5.12.8.3.36.3.14
		-- 1.3.6.1.4.1.37950.1.1.5.12.8.3.36.3.14
		connSlaveDns OBJECT-TYPE
			SYNTAX IpAddress
			MAX-ACCESS read-write
			STATUS current
			DESCRIPTION
				"Description."
			::= { wanConnCfg 14 }

		
--          1.3.6.1.4.1.37950.1.1.5.12.8.3.36.3.15
-- 1.3.6.1.4.1.37950.1.1.5.12.8.3.36.3.15
-- 1.3.6.1.4.1.37950.1.1.5.12.8.3.36.3.15
-- 1.3.6.1.4.1.37950.1.1.5.12.8.3.36.3.15
-- 1.3.6.1.4.1.37950.1.1.5.12.8.3.36.3.15
-- 1.3.6.1.4.1.37950.1.1.5.12.8.3.36.3.15
-- 1.3.6.1.4.1.37950.1.1.5.12.8.3.36.3.15
-- 1.3.6.1.4.1.37950.1.1.5.12.8.3.36.3.15
-- 1.3.6.1.4.1.37950.1.1.5.12.8.3.36.3.15
		-- 1.3.6.1.4.1.37950.1.1.5.12.8.3.36.3.15
		connPppoeProxy OBJECT-TYPE
			SYNTAX INTEGER
				{
				disable(0),
				enable(1)
				}
			MAX-ACCESS read-write
			STATUS current
			DESCRIPTION
				"Description."
			::= { wanConnCfg 15 }

		
--          1.3.6.1.4.1.37950.1.1.5.12.8.3.36.3.16
-- 1.3.6.1.4.1.37950.1.1.5.12.8.3.36.3.16
-- 1.3.6.1.4.1.37950.1.1.5.12.8.3.36.3.16
-- 1.3.6.1.4.1.37950.1.1.5.12.8.3.36.3.16
-- 1.3.6.1.4.1.37950.1.1.5.12.8.3.36.3.16
-- 1.3.6.1.4.1.37950.1.1.5.12.8.3.36.3.16
-- 1.3.6.1.4.1.37950.1.1.5.12.8.3.36.3.16
-- 1.3.6.1.4.1.37950.1.1.5.12.8.3.36.3.16
-- 1.3.6.1.4.1.37950.1.1.5.12.8.3.36.3.16
		-- 1.3.6.1.4.1.37950.1.1.5.12.8.3.36.3.16
		connPppoeUsername OBJECT-TYPE
			SYNTAX OCTET STRING
			MAX-ACCESS read-write
			STATUS current
			DESCRIPTION
				"Description."
			::= { wanConnCfg 16 }

		
--          1.3.6.1.4.1.37950.1.1.5.12.8.3.36.3.17
-- 1.3.6.1.4.1.37950.1.1.5.12.8.3.36.3.17
-- 1.3.6.1.4.1.37950.1.1.5.12.8.3.36.3.17
-- 1.3.6.1.4.1.37950.1.1.5.12.8.3.36.3.17
-- 1.3.6.1.4.1.37950.1.1.5.12.8.3.36.3.17
-- 1.3.6.1.4.1.37950.1.1.5.12.8.3.36.3.17
-- 1.3.6.1.4.1.37950.1.1.5.12.8.3.36.3.17
-- 1.3.6.1.4.1.37950.1.1.5.12.8.3.36.3.17
-- 1.3.6.1.4.1.37950.1.1.5.12.8.3.36.3.17
		-- 1.3.6.1.4.1.37950.1.1.5.12.8.3.36.3.17
		connPppoePassword OBJECT-TYPE
			SYNTAX OCTET STRING
			MAX-ACCESS read-write
			STATUS current
			DESCRIPTION
				"Description."
			::= { wanConnCfg 17 }

		
--          1.3.6.1.4.1.37950.1.1.5.12.8.3.36.3.18
-- 1.3.6.1.4.1.37950.1.1.5.12.8.3.36.3.18
-- 1.3.6.1.4.1.37950.1.1.5.12.8.3.36.3.18
-- 1.3.6.1.4.1.37950.1.1.5.12.8.3.36.3.18
-- 1.3.6.1.4.1.37950.1.1.5.12.8.3.36.3.18
-- 1.3.6.1.4.1.37950.1.1.5.12.8.3.36.3.18
-- 1.3.6.1.4.1.37950.1.1.5.12.8.3.36.3.18
-- 1.3.6.1.4.1.37950.1.1.5.12.8.3.36.3.18
-- 1.3.6.1.4.1.37950.1.1.5.12.8.3.36.3.18
		-- 1.3.6.1.4.1.37950.1.1.5.12.8.3.36.3.18
		connPppoeSerName OBJECT-TYPE
			SYNTAX OCTET STRING
			MAX-ACCESS read-write
			STATUS current
			DESCRIPTION
				"Description."
			::= { wanConnCfg 18 }

		
--          1.3.6.1.4.1.37950.1.1.5.12.8.3.36.3.19
-- 1.3.6.1.4.1.37950.1.1.5.12.8.3.36.3.19
-- 1.3.6.1.4.1.37950.1.1.5.12.8.3.36.3.19
-- 1.3.6.1.4.1.37950.1.1.5.12.8.3.36.3.19
-- 1.3.6.1.4.1.37950.1.1.5.12.8.3.36.3.19
-- 1.3.6.1.4.1.37950.1.1.5.12.8.3.36.3.19
-- 1.3.6.1.4.1.37950.1.1.5.12.8.3.36.3.19
-- 1.3.6.1.4.1.37950.1.1.5.12.8.3.36.3.19
-- 1.3.6.1.4.1.37950.1.1.5.12.8.3.36.3.19
		-- 1.3.6.1.4.1.37950.1.1.5.12.8.3.36.3.19
		connPppoeMode OBJECT-TYPE
			SYNTAX INTEGER
				{
				autoConnect(0),
				connecWhenPayload(1)
				}
			MAX-ACCESS read-write
			STATUS current
			DESCRIPTION
				"Description."
			::= { wanConnCfg 19 }

		
--          1.3.6.1.4.1.37950.1.1.5.12.8.3.36.3.20
-- 1.3.6.1.4.1.37950.1.1.5.12.8.3.36.3.20
-- 1.3.6.1.4.1.37950.1.1.5.12.8.3.36.3.20
-- 1.3.6.1.4.1.37950.1.1.5.12.8.3.36.3.20
-- 1.3.6.1.4.1.37950.1.1.5.12.8.3.36.3.20
-- 1.3.6.1.4.1.37950.1.1.5.12.8.3.36.3.20
-- 1.3.6.1.4.1.37950.1.1.5.12.8.3.36.3.20
-- 1.3.6.1.4.1.37950.1.1.5.12.8.3.36.3.20
-- 1.3.6.1.4.1.37950.1.1.5.12.8.3.36.3.20
		-- 1.3.6.1.4.1.37950.1.1.5.12.8.3.36.3.20
		connQosEnable OBJECT-TYPE
			SYNTAX INTEGER
				{
				disable(0),
				enable(1)
				}
			MAX-ACCESS read-write
			STATUS current
			DESCRIPTION
				"Description."
			::= { wanConnCfg 20 }

		
--          1.3.6.1.4.1.37950.1.1.5.12.8.3.36.3.21
-- 1.3.6.1.4.1.37950.1.1.5.12.8.3.36.3.21
-- 1.3.6.1.4.1.37950.1.1.5.12.8.3.36.3.21
-- 1.3.6.1.4.1.37950.1.1.5.12.8.3.36.3.21
-- 1.3.6.1.4.1.37950.1.1.5.12.8.3.36.3.21
-- 1.3.6.1.4.1.37950.1.1.5.12.8.3.36.3.21
-- 1.3.6.1.4.1.37950.1.1.5.12.8.3.36.3.21
-- 1.3.6.1.4.1.37950.1.1.5.12.8.3.36.3.21
-- 1.3.6.1.4.1.37950.1.1.5.12.8.3.36.3.21
		-- 1.3.6.1.4.1.37950.1.1.5.12.8.3.36.3.21
		connVlanMode OBJECT-TYPE
			SYNTAX INTEGER
				{
				disable(0),
				tag(1),
				transparent(2)
				}
			MAX-ACCESS read-write
			STATUS current
			DESCRIPTION
				"Description."
			::= { wanConnCfg 21 }

		
--          1.3.6.1.4.1.37950.1.1.5.12.8.3.36.3.22
-- 1.3.6.1.4.1.37950.1.1.5.12.8.3.36.3.22
-- 1.3.6.1.4.1.37950.1.1.5.12.8.3.36.3.22
-- 1.3.6.1.4.1.37950.1.1.5.12.8.3.36.3.22
-- 1.3.6.1.4.1.37950.1.1.5.12.8.3.36.3.22
-- 1.3.6.1.4.1.37950.1.1.5.12.8.3.36.3.22
-- 1.3.6.1.4.1.37950.1.1.5.12.8.3.36.3.22
-- 1.3.6.1.4.1.37950.1.1.5.12.8.3.36.3.22
-- 1.3.6.1.4.1.37950.1.1.5.12.8.3.36.3.22
		-- 1.3.6.1.4.1.37950.1.1.5.12.8.3.36.3.22
		connTranslationEnable OBJECT-TYPE
			SYNTAX INTEGER
				{
				disable(0),
				enable(1)
				}
			MAX-ACCESS read-write
			STATUS current
			DESCRIPTION
				"Description."
			::= { wanConnCfg 22 }

		
--          1.3.6.1.4.1.37950.1.1.5.12.8.3.36.3.23
-- 1.3.6.1.4.1.37950.1.1.5.12.8.3.36.3.23
-- 1.3.6.1.4.1.37950.1.1.5.12.8.3.36.3.23
-- 1.3.6.1.4.1.37950.1.1.5.12.8.3.36.3.23
-- 1.3.6.1.4.1.37950.1.1.5.12.8.3.36.3.23
-- 1.3.6.1.4.1.37950.1.1.5.12.8.3.36.3.23
-- 1.3.6.1.4.1.37950.1.1.5.12.8.3.36.3.23
-- 1.3.6.1.4.1.37950.1.1.5.12.8.3.36.3.23
-- 1.3.6.1.4.1.37950.1.1.5.12.8.3.36.3.23
		-- 1.3.6.1.4.1.37950.1.1.5.12.8.3.36.3.23
		connTranslationVlan OBJECT-TYPE
			SYNTAX INTEGER (0..4095)
			MAX-ACCESS read-write
			STATUS current
			DESCRIPTION
				"Description."
			::= { wanConnCfg 23 }

		
--          1.3.6.1.4.1.37950.1.1.5.12.8.3.36.3.24
-- 1.3.6.1.4.1.37950.1.1.5.12.8.3.36.3.24
-- 1.3.6.1.4.1.37950.1.1.5.12.8.3.36.3.24
-- 1.3.6.1.4.1.37950.1.1.5.12.8.3.36.3.24
-- 1.3.6.1.4.1.37950.1.1.5.12.8.3.36.3.24
-- 1.3.6.1.4.1.37950.1.1.5.12.8.3.36.3.24
-- 1.3.6.1.4.1.37950.1.1.5.12.8.3.36.3.24
-- 1.3.6.1.4.1.37950.1.1.5.12.8.3.36.3.24
-- 1.3.6.1.4.1.37950.1.1.5.12.8.3.36.3.24
		-- 1.3.6.1.4.1.37950.1.1.5.12.8.3.36.3.24
		connTranslationCos OBJECT-TYPE
			SYNTAX INTEGER (0..7)
			MAX-ACCESS read-write
			STATUS current
			DESCRIPTION
				"Description."
			::= { wanConnCfg 24 }

		
--          1.3.6.1.4.1.37950.1.1.5.12.8.3.36.3.25
-- 1.3.6.1.4.1.37950.1.1.5.12.8.3.36.3.25
-- 1.3.6.1.4.1.37950.1.1.5.12.8.3.36.3.25
-- 1.3.6.1.4.1.37950.1.1.5.12.8.3.36.3.25
-- 1.3.6.1.4.1.37950.1.1.5.12.8.3.36.3.25
-- 1.3.6.1.4.1.37950.1.1.5.12.8.3.36.3.25
-- 1.3.6.1.4.1.37950.1.1.5.12.8.3.36.3.25
-- 1.3.6.1.4.1.37950.1.1.5.12.8.3.36.3.25
-- 1.3.6.1.4.1.37950.1.1.5.12.8.3.36.3.25
		-- 1.3.6.1.4.1.37950.1.1.5.12.8.3.36.3.25
		connQinqEnable OBJECT-TYPE
			SYNTAX INTEGER
				{
				disable(0),
				enable(1)
				}
			MAX-ACCESS read-write
			STATUS current
			DESCRIPTION
				"Description."
			::= { wanConnCfg 25 }

		
--          1.3.6.1.4.1.37950.1.1.5.12.8.3.36.3.26
-- 1.3.6.1.4.1.37950.1.1.5.12.8.3.36.3.26
-- 1.3.6.1.4.1.37950.1.1.5.12.8.3.36.3.26
-- 1.3.6.1.4.1.37950.1.1.5.12.8.3.36.3.26
-- 1.3.6.1.4.1.37950.1.1.5.12.8.3.36.3.26
-- 1.3.6.1.4.1.37950.1.1.5.12.8.3.36.3.26
-- 1.3.6.1.4.1.37950.1.1.5.12.8.3.36.3.26
-- 1.3.6.1.4.1.37950.1.1.5.12.8.3.36.3.26
-- 1.3.6.1.4.1.37950.1.1.5.12.8.3.36.3.26
		-- 1.3.6.1.4.1.37950.1.1.5.12.8.3.36.3.26
		connQinqTpid OBJECT-TYPE
			SYNTAX Integer32 (0..65534)
			MAX-ACCESS read-write
			STATUS current
			DESCRIPTION
				"Description."
			::= { wanConnCfg 26 }

		
--          1.3.6.1.4.1.37950.1.1.5.12.8.3.36.3.27
-- 1.3.6.1.4.1.37950.1.1.5.12.8.3.36.3.27
-- 1.3.6.1.4.1.37950.1.1.5.12.8.3.36.3.27
-- 1.3.6.1.4.1.37950.1.1.5.12.8.3.36.3.27
-- 1.3.6.1.4.1.37950.1.1.5.12.8.3.36.3.27
-- 1.3.6.1.4.1.37950.1.1.5.12.8.3.36.3.27
-- 1.3.6.1.4.1.37950.1.1.5.12.8.3.36.3.27
-- 1.3.6.1.4.1.37950.1.1.5.12.8.3.36.3.27
-- 1.3.6.1.4.1.37950.1.1.5.12.8.3.36.3.27
		-- 1.3.6.1.4.1.37950.1.1.5.12.8.3.36.3.27
		connWanSvlan OBJECT-TYPE
			SYNTAX INTEGER (0..4095)
			MAX-ACCESS read-write
			STATUS current
			DESCRIPTION
				"Description."
			::= { wanConnCfg 27 }

		
--          1.3.6.1.4.1.37950.1.1.5.12.8.3.36.3.28
-- 1.3.6.1.4.1.37950.1.1.5.12.8.3.36.3.28
-- 1.3.6.1.4.1.37950.1.1.5.12.8.3.36.3.28
-- 1.3.6.1.4.1.37950.1.1.5.12.8.3.36.3.28
-- 1.3.6.1.4.1.37950.1.1.5.12.8.3.36.3.28
-- 1.3.6.1.4.1.37950.1.1.5.12.8.3.36.3.28
-- 1.3.6.1.4.1.37950.1.1.5.12.8.3.36.3.28
-- 1.3.6.1.4.1.37950.1.1.5.12.8.3.36.3.28
-- 1.3.6.1.4.1.37950.1.1.5.12.8.3.36.3.28
		-- 1.3.6.1.4.1.37950.1.1.5.12.8.3.36.3.28
		connSvlanCos OBJECT-TYPE
			SYNTAX INTEGER (0..7)
			MAX-ACCESS read-write
			STATUS current
			DESCRIPTION
				"Description."
			::= { wanConnCfg 28 }

		
--          1.3.6.1.4.1.37950.1.1.5.12.8.3.36.3.29
-- 1.3.6.1.4.1.37950.1.1.5.12.8.3.36.3.29
-- 1.3.6.1.4.1.37950.1.1.5.12.8.3.36.3.29
-- 1.3.6.1.4.1.37950.1.1.5.12.8.3.36.3.29
-- 1.3.6.1.4.1.37950.1.1.5.12.8.3.36.3.29
-- 1.3.6.1.4.1.37950.1.1.5.12.8.3.36.3.29
-- 1.3.6.1.4.1.37950.1.1.5.12.8.3.36.3.29
-- 1.3.6.1.4.1.37950.1.1.5.12.8.3.36.3.29
-- 1.3.6.1.4.1.37950.1.1.5.12.8.3.36.3.29
		-- 1.3.6.1.4.1.37950.1.1.5.12.8.3.36.3.29
		connCfgAction OBJECT-TYPE
			SYNTAX INTEGER { add(1) }
			MAX-ACCESS read-write
			STATUS current
			DESCRIPTION
				"Description."
			::= { wanConnCfg 29 }

		
--         1.3.6.1.4.1.37950.1.1.5.12.8.3.36.3.30
-- 1.3.6.1.4.1.37950.1.1.5.12.8.3.36.3.30
-- 1.3.6.1.4.1.37950.1.1.5.12.8.3.36.3.30
-- 1.3.6.1.4.1.37950.1.1.5.12.8.3.36.3.30
-- 1.3.6.1.4.1.37950.1.1.5.12.8.3.36.3.30
-- 1.3.6.1.4.1.37950.1.1.5.12.8.3.36.3.30
-- 1.3.6.1.4.1.37950.1.1.5.12.8.3.36.3.30
-- 1.3.6.1.4.1.37950.1.1.5.12.8.3.36.3.30
		-- 1.3.6.1.4.1.37950.1.1.5.12.8.3.36.3.30
		connRouteMtu OBJECT-TYPE
			SYNTAX Integer32 (0 | 576..1500)
			MAX-ACCESS read-write
			STATUS current
			DESCRIPTION
				"Description."
			::= { wanConnCfg 30 }

		
--          1.3.6.1.4.1.37950.1.1.5.12.8.3.36.4
-- 1.3.6.1.4.1.37950.1.1.5.12.8.3.36.4
-- 1.3.6.1.4.1.37950.1.1.5.12.8.3.36.4
-- 1.3.6.1.4.1.37950.1.1.5.12.8.3.36.4
-- 1.3.6.1.4.1.37950.1.1.5.12.8.3.36.4
-- 1.3.6.1.4.1.37950.1.1.5.12.8.3.36.4
-- 1.3.6.1.4.1.37950.1.1.5.12.8.3.36.4
-- 1.3.6.1.4.1.37950.1.1.5.12.8.3.36.4
-- 1.3.6.1.4.1.37950.1.1.5.12.8.3.36.4
		-- 1.3.6.1.4.1.37950.1.1.5.12.8.3.36.4
		wanConnCommit OBJECT IDENTIFIER ::= { onuWanConn 4 }

		
--          1.3.6.1.4.1.37950.1.1.5.12.8.3.36.4.1
-- 1.3.6.1.4.1.37950.1.1.5.12.8.3.36.4.1
-- 1.3.6.1.4.1.37950.1.1.5.12.8.3.36.4.1
-- 1.3.6.1.4.1.37950.1.1.5.12.8.3.36.4.1
-- 1.3.6.1.4.1.37950.1.1.5.12.8.3.36.4.1
-- 1.3.6.1.4.1.37950.1.1.5.12.8.3.36.4.1
-- 1.3.6.1.4.1.37950.1.1.5.12.8.3.36.4.1
-- 1.3.6.1.4.1.37950.1.1.5.12.8.3.36.4.1
-- 1.3.6.1.4.1.37950.1.1.5.12.8.3.36.4.1
		-- 1.3.6.1.4.1.37950.1.1.5.12.8.3.36.4.1
		connCommitAction OBJECT-TYPE
			SYNTAX INTEGER
				{
				commit(1),
				remove(2)
				}
			MAX-ACCESS read-write
			STATUS current
			DESCRIPTION
				"Description."
			::= { wanConnCommit 1 }

		
--          1.3.6.1.4.1.37950.1.1.5.12.8.3.37
-- 1.3.6.1.4.1.37950.1.1.5.12.8.3.37
-- 1.3.6.1.4.1.37950.1.1.5.12.8.3.37
-- 1.3.6.1.4.1.37950.1.1.5.12.8.3.37
-- 1.3.6.1.4.1.37950.1.1.5.12.8.3.37
-- 1.3.6.1.4.1.37950.1.1.5.12.8.3.37
-- 1.3.6.1.4.1.37950.1.1.5.12.8.3.37
-- 1.3.6.1.4.1.37950.1.1.5.12.8.3.37
-- 1.3.6.1.4.1.37950.1.1.5.12.8.3.37
		-- 1.3.6.1.4.1.37950.1.1.5.12.8.3.37
		onuPortMacLimit OBJECT IDENTIFIER ::= { srvProfileEdit 37 }

		
--          1.3.6.1.4.1.37950.1.1.5.12.8.3.37.1
-- 1.3.6.1.4.1.37950.1.1.5.12.8.3.37.1
-- 1.3.6.1.4.1.37950.1.1.5.12.8.3.37.1
-- 1.3.6.1.4.1.37950.1.1.5.12.8.3.37.1
-- 1.3.6.1.4.1.37950.1.1.5.12.8.3.37.1
-- 1.3.6.1.4.1.37950.1.1.5.12.8.3.37.1
-- 1.3.6.1.4.1.37950.1.1.5.12.8.3.37.1
-- 1.3.6.1.4.1.37950.1.1.5.12.8.3.37.1
-- 1.3.6.1.4.1.37950.1.1.5.12.8.3.37.1
		-- 1.3.6.1.4.1.37950.1.1.5.12.8.3.37.1
		macLimitEthNo OBJECT-TYPE
			SYNTAX INTEGER (1..255)
			MAX-ACCESS read-write
			STATUS current
			DESCRIPTION
				"Description."
			::= { onuPortMacLimit 1 }

		
--          1.3.6.1.4.1.37950.1.1.5.12.8.3.37.2
-- 1.3.6.1.4.1.37950.1.1.5.12.8.3.37.2
-- 1.3.6.1.4.1.37950.1.1.5.12.8.3.37.2
-- 1.3.6.1.4.1.37950.1.1.5.12.8.3.37.2
-- 1.3.6.1.4.1.37950.1.1.5.12.8.3.37.2
-- 1.3.6.1.4.1.37950.1.1.5.12.8.3.37.2
-- 1.3.6.1.4.1.37950.1.1.5.12.8.3.37.2
-- 1.3.6.1.4.1.37950.1.1.5.12.8.3.37.2
-- 1.3.6.1.4.1.37950.1.1.5.12.8.3.37.2
		-- 1.3.6.1.4.1.37950.1.1.5.12.8.3.37.2
		macLimit OBJECT-TYPE
			SYNTAX INTEGER (0..65535)
			MAX-ACCESS read-write
			STATUS current
			DESCRIPTION
				"Description."
			::= { onuPortMacLimit 2 }

		
--          1.3.6.1.4.1.37950.1.1.5.12.8.3.37.3
-- 1.3.6.1.4.1.37950.1.1.5.12.8.3.37.3
-- 1.3.6.1.4.1.37950.1.1.5.12.8.3.37.3
-- 1.3.6.1.4.1.37950.1.1.5.12.8.3.37.3
-- 1.3.6.1.4.1.37950.1.1.5.12.8.3.37.3
-- 1.3.6.1.4.1.37950.1.1.5.12.8.3.37.3
-- 1.3.6.1.4.1.37950.1.1.5.12.8.3.37.3
-- 1.3.6.1.4.1.37950.1.1.5.12.8.3.37.3
-- 1.3.6.1.4.1.37950.1.1.5.12.8.3.37.3
		-- 1.3.6.1.4.1.37950.1.1.5.12.8.3.37.3
		macLimitAction OBJECT-TYPE
			SYNTAX INTEGER
				{
				add(1),
				remove(2)
				}
			MAX-ACCESS read-write
			STATUS current
			DESCRIPTION
				"Description."
			::= { onuPortMacLimit 3 }

		
--          1.3.6.1.4.1.37950.1.1.5.12.8.3.38
-- 1.3.6.1.4.1.37950.1.1.5.12.8.3.38
-- 1.3.6.1.4.1.37950.1.1.5.12.8.3.38
-- 1.3.6.1.4.1.37950.1.1.5.12.8.3.38
-- 1.3.6.1.4.1.37950.1.1.5.12.8.3.38
-- 1.3.6.1.4.1.37950.1.1.5.12.8.3.38
-- 1.3.6.1.4.1.37950.1.1.5.12.8.3.38
-- 1.3.6.1.4.1.37950.1.1.5.12.8.3.38
-- 1.3.6.1.4.1.37950.1.1.5.12.8.3.38
		-- 1.3.6.1.4.1.37950.1.1.5.12.8.3.38
		onuPortPkgSuppress OBJECT IDENTIFIER ::= { srvProfileEdit 38 }

		
--          1.3.6.1.4.1.37950.1.1.5.12.8.3.38.1
-- 1.3.6.1.4.1.37950.1.1.5.12.8.3.38.1
-- 1.3.6.1.4.1.37950.1.1.5.12.8.3.38.1
-- 1.3.6.1.4.1.37950.1.1.5.12.8.3.38.1
-- 1.3.6.1.4.1.37950.1.1.5.12.8.3.38.1
-- 1.3.6.1.4.1.37950.1.1.5.12.8.3.38.1
-- 1.3.6.1.4.1.37950.1.1.5.12.8.3.38.1
-- 1.3.6.1.4.1.37950.1.1.5.12.8.3.38.1
-- 1.3.6.1.4.1.37950.1.1.5.12.8.3.38.1
		-- 1.3.6.1.4.1.37950.1.1.5.12.8.3.38.1
		pkgSuppressEthNo OBJECT-TYPE
			SYNTAX INTEGER (1..255)
			MAX-ACCESS read-write
			STATUS current
			DESCRIPTION
				"Description."
			::= { onuPortPkgSuppress 1 }

		
--          1.3.6.1.4.1.37950.1.1.5.12.8.3.38.2
-- 1.3.6.1.4.1.37950.1.1.5.12.8.3.38.2
-- 1.3.6.1.4.1.37950.1.1.5.12.8.3.38.2
-- 1.3.6.1.4.1.37950.1.1.5.12.8.3.38.2
-- 1.3.6.1.4.1.37950.1.1.5.12.8.3.38.2
-- 1.3.6.1.4.1.37950.1.1.5.12.8.3.38.2
-- 1.3.6.1.4.1.37950.1.1.5.12.8.3.38.2
-- 1.3.6.1.4.1.37950.1.1.5.12.8.3.38.2
-- 1.3.6.1.4.1.37950.1.1.5.12.8.3.38.2
		-- 1.3.6.1.4.1.37950.1.1.5.12.8.3.38.2
		pkgBroadcast OBJECT-TYPE
			SYNTAX INTEGER (0..1024000)
			MAX-ACCESS read-write
			STATUS current
			DESCRIPTION
				"Description."
			::= { onuPortPkgSuppress 2 }

		
--          1.3.6.1.4.1.37950.1.1.5.12.8.3.38.3
-- 1.3.6.1.4.1.37950.1.1.5.12.8.3.38.3
-- 1.3.6.1.4.1.37950.1.1.5.12.8.3.38.3
-- 1.3.6.1.4.1.37950.1.1.5.12.8.3.38.3
-- 1.3.6.1.4.1.37950.1.1.5.12.8.3.38.3
-- 1.3.6.1.4.1.37950.1.1.5.12.8.3.38.3
-- 1.3.6.1.4.1.37950.1.1.5.12.8.3.38.3
-- 1.3.6.1.4.1.37950.1.1.5.12.8.3.38.3
-- 1.3.6.1.4.1.37950.1.1.5.12.8.3.38.3
		-- 1.3.6.1.4.1.37950.1.1.5.12.8.3.38.3
		pkgMulticast OBJECT-TYPE
			SYNTAX INTEGER (0..1024000)
			MAX-ACCESS read-write
			STATUS current
			DESCRIPTION
				"Description."
			::= { onuPortPkgSuppress 3 }

		
--          1.3.6.1.4.1.37950.1.1.5.12.8.3.38.4
-- 1.3.6.1.4.1.37950.1.1.5.12.8.3.38.4
-- 1.3.6.1.4.1.37950.1.1.5.12.8.3.38.4
-- 1.3.6.1.4.1.37950.1.1.5.12.8.3.38.4
-- 1.3.6.1.4.1.37950.1.1.5.12.8.3.38.4
-- 1.3.6.1.4.1.37950.1.1.5.12.8.3.38.4
-- 1.3.6.1.4.1.37950.1.1.5.12.8.3.38.4
-- 1.3.6.1.4.1.37950.1.1.5.12.8.3.38.4
-- 1.3.6.1.4.1.37950.1.1.5.12.8.3.38.4
		-- 1.3.6.1.4.1.37950.1.1.5.12.8.3.38.4
		pkgUnknown OBJECT-TYPE
			SYNTAX INTEGER (0..1024000)
			MAX-ACCESS read-write
			STATUS current
			DESCRIPTION
				"Description."
			::= { onuPortPkgSuppress 4 }

		
--          1.3.6.1.4.1.37950.1.1.5.12.8.3.38.5
-- 1.3.6.1.4.1.37950.1.1.5.12.8.3.38.5
-- 1.3.6.1.4.1.37950.1.1.5.12.8.3.38.5
-- 1.3.6.1.4.1.37950.1.1.5.12.8.3.38.5
-- 1.3.6.1.4.1.37950.1.1.5.12.8.3.38.5
-- 1.3.6.1.4.1.37950.1.1.5.12.8.3.38.5
-- 1.3.6.1.4.1.37950.1.1.5.12.8.3.38.5
-- 1.3.6.1.4.1.37950.1.1.5.12.8.3.38.5
-- 1.3.6.1.4.1.37950.1.1.5.12.8.3.38.5
		-- 1.3.6.1.4.1.37950.1.1.5.12.8.3.38.5
		pkgSuppressAction OBJECT-TYPE
			SYNTAX INTEGER
				{
				add(1),
				remove(2)
				}
			MAX-ACCESS read-write
			STATUS current
			DESCRIPTION
				"Description."
			::= { onuPortPkgSuppress 5 }

		
--          1.3.6.1.4.1.37950.1.1.5.12.8.3.39
-- 1.3.6.1.4.1.37950.1.1.5.12.8.3.39
-- 1.3.6.1.4.1.37950.1.1.5.12.8.3.39
-- 1.3.6.1.4.1.37950.1.1.5.12.8.3.39
-- 1.3.6.1.4.1.37950.1.1.5.12.8.3.39
-- 1.3.6.1.4.1.37950.1.1.5.12.8.3.39
-- 1.3.6.1.4.1.37950.1.1.5.12.8.3.39
-- 1.3.6.1.4.1.37950.1.1.5.12.8.3.39
-- 1.3.6.1.4.1.37950.1.1.5.12.8.3.39
		-- 1.3.6.1.4.1.37950.1.1.5.12.8.3.39
		onuPortIsolateEnable OBJECT IDENTIFIER ::= { srvProfileEdit 39 }

		
--          1.3.6.1.4.1.37950.1.1.5.12.8.3.39.1
-- 1.3.6.1.4.1.37950.1.1.5.12.8.3.39.1
-- 1.3.6.1.4.1.37950.1.1.5.12.8.3.39.1
-- 1.3.6.1.4.1.37950.1.1.5.12.8.3.39.1
-- 1.3.6.1.4.1.37950.1.1.5.12.8.3.39.1
-- 1.3.6.1.4.1.37950.1.1.5.12.8.3.39.1
-- 1.3.6.1.4.1.37950.1.1.5.12.8.3.39.1
-- 1.3.6.1.4.1.37950.1.1.5.12.8.3.39.1
-- 1.3.6.1.4.1.37950.1.1.5.12.8.3.39.1
		-- 1.3.6.1.4.1.37950.1.1.5.12.8.3.39.1
		portIsolateEnable OBJECT-TYPE
			SYNTAX INTEGER
				{
				disable(0),
				enable(1)
				}
			MAX-ACCESS read-write
			STATUS current
			DESCRIPTION
				"Description."
			::= { onuPortIsolateEnable 1 }

		
--          1.3.6.1.4.1.37950.1.1.5.12.8.3.39.2
-- 1.3.6.1.4.1.37950.1.1.5.12.8.3.39.2
-- 1.3.6.1.4.1.37950.1.1.5.12.8.3.39.2
-- 1.3.6.1.4.1.37950.1.1.5.12.8.3.39.2
-- 1.3.6.1.4.1.37950.1.1.5.12.8.3.39.2
-- 1.3.6.1.4.1.37950.1.1.5.12.8.3.39.2
-- 1.3.6.1.4.1.37950.1.1.5.12.8.3.39.2
-- 1.3.6.1.4.1.37950.1.1.5.12.8.3.39.2
-- 1.3.6.1.4.1.37950.1.1.5.12.8.3.39.2
		-- 1.3.6.1.4.1.37950.1.1.5.12.8.3.39.2
		portIsolateAction OBJECT-TYPE
			SYNTAX INTEGER
				{
				add(1),
				remove(2)
				}
			MAX-ACCESS read-write
			STATUS current
			DESCRIPTION
				"Description."
			::= { onuPortIsolateEnable 2 }

		
--          1.3.6.1.4.1.37950.1.1.5.12.8.3.40
-- 1.3.6.1.4.1.37950.1.1.5.12.8.3.40
-- 1.3.6.1.4.1.37950.1.1.5.12.8.3.40
-- 1.3.6.1.4.1.37950.1.1.5.12.8.3.40
-- 1.3.6.1.4.1.37950.1.1.5.12.8.3.40
-- 1.3.6.1.4.1.37950.1.1.5.12.8.3.40
-- 1.3.6.1.4.1.37950.1.1.5.12.8.3.40
-- 1.3.6.1.4.1.37950.1.1.5.12.8.3.40
-- 1.3.6.1.4.1.37950.1.1.5.12.8.3.40
		-- 1.3.6.1.4.1.37950.1.1.5.12.8.3.40
		onuPortModeControl OBJECT IDENTIFIER ::= { srvProfileEdit 40 }

		
--          1.3.6.1.4.1.37950.1.1.5.12.8.3.40.1
-- 1.3.6.1.4.1.37950.1.1.5.12.8.3.40.1
-- 1.3.6.1.4.1.37950.1.1.5.12.8.3.40.1
-- 1.3.6.1.4.1.37950.1.1.5.12.8.3.40.1
-- 1.3.6.1.4.1.37950.1.1.5.12.8.3.40.1
-- 1.3.6.1.4.1.37950.1.1.5.12.8.3.40.1
-- 1.3.6.1.4.1.37950.1.1.5.12.8.3.40.1
-- 1.3.6.1.4.1.37950.1.1.5.12.8.3.40.1
-- 1.3.6.1.4.1.37950.1.1.5.12.8.3.40.1
		-- 1.3.6.1.4.1.37950.1.1.5.12.8.3.40.1
		modeControlEthNo OBJECT-TYPE
			SYNTAX INTEGER (1..255)
			MAX-ACCESS read-write
			STATUS current
			DESCRIPTION
				"Description."
			::= { onuPortModeControl 1 }

		
--          1.3.6.1.4.1.37950.1.1.5.12.8.3.40.2
-- 1.3.6.1.4.1.37950.1.1.5.12.8.3.40.2
-- 1.3.6.1.4.1.37950.1.1.5.12.8.3.40.2
-- 1.3.6.1.4.1.37950.1.1.5.12.8.3.40.2
-- 1.3.6.1.4.1.37950.1.1.5.12.8.3.40.2
-- 1.3.6.1.4.1.37950.1.1.5.12.8.3.40.2
-- 1.3.6.1.4.1.37950.1.1.5.12.8.3.40.2
-- 1.3.6.1.4.1.37950.1.1.5.12.8.3.40.2
-- 1.3.6.1.4.1.37950.1.1.5.12.8.3.40.2
		-- 1.3.6.1.4.1.37950.1.1.5.12.8.3.40.2
		modeControl OBJECT-TYPE
			SYNTAX INTEGER
				{
				s10hd(1),
				s10fd(2),
				s100hd(3),
				s100fd(4),
				s1000hd(5),
				s1000fd(6),
				s10000fd(7)
				}
			MAX-ACCESS read-write
			STATUS current
			DESCRIPTION
				"Description."
			::= { onuPortModeControl 2 }

		
--          1.3.6.1.4.1.37950.1.1.5.12.8.3.40.3
-- 1.3.6.1.4.1.37950.1.1.5.12.8.3.40.3
-- 1.3.6.1.4.1.37950.1.1.5.12.8.3.40.3
-- 1.3.6.1.4.1.37950.1.1.5.12.8.3.40.3
-- 1.3.6.1.4.1.37950.1.1.5.12.8.3.40.3
-- 1.3.6.1.4.1.37950.1.1.5.12.8.3.40.3
-- 1.3.6.1.4.1.37950.1.1.5.12.8.3.40.3
-- 1.3.6.1.4.1.37950.1.1.5.12.8.3.40.3
-- 1.3.6.1.4.1.37950.1.1.5.12.8.3.40.3
		-- 1.3.6.1.4.1.37950.1.1.5.12.8.3.40.3
		modeControlAction OBJECT-TYPE
			SYNTAX INTEGER
				{
				add(1),
				remove(2)
				}
			MAX-ACCESS read-write
			STATUS current
			DESCRIPTION
				"Description."
			::= { onuPortModeControl 3 }

		
--          1.3.6.1.4.1.37950.1.1.5.12.8.3.41
-- 1.3.6.1.4.1.37950.1.1.5.12.8.3.41
-- 1.3.6.1.4.1.37950.1.1.5.12.8.3.41
-- 1.3.6.1.4.1.37950.1.1.5.12.8.3.41
-- 1.3.6.1.4.1.37950.1.1.5.12.8.3.41
-- 1.3.6.1.4.1.37950.1.1.5.12.8.3.41
-- 1.3.6.1.4.1.37950.1.1.5.12.8.3.41
-- 1.3.6.1.4.1.37950.1.1.5.12.8.3.41
-- 1.3.6.1.4.1.37950.1.1.5.12.8.3.41
		-- 1.3.6.1.4.1.37950.1.1.5.12.8.3.41
		onuDhcpServer OBJECT IDENTIFIER ::= { srvProfileEdit 41 }

		
--          1.3.6.1.4.1.37950.1.1.5.12.8.3.41.1
-- 1.3.6.1.4.1.37950.1.1.5.12.8.3.41.1
-- 1.3.6.1.4.1.37950.1.1.5.12.8.3.41.1
-- 1.3.6.1.4.1.37950.1.1.5.12.8.3.41.1
-- 1.3.6.1.4.1.37950.1.1.5.12.8.3.41.1
-- 1.3.6.1.4.1.37950.1.1.5.12.8.3.41.1
-- 1.3.6.1.4.1.37950.1.1.5.12.8.3.41.1
-- 1.3.6.1.4.1.37950.1.1.5.12.8.3.41.1
-- 1.3.6.1.4.1.37950.1.1.5.12.8.3.41.1
		-- 1.3.6.1.4.1.37950.1.1.5.12.8.3.41.1
		dhcpLanip OBJECT-TYPE
			SYNTAX IpAddress
			MAX-ACCESS read-write
			STATUS current
			DESCRIPTION
				"Description."
			::= { onuDhcpServer 1 }

		
--          1.3.6.1.4.1.37950.1.1.5.12.8.3.41.2
-- 1.3.6.1.4.1.37950.1.1.5.12.8.3.41.2
-- 1.3.6.1.4.1.37950.1.1.5.12.8.3.41.2
-- 1.3.6.1.4.1.37950.1.1.5.12.8.3.41.2
-- 1.3.6.1.4.1.37950.1.1.5.12.8.3.41.2
-- 1.3.6.1.4.1.37950.1.1.5.12.8.3.41.2
-- 1.3.6.1.4.1.37950.1.1.5.12.8.3.41.2
-- 1.3.6.1.4.1.37950.1.1.5.12.8.3.41.2
-- 1.3.6.1.4.1.37950.1.1.5.12.8.3.41.2
		-- 1.3.6.1.4.1.37950.1.1.5.12.8.3.41.2
		dhcplanMask OBJECT-TYPE
			SYNTAX IpAddress
			MAX-ACCESS read-write
			STATUS current
			DESCRIPTION
				"Description."
			::= { onuDhcpServer 2 }

		
--          1.3.6.1.4.1.37950.1.1.5.12.8.3.41.3
-- 1.3.6.1.4.1.37950.1.1.5.12.8.3.41.3
-- 1.3.6.1.4.1.37950.1.1.5.12.8.3.41.3
-- 1.3.6.1.4.1.37950.1.1.5.12.8.3.41.3
-- 1.3.6.1.4.1.37950.1.1.5.12.8.3.41.3
-- 1.3.6.1.4.1.37950.1.1.5.12.8.3.41.3
-- 1.3.6.1.4.1.37950.1.1.5.12.8.3.41.3
-- 1.3.6.1.4.1.37950.1.1.5.12.8.3.41.3
-- 1.3.6.1.4.1.37950.1.1.5.12.8.3.41.3
		-- 1.3.6.1.4.1.37950.1.1.5.12.8.3.41.3
		dhcpServerEnable OBJECT-TYPE
			SYNTAX INTEGER
				{
				disable(0),
				enable(1),
				relay(2)
				}
			MAX-ACCESS read-write
			STATUS current
			DESCRIPTION
				"Description."
			::= { onuDhcpServer 3 }

		
--          1.3.6.1.4.1.37950.1.1.5.12.8.3.41.4
-- 1.3.6.1.4.1.37950.1.1.5.12.8.3.41.4
-- 1.3.6.1.4.1.37950.1.1.5.12.8.3.41.4
-- 1.3.6.1.4.1.37950.1.1.5.12.8.3.41.4
-- 1.3.6.1.4.1.37950.1.1.5.12.8.3.41.4
-- 1.3.6.1.4.1.37950.1.1.5.12.8.3.41.4
-- 1.3.6.1.4.1.37950.1.1.5.12.8.3.41.4
-- 1.3.6.1.4.1.37950.1.1.5.12.8.3.41.4
-- 1.3.6.1.4.1.37950.1.1.5.12.8.3.41.4
		-- 1.3.6.1.4.1.37950.1.1.5.12.8.3.41.4
		dhcpLease OBJECT-TYPE
			SYNTAX Unsigned32 (0..4294967295)
			MAX-ACCESS read-write
			STATUS current
			DESCRIPTION
				"Description."
			::= { onuDhcpServer 4 }

		
--          1.3.6.1.4.1.37950.1.1.5.12.8.3.41.5
-- 1.3.6.1.4.1.37950.1.1.5.12.8.3.41.5
-- 1.3.6.1.4.1.37950.1.1.5.12.8.3.41.5
-- 1.3.6.1.4.1.37950.1.1.5.12.8.3.41.5
-- 1.3.6.1.4.1.37950.1.1.5.12.8.3.41.5
-- 1.3.6.1.4.1.37950.1.1.5.12.8.3.41.5
-- 1.3.6.1.4.1.37950.1.1.5.12.8.3.41.5
-- 1.3.6.1.4.1.37950.1.1.5.12.8.3.41.5
-- 1.3.6.1.4.1.37950.1.1.5.12.8.3.41.5
		-- 1.3.6.1.4.1.37950.1.1.5.12.8.3.41.5
		dhcpBeginIp OBJECT-TYPE
			SYNTAX IpAddress
			MAX-ACCESS read-write
			STATUS current
			DESCRIPTION
				"Description."
			::= { onuDhcpServer 5 }

		
--          1.3.6.1.4.1.37950.1.1.5.12.8.3.41.6
-- 1.3.6.1.4.1.37950.1.1.5.12.8.3.41.6
-- 1.3.6.1.4.1.37950.1.1.5.12.8.3.41.6
-- 1.3.6.1.4.1.37950.1.1.5.12.8.3.41.6
-- 1.3.6.1.4.1.37950.1.1.5.12.8.3.41.6
-- 1.3.6.1.4.1.37950.1.1.5.12.8.3.41.6
-- 1.3.6.1.4.1.37950.1.1.5.12.8.3.41.6
-- 1.3.6.1.4.1.37950.1.1.5.12.8.3.41.6
-- 1.3.6.1.4.1.37950.1.1.5.12.8.3.41.6
		-- 1.3.6.1.4.1.37950.1.1.5.12.8.3.41.6
		dhcpEndIp OBJECT-TYPE
			SYNTAX IpAddress
			MAX-ACCESS read-write
			STATUS current
			DESCRIPTION
				"Description."
			::= { onuDhcpServer 6 }

		
--          1.3.6.1.4.1.37950.1.1.5.12.8.3.41.7
-- 1.3.6.1.4.1.37950.1.1.5.12.8.3.41.7
-- 1.3.6.1.4.1.37950.1.1.5.12.8.3.41.7
-- 1.3.6.1.4.1.37950.1.1.5.12.8.3.41.7
-- 1.3.6.1.4.1.37950.1.1.5.12.8.3.41.7
-- 1.3.6.1.4.1.37950.1.1.5.12.8.3.41.7
-- 1.3.6.1.4.1.37950.1.1.5.12.8.3.41.7
-- 1.3.6.1.4.1.37950.1.1.5.12.8.3.41.7
-- 1.3.6.1.4.1.37950.1.1.5.12.8.3.41.7
		-- 1.3.6.1.4.1.37950.1.1.5.12.8.3.41.7
		dhcpPoolType OBJECT-TYPE
			SYNTAX INTEGER
				{
				pc(0),
				camera(1),
				stb(2),
				ip-phone(3)
				}
			MAX-ACCESS read-write
			STATUS current
			DESCRIPTION
				"Description."
			::= { onuDhcpServer 7 }

		
--          1.3.6.1.4.1.37950.1.1.5.12.8.3.41.8
-- 1.3.6.1.4.1.37950.1.1.5.12.8.3.41.8
-- 1.3.6.1.4.1.37950.1.1.5.12.8.3.41.8
-- 1.3.6.1.4.1.37950.1.1.5.12.8.3.41.8
-- 1.3.6.1.4.1.37950.1.1.5.12.8.3.41.8
-- 1.3.6.1.4.1.37950.1.1.5.12.8.3.41.8
-- 1.3.6.1.4.1.37950.1.1.5.12.8.3.41.8
-- 1.3.6.1.4.1.37950.1.1.5.12.8.3.41.8
-- 1.3.6.1.4.1.37950.1.1.5.12.8.3.41.8
		-- 1.3.6.1.4.1.37950.1.1.5.12.8.3.41.8
		dhcpMasterDns OBJECT-TYPE
			SYNTAX IpAddress
			MAX-ACCESS read-write
			STATUS current
			DESCRIPTION
				"Description."
			::= { onuDhcpServer 8 }

		
--          1.3.6.1.4.1.37950.1.1.5.12.8.3.41.9
-- 1.3.6.1.4.1.37950.1.1.5.12.8.3.41.9
-- 1.3.6.1.4.1.37950.1.1.5.12.8.3.41.9
-- 1.3.6.1.4.1.37950.1.1.5.12.8.3.41.9
-- 1.3.6.1.4.1.37950.1.1.5.12.8.3.41.9
-- 1.3.6.1.4.1.37950.1.1.5.12.8.3.41.9
-- 1.3.6.1.4.1.37950.1.1.5.12.8.3.41.9
-- 1.3.6.1.4.1.37950.1.1.5.12.8.3.41.9
-- 1.3.6.1.4.1.37950.1.1.5.12.8.3.41.9
		-- 1.3.6.1.4.1.37950.1.1.5.12.8.3.41.9
		dhcpSlaveDns OBJECT-TYPE
			SYNTAX IpAddress
			MAX-ACCESS read-write
			STATUS current
			DESCRIPTION
				"Description."
			::= { onuDhcpServer 9 }

		
--          1.3.6.1.4.1.37950.1.1.5.12.8.3.41.10
-- 1.3.6.1.4.1.37950.1.1.5.12.8.3.41.10
-- 1.3.6.1.4.1.37950.1.1.5.12.8.3.41.10
-- 1.3.6.1.4.1.37950.1.1.5.12.8.3.41.10
-- 1.3.6.1.4.1.37950.1.1.5.12.8.3.41.10
-- 1.3.6.1.4.1.37950.1.1.5.12.8.3.41.10
-- 1.3.6.1.4.1.37950.1.1.5.12.8.3.41.10
-- 1.3.6.1.4.1.37950.1.1.5.12.8.3.41.10
-- 1.3.6.1.4.1.37950.1.1.5.12.8.3.41.10
		-- 1.3.6.1.4.1.37950.1.1.5.12.8.3.41.10
		dhcpGateway OBJECT-TYPE
			SYNTAX IpAddress
			MAX-ACCESS read-write
			STATUS current
			DESCRIPTION
				"Description."
			::= { onuDhcpServer 10 }

		
--          1.3.6.1.4.1.37950.1.1.5.12.8.3.41.11
-- 1.3.6.1.4.1.37950.1.1.5.12.8.3.41.11
-- 1.3.6.1.4.1.37950.1.1.5.12.8.3.41.11
-- 1.3.6.1.4.1.37950.1.1.5.12.8.3.41.11
-- 1.3.6.1.4.1.37950.1.1.5.12.8.3.41.11
-- 1.3.6.1.4.1.37950.1.1.5.12.8.3.41.11
-- 1.3.6.1.4.1.37950.1.1.5.12.8.3.41.11
-- 1.3.6.1.4.1.37950.1.1.5.12.8.3.41.11
-- 1.3.6.1.4.1.37950.1.1.5.12.8.3.41.11
		-- 1.3.6.1.4.1.37950.1.1.5.12.8.3.41.11
		dhcpRelayIp OBJECT-TYPE
			SYNTAX IpAddress
			MAX-ACCESS read-write
			STATUS current
			DESCRIPTION
				"Description."
			::= { onuDhcpServer 11 }

		
--          1.3.6.1.4.1.37950.1.1.5.12.8.3.41.12
-- 1.3.6.1.4.1.37950.1.1.5.12.8.3.41.12
-- 1.3.6.1.4.1.37950.1.1.5.12.8.3.41.12
-- 1.3.6.1.4.1.37950.1.1.5.12.8.3.41.12
-- 1.3.6.1.4.1.37950.1.1.5.12.8.3.41.12
-- 1.3.6.1.4.1.37950.1.1.5.12.8.3.41.12
-- 1.3.6.1.4.1.37950.1.1.5.12.8.3.41.12
-- 1.3.6.1.4.1.37950.1.1.5.12.8.3.41.12
-- 1.3.6.1.4.1.37950.1.1.5.12.8.3.41.12
		-- 1.3.6.1.4.1.37950.1.1.5.12.8.3.41.12
		dhcpAction OBJECT-TYPE
			SYNTAX INTEGER
				{
				commit(1),
				remove(2)
				}
			MAX-ACCESS read-write
			STATUS current
			DESCRIPTION
				"Description."
			::= { onuDhcpServer 12 }

		
--          1.3.6.1.4.1.37950.1.1.5.12.8.3.42
-- 1.3.6.1.4.1.37950.1.1.5.12.8.3.42
-- 1.3.6.1.4.1.37950.1.1.5.12.8.3.42
-- 1.3.6.1.4.1.37950.1.1.5.12.8.3.42
-- 1.3.6.1.4.1.37950.1.1.5.12.8.3.42
-- 1.3.6.1.4.1.37950.1.1.5.12.8.3.42
-- 1.3.6.1.4.1.37950.1.1.5.12.8.3.42
-- 1.3.6.1.4.1.37950.1.1.5.12.8.3.42
-- 1.3.6.1.4.1.37950.1.1.5.12.8.3.42
		-- 1.3.6.1.4.1.37950.1.1.5.12.8.3.42
		onuDhcpOption82 OBJECT IDENTIFIER ::= { srvProfileEdit 42 }

		
--          1.3.6.1.4.1.37950.1.1.5.12.8.3.42.1
-- 1.3.6.1.4.1.37950.1.1.5.12.8.3.42.1
-- 1.3.6.1.4.1.37950.1.1.5.12.8.3.42.1
-- 1.3.6.1.4.1.37950.1.1.5.12.8.3.42.1
-- 1.3.6.1.4.1.37950.1.1.5.12.8.3.42.1
-- 1.3.6.1.4.1.37950.1.1.5.12.8.3.42.1
-- 1.3.6.1.4.1.37950.1.1.5.12.8.3.42.1
-- 1.3.6.1.4.1.37950.1.1.5.12.8.3.42.1
-- 1.3.6.1.4.1.37950.1.1.5.12.8.3.42.1
		-- 1.3.6.1.4.1.37950.1.1.5.12.8.3.42.1
		dhcpOption82Enable OBJECT-TYPE
			SYNTAX INTEGER
				{
				disable(0),
				enable(1)
				}
			MAX-ACCESS read-write
			STATUS current
			DESCRIPTION
				"Description."
			::= { onuDhcpOption82 1 }

		
--          1.3.6.1.4.1.37950.1.1.5.12.8.3.42.2
-- 1.3.6.1.4.1.37950.1.1.5.12.8.3.42.2
-- 1.3.6.1.4.1.37950.1.1.5.12.8.3.42.2
-- 1.3.6.1.4.1.37950.1.1.5.12.8.3.42.2
-- 1.3.6.1.4.1.37950.1.1.5.12.8.3.42.2
-- 1.3.6.1.4.1.37950.1.1.5.12.8.3.42.2
-- 1.3.6.1.4.1.37950.1.1.5.12.8.3.42.2
-- 1.3.6.1.4.1.37950.1.1.5.12.8.3.42.2
-- 1.3.6.1.4.1.37950.1.1.5.12.8.3.42.2
		-- 1.3.6.1.4.1.37950.1.1.5.12.8.3.42.2
		dhcpOption82Action OBJECT-TYPE
			SYNTAX INTEGER
				{
				add(1),
				remove(2)
				}
			MAX-ACCESS read-write
			STATUS current
			DESCRIPTION
				"Description."
			::= { onuDhcpOption82 2 }

		
--          1.3.6.1.4.1.37950.1.1.5.12.8.3.43
-- 1.3.6.1.4.1.37950.1.1.5.12.8.3.43
-- 1.3.6.1.4.1.37950.1.1.5.12.8.3.43
-- 1.3.6.1.4.1.37950.1.1.5.12.8.3.43
-- 1.3.6.1.4.1.37950.1.1.5.12.8.3.43
-- 1.3.6.1.4.1.37950.1.1.5.12.8.3.43
-- 1.3.6.1.4.1.37950.1.1.5.12.8.3.43
-- 1.3.6.1.4.1.37950.1.1.5.12.8.3.43
-- 1.3.6.1.4.1.37950.1.1.5.12.8.3.43
		-- 1.3.6.1.4.1.37950.1.1.5.12.8.3.43
		onuPPPoE OBJECT IDENTIFIER ::= { srvProfileEdit 43 }

		
--          1.3.6.1.4.1.37950.1.1.5.12.8.3.43.1
-- 1.3.6.1.4.1.37950.1.1.5.12.8.3.43.1
-- 1.3.6.1.4.1.37950.1.1.5.12.8.3.43.1
-- 1.3.6.1.4.1.37950.1.1.5.12.8.3.43.1
-- 1.3.6.1.4.1.37950.1.1.5.12.8.3.43.1
-- 1.3.6.1.4.1.37950.1.1.5.12.8.3.43.1
-- 1.3.6.1.4.1.37950.1.1.5.12.8.3.43.1
-- 1.3.6.1.4.1.37950.1.1.5.12.8.3.43.1
-- 1.3.6.1.4.1.37950.1.1.5.12.8.3.43.1
		-- 1.3.6.1.4.1.37950.1.1.5.12.8.3.43.1
		pppoeEnable OBJECT-TYPE
			SYNTAX INTEGER
				{
				disable(0),
				enable(1)
				}
			MAX-ACCESS read-write
			STATUS current
			DESCRIPTION
				"Description."
			::= { onuPPPoE 1 }

		
--          1.3.6.1.4.1.37950.1.1.5.12.8.3.43.2
-- 1.3.6.1.4.1.37950.1.1.5.12.8.3.43.2
-- 1.3.6.1.4.1.37950.1.1.5.12.8.3.43.2
-- 1.3.6.1.4.1.37950.1.1.5.12.8.3.43.2
-- 1.3.6.1.4.1.37950.1.1.5.12.8.3.43.2
-- 1.3.6.1.4.1.37950.1.1.5.12.8.3.43.2
-- 1.3.6.1.4.1.37950.1.1.5.12.8.3.43.2
-- 1.3.6.1.4.1.37950.1.1.5.12.8.3.43.2
-- 1.3.6.1.4.1.37950.1.1.5.12.8.3.43.2
		-- 1.3.6.1.4.1.37950.1.1.5.12.8.3.43.2
		pppoeAction OBJECT-TYPE
			SYNTAX INTEGER
				{
				add(1),
				remove(2)
				}
			MAX-ACCESS read-write
			STATUS current
			DESCRIPTION
				"Description."
			::= { onuPPPoE 2 }

		
--          1.3.6.1.4.1.37950.1.1.5.12.8.3.44
-- 1.3.6.1.4.1.37950.1.1.5.12.8.3.44
-- 1.3.6.1.4.1.37950.1.1.5.12.8.3.44
-- 1.3.6.1.4.1.37950.1.1.5.12.8.3.44
-- 1.3.6.1.4.1.37950.1.1.5.12.8.3.44
-- 1.3.6.1.4.1.37950.1.1.5.12.8.3.44
-- 1.3.6.1.4.1.37950.1.1.5.12.8.3.44
-- 1.3.6.1.4.1.37950.1.1.5.12.8.3.44
-- 1.3.6.1.4.1.37950.1.1.5.12.8.3.44
		-- 1.3.6.1.4.1.37950.1.1.5.12.8.3.44
		onuDhcpV6 OBJECT IDENTIFIER ::= { srvProfileEdit 44 }

		
--          1.3.6.1.4.1.37950.1.1.5.12.8.3.44.1
-- 1.3.6.1.4.1.37950.1.1.5.12.8.3.44.1
-- 1.3.6.1.4.1.37950.1.1.5.12.8.3.44.1
-- 1.3.6.1.4.1.37950.1.1.5.12.8.3.44.1
-- 1.3.6.1.4.1.37950.1.1.5.12.8.3.44.1
-- 1.3.6.1.4.1.37950.1.1.5.12.8.3.44.1
-- 1.3.6.1.4.1.37950.1.1.5.12.8.3.44.1
-- 1.3.6.1.4.1.37950.1.1.5.12.8.3.44.1
-- 1.3.6.1.4.1.37950.1.1.5.12.8.3.44.1
		-- 1.3.6.1.4.1.37950.1.1.5.12.8.3.44.1
		dhcpV6Option18Enable OBJECT-TYPE
			SYNTAX INTEGER
				{
				disable(0),
				enable(1)
				}
			MAX-ACCESS read-write
			STATUS current
			DESCRIPTION
				"Description."
			::= { onuDhcpV6 1 }

		
--          1.3.6.1.4.1.37950.1.1.5.12.8.3.44.2
-- 1.3.6.1.4.1.37950.1.1.5.12.8.3.44.2
-- 1.3.6.1.4.1.37950.1.1.5.12.8.3.44.2
-- 1.3.6.1.4.1.37950.1.1.5.12.8.3.44.2
-- 1.3.6.1.4.1.37950.1.1.5.12.8.3.44.2
-- 1.3.6.1.4.1.37950.1.1.5.12.8.3.44.2
-- 1.3.6.1.4.1.37950.1.1.5.12.8.3.44.2
-- 1.3.6.1.4.1.37950.1.1.5.12.8.3.44.2
-- 1.3.6.1.4.1.37950.1.1.5.12.8.3.44.2
		-- 1.3.6.1.4.1.37950.1.1.5.12.8.3.44.2
		dhcpV6Option37Enable OBJECT-TYPE
			SYNTAX INTEGER
				{
				disable(0),
				enable(1)
				}
			MAX-ACCESS read-write
			STATUS current
			DESCRIPTION
				"Description."
			::= { onuDhcpV6 2 }

		
--          1.3.6.1.4.1.37950.1.1.5.12.8.3.44.3
-- 1.3.6.1.4.1.37950.1.1.5.12.8.3.44.3
-- 1.3.6.1.4.1.37950.1.1.5.12.8.3.44.3
-- 1.3.6.1.4.1.37950.1.1.5.12.8.3.44.3
-- 1.3.6.1.4.1.37950.1.1.5.12.8.3.44.3
-- 1.3.6.1.4.1.37950.1.1.5.12.8.3.44.3
-- 1.3.6.1.4.1.37950.1.1.5.12.8.3.44.3
-- 1.3.6.1.4.1.37950.1.1.5.12.8.3.44.3
-- 1.3.6.1.4.1.37950.1.1.5.12.8.3.44.3
		-- 1.3.6.1.4.1.37950.1.1.5.12.8.3.44.3
		dhcpV6Action OBJECT-TYPE
			SYNTAX INTEGER
				{
				add(1),
				remove(2)
				}
			MAX-ACCESS read-write
			STATUS current
			DESCRIPTION
				"Description."
			::= { onuDhcpV6 3 }

		
--         1.3.6.1.4.1.37950.1.1.5.12.8.3.45
-- 1.3.6.1.4.1.37950.1.1.5.12.8.3.45
-- 1.3.6.1.4.1.37950.1.1.5.12.8.3.45
-- 1.3.6.1.4.1.37950.1.1.5.12.8.3.45
-- 1.3.6.1.4.1.37950.1.1.5.12.8.3.45
-- 1.3.6.1.4.1.37950.1.1.5.12.8.3.45
-- 1.3.6.1.4.1.37950.1.1.5.12.8.3.45
-- 1.3.6.1.4.1.37950.1.1.5.12.8.3.45
		-- 1.3.6.1.4.1.37950.1.1.5.12.8.3.45
		onuSecurity OBJECT IDENTIFIER ::= { srvProfileEdit 45 }

		
--         1.3.6.1.4.1.37950.1.1.5.12.8.3.45.1
-- 1.3.6.1.4.1.37950.1.1.5.12.8.3.45.1
-- 1.3.6.1.4.1.37950.1.1.5.12.8.3.45.1
-- 1.3.6.1.4.1.37950.1.1.5.12.8.3.45.1
-- 1.3.6.1.4.1.37950.1.1.5.12.8.3.45.1
-- 1.3.6.1.4.1.37950.1.1.5.12.8.3.45.1
-- 1.3.6.1.4.1.37950.1.1.5.12.8.3.45.1
-- 1.3.6.1.4.1.37950.1.1.5.12.8.3.45.1
		-- 1.3.6.1.4.1.37950.1.1.5.12.8.3.45.1
		onuUsername OBJECT IDENTIFIER ::= { onuSecurity 1 }

		
--         1.3.6.1.4.1.37950.1.1.5.12.8.3.45.1.1
-- 1.3.6.1.4.1.37950.1.1.5.12.8.3.45.1.1
-- 1.3.6.1.4.1.37950.1.1.5.12.8.3.45.1.1
-- 1.3.6.1.4.1.37950.1.1.5.12.8.3.45.1.1
-- 1.3.6.1.4.1.37950.1.1.5.12.8.3.45.1.1
-- 1.3.6.1.4.1.37950.1.1.5.12.8.3.45.1.1
-- 1.3.6.1.4.1.37950.1.1.5.12.8.3.45.1.1
-- 1.3.6.1.4.1.37950.1.1.5.12.8.3.45.1.1
		-- 1.3.6.1.4.1.37950.1.1.5.12.8.3.45.1.1
		adminControl OBJECT-TYPE
			SYNTAX INTEGER
				{
				disable(0),
				enable(1)
				}
			MAX-ACCESS read-write
			STATUS current
			DESCRIPTION
				"Description."
			::= { onuUsername 1 }

		
--         1.3.6.1.4.1.37950.1.1.5.12.8.3.45.1.2
-- 1.3.6.1.4.1.37950.1.1.5.12.8.3.45.1.2
-- 1.3.6.1.4.1.37950.1.1.5.12.8.3.45.1.2
-- 1.3.6.1.4.1.37950.1.1.5.12.8.3.45.1.2
-- 1.3.6.1.4.1.37950.1.1.5.12.8.3.45.1.2
-- 1.3.6.1.4.1.37950.1.1.5.12.8.3.45.1.2
-- 1.3.6.1.4.1.37950.1.1.5.12.8.3.45.1.2
-- 1.3.6.1.4.1.37950.1.1.5.12.8.3.45.1.2
		-- 1.3.6.1.4.1.37950.1.1.5.12.8.3.45.1.2
		adminName OBJECT-TYPE
			SYNTAX OCTET STRING
			MAX-ACCESS read-write
			STATUS current
			DESCRIPTION
				"Description."
			::= { onuUsername 2 }

		
--         1.3.6.1.4.1.37950.1.1.5.12.8.3.45.1.3
-- 1.3.6.1.4.1.37950.1.1.5.12.8.3.45.1.3
-- 1.3.6.1.4.1.37950.1.1.5.12.8.3.45.1.3
-- 1.3.6.1.4.1.37950.1.1.5.12.8.3.45.1.3
-- 1.3.6.1.4.1.37950.1.1.5.12.8.3.45.1.3
-- 1.3.6.1.4.1.37950.1.1.5.12.8.3.45.1.3
-- 1.3.6.1.4.1.37950.1.1.5.12.8.3.45.1.3
-- 1.3.6.1.4.1.37950.1.1.5.12.8.3.45.1.3
		-- 1.3.6.1.4.1.37950.1.1.5.12.8.3.45.1.3
		adminPwd OBJECT-TYPE
			SYNTAX OCTET STRING
			MAX-ACCESS read-write
			STATUS current
			DESCRIPTION
				"Description."
			::= { onuUsername 3 }

		
--         1.3.6.1.4.1.37950.1.1.5.12.8.3.45.1.4
-- 1.3.6.1.4.1.37950.1.1.5.12.8.3.45.1.4
-- 1.3.6.1.4.1.37950.1.1.5.12.8.3.45.1.4
-- 1.3.6.1.4.1.37950.1.1.5.12.8.3.45.1.4
-- 1.3.6.1.4.1.37950.1.1.5.12.8.3.45.1.4
-- 1.3.6.1.4.1.37950.1.1.5.12.8.3.45.1.4
-- 1.3.6.1.4.1.37950.1.1.5.12.8.3.45.1.4
-- 1.3.6.1.4.1.37950.1.1.5.12.8.3.45.1.4
		-- 1.3.6.1.4.1.37950.1.1.5.12.8.3.45.1.4
		userControl OBJECT-TYPE
			SYNTAX INTEGER
				{
				disable(0),
				enable(1)
				}
			MAX-ACCESS read-write
			STATUS current
			DESCRIPTION
				"Description."
			::= { onuUsername 4 }

		
--         1.3.6.1.4.1.37950.1.1.5.12.8.3.45.1.5
-- 1.3.6.1.4.1.37950.1.1.5.12.8.3.45.1.5
-- 1.3.6.1.4.1.37950.1.1.5.12.8.3.45.1.5
-- 1.3.6.1.4.1.37950.1.1.5.12.8.3.45.1.5
-- 1.3.6.1.4.1.37950.1.1.5.12.8.3.45.1.5
-- 1.3.6.1.4.1.37950.1.1.5.12.8.3.45.1.5
-- 1.3.6.1.4.1.37950.1.1.5.12.8.3.45.1.5
-- 1.3.6.1.4.1.37950.1.1.5.12.8.3.45.1.5
		-- 1.3.6.1.4.1.37950.1.1.5.12.8.3.45.1.5
		username OBJECT-TYPE
			SYNTAX OCTET STRING
			MAX-ACCESS read-write
			STATUS current
			DESCRIPTION
				"Description."
			::= { onuUsername 5 }

		
--         1.3.6.1.4.1.37950.1.1.5.12.8.3.45.1.6
-- 1.3.6.1.4.1.37950.1.1.5.12.8.3.45.1.6
-- 1.3.6.1.4.1.37950.1.1.5.12.8.3.45.1.6
-- 1.3.6.1.4.1.37950.1.1.5.12.8.3.45.1.6
-- 1.3.6.1.4.1.37950.1.1.5.12.8.3.45.1.6
-- 1.3.6.1.4.1.37950.1.1.5.12.8.3.45.1.6
-- 1.3.6.1.4.1.37950.1.1.5.12.8.3.45.1.6
-- 1.3.6.1.4.1.37950.1.1.5.12.8.3.45.1.6
		-- 1.3.6.1.4.1.37950.1.1.5.12.8.3.45.1.6
		userPwd OBJECT-TYPE
			SYNTAX OCTET STRING
			MAX-ACCESS read-write
			STATUS current
			DESCRIPTION
				"Description."
			::= { onuUsername 6 }

		
--         1.3.6.1.4.1.37950.1.1.5.12.8.3.45.1.7
-- 1.3.6.1.4.1.37950.1.1.5.12.8.3.45.1.7
-- 1.3.6.1.4.1.37950.1.1.5.12.8.3.45.1.7
-- 1.3.6.1.4.1.37950.1.1.5.12.8.3.45.1.7
-- 1.3.6.1.4.1.37950.1.1.5.12.8.3.45.1.7
-- 1.3.6.1.4.1.37950.1.1.5.12.8.3.45.1.7
-- 1.3.6.1.4.1.37950.1.1.5.12.8.3.45.1.7
-- 1.3.6.1.4.1.37950.1.1.5.12.8.3.45.1.7
		-- 1.3.6.1.4.1.37950.1.1.5.12.8.3.45.1.7
		controlAction OBJECT-TYPE
			SYNTAX INTEGER
				{
				remove(0),
				commit(1)
				}
			MAX-ACCESS read-write
			STATUS current
			DESCRIPTION
				"Description."
			::= { onuUsername 7 }

		
--         1.3.6.1.4.1.37950.1.1.5.12.8.3.45.2
-- 1.3.6.1.4.1.37950.1.1.5.12.8.3.45.2
-- 1.3.6.1.4.1.37950.1.1.5.12.8.3.45.2
-- 1.3.6.1.4.1.37950.1.1.5.12.8.3.45.2
-- 1.3.6.1.4.1.37950.1.1.5.12.8.3.45.2
-- 1.3.6.1.4.1.37950.1.1.5.12.8.3.45.2
-- 1.3.6.1.4.1.37950.1.1.5.12.8.3.45.2
-- 1.3.6.1.4.1.37950.1.1.5.12.8.3.45.2
		-- 1.3.6.1.4.1.37950.1.1.5.12.8.3.45.2
		onuFirewall OBJECT IDENTIFIER ::= { onuSecurity 2 }

		
--         1.3.6.1.4.1.37950.1.1.5.12.8.3.45.2.1
-- 1.3.6.1.4.1.37950.1.1.5.12.8.3.45.2.1
-- 1.3.6.1.4.1.37950.1.1.5.12.8.3.45.2.1
-- 1.3.6.1.4.1.37950.1.1.5.12.8.3.45.2.1
-- 1.3.6.1.4.1.37950.1.1.5.12.8.3.45.2.1
-- 1.3.6.1.4.1.37950.1.1.5.12.8.3.45.2.1
-- 1.3.6.1.4.1.37950.1.1.5.12.8.3.45.2.1
-- 1.3.6.1.4.1.37950.1.1.5.12.8.3.45.2.1
		-- 1.3.6.1.4.1.37950.1.1.5.12.8.3.45.2.1
		level OBJECT-TYPE
			SYNTAX INTEGER
				{
				disable(0),
				low(1),
				middle(2),
				high(3),
				remove(4)
				}
			MAX-ACCESS read-write
			STATUS current
			DESCRIPTION
				"Description."
			::= { onuFirewall 1 }

		
--         1.3.6.1.4.1.37950.1.1.5.12.8.3.45.3
-- 1.3.6.1.4.1.37950.1.1.5.12.8.3.45.3
-- 1.3.6.1.4.1.37950.1.1.5.12.8.3.45.3
-- 1.3.6.1.4.1.37950.1.1.5.12.8.3.45.3
-- 1.3.6.1.4.1.37950.1.1.5.12.8.3.45.3
-- 1.3.6.1.4.1.37950.1.1.5.12.8.3.45.3
-- 1.3.6.1.4.1.37950.1.1.5.12.8.3.45.3
-- 1.3.6.1.4.1.37950.1.1.5.12.8.3.45.3
		-- 1.3.6.1.4.1.37950.1.1.5.12.8.3.45.3
		onuAclCommit OBJECT-TYPE
			SYNTAX INTEGER { commit(1) }
			MAX-ACCESS read-write
			STATUS current
			DESCRIPTION
				"Description."
			::= { onuSecurity 3 }

		
--         1.3.6.1.4.1.37950.1.1.5.12.8.3.45.4
-- 1.3.6.1.4.1.37950.1.1.5.12.8.3.45.4
-- 1.3.6.1.4.1.37950.1.1.5.12.8.3.45.4
-- 1.3.6.1.4.1.37950.1.1.5.12.8.3.45.4
-- 1.3.6.1.4.1.37950.1.1.5.12.8.3.45.4
-- 1.3.6.1.4.1.37950.1.1.5.12.8.3.45.4
-- 1.3.6.1.4.1.37950.1.1.5.12.8.3.45.4
-- 1.3.6.1.4.1.37950.1.1.5.12.8.3.45.4
		-- 1.3.6.1.4.1.37950.1.1.5.12.8.3.45.4
		onuAcl OBJECT IDENTIFIER ::= { onuSecurity 4 }

		
--         1.3.6.1.4.1.37950.1.1.5.12.8.3.45.4.1
-- 1.3.6.1.4.1.37950.1.1.5.12.8.3.45.4.1
-- 1.3.6.1.4.1.37950.1.1.5.12.8.3.45.4.1
-- 1.3.6.1.4.1.37950.1.1.5.12.8.3.45.4.1
-- 1.3.6.1.4.1.37950.1.1.5.12.8.3.45.4.1
-- 1.3.6.1.4.1.37950.1.1.5.12.8.3.45.4.1
-- 1.3.6.1.4.1.37950.1.1.5.12.8.3.45.4.1
-- 1.3.6.1.4.1.37950.1.1.5.12.8.3.45.4.1
		-- 1.3.6.1.4.1.37950.1.1.5.12.8.3.45.4.1
		aclProtocolType OBJECT-TYPE
			SYNTAX INTEGER
				{
				telnet(0),
				ftp(1),
				http(2),
				https(3),
				tftp(4),
				ping(5)
				}
			MAX-ACCESS read-write
			STATUS current
			DESCRIPTION
				"Description."
			::= { onuAcl 1 }

		
--         1.3.6.1.4.1.37950.1.1.5.12.8.3.45.4.2
-- 1.3.6.1.4.1.37950.1.1.5.12.8.3.45.4.2
-- 1.3.6.1.4.1.37950.1.1.5.12.8.3.45.4.2
-- 1.3.6.1.4.1.37950.1.1.5.12.8.3.45.4.2
-- 1.3.6.1.4.1.37950.1.1.5.12.8.3.45.4.2
-- 1.3.6.1.4.1.37950.1.1.5.12.8.3.45.4.2
-- 1.3.6.1.4.1.37950.1.1.5.12.8.3.45.4.2
-- 1.3.6.1.4.1.37950.1.1.5.12.8.3.45.4.2
		-- 1.3.6.1.4.1.37950.1.1.5.12.8.3.45.4.2
		aclControl OBJECT-TYPE
			SYNTAX INTEGER
				{
				disable(0),
				enable(1)
				}
			MAX-ACCESS read-write
			STATUS current
			DESCRIPTION
				"Description."
			::= { onuAcl 2 }

		
--         1.3.6.1.4.1.37950.1.1.5.12.8.3.45.4.3
-- 1.3.6.1.4.1.37950.1.1.5.12.8.3.45.4.3
-- 1.3.6.1.4.1.37950.1.1.5.12.8.3.45.4.3
-- 1.3.6.1.4.1.37950.1.1.5.12.8.3.45.4.3
-- 1.3.6.1.4.1.37950.1.1.5.12.8.3.45.4.3
-- 1.3.6.1.4.1.37950.1.1.5.12.8.3.45.4.3
-- 1.3.6.1.4.1.37950.1.1.5.12.8.3.45.4.3
-- 1.3.6.1.4.1.37950.1.1.5.12.8.3.45.4.3
		-- 1.3.6.1.4.1.37950.1.1.5.12.8.3.45.4.3
		aclLanControl OBJECT-TYPE
			SYNTAX INTEGER
				{
				disable(0),
				enable(1)
				}
			MAX-ACCESS read-write
			STATUS current
			DESCRIPTION
				"Description."
			::= { onuAcl 3 }

		
--         1.3.6.1.4.1.37950.1.1.5.12.8.3.45.4.4
-- 1.3.6.1.4.1.37950.1.1.5.12.8.3.45.4.4
-- 1.3.6.1.4.1.37950.1.1.5.12.8.3.45.4.4
-- 1.3.6.1.4.1.37950.1.1.5.12.8.3.45.4.4
-- 1.3.6.1.4.1.37950.1.1.5.12.8.3.45.4.4
-- 1.3.6.1.4.1.37950.1.1.5.12.8.3.45.4.4
-- 1.3.6.1.4.1.37950.1.1.5.12.8.3.45.4.4
-- 1.3.6.1.4.1.37950.1.1.5.12.8.3.45.4.4
		-- 1.3.6.1.4.1.37950.1.1.5.12.8.3.45.4.4
		aclWanControl OBJECT-TYPE
			SYNTAX INTEGER
				{
				disable(0),
				enable(1)
				}
			MAX-ACCESS read-write
			STATUS current
			DESCRIPTION
				"Description."
			::= { onuAcl 4 }

		
--         1.3.6.1.4.1.37950.1.1.5.12.8.3.45.4.5
-- 1.3.6.1.4.1.37950.1.1.5.12.8.3.45.4.5
-- 1.3.6.1.4.1.37950.1.1.5.12.8.3.45.4.5
-- 1.3.6.1.4.1.37950.1.1.5.12.8.3.45.4.5
-- 1.3.6.1.4.1.37950.1.1.5.12.8.3.45.4.5
-- 1.3.6.1.4.1.37950.1.1.5.12.8.3.45.4.5
-- 1.3.6.1.4.1.37950.1.1.5.12.8.3.45.4.5
-- 1.3.6.1.4.1.37950.1.1.5.12.8.3.45.4.5
		-- 1.3.6.1.4.1.37950.1.1.5.12.8.3.45.4.5
		aclIPv4Control OBJECT-TYPE
			SYNTAX INTEGER
				{
				disable(0),
				enable(1)
				}
			MAX-ACCESS read-write
			STATUS current
			DESCRIPTION
				"Description."
			::= { onuAcl 5 }

		
--         1.3.6.1.4.1.37950.1.1.5.12.8.3.45.4.6
-- 1.3.6.1.4.1.37950.1.1.5.12.8.3.45.4.6
-- 1.3.6.1.4.1.37950.1.1.5.12.8.3.45.4.6
-- 1.3.6.1.4.1.37950.1.1.5.12.8.3.45.4.6
-- 1.3.6.1.4.1.37950.1.1.5.12.8.3.45.4.6
-- 1.3.6.1.4.1.37950.1.1.5.12.8.3.45.4.6
-- 1.3.6.1.4.1.37950.1.1.5.12.8.3.45.4.6
-- 1.3.6.1.4.1.37950.1.1.5.12.8.3.45.4.6
		-- 1.3.6.1.4.1.37950.1.1.5.12.8.3.45.4.6
		aclIPv4Addr OBJECT-TYPE
			SYNTAX IpAddress
			MAX-ACCESS read-write
			STATUS current
			DESCRIPTION
				"Description."
			::= { onuAcl 6 }

		
--         1.3.6.1.4.1.37950.1.1.5.12.8.3.45.4.7
-- 1.3.6.1.4.1.37950.1.1.5.12.8.3.45.4.7
-- 1.3.6.1.4.1.37950.1.1.5.12.8.3.45.4.7
-- 1.3.6.1.4.1.37950.1.1.5.12.8.3.45.4.7
-- 1.3.6.1.4.1.37950.1.1.5.12.8.3.45.4.7
-- 1.3.6.1.4.1.37950.1.1.5.12.8.3.45.4.7
-- 1.3.6.1.4.1.37950.1.1.5.12.8.3.45.4.7
-- 1.3.6.1.4.1.37950.1.1.5.12.8.3.45.4.7
		-- 1.3.6.1.4.1.37950.1.1.5.12.8.3.45.4.7
		aclIPv4Mask OBJECT-TYPE
			SYNTAX IpAddress
			MAX-ACCESS read-write
			STATUS current
			DESCRIPTION
				"Description."
			::= { onuAcl 7 }

		
--         1.3.6.1.4.1.37950.1.1.5.12.8.3.45.4.8
-- 1.3.6.1.4.1.37950.1.1.5.12.8.3.45.4.8
-- 1.3.6.1.4.1.37950.1.1.5.12.8.3.45.4.8
-- 1.3.6.1.4.1.37950.1.1.5.12.8.3.45.4.8
-- 1.3.6.1.4.1.37950.1.1.5.12.8.3.45.4.8
-- 1.3.6.1.4.1.37950.1.1.5.12.8.3.45.4.8
-- 1.3.6.1.4.1.37950.1.1.5.12.8.3.45.4.8
-- 1.3.6.1.4.1.37950.1.1.5.12.8.3.45.4.8
		-- 1.3.6.1.4.1.37950.1.1.5.12.8.3.45.4.8
		aclIPv6Control OBJECT-TYPE
			SYNTAX INTEGER
				{
				disable(0),
				enable(1)
				}
			MAX-ACCESS read-write
			STATUS current
			DESCRIPTION
				"Description."
			::= { onuAcl 8 }

		
--         1.3.6.1.4.1.37950.1.1.5.12.8.3.45.4.9
-- 1.3.6.1.4.1.37950.1.1.5.12.8.3.45.4.9
-- 1.3.6.1.4.1.37950.1.1.5.12.8.3.45.4.9
-- 1.3.6.1.4.1.37950.1.1.5.12.8.3.45.4.9
-- 1.3.6.1.4.1.37950.1.1.5.12.8.3.45.4.9
-- 1.3.6.1.4.1.37950.1.1.5.12.8.3.45.4.9
-- 1.3.6.1.4.1.37950.1.1.5.12.8.3.45.4.9
-- 1.3.6.1.4.1.37950.1.1.5.12.8.3.45.4.9
		-- 1.3.6.1.4.1.37950.1.1.5.12.8.3.45.4.9
		aclIPv6Address OBJECT-TYPE
			SYNTAX OCTET STRING
			MAX-ACCESS read-write
			STATUS current
			DESCRIPTION
				"Description."
			::= { onuAcl 9 }

		
--         1.3.6.1.4.1.37950.1.1.5.12.8.3.45.4.10
-- 1.3.6.1.4.1.37950.1.1.5.12.8.3.45.4.10
-- 1.3.6.1.4.1.37950.1.1.5.12.8.3.45.4.10
-- 1.3.6.1.4.1.37950.1.1.5.12.8.3.45.4.10
-- 1.3.6.1.4.1.37950.1.1.5.12.8.3.45.4.10
-- 1.3.6.1.4.1.37950.1.1.5.12.8.3.45.4.10
-- 1.3.6.1.4.1.37950.1.1.5.12.8.3.45.4.10
-- 1.3.6.1.4.1.37950.1.1.5.12.8.3.45.4.10
		-- 1.3.6.1.4.1.37950.1.1.5.12.8.3.45.4.10
		aclIPv6Prefix OBJECT-TYPE
			SYNTAX Unsigned32
			MAX-ACCESS read-write
			STATUS current
			DESCRIPTION
				"Description."
			::= { onuAcl 10 }

		
--         1.3.6.1.4.1.37950.1.1.5.12.8.3.45.4.11
-- 1.3.6.1.4.1.37950.1.1.5.12.8.3.45.4.11
-- 1.3.6.1.4.1.37950.1.1.5.12.8.3.45.4.11
-- 1.3.6.1.4.1.37950.1.1.5.12.8.3.45.4.11
-- 1.3.6.1.4.1.37950.1.1.5.12.8.3.45.4.11
-- 1.3.6.1.4.1.37950.1.1.5.12.8.3.45.4.11
-- 1.3.6.1.4.1.37950.1.1.5.12.8.3.45.4.11
-- 1.3.6.1.4.1.37950.1.1.5.12.8.3.45.4.11
		-- 1.3.6.1.4.1.37950.1.1.5.12.8.3.45.4.11
		aclProtocolPort OBJECT-TYPE
			SYNTAX Unsigned32 (0..65535)
			MAX-ACCESS read-write
			STATUS current
			DESCRIPTION
				"Description."
			::= { onuAcl 11 }

		
--         1.3.6.1.4.1.37950.1.1.5.12.8.3.45.4.12
-- 1.3.6.1.4.1.37950.1.1.5.12.8.3.45.4.12
-- 1.3.6.1.4.1.37950.1.1.5.12.8.3.45.4.12
-- 1.3.6.1.4.1.37950.1.1.5.12.8.3.45.4.12
-- 1.3.6.1.4.1.37950.1.1.5.12.8.3.45.4.12
-- 1.3.6.1.4.1.37950.1.1.5.12.8.3.45.4.12
-- 1.3.6.1.4.1.37950.1.1.5.12.8.3.45.4.12
-- 1.3.6.1.4.1.37950.1.1.5.12.8.3.45.4.12
		-- 1.3.6.1.4.1.37950.1.1.5.12.8.3.45.4.12
		aclAction OBJECT-TYPE
			SYNTAX INTEGER
				{
				remove(0),
				commit(1)
				}
			MAX-ACCESS read-write
			STATUS current
			DESCRIPTION
				"Description."
			::= { onuAcl 12 }

		
--         1.3.6.1.4.1.37950.1.1.5.12.8.3.46
-- 1.3.6.1.4.1.37950.1.1.5.12.8.3.46
-- 1.3.6.1.4.1.37950.1.1.5.12.8.3.46
-- 1.3.6.1.4.1.37950.1.1.5.12.8.3.46
-- 1.3.6.1.4.1.37950.1.1.5.12.8.3.46
-- 1.3.6.1.4.1.37950.1.1.5.12.8.3.46
-- 1.3.6.1.4.1.37950.1.1.5.12.8.3.46
-- 1.3.6.1.4.1.37950.1.1.5.12.8.3.46
		-- 1.3.6.1.4.1.37950.1.1.5.12.8.3.46
		onuWifiSwitch1 OBJECT IDENTIFIER ::= { srvProfileEdit 46 }

		
--         1.3.6.1.4.1.37950.1.1.5.12.8.3.46.1
-- 1.3.6.1.4.1.37950.1.1.5.12.8.3.46.1
-- 1.3.6.1.4.1.37950.1.1.5.12.8.3.46.1
-- 1.3.6.1.4.1.37950.1.1.5.12.8.3.46.1
-- 1.3.6.1.4.1.37950.1.1.5.12.8.3.46.1
-- 1.3.6.1.4.1.37950.1.1.5.12.8.3.46.1
-- 1.3.6.1.4.1.37950.1.1.5.12.8.3.46.1
-- 1.3.6.1.4.1.37950.1.1.5.12.8.3.46.1
		-- 1.3.6.1.4.1.37950.1.1.5.12.8.3.46.1
		wifiApmoduleEnable OBJECT-TYPE
			SYNTAX INTEGER
				{
				disable(0),
				enable(1)
				}
			MAX-ACCESS read-write
			STATUS current
			DESCRIPTION
				"Description."
			::= { onuWifiSwitch1 1 }

		
--         1.3.6.1.4.1.37950.1.1.5.12.8.3.46.2
-- 1.3.6.1.4.1.37950.1.1.5.12.8.3.46.2
-- 1.3.6.1.4.1.37950.1.1.5.12.8.3.46.2
-- 1.3.6.1.4.1.37950.1.1.5.12.8.3.46.2
-- 1.3.6.1.4.1.37950.1.1.5.12.8.3.46.2
-- 1.3.6.1.4.1.37950.1.1.5.12.8.3.46.2
-- 1.3.6.1.4.1.37950.1.1.5.12.8.3.46.2
-- 1.3.6.1.4.1.37950.1.1.5.12.8.3.46.2
		-- 1.3.6.1.4.1.37950.1.1.5.12.8.3.46.2
		wifiCountry OBJECT-TYPE
			SYNTAX INTEGER
				{
				etsi(0),
				fcc(1),
				ic(2),
				spain(3),
				france(4),
				mkk(5),
				isreal(6),
				mkk2(7),
				mkk3(8),
				russian(9),
				cn(10),
				global(11),
				world-wide(12),
				mkk1(13),
				ncc(14)
				}
			MAX-ACCESS read-write
			STATUS current
			DESCRIPTION
				"Description."
			::= { onuWifiSwitch1 2 }

		
--         1.3.6.1.4.1.37950.1.1.5.12.8.3.46.3
-- 1.3.6.1.4.1.37950.1.1.5.12.8.3.46.3
-- 1.3.6.1.4.1.37950.1.1.5.12.8.3.46.3
-- 1.3.6.1.4.1.37950.1.1.5.12.8.3.46.3
-- 1.3.6.1.4.1.37950.1.1.5.12.8.3.46.3
-- 1.3.6.1.4.1.37950.1.1.5.12.8.3.46.3
-- 1.3.6.1.4.1.37950.1.1.5.12.8.3.46.3
-- 1.3.6.1.4.1.37950.1.1.5.12.8.3.46.3
		-- 1.3.6.1.4.1.37950.1.1.5.12.8.3.46.3
		wifiChannel OBJECT-TYPE
			SYNTAX INTEGER (0..13)
			MAX-ACCESS read-write
			STATUS current
			DESCRIPTION
				"Description."
			::= { onuWifiSwitch1 3 }

		
--         1.3.6.1.4.1.37950.1.1.5.12.8.3.46.4
-- 1.3.6.1.4.1.37950.1.1.5.12.8.3.46.4
-- 1.3.6.1.4.1.37950.1.1.5.12.8.3.46.4
-- 1.3.6.1.4.1.37950.1.1.5.12.8.3.46.4
-- 1.3.6.1.4.1.37950.1.1.5.12.8.3.46.4
-- 1.3.6.1.4.1.37950.1.1.5.12.8.3.46.4
-- 1.3.6.1.4.1.37950.1.1.5.12.8.3.46.4
-- 1.3.6.1.4.1.37950.1.1.5.12.8.3.46.4
		-- 1.3.6.1.4.1.37950.1.1.5.12.8.3.46.4
		wifiStandard OBJECT-TYPE
			SYNTAX INTEGER
				{
				s80211b(0),
				s80211g(1),
				s80211bg(2),
				s80211n(3),
				s80211bgn(4),
				s80211ac(5),
				s80211a(6),
				s80211an(7),
				s80211nac(8),
				s80211anac(9),
				s80211aan(10),
				s80211ax(11),
				s80211anacax(12)
				}
			MAX-ACCESS read-write
			STATUS current
			DESCRIPTION
				"Description."
			::= { onuWifiSwitch1 4 }

		
--         1.3.6.1.4.1.37950.1.1.5.12.8.3.46.5
-- 1.3.6.1.4.1.37950.1.1.5.12.8.3.46.5
-- 1.3.6.1.4.1.37950.1.1.5.12.8.3.46.5
-- 1.3.6.1.4.1.37950.1.1.5.12.8.3.46.5
-- 1.3.6.1.4.1.37950.1.1.5.12.8.3.46.5
-- 1.3.6.1.4.1.37950.1.1.5.12.8.3.46.5
-- 1.3.6.1.4.1.37950.1.1.5.12.8.3.46.5
-- 1.3.6.1.4.1.37950.1.1.5.12.8.3.46.5
		-- 1.3.6.1.4.1.37950.1.1.5.12.8.3.46.5
		wifiPower OBJECT-TYPE
			SYNTAX INTEGER (0..20)
			MAX-ACCESS read-write
			STATUS current
			DESCRIPTION
				"Description."
			::= { onuWifiSwitch1 5 }

		
--         1.3.6.1.4.1.37950.1.1.5.12.8.3.46.6
-- 1.3.6.1.4.1.37950.1.1.5.12.8.3.46.6
-- 1.3.6.1.4.1.37950.1.1.5.12.8.3.46.6
-- 1.3.6.1.4.1.37950.1.1.5.12.8.3.46.6
-- 1.3.6.1.4.1.37950.1.1.5.12.8.3.46.6
-- 1.3.6.1.4.1.37950.1.1.5.12.8.3.46.6
-- 1.3.6.1.4.1.37950.1.1.5.12.8.3.46.6
-- 1.3.6.1.4.1.37950.1.1.5.12.8.3.46.6
		-- 1.3.6.1.4.1.37950.1.1.5.12.8.3.46.6
		wifiSwitchAction OBJECT-TYPE
			SYNTAX INTEGER
				{
				add(1),
				remove(2)
				}
			MAX-ACCESS read-write
			STATUS current
			DESCRIPTION
				"Description."
			::= { onuWifiSwitch1 6 }

		
--         1.3.6.1.4.1.37950.1.1.5.12.8.3.46.7
-- 1.3.6.1.4.1.37950.1.1.5.12.8.3.46.7
-- 1.3.6.1.4.1.37950.1.1.5.12.8.3.46.7
-- 1.3.6.1.4.1.37950.1.1.5.12.8.3.46.7
-- 1.3.6.1.4.1.37950.1.1.5.12.8.3.46.7
-- 1.3.6.1.4.1.37950.1.1.5.12.8.3.46.7
-- 1.3.6.1.4.1.37950.1.1.5.12.8.3.46.7
-- 1.3.6.1.4.1.37950.1.1.5.12.8.3.46.7
		-- 1.3.6.1.4.1.37950.1.1.5.12.8.3.46.7
		wifiChannelWidth OBJECT-TYPE
			SYNTAX INTEGER
				{
				s20(0),
				s40(1),
				s80(2),
				s20-40(3)
				}
			MAX-ACCESS read-write
			STATUS current
			DESCRIPTION
				"Description."
			::= { onuWifiSwitch1 7 }

		
--          1.3.6.1.4.1.37950.1.1.5.12.8.3.46.8
-- 1.3.6.1.4.1.37950.1.1.5.12.8.3.46.8
-- 1.3.6.1.4.1.37950.1.1.5.12.8.3.46.8
-- 1.3.6.1.4.1.37950.1.1.5.12.8.3.46.8
-- 1.3.6.1.4.1.37950.1.1.5.12.8.3.46.8
-- 1.3.6.1.4.1.37950.1.1.5.12.8.3.46.8
-- 1.3.6.1.4.1.37950.1.1.5.12.8.3.46.8
-- 1.3.6.1.4.1.37950.1.1.5.12.8.3.46.8
-- 1.3.6.1.4.1.37950.1.1.5.12.8.3.46.8
		-- 1.3.6.1.4.1.37950.1.1.5.12.8.3.46.8
		wifiEasyMeshStatus OBJECT-TYPE
			SYNTAX INTEGER
				{
				disable(0),
				enable(1)
				}
			MAX-ACCESS read-write
			STATUS current
			DESCRIPTION
				"Description."
			::= { onuWifiSwitch1 8 }

		
--         1.3.6.1.4.1.37950.1.1.5.12.8.3.47
-- 1.3.6.1.4.1.37950.1.1.5.12.8.3.47
-- 1.3.6.1.4.1.37950.1.1.5.12.8.3.47
-- 1.3.6.1.4.1.37950.1.1.5.12.8.3.47
-- 1.3.6.1.4.1.37950.1.1.5.12.8.3.47
-- 1.3.6.1.4.1.37950.1.1.5.12.8.3.47
-- 1.3.6.1.4.1.37950.1.1.5.12.8.3.47
-- 1.3.6.1.4.1.37950.1.1.5.12.8.3.47
		-- 1.3.6.1.4.1.37950.1.1.5.12.8.3.47
		onuDhcpv6Server OBJECT IDENTIFIER ::= { srvProfileEdit 47 }

		
--         1.3.6.1.4.1.37950.1.1.5.12.8.3.47.1
-- 1.3.6.1.4.1.37950.1.1.5.12.8.3.47.1
-- 1.3.6.1.4.1.37950.1.1.5.12.8.3.47.1
-- 1.3.6.1.4.1.37950.1.1.5.12.8.3.47.1
-- 1.3.6.1.4.1.37950.1.1.5.12.8.3.47.1
-- 1.3.6.1.4.1.37950.1.1.5.12.8.3.47.1
-- 1.3.6.1.4.1.37950.1.1.5.12.8.3.47.1
-- 1.3.6.1.4.1.37950.1.1.5.12.8.3.47.1
		-- 1.3.6.1.4.1.37950.1.1.5.12.8.3.47.1
		dhcpv6Lanip OBJECT-TYPE
			SYNTAX OCTET STRING
			MAX-ACCESS read-write
			STATUS current
			DESCRIPTION
				"Description."
			::= { onuDhcpv6Server 1 }

		
--         1.3.6.1.4.1.37950.1.1.5.12.8.3.47.2
-- 1.3.6.1.4.1.37950.1.1.5.12.8.3.47.2
-- 1.3.6.1.4.1.37950.1.1.5.12.8.3.47.2
-- 1.3.6.1.4.1.37950.1.1.5.12.8.3.47.2
-- 1.3.6.1.4.1.37950.1.1.5.12.8.3.47.2
-- 1.3.6.1.4.1.37950.1.1.5.12.8.3.47.2
-- 1.3.6.1.4.1.37950.1.1.5.12.8.3.47.2
-- 1.3.6.1.4.1.37950.1.1.5.12.8.3.47.2
		-- 1.3.6.1.4.1.37950.1.1.5.12.8.3.47.2
		dhcpv6lanPrefixlen OBJECT-TYPE
			SYNTAX INTEGER (0..128)
			MAX-ACCESS read-write
			STATUS current
			DESCRIPTION
				"Description."
			::= { onuDhcpv6Server 2 }

		
--         1.3.6.1.4.1.37950.1.1.5.12.8.3.47.3
-- 1.3.6.1.4.1.37950.1.1.5.12.8.3.47.3
-- 1.3.6.1.4.1.37950.1.1.5.12.8.3.47.3
-- 1.3.6.1.4.1.37950.1.1.5.12.8.3.47.3
-- 1.3.6.1.4.1.37950.1.1.5.12.8.3.47.3
-- 1.3.6.1.4.1.37950.1.1.5.12.8.3.47.3
-- 1.3.6.1.4.1.37950.1.1.5.12.8.3.47.3
-- 1.3.6.1.4.1.37950.1.1.5.12.8.3.47.3
		-- 1.3.6.1.4.1.37950.1.1.5.12.8.3.47.3
		dhcpv6PrefixMode OBJECT-TYPE
			SYNTAX INTEGER
				{
				disable(0),
				static(1)
				}
			MAX-ACCESS read-write
			STATUS current
			DESCRIPTION
				"Description."
			::= { onuDhcpv6Server 3 }

		
--         1.3.6.1.4.1.37950.1.1.5.12.8.3.47.4
-- 1.3.6.1.4.1.37950.1.1.5.12.8.3.47.4
-- 1.3.6.1.4.1.37950.1.1.5.12.8.3.47.4
-- 1.3.6.1.4.1.37950.1.1.5.12.8.3.47.4
-- 1.3.6.1.4.1.37950.1.1.5.12.8.3.47.4
-- 1.3.6.1.4.1.37950.1.1.5.12.8.3.47.4
-- 1.3.6.1.4.1.37950.1.1.5.12.8.3.47.4
-- 1.3.6.1.4.1.37950.1.1.5.12.8.3.47.4
		-- 1.3.6.1.4.1.37950.1.1.5.12.8.3.47.4
		dhcpv6PrefixModeIp OBJECT-TYPE
			SYNTAX OCTET STRING
			MAX-ACCESS read-write
			STATUS current
			DESCRIPTION
				"Description."
			::= { onuDhcpv6Server 4 }

		
--         1.3.6.1.4.1.37950.1.1.5.12.8.3.47.5
-- 1.3.6.1.4.1.37950.1.1.5.12.8.3.47.5
-- 1.3.6.1.4.1.37950.1.1.5.12.8.3.47.5
-- 1.3.6.1.4.1.37950.1.1.5.12.8.3.47.5
-- 1.3.6.1.4.1.37950.1.1.5.12.8.3.47.5
-- 1.3.6.1.4.1.37950.1.1.5.12.8.3.47.5
-- 1.3.6.1.4.1.37950.1.1.5.12.8.3.47.5
-- 1.3.6.1.4.1.37950.1.1.5.12.8.3.47.5
		-- 1.3.6.1.4.1.37950.1.1.5.12.8.3.47.5
		dhcpv6ServerEnable OBJECT-TYPE
			SYNTAX INTEGER
				{
				disable(0),
				enable(1),
				relay(2)
				}
			MAX-ACCESS read-write
			STATUS current
			DESCRIPTION
				"Description."
			::= { onuDhcpv6Server 5 }

		
--         1.3.6.1.4.1.37950.1.1.5.12.8.3.47.6
-- 1.3.6.1.4.1.37950.1.1.5.12.8.3.47.6
-- 1.3.6.1.4.1.37950.1.1.5.12.8.3.47.6
-- 1.3.6.1.4.1.37950.1.1.5.12.8.3.47.6
-- 1.3.6.1.4.1.37950.1.1.5.12.8.3.47.6
-- 1.3.6.1.4.1.37950.1.1.5.12.8.3.47.6
-- 1.3.6.1.4.1.37950.1.1.5.12.8.3.47.6
-- 1.3.6.1.4.1.37950.1.1.5.12.8.3.47.6
		-- 1.3.6.1.4.1.37950.1.1.5.12.8.3.47.6
		dhcpv6Preference OBJECT-TYPE
			SYNTAX Unsigned32 (0..4294967295)
			MAX-ACCESS read-write
			STATUS current
			DESCRIPTION
				"Description."
			::= { onuDhcpv6Server 6 }

		
--         1.3.6.1.4.1.37950.1.1.5.12.8.3.47.7
-- 1.3.6.1.4.1.37950.1.1.5.12.8.3.47.7
-- 1.3.6.1.4.1.37950.1.1.5.12.8.3.47.7
-- 1.3.6.1.4.1.37950.1.1.5.12.8.3.47.7
-- 1.3.6.1.4.1.37950.1.1.5.12.8.3.47.7
-- 1.3.6.1.4.1.37950.1.1.5.12.8.3.47.7
-- 1.3.6.1.4.1.37950.1.1.5.12.8.3.47.7
-- 1.3.6.1.4.1.37950.1.1.5.12.8.3.47.7
		-- 1.3.6.1.4.1.37950.1.1.5.12.8.3.47.7
		dhcpv6BeginIp OBJECT-TYPE
			SYNTAX OCTET STRING
			MAX-ACCESS read-write
			STATUS current
			DESCRIPTION
				"Description."
			::= { onuDhcpv6Server 7 }

		
--         1.3.6.1.4.1.37950.1.1.5.12.8.3.47.8
-- 1.3.6.1.4.1.37950.1.1.5.12.8.3.47.8
-- 1.3.6.1.4.1.37950.1.1.5.12.8.3.47.8
-- 1.3.6.1.4.1.37950.1.1.5.12.8.3.47.8
-- 1.3.6.1.4.1.37950.1.1.5.12.8.3.47.8
-- 1.3.6.1.4.1.37950.1.1.5.12.8.3.47.8
-- 1.3.6.1.4.1.37950.1.1.5.12.8.3.47.8
-- 1.3.6.1.4.1.37950.1.1.5.12.8.3.47.8
		-- 1.3.6.1.4.1.37950.1.1.5.12.8.3.47.8
		dhcpv6EndIp OBJECT-TYPE
			SYNTAX OCTET STRING
			MAX-ACCESS read-write
			STATUS current
			DESCRIPTION
				"Description."
			::= { onuDhcpv6Server 8 }

		
--         1.3.6.1.4.1.37950.1.1.5.12.8.3.47.9
-- 1.3.6.1.4.1.37950.1.1.5.12.8.3.47.9
-- 1.3.6.1.4.1.37950.1.1.5.12.8.3.47.9
-- 1.3.6.1.4.1.37950.1.1.5.12.8.3.47.9
-- 1.3.6.1.4.1.37950.1.1.5.12.8.3.47.9
-- 1.3.6.1.4.1.37950.1.1.5.12.8.3.47.9
-- 1.3.6.1.4.1.37950.1.1.5.12.8.3.47.9
-- 1.3.6.1.4.1.37950.1.1.5.12.8.3.47.9
		-- 1.3.6.1.4.1.37950.1.1.5.12.8.3.47.9
		dhcpv6PoolType OBJECT-TYPE
			SYNTAX INTEGER
				{
				pc(0),
				camera(1),
				stb(2),
				ip-phone(3)
				}
			MAX-ACCESS read-write
			STATUS current
			DESCRIPTION
				"Description."
			::= { onuDhcpv6Server 9 }

		
--         1.3.6.1.4.1.37950.1.1.5.12.8.3.47.10
-- 1.3.6.1.4.1.37950.1.1.5.12.8.3.47.10
-- 1.3.6.1.4.1.37950.1.1.5.12.8.3.47.10
-- 1.3.6.1.4.1.37950.1.1.5.12.8.3.47.10
-- 1.3.6.1.4.1.37950.1.1.5.12.8.3.47.10
-- 1.3.6.1.4.1.37950.1.1.5.12.8.3.47.10
-- 1.3.6.1.4.1.37950.1.1.5.12.8.3.47.10
-- 1.3.6.1.4.1.37950.1.1.5.12.8.3.47.10
		-- 1.3.6.1.4.1.37950.1.1.5.12.8.3.47.10
		dhcpv6MasterDns OBJECT-TYPE
			SYNTAX OCTET STRING
			MAX-ACCESS read-write
			STATUS current
			DESCRIPTION
				"Description."
			::= { onuDhcpv6Server 10 }

		
--         1.3.6.1.4.1.37950.1.1.5.12.8.3.47.11
-- 1.3.6.1.4.1.37950.1.1.5.12.8.3.47.11
-- 1.3.6.1.4.1.37950.1.1.5.12.8.3.47.11
-- 1.3.6.1.4.1.37950.1.1.5.12.8.3.47.11
-- 1.3.6.1.4.1.37950.1.1.5.12.8.3.47.11
-- 1.3.6.1.4.1.37950.1.1.5.12.8.3.47.11
-- 1.3.6.1.4.1.37950.1.1.5.12.8.3.47.11
-- 1.3.6.1.4.1.37950.1.1.5.12.8.3.47.11
		-- 1.3.6.1.4.1.37950.1.1.5.12.8.3.47.11
		dhcpv6SlaveDns OBJECT-TYPE
			SYNTAX OCTET STRING
			MAX-ACCESS read-write
			STATUS current
			DESCRIPTION
				"Description."
			::= { onuDhcpv6Server 11 }

		
--         1.3.6.1.4.1.37950.1.1.5.12.8.3.47.12
-- 1.3.6.1.4.1.37950.1.1.5.12.8.3.47.12
-- 1.3.6.1.4.1.37950.1.1.5.12.8.3.47.12
-- 1.3.6.1.4.1.37950.1.1.5.12.8.3.47.12
-- 1.3.6.1.4.1.37950.1.1.5.12.8.3.47.12
-- 1.3.6.1.4.1.37950.1.1.5.12.8.3.47.12
-- 1.3.6.1.4.1.37950.1.1.5.12.8.3.47.12
-- 1.3.6.1.4.1.37950.1.1.5.12.8.3.47.12
		-- 1.3.6.1.4.1.37950.1.1.5.12.8.3.47.12
		dhcpv6Gateway OBJECT-TYPE
			SYNTAX OCTET STRING
			MAX-ACCESS read-write
			STATUS current
			DESCRIPTION
				"Description."
			::= { onuDhcpv6Server 12 }

		
--         1.3.6.1.4.1.37950.1.1.5.12.8.3.47.13
-- 1.3.6.1.4.1.37950.1.1.5.12.8.3.47.13
-- 1.3.6.1.4.1.37950.1.1.5.12.8.3.47.13
-- 1.3.6.1.4.1.37950.1.1.5.12.8.3.47.13
-- 1.3.6.1.4.1.37950.1.1.5.12.8.3.47.13
-- 1.3.6.1.4.1.37950.1.1.5.12.8.3.47.13
-- 1.3.6.1.4.1.37950.1.1.5.12.8.3.47.13
-- 1.3.6.1.4.1.37950.1.1.5.12.8.3.47.13
		-- 1.3.6.1.4.1.37950.1.1.5.12.8.3.47.13
		dhcpv6RelayIp OBJECT-TYPE
			SYNTAX OCTET STRING
			MAX-ACCESS read-write
			STATUS current
			DESCRIPTION
				"Description."
			::= { onuDhcpv6Server 13 }

		
--         1.3.6.1.4.1.37950.1.1.5.12.8.3.47.14
-- 1.3.6.1.4.1.37950.1.1.5.12.8.3.47.14
-- 1.3.6.1.4.1.37950.1.1.5.12.8.3.47.14
-- 1.3.6.1.4.1.37950.1.1.5.12.8.3.47.14
-- 1.3.6.1.4.1.37950.1.1.5.12.8.3.47.14
-- 1.3.6.1.4.1.37950.1.1.5.12.8.3.47.14
-- 1.3.6.1.4.1.37950.1.1.5.12.8.3.47.14
-- 1.3.6.1.4.1.37950.1.1.5.12.8.3.47.14
		-- 1.3.6.1.4.1.37950.1.1.5.12.8.3.47.14
		dhcpv6RA OBJECT-TYPE
			SYNTAX INTEGER
				{
				disable(0),
				enable(1)
				}
			MAX-ACCESS read-write
			STATUS current
			DESCRIPTION
				"Description."
			::= { onuDhcpv6Server 14 }

		
--         1.3.6.1.4.1.37950.1.1.5.12.8.3.47.15
-- 1.3.6.1.4.1.37950.1.1.5.12.8.3.47.15
-- 1.3.6.1.4.1.37950.1.1.5.12.8.3.47.15
-- 1.3.6.1.4.1.37950.1.1.5.12.8.3.47.15
-- 1.3.6.1.4.1.37950.1.1.5.12.8.3.47.15
-- 1.3.6.1.4.1.37950.1.1.5.12.8.3.47.15
-- 1.3.6.1.4.1.37950.1.1.5.12.8.3.47.15
-- 1.3.6.1.4.1.37950.1.1.5.12.8.3.47.15
		-- 1.3.6.1.4.1.37950.1.1.5.12.8.3.47.15
		dhcpv6RAManage OBJECT-TYPE
			SYNTAX INTEGER
				{
				disable(0),
				enable(1)
				}
			MAX-ACCESS read-write
			STATUS current
			DESCRIPTION
				"Description."
			::= { onuDhcpv6Server 15 }

		
--         1.3.6.1.4.1.37950.1.1.5.12.8.3.47.16
-- 1.3.6.1.4.1.37950.1.1.5.12.8.3.47.16
-- 1.3.6.1.4.1.37950.1.1.5.12.8.3.47.16
-- 1.3.6.1.4.1.37950.1.1.5.12.8.3.47.16
-- 1.3.6.1.4.1.37950.1.1.5.12.8.3.47.16
-- 1.3.6.1.4.1.37950.1.1.5.12.8.3.47.16
-- 1.3.6.1.4.1.37950.1.1.5.12.8.3.47.16
-- 1.3.6.1.4.1.37950.1.1.5.12.8.3.47.16
		-- 1.3.6.1.4.1.37950.1.1.5.12.8.3.47.16
		dhcpv6RAOther OBJECT-TYPE
			SYNTAX INTEGER
				{
				disable(0),
				enable(1)
				}
			MAX-ACCESS read-write
			STATUS current
			DESCRIPTION
				"Description."
			::= { onuDhcpv6Server 16 }

		
--         1.3.6.1.4.1.37950.1.1.5.12.8.3.47.17
-- 1.3.6.1.4.1.37950.1.1.5.12.8.3.47.17
-- 1.3.6.1.4.1.37950.1.1.5.12.8.3.47.17
-- 1.3.6.1.4.1.37950.1.1.5.12.8.3.47.17
-- 1.3.6.1.4.1.37950.1.1.5.12.8.3.47.17
-- 1.3.6.1.4.1.37950.1.1.5.12.8.3.47.17
-- 1.3.6.1.4.1.37950.1.1.5.12.8.3.47.17
-- 1.3.6.1.4.1.37950.1.1.5.12.8.3.47.17
		-- 1.3.6.1.4.1.37950.1.1.5.12.8.3.47.17
		dhcpv6RAMaxInterval OBJECT-TYPE
			SYNTAX Integer32 (1..1800)
			MAX-ACCESS read-write
			STATUS current
			DESCRIPTION
				"Description."
			::= { onuDhcpv6Server 17 }

		
--         1.3.6.1.4.1.37950.1.1.5.12.8.3.47.18
-- 1.3.6.1.4.1.37950.1.1.5.12.8.3.47.18
-- 1.3.6.1.4.1.37950.1.1.5.12.8.3.47.18
-- 1.3.6.1.4.1.37950.1.1.5.12.8.3.47.18
-- 1.3.6.1.4.1.37950.1.1.5.12.8.3.47.18
-- 1.3.6.1.4.1.37950.1.1.5.12.8.3.47.18
-- 1.3.6.1.4.1.37950.1.1.5.12.8.3.47.18
-- 1.3.6.1.4.1.37950.1.1.5.12.8.3.47.18
		-- 1.3.6.1.4.1.37950.1.1.5.12.8.3.47.18
		dhcpv6RAMinInterval OBJECT-TYPE
			SYNTAX Integer32 (1..1800)
			MAX-ACCESS read-write
			STATUS current
			DESCRIPTION
				"Description."
			::= { onuDhcpv6Server 18 }

		
--         1.3.6.1.4.1.37950.1.1.5.12.8.3.47.19
-- 1.3.6.1.4.1.37950.1.1.5.12.8.3.47.19
-- 1.3.6.1.4.1.37950.1.1.5.12.8.3.47.19
-- 1.3.6.1.4.1.37950.1.1.5.12.8.3.47.19
-- 1.3.6.1.4.1.37950.1.1.5.12.8.3.47.19
-- 1.3.6.1.4.1.37950.1.1.5.12.8.3.47.19
-- 1.3.6.1.4.1.37950.1.1.5.12.8.3.47.19
-- 1.3.6.1.4.1.37950.1.1.5.12.8.3.47.19
		-- 1.3.6.1.4.1.37950.1.1.5.12.8.3.47.19
		dhcpv6Action OBJECT-TYPE
			SYNTAX INTEGER
				{
				commit(1),
				remove(2)
				}
			MAX-ACCESS read-write
			STATUS current
			DESCRIPTION
				"Description."
			::= { onuDhcpv6Server 19 }

		
--         1.3.6.1.4.1.37950.1.1.5.12.8.3.47.20
-- 1.3.6.1.4.1.37950.1.1.5.12.8.3.47.20
-- 1.3.6.1.4.1.37950.1.1.5.12.8.3.47.20
-- 1.3.6.1.4.1.37950.1.1.5.12.8.3.47.20
-- 1.3.6.1.4.1.37950.1.1.5.12.8.3.47.20
-- 1.3.6.1.4.1.37950.1.1.5.12.8.3.47.20
-- 1.3.6.1.4.1.37950.1.1.5.12.8.3.47.20
-- 1.3.6.1.4.1.37950.1.1.5.12.8.3.47.20
		-- 1.3.6.1.4.1.37950.1.1.5.12.8.3.47.20
		dhcpv6Valid OBJECT-TYPE
			SYNTAX Unsigned32 (0..4294967295)
			MAX-ACCESS read-write
			STATUS current
			DESCRIPTION
				"Description."
			::= { onuDhcpv6Server 20 }

		
--         1.3.6.1.4.1.37950.1.1.5.12.8.3.47.21
-- 1.3.6.1.4.1.37950.1.1.5.12.8.3.47.21
-- 1.3.6.1.4.1.37950.1.1.5.12.8.3.47.21
-- 1.3.6.1.4.1.37950.1.1.5.12.8.3.47.21
-- 1.3.6.1.4.1.37950.1.1.5.12.8.3.47.21
-- 1.3.6.1.4.1.37950.1.1.5.12.8.3.47.21
-- 1.3.6.1.4.1.37950.1.1.5.12.8.3.47.21
-- 1.3.6.1.4.1.37950.1.1.5.12.8.3.47.21
		-- 1.3.6.1.4.1.37950.1.1.5.12.8.3.47.21
		dhcpv6DnsMode OBJECT-TYPE
			SYNTAX INTEGER
				{
				wanconnection(0),
				static(1),
				hgwproxy(2)
				}
			MAX-ACCESS read-write
			STATUS current
			DESCRIPTION
				"Description."
			::= { onuDhcpv6Server 21 }

		
--           1.3.6.1.4.1.37950.1.1.5.12.8.3.36
-- 1.3.6.1.4.1.37950.1.1.5.12.8.3.48
-- 1.3.6.1.4.1.37950.1.1.5.12.8.3.48
-- 1.3.6.1.4.1.37950.1.1.5.12.8.3.48
-- 1.3.6.1.4.1.37950.1.1.5.12.8.3.48
-- 1.3.6.1.4.1.37950.1.1.5.12.8.3.48
-- 1.3.6.1.4.1.37950.1.1.5.12.8.3.48
-- 1.3.6.1.4.1.37950.1.1.5.12.8.3.48
-- 1.3.6.1.4.1.37950.1.1.5.12.8.3.48
		-- 1.3.6.1.4.1.37950.1.1.5.12.8.3.48
		onuWanConnV6 OBJECT IDENTIFIER ::= { srvProfileEdit 48 }

		
--           1.3.6.1.4.1.37950.1.1.5.12.8.3.36.1
-- 1.3.6.1.4.1.37950.1.1.5.12.8.3.48.1
-- 1.3.6.1.4.1.37950.1.1.5.12.8.3.48.1
-- 1.3.6.1.4.1.37950.1.1.5.12.8.3.48.1
-- 1.3.6.1.4.1.37950.1.1.5.12.8.3.48.1
-- 1.3.6.1.4.1.37950.1.1.5.12.8.3.48.1
-- 1.3.6.1.4.1.37950.1.1.5.12.8.3.48.1
-- 1.3.6.1.4.1.37950.1.1.5.12.8.3.48.1
-- 1.3.6.1.4.1.37950.1.1.5.12.8.3.48.1
		-- 1.3.6.1.4.1.37950.1.1.5.12.8.3.48.1
		v6WanConnAdd OBJECT IDENTIFIER ::= { onuWanConnV6 1 }

		
--           1.3.6.1.4.1.37950.1.1.5.12.8.3.36.1.1
-- 1.3.6.1.4.1.37950.1.1.5.12.8.3.48.1.1
-- 1.3.6.1.4.1.37950.1.1.5.12.8.3.48.1.1
-- 1.3.6.1.4.1.37950.1.1.5.12.8.3.48.1.1
-- 1.3.6.1.4.1.37950.1.1.5.12.8.3.48.1.1
-- 1.3.6.1.4.1.37950.1.1.5.12.8.3.48.1.1
-- 1.3.6.1.4.1.37950.1.1.5.12.8.3.48.1.1
-- 1.3.6.1.4.1.37950.1.1.5.12.8.3.48.1.1
-- 1.3.6.1.4.1.37950.1.1.5.12.8.3.48.1.1
		-- 1.3.6.1.4.1.37950.1.1.5.12.8.3.48.1.1
		v6connType OBJECT-TYPE
			SYNTAX INTEGER
				{
				bridge(0),
				route(1)
				}
			MAX-ACCESS read-write
			STATUS current
			DESCRIPTION
				"Description."
			::= { v6WanConnAdd 1 }

		
--           1.3.6.1.4.1.37950.1.1.5.12.8.3.36.1.2
-- 1.3.6.1.4.1.37950.1.1.5.12.8.3.48.1.2
-- 1.3.6.1.4.1.37950.1.1.5.12.8.3.48.1.2
-- 1.3.6.1.4.1.37950.1.1.5.12.8.3.48.1.2
-- 1.3.6.1.4.1.37950.1.1.5.12.8.3.48.1.2
-- 1.3.6.1.4.1.37950.1.1.5.12.8.3.48.1.2
-- 1.3.6.1.4.1.37950.1.1.5.12.8.3.48.1.2
-- 1.3.6.1.4.1.37950.1.1.5.12.8.3.48.1.2
-- 1.3.6.1.4.1.37950.1.1.5.12.8.3.48.1.2
		-- 1.3.6.1.4.1.37950.1.1.5.12.8.3.48.1.2
		v6connAddAction OBJECT-TYPE
			SYNTAX INTEGER { add(1) }
			MAX-ACCESS read-write
			STATUS current
			DESCRIPTION
				"Description."
			::= { v6WanConnAdd 2 }

		
--           1.3.6.1.4.1.37950.1.1.5.12.8.3.36.2
-- 1.3.6.1.4.1.37950.1.1.5.12.8.3.48.2
-- 1.3.6.1.4.1.37950.1.1.5.12.8.3.48.2
-- 1.3.6.1.4.1.37950.1.1.5.12.8.3.48.2
-- 1.3.6.1.4.1.37950.1.1.5.12.8.3.48.2
-- 1.3.6.1.4.1.37950.1.1.5.12.8.3.48.2
-- 1.3.6.1.4.1.37950.1.1.5.12.8.3.48.2
-- 1.3.6.1.4.1.37950.1.1.5.12.8.3.48.2
-- 1.3.6.1.4.1.37950.1.1.5.12.8.3.48.2
		-- 1.3.6.1.4.1.37950.1.1.5.12.8.3.48.2
		v6WanConnDelete OBJECT IDENTIFIER ::= { onuWanConnV6 2 }

		
--           1.3.6.1.4.1.37950.1.1.5.12.8.3.36.2.1
-- 1.3.6.1.4.1.37950.1.1.5.12.8.3.48.2.1
-- 1.3.6.1.4.1.37950.1.1.5.12.8.3.48.2.1
-- 1.3.6.1.4.1.37950.1.1.5.12.8.3.48.2.1
-- 1.3.6.1.4.1.37950.1.1.5.12.8.3.48.2.1
-- 1.3.6.1.4.1.37950.1.1.5.12.8.3.48.2.1
-- 1.3.6.1.4.1.37950.1.1.5.12.8.3.48.2.1
-- 1.3.6.1.4.1.37950.1.1.5.12.8.3.48.2.1
-- 1.3.6.1.4.1.37950.1.1.5.12.8.3.48.2.1
		-- 1.3.6.1.4.1.37950.1.1.5.12.8.3.48.2.1
		v6connIndexD OBJECT-TYPE
			SYNTAX Integer32 (1..8)
			MAX-ACCESS read-write
			STATUS current
			DESCRIPTION
				"Description."
			::= { v6WanConnDelete 1 }

		
--           1.3.6.1.4.1.37950.1.1.5.12.8.3.36.2.2
-- 1.3.6.1.4.1.37950.1.1.5.12.8.3.48.2.2
-- 1.3.6.1.4.1.37950.1.1.5.12.8.3.48.2.2
-- 1.3.6.1.4.1.37950.1.1.5.12.8.3.48.2.2
-- 1.3.6.1.4.1.37950.1.1.5.12.8.3.48.2.2
-- 1.3.6.1.4.1.37950.1.1.5.12.8.3.48.2.2
-- 1.3.6.1.4.1.37950.1.1.5.12.8.3.48.2.2
-- 1.3.6.1.4.1.37950.1.1.5.12.8.3.48.2.2
-- 1.3.6.1.4.1.37950.1.1.5.12.8.3.48.2.2
		-- 1.3.6.1.4.1.37950.1.1.5.12.8.3.48.2.2
		v6connDeleteAction OBJECT-TYPE
			SYNTAX INTEGER { delete(1) }
			MAX-ACCESS read-write
			STATUS current
			DESCRIPTION
				"Description."
			::= { v6WanConnDelete 2 }

		
--           1.3.6.1.4.1.37950.1.1.5.12.3.1.6.3
-- 1.3.6.1.4.1.37950.1.1.5.12.8.3.48.3
-- 1.3.6.1.4.1.37950.1.1.5.12.8.3.48.3
-- 1.3.6.1.4.1.37950.1.1.5.12.8.3.48.3
-- 1.3.6.1.4.1.37950.1.1.5.12.8.3.48.3
-- 1.3.6.1.4.1.37950.1.1.5.12.8.3.48.3
-- 1.3.6.1.4.1.37950.1.1.5.12.8.3.48.3
-- 1.3.6.1.4.1.37950.1.1.5.12.8.3.48.3
-- 1.3.6.1.4.1.37950.1.1.5.12.8.3.48.3
		-- 1.3.6.1.4.1.37950.1.1.5.12.8.3.48.3
		v6WanConnCfg OBJECT IDENTIFIER ::= { onuWanConnV6 3 }

		
--           1.3.6.1.4.1.37950.1.1.5.12.3.1.6.3.3
-- 1.3.6.1.4.1.37950.1.1.5.12.8.3.48.3.1
-- 1.3.6.1.4.1.37950.1.1.5.12.8.3.48.3.1
-- 1.3.6.1.4.1.37950.1.1.5.12.8.3.48.3.1
-- 1.3.6.1.4.1.37950.1.1.5.12.8.3.48.3.1
-- 1.3.6.1.4.1.37950.1.1.5.12.8.3.48.3.1
-- 1.3.6.1.4.1.37950.1.1.5.12.8.3.48.3.1
-- 1.3.6.1.4.1.37950.1.1.5.12.8.3.48.3.1
-- 1.3.6.1.4.1.37950.1.1.5.12.8.3.48.3.1
		-- 1.3.6.1.4.1.37950.1.1.5.12.8.3.48.3.1
		v6ConnIndex OBJECT-TYPE
			SYNTAX INTEGER (1..8)
			MAX-ACCESS read-write
			STATUS current
			DESCRIPTION
				"Description."
			::= { v6WanConnCfg 1 }

		
--           1.3.6.1.4.1.37950.1.1.5.12.3.1.6.3.4
-- 1.3.6.1.4.1.37950.1.1.5.12.8.3.48.3.2
-- 1.3.6.1.4.1.37950.1.1.5.12.8.3.48.3.2
-- 1.3.6.1.4.1.37950.1.1.5.12.8.3.48.3.2
-- 1.3.6.1.4.1.37950.1.1.5.12.8.3.48.3.2
-- 1.3.6.1.4.1.37950.1.1.5.12.8.3.48.3.2
-- 1.3.6.1.4.1.37950.1.1.5.12.8.3.48.3.2
-- 1.3.6.1.4.1.37950.1.1.5.12.8.3.48.3.2
-- 1.3.6.1.4.1.37950.1.1.5.12.8.3.48.3.2
		-- 1.3.6.1.4.1.37950.1.1.5.12.8.3.48.3.2
		v6ConnBindLan OBJECT-TYPE
			SYNTAX INTEGER (0..15)
			MAX-ACCESS read-write
			STATUS current
			DESCRIPTION
				"Description."
			::= { v6WanConnCfg 2 }

		
--           1.3.6.1.4.1.37950.1.1.5.12.3.1.6.3.5
-- 1.3.6.1.4.1.37950.1.1.5.12.8.3.48.3.3
-- 1.3.6.1.4.1.37950.1.1.5.12.8.3.48.3.3
-- 1.3.6.1.4.1.37950.1.1.5.12.8.3.48.3.3
-- 1.3.6.1.4.1.37950.1.1.5.12.8.3.48.3.3
-- 1.3.6.1.4.1.37950.1.1.5.12.8.3.48.3.3
-- 1.3.6.1.4.1.37950.1.1.5.12.8.3.48.3.3
-- 1.3.6.1.4.1.37950.1.1.5.12.8.3.48.3.3
-- 1.3.6.1.4.1.37950.1.1.5.12.8.3.48.3.3
		-- 1.3.6.1.4.1.37950.1.1.5.12.8.3.48.3.3
		v6ConnBindSsid OBJECT-TYPE
			SYNTAX INTEGER (0..65535)
			MAX-ACCESS read-write
			STATUS current
			DESCRIPTION
				"Description."
			::= { v6WanConnCfg 3 }

		
--           1.3.6.1.4.1.37950.1.1.5.12.3.1.6.3.6
-- 1.3.6.1.4.1.37950.1.1.5.12.8.3.48.3.4
-- 1.3.6.1.4.1.37950.1.1.5.12.8.3.48.3.4
-- 1.3.6.1.4.1.37950.1.1.5.12.8.3.48.3.4
-- 1.3.6.1.4.1.37950.1.1.5.12.8.3.48.3.4
-- 1.3.6.1.4.1.37950.1.1.5.12.8.3.48.3.4
-- 1.3.6.1.4.1.37950.1.1.5.12.8.3.48.3.4
-- 1.3.6.1.4.1.37950.1.1.5.12.8.3.48.3.4
-- 1.3.6.1.4.1.37950.1.1.5.12.8.3.48.3.4
		-- 1.3.6.1.4.1.37950.1.1.5.12.8.3.48.3.4
		v6WanMode OBJECT-TYPE
			SYNTAX INTEGER
				{
				internet(0),
				multicast(1),
				tr069(2),
				tr069-internet(3),
				tr069-voip(4),
				voip-internet(5),
				tr069-voip-internet(6),
				voip(7),
				other(100)
				}
			MAX-ACCESS read-write
			STATUS current
			DESCRIPTION
				"Description."
			::= { v6WanConnCfg 4 }

		
--           1.3.6.1.4.1.37950.1.1.5.12.3.1.6.3.7
-- 1.3.6.1.4.1.37950.1.1.5.12.8.3.48.3.5
-- 1.3.6.1.4.1.37950.1.1.5.12.8.3.48.3.5
-- 1.3.6.1.4.1.37950.1.1.5.12.8.3.48.3.5
-- 1.3.6.1.4.1.37950.1.1.5.12.8.3.48.3.5
-- 1.3.6.1.4.1.37950.1.1.5.12.8.3.48.3.5
-- 1.3.6.1.4.1.37950.1.1.5.12.8.3.48.3.5
-- 1.3.6.1.4.1.37950.1.1.5.12.8.3.48.3.5
-- 1.3.6.1.4.1.37950.1.1.5.12.8.3.48.3.5
		-- 1.3.6.1.4.1.37950.1.1.5.12.8.3.48.3.5
		v6ConnTypeCfg OBJECT-TYPE
			SYNTAX INTEGER
				{
				bridge(0),
				route(1)
				}
			MAX-ACCESS read-write
			STATUS current
			DESCRIPTION
				"Description."
			::= { v6WanConnCfg 5 }

		
--           1.3.6.1.4.1.37950.1.1.5.12.3.1.6.3.8
-- 1.3.6.1.4.1.37950.1.1.5.12.8.3.48.3.6
-- 1.3.6.1.4.1.37950.1.1.5.12.8.3.48.3.6
-- 1.3.6.1.4.1.37950.1.1.5.12.8.3.48.3.6
-- 1.3.6.1.4.1.37950.1.1.5.12.8.3.48.3.6
-- 1.3.6.1.4.1.37950.1.1.5.12.8.3.48.3.6
-- 1.3.6.1.4.1.37950.1.1.5.12.8.3.48.3.6
-- 1.3.6.1.4.1.37950.1.1.5.12.8.3.48.3.6
-- 1.3.6.1.4.1.37950.1.1.5.12.8.3.48.3.6
		-- 1.3.6.1.4.1.37950.1.1.5.12.8.3.48.3.6
		v6ConnVlanId OBJECT-TYPE
			SYNTAX Integer32 (0..4095)
			MAX-ACCESS read-write
			STATUS current
			DESCRIPTION
				"Description."
			::= { v6WanConnCfg 6 }

		
--           1.3.6.1.4.1.37950.1.1.5.12.3.1.6.3.9
-- 1.3.6.1.4.1.37950.1.1.5.12.8.3.48.3.7
-- 1.3.6.1.4.1.37950.1.1.5.12.8.3.48.3.7
-- 1.3.6.1.4.1.37950.1.1.5.12.8.3.48.3.7
-- 1.3.6.1.4.1.37950.1.1.5.12.8.3.48.3.7
-- 1.3.6.1.4.1.37950.1.1.5.12.8.3.48.3.7
-- 1.3.6.1.4.1.37950.1.1.5.12.8.3.48.3.7
-- 1.3.6.1.4.1.37950.1.1.5.12.8.3.48.3.7
-- 1.3.6.1.4.1.37950.1.1.5.12.8.3.48.3.7
		-- 1.3.6.1.4.1.37950.1.1.5.12.8.3.48.3.7
		v6ConnCos OBJECT-TYPE
			SYNTAX INTEGER (0..7)
			MAX-ACCESS read-write
			STATUS current
			DESCRIPTION
				"Description."
			::= { v6WanConnCfg 7 }

		
--           1.3.6.1.4.1.37950.1.1.5.12.3.1.6.3.31
-- 1.3.6.1.4.1.37950.1.1.5.12.8.3.48.3.8
-- 1.3.6.1.4.1.37950.1.1.5.12.8.3.48.3.8
-- 1.3.6.1.4.1.37950.1.1.5.12.8.3.48.3.8
-- 1.3.6.1.4.1.37950.1.1.5.12.8.3.48.3.8
-- 1.3.6.1.4.1.37950.1.1.5.12.8.3.48.3.8
-- 1.3.6.1.4.1.37950.1.1.5.12.8.3.48.3.8
-- 1.3.6.1.4.1.37950.1.1.5.12.8.3.48.3.8
-- 1.3.6.1.4.1.37950.1.1.5.12.8.3.48.3.8
		-- 1.3.6.1.4.1.37950.1.1.5.12.8.3.48.3.8
		v6ConnIpProtocol OBJECT-TYPE
			SYNTAX INTEGER
				{
				ipv4(0),
				ipv6(1),
				ipv4-ipv6(2)
				}
			MAX-ACCESS read-write
			STATUS current
			DESCRIPTION
				"Description."
			::= { v6WanConnCfg 8 }

		
--           1.3.6.1.4.1.37950.1.1.5.12.3.1.6.3.11
-- 1.3.6.1.4.1.37950.1.1.5.12.8.3.48.3.9
-- 1.3.6.1.4.1.37950.1.1.5.12.8.3.48.3.9
-- 1.3.6.1.4.1.37950.1.1.5.12.8.3.48.3.9
-- 1.3.6.1.4.1.37950.1.1.5.12.8.3.48.3.9
-- 1.3.6.1.4.1.37950.1.1.5.12.8.3.48.3.9
-- 1.3.6.1.4.1.37950.1.1.5.12.8.3.48.3.9
-- 1.3.6.1.4.1.37950.1.1.5.12.8.3.48.3.9
-- 1.3.6.1.4.1.37950.1.1.5.12.8.3.48.3.9
		-- 1.3.6.1.4.1.37950.1.1.5.12.8.3.48.3.9
		v6ConnModeCfg OBJECT-TYPE
			SYNTAX INTEGER
				{
				dhcp(0),
				static(1),
				pppoe(2)
				}
			MAX-ACCESS read-write
			STATUS current
			DESCRIPTION
				"Description."
			::= { v6WanConnCfg 9 }

		
--           1.3.6.1.4.1.37950.1.1.5.12.3.1.6.3.12
-- 1.3.6.1.4.1.37950.1.1.5.12.8.3.48.3.10
-- 1.3.6.1.4.1.37950.1.1.5.12.8.3.48.3.10
-- 1.3.6.1.4.1.37950.1.1.5.12.8.3.48.3.10
-- 1.3.6.1.4.1.37950.1.1.5.12.8.3.48.3.10
-- 1.3.6.1.4.1.37950.1.1.5.12.8.3.48.3.10
-- 1.3.6.1.4.1.37950.1.1.5.12.8.3.48.3.10
-- 1.3.6.1.4.1.37950.1.1.5.12.8.3.48.3.10
-- 1.3.6.1.4.1.37950.1.1.5.12.8.3.48.3.10
		-- 1.3.6.1.4.1.37950.1.1.5.12.8.3.48.3.10
		v6ConnIpAddressIpv4 OBJECT-TYPE
			SYNTAX IpAddress
			MAX-ACCESS read-write
			STATUS current
			DESCRIPTION
				"Description."
			::= { v6WanConnCfg 10 }

		
--           1.3.6.1.4.1.37950.1.1.5.12.3.1.6.3.13
-- 1.3.6.1.4.1.37950.1.1.5.12.8.3.48.3.11
-- 1.3.6.1.4.1.37950.1.1.5.12.8.3.48.3.11
-- 1.3.6.1.4.1.37950.1.1.5.12.8.3.48.3.11
-- 1.3.6.1.4.1.37950.1.1.5.12.8.3.48.3.11
-- 1.3.6.1.4.1.37950.1.1.5.12.8.3.48.3.11
-- 1.3.6.1.4.1.37950.1.1.5.12.8.3.48.3.11
-- 1.3.6.1.4.1.37950.1.1.5.12.8.3.48.3.11
-- 1.3.6.1.4.1.37950.1.1.5.12.8.3.48.3.11
		-- 1.3.6.1.4.1.37950.1.1.5.12.8.3.48.3.11
		v6ConnIpNetMaskIpv4 OBJECT-TYPE
			SYNTAX IpAddress
			MAX-ACCESS read-write
			STATUS current
			DESCRIPTION
				"Description."
			::= { v6WanConnCfg 11 }

		
--           1.3.6.1.4.1.37950.1.1.5.12.3.1.6.3.14
-- 1.3.6.1.4.1.37950.1.1.5.12.8.3.48.3.12
-- 1.3.6.1.4.1.37950.1.1.5.12.8.3.48.3.12
-- 1.3.6.1.4.1.37950.1.1.5.12.8.3.48.3.12
-- 1.3.6.1.4.1.37950.1.1.5.12.8.3.48.3.12
-- 1.3.6.1.4.1.37950.1.1.5.12.8.3.48.3.12
-- 1.3.6.1.4.1.37950.1.1.5.12.8.3.48.3.12
-- 1.3.6.1.4.1.37950.1.1.5.12.8.3.48.3.12
-- 1.3.6.1.4.1.37950.1.1.5.12.8.3.48.3.12
		-- 1.3.6.1.4.1.37950.1.1.5.12.8.3.48.3.12
		v6ConnGatewayIpv4 OBJECT-TYPE
			SYNTAX IpAddress
			MAX-ACCESS read-write
			STATUS current
			DESCRIPTION
				"Description."
			::= { v6WanConnCfg 12 }

		
--           1.3.6.1.4.1.37950.1.1.5.12.3.1.6.3.27
-- 1.3.6.1.4.1.37950.1.1.5.12.8.3.48.3.13
-- 1.3.6.1.4.1.37950.1.1.5.12.8.3.48.3.13
-- 1.3.6.1.4.1.37950.1.1.5.12.8.3.48.3.13
-- 1.3.6.1.4.1.37950.1.1.5.12.8.3.48.3.13
-- 1.3.6.1.4.1.37950.1.1.5.12.8.3.48.3.13
-- 1.3.6.1.4.1.37950.1.1.5.12.8.3.48.3.13
-- 1.3.6.1.4.1.37950.1.1.5.12.8.3.48.3.13
-- 1.3.6.1.4.1.37950.1.1.5.12.8.3.48.3.13
		-- 1.3.6.1.4.1.37950.1.1.5.12.8.3.48.3.13
		v6ConnDnsEnableIpv4 OBJECT-TYPE
			SYNTAX INTEGER
				{
				disable(0),
				enable(1)
				}
			MAX-ACCESS read-write
			STATUS current
			DESCRIPTION
				"Description."
			::= { v6WanConnCfg 13 }

		
--           1.3.6.1.4.1.37950.1.1.5.12.3.1.6.3.15
-- 1.3.6.1.4.1.37950.1.1.5.12.8.3.48.3.14
-- 1.3.6.1.4.1.37950.1.1.5.12.8.3.48.3.14
-- 1.3.6.1.4.1.37950.1.1.5.12.8.3.48.3.14
-- 1.3.6.1.4.1.37950.1.1.5.12.8.3.48.3.14
-- 1.3.6.1.4.1.37950.1.1.5.12.8.3.48.3.14
-- 1.3.6.1.4.1.37950.1.1.5.12.8.3.48.3.14
-- 1.3.6.1.4.1.37950.1.1.5.12.8.3.48.3.14
-- 1.3.6.1.4.1.37950.1.1.5.12.8.3.48.3.14
		-- 1.3.6.1.4.1.37950.1.1.5.12.8.3.48.3.14
		v6ConnMasterDnsIpv4 OBJECT-TYPE
			SYNTAX IpAddress
			MAX-ACCESS read-write
			STATUS current
			DESCRIPTION
				"Description."
			::= { v6WanConnCfg 14 }

		
--           1.3.6.1.4.1.37950.1.1.5.12.3.1.6.3.16
-- 1.3.6.1.4.1.37950.1.1.5.12.8.3.48.3.15
-- 1.3.6.1.4.1.37950.1.1.5.12.8.3.48.3.15
-- 1.3.6.1.4.1.37950.1.1.5.12.8.3.48.3.15
-- 1.3.6.1.4.1.37950.1.1.5.12.8.3.48.3.15
-- 1.3.6.1.4.1.37950.1.1.5.12.8.3.48.3.15
-- 1.3.6.1.4.1.37950.1.1.5.12.8.3.48.3.15
-- 1.3.6.1.4.1.37950.1.1.5.12.8.3.48.3.15
-- 1.3.6.1.4.1.37950.1.1.5.12.8.3.48.3.15
		-- 1.3.6.1.4.1.37950.1.1.5.12.8.3.48.3.15
		v6ConnSlaveDnsIpv4 OBJECT-TYPE
			SYNTAX IpAddress
			MAX-ACCESS read-write
			STATUS current
			DESCRIPTION
				"Description."
			::= { v6WanConnCfg 15 }

		
--           1.3.6.1.4.1.37950.1.1.5.12.3.1.6.3.10
-- 1.3.6.1.4.1.37950.1.1.5.12.8.3.48.3.16
-- 1.3.6.1.4.1.37950.1.1.5.12.8.3.48.3.16
-- 1.3.6.1.4.1.37950.1.1.5.12.8.3.48.3.16
-- 1.3.6.1.4.1.37950.1.1.5.12.8.3.48.3.16
-- 1.3.6.1.4.1.37950.1.1.5.12.8.3.48.3.16
-- 1.3.6.1.4.1.37950.1.1.5.12.8.3.48.3.16
-- 1.3.6.1.4.1.37950.1.1.5.12.8.3.48.3.16
-- 1.3.6.1.4.1.37950.1.1.5.12.8.3.48.3.16
		-- 1.3.6.1.4.1.37950.1.1.5.12.8.3.48.3.16
		v6ConnNatEnable OBJECT-TYPE
			SYNTAX INTEGER
				{
				disable(0),
				enable(1)
				}
			MAX-ACCESS read-write
			STATUS current
			DESCRIPTION
				"Description."
			::= { v6WanConnCfg 16 }

		
--           1.3.6.1.4.1.37950.1.1.5.12.3.1.6.3.31
-- 1.3.6.1.4.1.37950.1.1.5.12.8.3.48.3.17
-- 1.3.6.1.4.1.37950.1.1.5.12.8.3.48.3.17
-- 1.3.6.1.4.1.37950.1.1.5.12.8.3.48.3.17
-- 1.3.6.1.4.1.37950.1.1.5.12.8.3.48.3.17
-- 1.3.6.1.4.1.37950.1.1.5.12.8.3.48.3.17
-- 1.3.6.1.4.1.37950.1.1.5.12.8.3.48.3.17
-- 1.3.6.1.4.1.37950.1.1.5.12.8.3.48.3.17
-- 1.3.6.1.4.1.37950.1.1.5.12.8.3.48.3.17
		-- 1.3.6.1.4.1.37950.1.1.5.12.8.3.48.3.17
		v6ConnAddressIpv6 OBJECT-TYPE
			SYNTAX OCTET STRING
			MAX-ACCESS read-write
			STATUS current
			DESCRIPTION
				"Description."
			::= { v6WanConnCfg 17 }

		
--           1.3.6.1.4.1.37950.1.1.5.12.3.1.6.3.31
-- 1.3.6.1.4.1.37950.1.1.5.12.8.3.48.3.18
-- 1.3.6.1.4.1.37950.1.1.5.12.8.3.48.3.18
-- 1.3.6.1.4.1.37950.1.1.5.12.8.3.48.3.18
-- 1.3.6.1.4.1.37950.1.1.5.12.8.3.48.3.18
-- 1.3.6.1.4.1.37950.1.1.5.12.8.3.48.3.18
-- 1.3.6.1.4.1.37950.1.1.5.12.8.3.48.3.18
-- 1.3.6.1.4.1.37950.1.1.5.12.8.3.48.3.18
-- 1.3.6.1.4.1.37950.1.1.5.12.8.3.48.3.18
		-- 1.3.6.1.4.1.37950.1.1.5.12.8.3.48.3.18
		v6ConnPrefixLenIpv6 OBJECT-TYPE
			SYNTAX INTEGER (0..128)
			MAX-ACCESS read-write
			STATUS current
			DESCRIPTION
				"Description."
			::= { v6WanConnCfg 18 }

		
--           1.3.6.1.4.1.37950.1.1.5.12.3.1.6.3.31
-- 1.3.6.1.4.1.37950.1.1.5.12.8.3.48.3.19
-- 1.3.6.1.4.1.37950.1.1.5.12.8.3.48.3.19
-- 1.3.6.1.4.1.37950.1.1.5.12.8.3.48.3.19
-- 1.3.6.1.4.1.37950.1.1.5.12.8.3.48.3.19
-- 1.3.6.1.4.1.37950.1.1.5.12.8.3.48.3.19
-- 1.3.6.1.4.1.37950.1.1.5.12.8.3.48.3.19
-- 1.3.6.1.4.1.37950.1.1.5.12.8.3.48.3.19
-- 1.3.6.1.4.1.37950.1.1.5.12.8.3.48.3.19
		-- 1.3.6.1.4.1.37950.1.1.5.12.8.3.48.3.19
		v6ConnGatewayIpv6 OBJECT-TYPE
			SYNTAX OCTET STRING
			MAX-ACCESS read-write
			STATUS current
			DESCRIPTION
				"Description."
			::= { v6WanConnCfg 19 }

		
--           1.3.6.1.4.1.37950.1.1.5.12.3.1.6.3.27
-- 1.3.6.1.4.1.37950.1.1.5.12.8.3.48.3.20
-- 1.3.6.1.4.1.37950.1.1.5.12.8.3.48.3.20
-- 1.3.6.1.4.1.37950.1.1.5.12.8.3.48.3.20
-- 1.3.6.1.4.1.37950.1.1.5.12.8.3.48.3.20
-- 1.3.6.1.4.1.37950.1.1.5.12.8.3.48.3.20
-- 1.3.6.1.4.1.37950.1.1.5.12.8.3.48.3.20
-- 1.3.6.1.4.1.37950.1.1.5.12.8.3.48.3.20
-- 1.3.6.1.4.1.37950.1.1.5.12.8.3.48.3.20
		-- 1.3.6.1.4.1.37950.1.1.5.12.8.3.48.3.20
		v6ConnDnsEnableIpv6 OBJECT-TYPE
			SYNTAX INTEGER
				{
				disable(0),
				enable(1)
				}
			MAX-ACCESS read-write
			STATUS current
			DESCRIPTION
				"Description."
			::= { v6WanConnCfg 20 }

		
--           1.3.6.1.4.1.37950.1.1.5.12.3.1.6.3.31
-- 1.3.6.1.4.1.37950.1.1.5.12.8.3.48.3.21
-- 1.3.6.1.4.1.37950.1.1.5.12.8.3.48.3.21
-- 1.3.6.1.4.1.37950.1.1.5.12.8.3.48.3.21
-- 1.3.6.1.4.1.37950.1.1.5.12.8.3.48.3.21
-- 1.3.6.1.4.1.37950.1.1.5.12.8.3.48.3.21
-- 1.3.6.1.4.1.37950.1.1.5.12.8.3.48.3.21
-- 1.3.6.1.4.1.37950.1.1.5.12.8.3.48.3.21
-- 1.3.6.1.4.1.37950.1.1.5.12.8.3.48.3.21
		-- 1.3.6.1.4.1.37950.1.1.5.12.8.3.48.3.21
		v6ConnMasterDnsIpv6 OBJECT-TYPE
			SYNTAX OCTET STRING
			MAX-ACCESS read-write
			STATUS current
			DESCRIPTION
				"Description."
			::= { v6WanConnCfg 21 }

		
--           1.3.6.1.4.1.37950.1.1.5.12.3.1.6.3.31
-- 1.3.6.1.4.1.37950.1.1.5.12.8.3.48.3.22
-- 1.3.6.1.4.1.37950.1.1.5.12.8.3.48.3.22
-- 1.3.6.1.4.1.37950.1.1.5.12.8.3.48.3.22
-- 1.3.6.1.4.1.37950.1.1.5.12.8.3.48.3.22
-- 1.3.6.1.4.1.37950.1.1.5.12.8.3.48.3.22
-- 1.3.6.1.4.1.37950.1.1.5.12.8.3.48.3.22
-- 1.3.6.1.4.1.37950.1.1.5.12.8.3.48.3.22
-- 1.3.6.1.4.1.37950.1.1.5.12.8.3.48.3.22
		-- 1.3.6.1.4.1.37950.1.1.5.12.8.3.48.3.22
		v6ConnSlaveDnsIpv6 OBJECT-TYPE
			SYNTAX OCTET STRING
			MAX-ACCESS read-write
			STATUS current
			DESCRIPTION
				"Description."
			::= { v6WanConnCfg 22 }

		
--           1.3.6.1.4.1.37950.1.1.5.12.3.1.6.3.31
-- 1.3.6.1.4.1.37950.1.1.5.12.8.3.48.3.23
-- 1.3.6.1.4.1.37950.1.1.5.12.8.3.48.3.23
-- 1.3.6.1.4.1.37950.1.1.5.12.8.3.48.3.23
-- 1.3.6.1.4.1.37950.1.1.5.12.8.3.48.3.23
-- 1.3.6.1.4.1.37950.1.1.5.12.8.3.48.3.23
-- 1.3.6.1.4.1.37950.1.1.5.12.8.3.48.3.23
-- 1.3.6.1.4.1.37950.1.1.5.12.8.3.48.3.23
-- 1.3.6.1.4.1.37950.1.1.5.12.8.3.48.3.23
		-- 1.3.6.1.4.1.37950.1.1.5.12.8.3.48.3.23
		v6ConnSlaac OBJECT-TYPE
			SYNTAX INTEGER
				{
				disable(0),
				enable(1)
				}
			MAX-ACCESS read-write
			STATUS current
			DESCRIPTION
				"Description."
			::= { v6WanConnCfg 23 }

		
--           1.3.6.1.4.1.37950.1.1.5.12.3.1.6.3.17
-- 1.3.6.1.4.1.37950.1.1.5.12.8.3.48.3.24
-- 1.3.6.1.4.1.37950.1.1.5.12.8.3.48.3.24
-- 1.3.6.1.4.1.37950.1.1.5.12.8.3.48.3.24
-- 1.3.6.1.4.1.37950.1.1.5.12.8.3.48.3.24
-- 1.3.6.1.4.1.37950.1.1.5.12.8.3.48.3.24
-- 1.3.6.1.4.1.37950.1.1.5.12.8.3.48.3.24
-- 1.3.6.1.4.1.37950.1.1.5.12.8.3.48.3.24
-- 1.3.6.1.4.1.37950.1.1.5.12.8.3.48.3.24
		-- 1.3.6.1.4.1.37950.1.1.5.12.8.3.48.3.24
		v6ConnPppoeProxy OBJECT-TYPE
			SYNTAX INTEGER
				{
				disable(0),
				enable(1)
				}
			MAX-ACCESS read-write
			STATUS current
			DESCRIPTION
				"Description."
			::= { v6WanConnCfg 24 }

		
--           1.3.6.1.4.1.37950.1.1.5.12.3.1.6.3.18
-- 1.3.6.1.4.1.37950.1.1.5.12.8.3.48.3.25
-- 1.3.6.1.4.1.37950.1.1.5.12.8.3.48.3.25
-- 1.3.6.1.4.1.37950.1.1.5.12.8.3.48.3.25
-- 1.3.6.1.4.1.37950.1.1.5.12.8.3.48.3.25
-- 1.3.6.1.4.1.37950.1.1.5.12.8.3.48.3.25
-- 1.3.6.1.4.1.37950.1.1.5.12.8.3.48.3.25
-- 1.3.6.1.4.1.37950.1.1.5.12.8.3.48.3.25
-- 1.3.6.1.4.1.37950.1.1.5.12.8.3.48.3.25
		-- 1.3.6.1.4.1.37950.1.1.5.12.8.3.48.3.25
		v6ConnPppoeUsername OBJECT-TYPE
			SYNTAX OCTET STRING
			MAX-ACCESS read-write
			STATUS current
			DESCRIPTION
				"Description."
			::= { v6WanConnCfg 25 }

		
--           1.3.6.1.4.1.37950.1.1.5.12.3.1.6.3.19
-- 1.3.6.1.4.1.37950.1.1.5.12.8.3.48.3.26
-- 1.3.6.1.4.1.37950.1.1.5.12.8.3.48.3.26
-- 1.3.6.1.4.1.37950.1.1.5.12.8.3.48.3.26
-- 1.3.6.1.4.1.37950.1.1.5.12.8.3.48.3.26
-- 1.3.6.1.4.1.37950.1.1.5.12.8.3.48.3.26
-- 1.3.6.1.4.1.37950.1.1.5.12.8.3.48.3.26
-- 1.3.6.1.4.1.37950.1.1.5.12.8.3.48.3.26
-- 1.3.6.1.4.1.37950.1.1.5.12.8.3.48.3.26
		-- 1.3.6.1.4.1.37950.1.1.5.12.8.3.48.3.26
		v6ConnPppoePassword OBJECT-TYPE
			SYNTAX OCTET STRING
			MAX-ACCESS read-write
			STATUS current
			DESCRIPTION
				"Description."
			::= { v6WanConnCfg 26 }

		
--           1.3.6.1.4.1.37950.1.1.5.12.3.1.6.3.20
-- 1.3.6.1.4.1.37950.1.1.5.12.8.3.48.3.27
-- 1.3.6.1.4.1.37950.1.1.5.12.8.3.48.3.27
-- 1.3.6.1.4.1.37950.1.1.5.12.8.3.48.3.27
-- 1.3.6.1.4.1.37950.1.1.5.12.8.3.48.3.27
-- 1.3.6.1.4.1.37950.1.1.5.12.8.3.48.3.27
-- 1.3.6.1.4.1.37950.1.1.5.12.8.3.48.3.27
-- 1.3.6.1.4.1.37950.1.1.5.12.8.3.48.3.27
-- 1.3.6.1.4.1.37950.1.1.5.12.8.3.48.3.27
		-- 1.3.6.1.4.1.37950.1.1.5.12.8.3.48.3.27
		v6ConnPppoeSerName OBJECT-TYPE
			SYNTAX OCTET STRING
			MAX-ACCESS read-write
			STATUS current
			DESCRIPTION
				"Description."
			::= { v6WanConnCfg 27 }

		
--           1.3.6.1.4.1.37950.1.1.5.12.3.1.6.3.21
-- 1.3.6.1.4.1.37950.1.1.5.12.8.3.48.3.28
-- 1.3.6.1.4.1.37950.1.1.5.12.8.3.48.3.28
-- 1.3.6.1.4.1.37950.1.1.5.12.8.3.48.3.28
-- 1.3.6.1.4.1.37950.1.1.5.12.8.3.48.3.28
-- 1.3.6.1.4.1.37950.1.1.5.12.8.3.48.3.28
-- 1.3.6.1.4.1.37950.1.1.5.12.8.3.48.3.28
-- 1.3.6.1.4.1.37950.1.1.5.12.8.3.48.3.28
-- 1.3.6.1.4.1.37950.1.1.5.12.8.3.48.3.28
		-- 1.3.6.1.4.1.37950.1.1.5.12.8.3.48.3.28
		v6ConnPppoeMode OBJECT-TYPE
			SYNTAX INTEGER
				{
				autoConnect(0),
				flowconnect(1)
				}
			MAX-ACCESS read-write
			STATUS current
			DESCRIPTION
				"Description."
			::= { v6WanConnCfg 28 }

		
--           1.3.6.1.4.1.37950.1.1.5.12.3.1.6.3.31
-- 1.3.6.1.4.1.37950.1.1.5.12.8.3.48.3.29
-- 1.3.6.1.4.1.37950.1.1.5.12.8.3.48.3.29
-- 1.3.6.1.4.1.37950.1.1.5.12.8.3.48.3.29
-- 1.3.6.1.4.1.37950.1.1.5.12.8.3.48.3.29
-- 1.3.6.1.4.1.37950.1.1.5.12.8.3.48.3.29
-- 1.3.6.1.4.1.37950.1.1.5.12.8.3.48.3.29
-- 1.3.6.1.4.1.37950.1.1.5.12.8.3.48.3.29
-- 1.3.6.1.4.1.37950.1.1.5.12.8.3.48.3.29
		-- 1.3.6.1.4.1.37950.1.1.5.12.8.3.48.3.29
		v6ConnDhcpv6ClientAddress OBJECT-TYPE
			SYNTAX INTEGER
				{
				disable(0),
				enable(1)
				}
			MAX-ACCESS read-write
			STATUS current
			DESCRIPTION
				"Description."
			::= { v6WanConnCfg 29 }

		
--           1.3.6.1.4.1.37950.1.1.5.12.3.1.6.3.31
-- 1.3.6.1.4.1.37950.1.1.5.12.8.3.48.3.30
-- 1.3.6.1.4.1.37950.1.1.5.12.8.3.48.3.30
-- 1.3.6.1.4.1.37950.1.1.5.12.8.3.48.3.30
-- 1.3.6.1.4.1.37950.1.1.5.12.8.3.48.3.30
-- 1.3.6.1.4.1.37950.1.1.5.12.8.3.48.3.30
-- 1.3.6.1.4.1.37950.1.1.5.12.8.3.48.3.30
-- 1.3.6.1.4.1.37950.1.1.5.12.8.3.48.3.30
-- 1.3.6.1.4.1.37950.1.1.5.12.8.3.48.3.30
		-- 1.3.6.1.4.1.37950.1.1.5.12.8.3.48.3.30
		v6ConnDhcpv6ClientPrefix OBJECT-TYPE
			SYNTAX INTEGER
				{
				disable(0),
				enable(1)
				}
			MAX-ACCESS read-write
			STATUS current
			DESCRIPTION
				"Description."
			::= { v6WanConnCfg 30 }

		
--           1.3.6.1.4.1.37950.1.1.5.12.3.1.6.3.31
-- 1.3.6.1.4.1.37950.1.1.5.12.8.3.48.3.31
-- 1.3.6.1.4.1.37950.1.1.5.12.8.3.48.3.31
-- 1.3.6.1.4.1.37950.1.1.5.12.8.3.48.3.31
-- 1.3.6.1.4.1.37950.1.1.5.12.8.3.48.3.31
-- 1.3.6.1.4.1.37950.1.1.5.12.8.3.48.3.31
-- 1.3.6.1.4.1.37950.1.1.5.12.8.3.48.3.31
-- 1.3.6.1.4.1.37950.1.1.5.12.8.3.48.3.31
-- 1.3.6.1.4.1.37950.1.1.5.12.8.3.48.3.31
		-- 1.3.6.1.4.1.37950.1.1.5.12.8.3.48.3.31
		v6ConnDsLiteEnable OBJECT-TYPE
			SYNTAX INTEGER
				{
				disable(0),
				enable(1)
				}
			MAX-ACCESS read-write
			STATUS current
			DESCRIPTION
				"Description."
			::= { v6WanConnCfg 31 }

		
--           1.3.6.1.4.1.37950.1.1.5.12.3.1.6.3.31
-- 1.3.6.1.4.1.37950.1.1.5.12.8.3.48.3.32
-- 1.3.6.1.4.1.37950.1.1.5.12.8.3.48.3.32
-- 1.3.6.1.4.1.37950.1.1.5.12.8.3.48.3.32
-- 1.3.6.1.4.1.37950.1.1.5.12.8.3.48.3.32
-- 1.3.6.1.4.1.37950.1.1.5.12.8.3.48.3.32
-- 1.3.6.1.4.1.37950.1.1.5.12.8.3.48.3.32
-- 1.3.6.1.4.1.37950.1.1.5.12.8.3.48.3.32
-- 1.3.6.1.4.1.37950.1.1.5.12.8.3.48.3.32
		-- 1.3.6.1.4.1.37950.1.1.5.12.8.3.48.3.32
		v6ConnDsLiteAftrMode OBJECT-TYPE
			SYNTAX INTEGER
				{
				dhcpv6(0),
				manual(1)
				}
			MAX-ACCESS read-write
			STATUS current
			DESCRIPTION
				"Description."
			::= { v6WanConnCfg 32 }

		
--           1.3.6.1.4.1.37950.1.1.5.12.3.1.6.3.31
-- 1.3.6.1.4.1.37950.1.1.5.12.8.3.48.3.33
-- 1.3.6.1.4.1.37950.1.1.5.12.8.3.48.3.33
-- 1.3.6.1.4.1.37950.1.1.5.12.8.3.48.3.33
-- 1.3.6.1.4.1.37950.1.1.5.12.8.3.48.3.33
-- 1.3.6.1.4.1.37950.1.1.5.12.8.3.48.3.33
-- 1.3.6.1.4.1.37950.1.1.5.12.8.3.48.3.33
-- 1.3.6.1.4.1.37950.1.1.5.12.8.3.48.3.33
-- 1.3.6.1.4.1.37950.1.1.5.12.8.3.48.3.33
		-- 1.3.6.1.4.1.37950.1.1.5.12.8.3.48.3.33
		v6ConnDsLiteAddressType OBJECT-TYPE
			SYNTAX INTEGER
				{
				ipv6(0),
				dns(1)
				}
			MAX-ACCESS read-write
			STATUS current
			DESCRIPTION
				"Description."
			::= { v6WanConnCfg 33 }

		
--           1.3.6.1.4.1.37950.1.1.5.12.3.1.6.3.31
-- 1.3.6.1.4.1.37950.1.1.5.12.8.3.48.3.34
-- 1.3.6.1.4.1.37950.1.1.5.12.8.3.48.3.34
-- 1.3.6.1.4.1.37950.1.1.5.12.8.3.48.3.34
-- 1.3.6.1.4.1.37950.1.1.5.12.8.3.48.3.34
-- 1.3.6.1.4.1.37950.1.1.5.12.8.3.48.3.34
-- 1.3.6.1.4.1.37950.1.1.5.12.8.3.48.3.34
-- 1.3.6.1.4.1.37950.1.1.5.12.8.3.48.3.34
-- 1.3.6.1.4.1.37950.1.1.5.12.8.3.48.3.34
		-- 1.3.6.1.4.1.37950.1.1.5.12.8.3.48.3.34
		v6ConnDsLiteAddress OBJECT-TYPE
			SYNTAX OCTET STRING
			MAX-ACCESS read-write
			STATUS current
			DESCRIPTION
				"Description."
			::= { v6WanConnCfg 34 }

		
--           1.3.6.1.4.1.37950.1.1.5.12.3.1.6.3.22
-- 1.3.6.1.4.1.37950.1.1.5.12.8.3.48.3.35
-- 1.3.6.1.4.1.37950.1.1.5.12.8.3.48.3.35
-- 1.3.6.1.4.1.37950.1.1.5.12.8.3.48.3.35
-- 1.3.6.1.4.1.37950.1.1.5.12.8.3.48.3.35
-- 1.3.6.1.4.1.37950.1.1.5.12.8.3.48.3.35
-- 1.3.6.1.4.1.37950.1.1.5.12.8.3.48.3.35
-- 1.3.6.1.4.1.37950.1.1.5.12.8.3.48.3.35
-- 1.3.6.1.4.1.37950.1.1.5.12.8.3.48.3.35
		-- 1.3.6.1.4.1.37950.1.1.5.12.8.3.48.3.35
		v6ConnQosEnable OBJECT-TYPE
			SYNTAX INTEGER
				{
				disable(0),
				enable(1)
				}
			MAX-ACCESS read-write
			STATUS current
			DESCRIPTION
				"Description."
			::= { v6WanConnCfg 35 }

		
--           1.3.6.1.4.1.37950.1.1.5.12.3.1.6.3.23
-- 1.3.6.1.4.1.37950.1.1.5.12.8.3.48.3.36
-- 1.3.6.1.4.1.37950.1.1.5.12.8.3.48.3.36
-- 1.3.6.1.4.1.37950.1.1.5.12.8.3.48.3.36
-- 1.3.6.1.4.1.37950.1.1.5.12.8.3.48.3.36
-- 1.3.6.1.4.1.37950.1.1.5.12.8.3.48.3.36
-- 1.3.6.1.4.1.37950.1.1.5.12.8.3.48.3.36
-- 1.3.6.1.4.1.37950.1.1.5.12.8.3.48.3.36
-- 1.3.6.1.4.1.37950.1.1.5.12.8.3.48.3.36
		-- 1.3.6.1.4.1.37950.1.1.5.12.8.3.48.3.36
		v6ConnVlanMode OBJECT-TYPE
			SYNTAX INTEGER
				{
				disable(0),
				tag(1),
				transparent(2)
				}
			MAX-ACCESS read-write
			STATUS current
			DESCRIPTION
				"Description."
			::= { v6WanConnCfg 36 }

		
--           1.3.6.1.4.1.37950.1.1.5.12.3.1.6.3.24
-- 1.3.6.1.4.1.37950.1.1.5.12.8.3.48.3.37
-- 1.3.6.1.4.1.37950.1.1.5.12.8.3.48.3.37
-- 1.3.6.1.4.1.37950.1.1.5.12.8.3.48.3.37
-- 1.3.6.1.4.1.37950.1.1.5.12.8.3.48.3.37
-- 1.3.6.1.4.1.37950.1.1.5.12.8.3.48.3.37
-- 1.3.6.1.4.1.37950.1.1.5.12.8.3.48.3.37
-- 1.3.6.1.4.1.37950.1.1.5.12.8.3.48.3.37
-- 1.3.6.1.4.1.37950.1.1.5.12.8.3.48.3.37
		-- 1.3.6.1.4.1.37950.1.1.5.12.8.3.48.3.37
		v6ConnTranslationEnable OBJECT-TYPE
			SYNTAX INTEGER
				{
				disable(0),
				enable(1)
				}
			MAX-ACCESS read-write
			STATUS current
			DESCRIPTION
				"Description."
			::= { v6WanConnCfg 37 }

		
--           1.3.6.1.4.1.37950.1.1.5.12.3.1.6.3.25
-- 1.3.6.1.4.1.37950.1.1.5.12.8.3.48.3.38
-- 1.3.6.1.4.1.37950.1.1.5.12.8.3.48.3.38
-- 1.3.6.1.4.1.37950.1.1.5.12.8.3.48.3.38
-- 1.3.6.1.4.1.37950.1.1.5.12.8.3.48.3.38
-- 1.3.6.1.4.1.37950.1.1.5.12.8.3.48.3.38
-- 1.3.6.1.4.1.37950.1.1.5.12.8.3.48.3.38
-- 1.3.6.1.4.1.37950.1.1.5.12.8.3.48.3.38
-- 1.3.6.1.4.1.37950.1.1.5.12.8.3.48.3.38
		-- 1.3.6.1.4.1.37950.1.1.5.12.8.3.48.3.38
		v6ConnTranslationVlan OBJECT-TYPE
			SYNTAX INTEGER (1..4095)
			MAX-ACCESS read-write
			STATUS current
			DESCRIPTION
				"Description."
			::= { v6WanConnCfg 38 }

		
--           1.3.6.1.4.1.37950.1.1.5.12.3.1.6.3.26
-- 1.3.6.1.4.1.37950.1.1.5.12.8.3.48.3.39
-- 1.3.6.1.4.1.37950.1.1.5.12.8.3.48.3.39
-- 1.3.6.1.4.1.37950.1.1.5.12.8.3.48.3.39
-- 1.3.6.1.4.1.37950.1.1.5.12.8.3.48.3.39
-- 1.3.6.1.4.1.37950.1.1.5.12.8.3.48.3.39
-- 1.3.6.1.4.1.37950.1.1.5.12.8.3.48.3.39
-- 1.3.6.1.4.1.37950.1.1.5.12.8.3.48.3.39
-- 1.3.6.1.4.1.37950.1.1.5.12.8.3.48.3.39
		-- 1.3.6.1.4.1.37950.1.1.5.12.8.3.48.3.39
		v6ConnTranslationCos OBJECT-TYPE
			SYNTAX INTEGER (0..7)
			MAX-ACCESS read-write
			STATUS current
			DESCRIPTION
				"Description."
			::= { v6WanConnCfg 39 }

		
--           1.3.6.1.4.1.37950.1.1.5.12.3.1.6.3.27
-- 1.3.6.1.4.1.37950.1.1.5.12.8.3.48.3.40
-- 1.3.6.1.4.1.37950.1.1.5.12.8.3.48.3.40
-- 1.3.6.1.4.1.37950.1.1.5.12.8.3.48.3.40
-- 1.3.6.1.4.1.37950.1.1.5.12.8.3.48.3.40
-- 1.3.6.1.4.1.37950.1.1.5.12.8.3.48.3.40
-- 1.3.6.1.4.1.37950.1.1.5.12.8.3.48.3.40
-- 1.3.6.1.4.1.37950.1.1.5.12.8.3.48.3.40
-- 1.3.6.1.4.1.37950.1.1.5.12.8.3.48.3.40
		-- 1.3.6.1.4.1.37950.1.1.5.12.8.3.48.3.40
		v6ConnQinqEnable OBJECT-TYPE
			SYNTAX INTEGER
				{
				disable(0),
				enable(1)
				}
			MAX-ACCESS read-write
			STATUS current
			DESCRIPTION
				"Description."
			::= { v6WanConnCfg 40 }

		
--           1.3.6.1.4.1.37950.1.1.5.12.3.1.6.3.28
-- 1.3.6.1.4.1.37950.1.1.5.12.8.3.48.3.41
-- 1.3.6.1.4.1.37950.1.1.5.12.8.3.48.3.41
-- 1.3.6.1.4.1.37950.1.1.5.12.8.3.48.3.41
-- 1.3.6.1.4.1.37950.1.1.5.12.8.3.48.3.41
-- 1.3.6.1.4.1.37950.1.1.5.12.8.3.48.3.41
-- 1.3.6.1.4.1.37950.1.1.5.12.8.3.48.3.41
-- 1.3.6.1.4.1.37950.1.1.5.12.8.3.48.3.41
-- 1.3.6.1.4.1.37950.1.1.5.12.8.3.48.3.41
		-- 1.3.6.1.4.1.37950.1.1.5.12.8.3.48.3.41
		v6ConnQinqTpid OBJECT-TYPE
			SYNTAX Integer32 (1..65534)
			MAX-ACCESS read-write
			STATUS current
			DESCRIPTION
				"Description."
			::= { v6WanConnCfg 41 }

		
--           1.3.6.1.4.1.37950.1.1.5.12.3.1.6.3.29
-- 1.3.6.1.4.1.37950.1.1.5.12.8.3.48.3.42
-- 1.3.6.1.4.1.37950.1.1.5.12.8.3.48.3.42
-- 1.3.6.1.4.1.37950.1.1.5.12.8.3.48.3.42
-- 1.3.6.1.4.1.37950.1.1.5.12.8.3.48.3.42
-- 1.3.6.1.4.1.37950.1.1.5.12.8.3.48.3.42
-- 1.3.6.1.4.1.37950.1.1.5.12.8.3.48.3.42
-- 1.3.6.1.4.1.37950.1.1.5.12.8.3.48.3.42
-- 1.3.6.1.4.1.37950.1.1.5.12.8.3.48.3.42
		-- 1.3.6.1.4.1.37950.1.1.5.12.8.3.48.3.42
		v6ConnWanSvlanId OBJECT-TYPE
			SYNTAX INTEGER (1..4095)
			MAX-ACCESS read-write
			STATUS current
			DESCRIPTION
				"Description."
			::= { v6WanConnCfg 42 }

		
--           1.3.6.1.4.1.37950.1.1.5.12.3.1.6.3.30
-- 1.3.6.1.4.1.37950.1.1.5.12.8.3.48.3.43
-- 1.3.6.1.4.1.37950.1.1.5.12.8.3.48.3.43
-- 1.3.6.1.4.1.37950.1.1.5.12.8.3.48.3.43
-- 1.3.6.1.4.1.37950.1.1.5.12.8.3.48.3.43
-- 1.3.6.1.4.1.37950.1.1.5.12.8.3.48.3.43
-- 1.3.6.1.4.1.37950.1.1.5.12.8.3.48.3.43
-- 1.3.6.1.4.1.37950.1.1.5.12.8.3.48.3.43
-- 1.3.6.1.4.1.37950.1.1.5.12.8.3.48.3.43
		-- 1.3.6.1.4.1.37950.1.1.5.12.8.3.48.3.43
		v6ConnSvlanCos OBJECT-TYPE
			SYNTAX INTEGER (0..7)
			MAX-ACCESS read-write
			STATUS current
			DESCRIPTION
				"Description."
			::= { v6WanConnCfg 43 }

		
--           1.3.6.1.4.1.37950.1.1.5.12.3.1.6.3.31
-- 1.3.6.1.4.1.37950.1.1.5.12.8.3.48.3.44
-- 1.3.6.1.4.1.37950.1.1.5.12.8.3.48.3.44
-- 1.3.6.1.4.1.37950.1.1.5.12.8.3.48.3.44
-- 1.3.6.1.4.1.37950.1.1.5.12.8.3.48.3.44
-- 1.3.6.1.4.1.37950.1.1.5.12.8.3.48.3.44
-- 1.3.6.1.4.1.37950.1.1.5.12.8.3.48.3.44
-- 1.3.6.1.4.1.37950.1.1.5.12.8.3.48.3.44
-- 1.3.6.1.4.1.37950.1.1.5.12.8.3.48.3.44
		-- 1.3.6.1.4.1.37950.1.1.5.12.8.3.48.3.44
		v6ConnRouteMtu OBJECT-TYPE
			SYNTAX Integer32 (576..1500)
			MAX-ACCESS read-write
			STATUS current
			DESCRIPTION
				"Description."
			::= { v6WanConnCfg 44 }

		
--           1.3.6.1.4.1.37950.1.1.5.12.3.1.6.3.31
-- 1.3.6.1.4.1.37950.1.1.5.12.8.3.48.3.45
-- 1.3.6.1.4.1.37950.1.1.5.12.8.3.48.3.45
-- 1.3.6.1.4.1.37950.1.1.5.12.8.3.48.3.45
-- 1.3.6.1.4.1.37950.1.1.5.12.8.3.48.3.45
-- 1.3.6.1.4.1.37950.1.1.5.12.8.3.48.3.45
-- 1.3.6.1.4.1.37950.1.1.5.12.8.3.48.3.45
-- 1.3.6.1.4.1.37950.1.1.5.12.8.3.48.3.45
-- 1.3.6.1.4.1.37950.1.1.5.12.8.3.48.3.45
		-- 1.3.6.1.4.1.37950.1.1.5.12.8.3.48.3.45
		v6ConnCfgAction OBJECT-TYPE
			SYNTAX INTEGER { add(1) }
			MAX-ACCESS read-write
			STATUS current
			DESCRIPTION
				"Description."
			::= { v6WanConnCfg 45 }

		
--           1.3.6.1.4.1.37950.1.1.5.12.8.3.36.4
-- 1.3.6.1.4.1.37950.1.1.5.12.8.3.48.4
-- 1.3.6.1.4.1.37950.1.1.5.12.8.3.48.4
-- 1.3.6.1.4.1.37950.1.1.5.12.8.3.48.4
-- 1.3.6.1.4.1.37950.1.1.5.12.8.3.48.4
-- 1.3.6.1.4.1.37950.1.1.5.12.8.3.48.4
-- 1.3.6.1.4.1.37950.1.1.5.12.8.3.48.4
-- 1.3.6.1.4.1.37950.1.1.5.12.8.3.48.4
-- 1.3.6.1.4.1.37950.1.1.5.12.8.3.48.4
		-- 1.3.6.1.4.1.37950.1.1.5.12.8.3.48.4
		v6WanConnCommit OBJECT IDENTIFIER ::= { onuWanConnV6 4 }

		
--           1.3.6.1.4.1.37950.1.1.5.12.8.3.36.4.1
-- 1.3.6.1.4.1.37950.1.1.5.12.8.3.48.4.1
-- 1.3.6.1.4.1.37950.1.1.5.12.8.3.48.4.1
-- 1.3.6.1.4.1.37950.1.1.5.12.8.3.48.4.1
-- 1.3.6.1.4.1.37950.1.1.5.12.8.3.48.4.1
-- 1.3.6.1.4.1.37950.1.1.5.12.8.3.48.4.1
-- 1.3.6.1.4.1.37950.1.1.5.12.8.3.48.4.1
-- 1.3.6.1.4.1.37950.1.1.5.12.8.3.48.4.1
-- 1.3.6.1.4.1.37950.1.1.5.12.8.3.48.4.1
		-- 1.3.6.1.4.1.37950.1.1.5.12.8.3.48.4.1
		v6ConnCommitAction OBJECT-TYPE
			SYNTAX INTEGER
				{
				commit(1),
				remove(2)
				}
			MAX-ACCESS read-write
			STATUS current
			DESCRIPTION
				"Description."
			::= { v6WanConnCommit 1 }

		
--         1.3.6.1.4.1.37950.1.1.5.12.8.3.49
-- 1.3.6.1.4.1.37950.1.1.5.12.8.3.49
-- 1.3.6.1.4.1.37950.1.1.5.12.8.3.49
-- 1.3.6.1.4.1.37950.1.1.5.12.8.3.49
-- 1.3.6.1.4.1.37950.1.1.5.12.8.3.49
-- 1.3.6.1.4.1.37950.1.1.5.12.8.3.49
-- 1.3.6.1.4.1.37950.1.1.5.12.8.3.49
-- 1.3.6.1.4.1.37950.1.1.5.12.8.3.49
		-- 1.3.6.1.4.1.37950.1.1.5.12.8.3.49
		onuTr069 OBJECT IDENTIFIER ::= { srvProfileEdit 49 }

		
--         1.3.6.1.4.1.37950.1.1.5.12.8.3.49.1
-- 1.3.6.1.4.1.37950.1.1.5.12.8.3.49.1
-- 1.3.6.1.4.1.37950.1.1.5.12.8.3.49.1
-- 1.3.6.1.4.1.37950.1.1.5.12.8.3.49.1
-- 1.3.6.1.4.1.37950.1.1.5.12.8.3.49.1
-- 1.3.6.1.4.1.37950.1.1.5.12.8.3.49.1
-- 1.3.6.1.4.1.37950.1.1.5.12.8.3.49.1
-- 1.3.6.1.4.1.37950.1.1.5.12.8.3.49.1
		-- 1.3.6.1.4.1.37950.1.1.5.12.8.3.49.1
		onuTr069Manage OBJECT IDENTIFIER ::= { onuTr069 1 }

		
--         1.3.6.1.4.1.37950.1.1.5.12.8.3.49.1.1
-- 1.3.6.1.4.1.37950.1.1.5.12.8.3.49.1.1
-- 1.3.6.1.4.1.37950.1.1.5.12.8.3.49.1.1
-- 1.3.6.1.4.1.37950.1.1.5.12.8.3.49.1.1
-- 1.3.6.1.4.1.37950.1.1.5.12.8.3.49.1.1
-- 1.3.6.1.4.1.37950.1.1.5.12.8.3.49.1.1
-- 1.3.6.1.4.1.37950.1.1.5.12.8.3.49.1.1
-- 1.3.6.1.4.1.37950.1.1.5.12.8.3.49.1.1
		-- 1.3.6.1.4.1.37950.1.1.5.12.8.3.49.1.1
		mngStatus OBJECT-TYPE
			SYNTAX INTEGER
				{
				disable(0),
				enable(1)
				}
			MAX-ACCESS read-write
			STATUS current
			DESCRIPTION
				"Description."
			::= { onuTr069Manage 1 }

		
--         1.3.6.1.4.1.37950.1.1.5.12.8.3.49.1.2
-- 1.3.6.1.4.1.37950.1.1.5.12.8.3.49.1.2
-- 1.3.6.1.4.1.37950.1.1.5.12.8.3.49.1.2
-- 1.3.6.1.4.1.37950.1.1.5.12.8.3.49.1.2
-- 1.3.6.1.4.1.37950.1.1.5.12.8.3.49.1.2
-- 1.3.6.1.4.1.37950.1.1.5.12.8.3.49.1.2
-- 1.3.6.1.4.1.37950.1.1.5.12.8.3.49.1.2
-- 1.3.6.1.4.1.37950.1.1.5.12.8.3.49.1.2
		-- 1.3.6.1.4.1.37950.1.1.5.12.8.3.49.1.2
		mngAcsAddress OBJECT-TYPE
			SYNTAX OCTET STRING (SIZE (0..128))
			MAX-ACCESS read-write
			STATUS current
			DESCRIPTION
				"Description."
			::= { onuTr069Manage 2 }

		
--         1.3.6.1.4.1.37950.1.1.5.12.8.3.49.1.3
-- 1.3.6.1.4.1.37950.1.1.5.12.8.3.49.1.3
-- 1.3.6.1.4.1.37950.1.1.5.12.8.3.49.1.3
-- 1.3.6.1.4.1.37950.1.1.5.12.8.3.49.1.3
-- 1.3.6.1.4.1.37950.1.1.5.12.8.3.49.1.3
-- 1.3.6.1.4.1.37950.1.1.5.12.8.3.49.1.3
-- 1.3.6.1.4.1.37950.1.1.5.12.8.3.49.1.3
-- 1.3.6.1.4.1.37950.1.1.5.12.8.3.49.1.3
		-- 1.3.6.1.4.1.37950.1.1.5.12.8.3.49.1.3
		mngAcsUsername OBJECT-TYPE
			SYNTAX OCTET STRING (SIZE (0..64))
			MAX-ACCESS read-write
			STATUS current
			DESCRIPTION
				"Description."
			::= { onuTr069Manage 3 }

		
--         1.3.6.1.4.1.37950.1.1.5.12.8.3.49.1.4
-- 1.3.6.1.4.1.37950.1.1.5.12.8.3.49.1.4
-- 1.3.6.1.4.1.37950.1.1.5.12.8.3.49.1.4
-- 1.3.6.1.4.1.37950.1.1.5.12.8.3.49.1.4
-- 1.3.6.1.4.1.37950.1.1.5.12.8.3.49.1.4
-- 1.3.6.1.4.1.37950.1.1.5.12.8.3.49.1.4
-- 1.3.6.1.4.1.37950.1.1.5.12.8.3.49.1.4
-- 1.3.6.1.4.1.37950.1.1.5.12.8.3.49.1.4
		-- 1.3.6.1.4.1.37950.1.1.5.12.8.3.49.1.4
		mngAcsPassword OBJECT-TYPE
			SYNTAX OCTET STRING (SIZE (0..64))
			MAX-ACCESS read-write
			STATUS current
			DESCRIPTION
				"Description."
			::= { onuTr069Manage 4 }

		
--         1.3.6.1.4.1.37950.1.1.5.12.8.3.49.1.5
-- 1.3.6.1.4.1.37950.1.1.5.12.8.3.49.1.5
-- 1.3.6.1.4.1.37950.1.1.5.12.8.3.49.1.5
-- 1.3.6.1.4.1.37950.1.1.5.12.8.3.49.1.5
-- 1.3.6.1.4.1.37950.1.1.5.12.8.3.49.1.5
-- 1.3.6.1.4.1.37950.1.1.5.12.8.3.49.1.5
-- 1.3.6.1.4.1.37950.1.1.5.12.8.3.49.1.5
-- 1.3.6.1.4.1.37950.1.1.5.12.8.3.49.1.5
		-- 1.3.6.1.4.1.37950.1.1.5.12.8.3.49.1.5
		mngCertificateEn OBJECT-TYPE
			SYNTAX INTEGER
				{
				disable(0),
				enable(1)
				}
			MAX-ACCESS read-write
			STATUS current
			DESCRIPTION
				"Description."
			::= { onuTr069Manage 5 }

		
--         1.3.6.1.4.1.37950.1.1.5.12.8.3.49.1.6
-- 1.3.6.1.4.1.37950.1.1.5.12.8.3.49.1.6
-- 1.3.6.1.4.1.37950.1.1.5.12.8.3.49.1.6
-- 1.3.6.1.4.1.37950.1.1.5.12.8.3.49.1.6
-- 1.3.6.1.4.1.37950.1.1.5.12.8.3.49.1.6
-- 1.3.6.1.4.1.37950.1.1.5.12.8.3.49.1.6
-- 1.3.6.1.4.1.37950.1.1.5.12.8.3.49.1.6
-- 1.3.6.1.4.1.37950.1.1.5.12.8.3.49.1.6
		-- 1.3.6.1.4.1.37950.1.1.5.12.8.3.49.1.6
		mngInformEn OBJECT-TYPE
			SYNTAX INTEGER
				{
				disable(0),
				enable(1)
				}
			MAX-ACCESS read-write
			STATUS current
			DESCRIPTION
				"Description."
			::= { onuTr069Manage 6 }

		
--         1.3.6.1.4.1.37950.1.1.5.12.8.3.49.1.7
-- 1.3.6.1.4.1.37950.1.1.5.12.8.3.49.1.7
-- 1.3.6.1.4.1.37950.1.1.5.12.8.3.49.1.7
-- 1.3.6.1.4.1.37950.1.1.5.12.8.3.49.1.7
-- 1.3.6.1.4.1.37950.1.1.5.12.8.3.49.1.7
-- 1.3.6.1.4.1.37950.1.1.5.12.8.3.49.1.7
-- 1.3.6.1.4.1.37950.1.1.5.12.8.3.49.1.7
-- 1.3.6.1.4.1.37950.1.1.5.12.8.3.49.1.7
		-- 1.3.6.1.4.1.37950.1.1.5.12.8.3.49.1.7
		mngInformIntervalTime OBJECT-TYPE
			SYNTAX Unsigned32 (0..4294967295)
			MAX-ACCESS read-write
			STATUS current
			DESCRIPTION
				"Description."
			::= { onuTr069Manage 7 }

		
--         1.3.6.1.4.1.37950.1.1.5.12.8.3.49.1.8
-- 1.3.6.1.4.1.37950.1.1.5.12.8.3.49.1.8
-- 1.3.6.1.4.1.37950.1.1.5.12.8.3.49.1.8
-- 1.3.6.1.4.1.37950.1.1.5.12.8.3.49.1.8
-- 1.3.6.1.4.1.37950.1.1.5.12.8.3.49.1.8
-- 1.3.6.1.4.1.37950.1.1.5.12.8.3.49.1.8
-- 1.3.6.1.4.1.37950.1.1.5.12.8.3.49.1.8
-- 1.3.6.1.4.1.37950.1.1.5.12.8.3.49.1.8
		-- 1.3.6.1.4.1.37950.1.1.5.12.8.3.49.1.8
		mngRevConnUsername OBJECT-TYPE
			SYNTAX OCTET STRING (SIZE (0..64))
			MAX-ACCESS read-write
			STATUS current
			DESCRIPTION
				"Description."
			::= { onuTr069Manage 8 }

		
--         1.3.6.1.4.1.37950.1.1.5.12.8.3.49.1.9
-- 1.3.6.1.4.1.37950.1.1.5.12.8.3.49.1.9
-- 1.3.6.1.4.1.37950.1.1.5.12.8.3.49.1.9
-- 1.3.6.1.4.1.37950.1.1.5.12.8.3.49.1.9
-- 1.3.6.1.4.1.37950.1.1.5.12.8.3.49.1.9
-- 1.3.6.1.4.1.37950.1.1.5.12.8.3.49.1.9
-- 1.3.6.1.4.1.37950.1.1.5.12.8.3.49.1.9
-- 1.3.6.1.4.1.37950.1.1.5.12.8.3.49.1.9
		-- 1.3.6.1.4.1.37950.1.1.5.12.8.3.49.1.9
		mngRevConnPassword OBJECT-TYPE
			SYNTAX OCTET STRING (SIZE (0..64))
			MAX-ACCESS read-write
			STATUS current
			DESCRIPTION
				"Description."
			::= { onuTr069Manage 9 }

		
--         1.3.6.1.4.1.37950.1.1.5.12.8.3.49.1.10
-- 1.3.6.1.4.1.37950.1.1.5.12.8.3.49.1.10
-- 1.3.6.1.4.1.37950.1.1.5.12.8.3.49.1.10
-- 1.3.6.1.4.1.37950.1.1.5.12.8.3.49.1.10
-- 1.3.6.1.4.1.37950.1.1.5.12.8.3.49.1.10
-- 1.3.6.1.4.1.37950.1.1.5.12.8.3.49.1.10
-- 1.3.6.1.4.1.37950.1.1.5.12.8.3.49.1.10
-- 1.3.6.1.4.1.37950.1.1.5.12.8.3.49.1.10
		-- 1.3.6.1.4.1.37950.1.1.5.12.8.3.49.1.10
		mngAction OBJECT-TYPE
			SYNTAX INTEGER
				{
				submit(1),
				remove(2)
				}
			MAX-ACCESS read-write
			STATUS current
			DESCRIPTION
				"Description."
			::= { onuTr069Manage 10 }

		
--         1.3.6.1.4.1.37950.1.1.5.12.8.3.49.2
-- 1.3.6.1.4.1.37950.1.1.5.12.8.3.49.2
-- 1.3.6.1.4.1.37950.1.1.5.12.8.3.49.2
-- 1.3.6.1.4.1.37950.1.1.5.12.8.3.49.2
-- 1.3.6.1.4.1.37950.1.1.5.12.8.3.49.2
-- 1.3.6.1.4.1.37950.1.1.5.12.8.3.49.2
-- 1.3.6.1.4.1.37950.1.1.5.12.8.3.49.2
-- 1.3.6.1.4.1.37950.1.1.5.12.8.3.49.2
		-- 1.3.6.1.4.1.37950.1.1.5.12.8.3.49.2
		onuTr069Stun OBJECT IDENTIFIER ::= { onuTr069 2 }

		
--         1.3.6.1.4.1.37950.1.1.5.12.8.3.49.2.1
-- 1.3.6.1.4.1.37950.1.1.5.12.8.3.49.2.1
-- 1.3.6.1.4.1.37950.1.1.5.12.8.3.49.2.1
-- 1.3.6.1.4.1.37950.1.1.5.12.8.3.49.2.1
-- 1.3.6.1.4.1.37950.1.1.5.12.8.3.49.2.1
-- 1.3.6.1.4.1.37950.1.1.5.12.8.3.49.2.1
-- 1.3.6.1.4.1.37950.1.1.5.12.8.3.49.2.1
-- 1.3.6.1.4.1.37950.1.1.5.12.8.3.49.2.1
		-- 1.3.6.1.4.1.37950.1.1.5.12.8.3.49.2.1
		stunStatus OBJECT-TYPE
			SYNTAX INTEGER
				{
				disable(0),
				enable(1)
				}
			MAX-ACCESS read-write
			STATUS current
			DESCRIPTION
				"Description."
			::= { onuTr069Stun 1 }

		
--         1.3.6.1.4.1.37950.1.1.5.12.8.3.49.2.2
-- 1.3.6.1.4.1.37950.1.1.5.12.8.3.49.2.2
-- 1.3.6.1.4.1.37950.1.1.5.12.8.3.49.2.2
-- 1.3.6.1.4.1.37950.1.1.5.12.8.3.49.2.2
-- 1.3.6.1.4.1.37950.1.1.5.12.8.3.49.2.2
-- 1.3.6.1.4.1.37950.1.1.5.12.8.3.49.2.2
-- 1.3.6.1.4.1.37950.1.1.5.12.8.3.49.2.2
-- 1.3.6.1.4.1.37950.1.1.5.12.8.3.49.2.2
		-- 1.3.6.1.4.1.37950.1.1.5.12.8.3.49.2.2
		stunServerAddress OBJECT-TYPE
			SYNTAX OCTET STRING (SIZE (0..128))
			MAX-ACCESS read-write
			STATUS current
			DESCRIPTION
				"Description."
			::= { onuTr069Stun 2 }

		
--         1.3.6.1.4.1.37950.1.1.5.12.8.3.49.2.3
-- 1.3.6.1.4.1.37950.1.1.5.12.8.3.49.2.3
-- 1.3.6.1.4.1.37950.1.1.5.12.8.3.49.2.3
-- 1.3.6.1.4.1.37950.1.1.5.12.8.3.49.2.3
-- 1.3.6.1.4.1.37950.1.1.5.12.8.3.49.2.3
-- 1.3.6.1.4.1.37950.1.1.5.12.8.3.49.2.3
-- 1.3.6.1.4.1.37950.1.1.5.12.8.3.49.2.3
-- 1.3.6.1.4.1.37950.1.1.5.12.8.3.49.2.3
		-- 1.3.6.1.4.1.37950.1.1.5.12.8.3.49.2.3
		stunServerPort OBJECT-TYPE
			SYNTAX Integer32 (1..65535)
			MAX-ACCESS read-write
			STATUS current
			DESCRIPTION
				"Description."
			::= { onuTr069Stun 3 }

		
--         1.3.6.1.4.1.37950.1.1.5.12.8.3.49.2.4
-- 1.3.6.1.4.1.37950.1.1.5.12.8.3.49.2.4
-- 1.3.6.1.4.1.37950.1.1.5.12.8.3.49.2.4
-- 1.3.6.1.4.1.37950.1.1.5.12.8.3.49.2.4
-- 1.3.6.1.4.1.37950.1.1.5.12.8.3.49.2.4
-- 1.3.6.1.4.1.37950.1.1.5.12.8.3.49.2.4
-- 1.3.6.1.4.1.37950.1.1.5.12.8.3.49.2.4
-- 1.3.6.1.4.1.37950.1.1.5.12.8.3.49.2.4
		-- 1.3.6.1.4.1.37950.1.1.5.12.8.3.49.2.4
		stunServerUsername OBJECT-TYPE
			SYNTAX OCTET STRING (SIZE (0..64))
			MAX-ACCESS read-write
			STATUS current
			DESCRIPTION
				"Description."
			::= { onuTr069Stun 4 }

		
--         1.3.6.1.4.1.37950.1.1.5.12.8.3.49.2.5
-- 1.3.6.1.4.1.37950.1.1.5.12.8.3.49.2.5
-- 1.3.6.1.4.1.37950.1.1.5.12.8.3.49.2.5
-- 1.3.6.1.4.1.37950.1.1.5.12.8.3.49.2.5
-- 1.3.6.1.4.1.37950.1.1.5.12.8.3.49.2.5
-- 1.3.6.1.4.1.37950.1.1.5.12.8.3.49.2.5
-- 1.3.6.1.4.1.37950.1.1.5.12.8.3.49.2.5
-- 1.3.6.1.4.1.37950.1.1.5.12.8.3.49.2.5
		-- 1.3.6.1.4.1.37950.1.1.5.12.8.3.49.2.5
		stunServerPassword OBJECT-TYPE
			SYNTAX OCTET STRING (SIZE (0..64))
			MAX-ACCESS read-write
			STATUS current
			DESCRIPTION
				"Description."
			::= { onuTr069Stun 5 }

		
--         1.3.6.1.4.1.37950.1.1.5.12.8.3.49.2.6
-- 1.3.6.1.4.1.37950.1.1.5.12.8.3.49.2.6
-- 1.3.6.1.4.1.37950.1.1.5.12.8.3.49.2.6
-- 1.3.6.1.4.1.37950.1.1.5.12.8.3.49.2.6
-- 1.3.6.1.4.1.37950.1.1.5.12.8.3.49.2.6
-- 1.3.6.1.4.1.37950.1.1.5.12.8.3.49.2.6
-- 1.3.6.1.4.1.37950.1.1.5.12.8.3.49.2.6
-- 1.3.6.1.4.1.37950.1.1.5.12.8.3.49.2.6
		-- 1.3.6.1.4.1.37950.1.1.5.12.8.3.49.2.6
		stunAction OBJECT-TYPE
			SYNTAX INTEGER
				{
				submit(1),
				remove(2)
				}
			MAX-ACCESS read-write
			STATUS current
			DESCRIPTION
				"Description."
			::= { onuTr069Stun 6 }

		
--          1.3.6.1.4.1.37950.1.1.5.12.8.3.39
-- 1.3.6.1.4.1.37950.1.1.5.12.8.3.39
-- 1.3.6.1.4.1.37950.1.1.5.12.8.3.39
-- 1.3.6.1.4.1.37950.1.1.5.12.8.3.50
-- 1.3.6.1.4.1.37950.1.1.5.12.8.3.50
-- 1.3.6.1.4.1.37950.1.1.5.12.8.3.50
-- 1.3.6.1.4.1.37950.1.1.5.12.8.3.50
-- 1.3.6.1.4.1.37950.1.1.5.12.8.3.50
-- 1.3.6.1.4.1.37950.1.1.5.12.8.3.50
		-- 1.3.6.1.4.1.37950.1.1.5.12.8.3.50
		onuNatType OBJECT IDENTIFIER ::= { srvProfileEdit 50 }

		
--          1.3.6.1.4.1.37950.1.1.5.12.8.3.39.1
-- 1.3.6.1.4.1.37950.1.1.5.12.8.3.39.1
-- 1.3.6.1.4.1.37950.1.1.5.12.8.3.39.1
-- 1.3.6.1.4.1.37950.1.1.5.12.8.3.50.1
-- 1.3.6.1.4.1.37950.1.1.5.12.8.3.50.1
-- 1.3.6.1.4.1.37950.1.1.5.12.8.3.50.1
-- 1.3.6.1.4.1.37950.1.1.5.12.8.3.50.1
-- 1.3.6.1.4.1.37950.1.1.5.12.8.3.50.1
-- 1.3.6.1.4.1.37950.1.1.5.12.8.3.50.1
		-- 1.3.6.1.4.1.37950.1.1.5.12.8.3.50.1
		natType OBJECT-TYPE
			SYNTAX INTEGER
				{
				nat1(1),
				nat2(2),
				nat3(3),
				nat4-napt(4)
				}
			MAX-ACCESS read-write
			STATUS current
			DESCRIPTION
				"Description."
			::= { onuNatType 1 }

		
--          1.3.6.1.4.1.37950.1.1.5.12.8.3.39.2
-- 1.3.6.1.4.1.37950.1.1.5.12.8.3.39.2
-- 1.3.6.1.4.1.37950.1.1.5.12.8.3.39.2
-- 1.3.6.1.4.1.37950.1.1.5.12.8.3.50.2
-- 1.3.6.1.4.1.37950.1.1.5.12.8.3.50.2
-- 1.3.6.1.4.1.37950.1.1.5.12.8.3.50.2
-- 1.3.6.1.4.1.37950.1.1.5.12.8.3.50.2
-- 1.3.6.1.4.1.37950.1.1.5.12.8.3.50.2
-- 1.3.6.1.4.1.37950.1.1.5.12.8.3.50.2
		-- 1.3.6.1.4.1.37950.1.1.5.12.8.3.50.2
		natTypeAction OBJECT-TYPE
			SYNTAX INTEGER
				{
				add(1),
				remove(2)
				}
			MAX-ACCESS read-write
			STATUS current
			DESCRIPTION
				"Description."
			::= { onuNatType 2 }

		
--          1.3.6.1.4.1.37950.1.1.5.12.8.3.39
-- 1.3.6.1.4.1.37950.1.1.5.12.8.3.39
-- 1.3.6.1.4.1.37950.1.1.5.12.8.3.39
-- 1.3.6.1.4.1.37950.1.1.5.12.8.3.51
-- 1.3.6.1.4.1.37950.1.1.5.12.8.3.51
-- 1.3.6.1.4.1.37950.1.1.5.12.8.3.51
-- 1.3.6.1.4.1.37950.1.1.5.12.8.3.51
-- 1.3.6.1.4.1.37950.1.1.5.12.8.3.51
-- 1.3.6.1.4.1.37950.1.1.5.12.8.3.51
		-- 1.3.6.1.4.1.37950.1.1.5.12.8.3.51
		onuUPnP OBJECT IDENTIFIER ::= { srvProfileEdit 51 }

		
--          1.3.6.1.4.1.37950.1.1.5.12.8.3.39.1
-- 1.3.6.1.4.1.37950.1.1.5.12.8.3.39.1
-- 1.3.6.1.4.1.37950.1.1.5.12.8.3.39.1
-- 1.3.6.1.4.1.37950.1.1.5.12.8.3.51.1
-- 1.3.6.1.4.1.37950.1.1.5.12.8.3.51.1
-- 1.3.6.1.4.1.37950.1.1.5.12.8.3.51.1
-- 1.3.6.1.4.1.37950.1.1.5.12.8.3.51.1
-- 1.3.6.1.4.1.37950.1.1.5.12.8.3.51.1
-- 1.3.6.1.4.1.37950.1.1.5.12.8.3.51.1
		-- 1.3.6.1.4.1.37950.1.1.5.12.8.3.51.1
		upnpStatus OBJECT-TYPE
			SYNTAX INTEGER
				{
				disable(0),
				enable(1)
				}
			MAX-ACCESS read-write
			STATUS current
			DESCRIPTION
				"Description."
			::= { onuUPnP 1 }

		
--       1.3.6.1.4.1.37950.1.1.5.12.8.3.51.3
-- 1.3.6.1.4.1.37950.1.1.5.12.8.3.51.3
-- 1.3.6.1.4.1.37950.1.1.5.12.8.3.51.3
-- 1.3.6.1.4.1.37950.1.1.5.12.8.3.51.3
-- 1.3.6.1.4.1.37950.1.1.5.12.8.3.51.3
-- 1.3.6.1.4.1.37950.1.1.5.12.8.3.51.3
		-- 1.3.6.1.4.1.37950.1.1.5.12.8.3.51.3
		upnpWanIndex OBJECT-TYPE
			SYNTAX Integer32 (1..8)
			MAX-ACCESS read-write
			STATUS current
			DESCRIPTION
				"Description."
			::= { onuUPnP 3 }

		
--          1.3.6.1.4.1.37950.1.1.5.12.8.3.39.2
-- 1.3.6.1.4.1.37950.1.1.5.12.8.3.39.2
-- 1.3.6.1.4.1.37950.1.1.5.12.8.3.39.2
-- 1.3.6.1.4.1.37950.1.1.5.12.8.3.51.4
-- 1.3.6.1.4.1.37950.1.1.5.12.8.3.51.4
-- 1.3.6.1.4.1.37950.1.1.5.12.8.3.51.4
-- 1.3.6.1.4.1.37950.1.1.5.12.8.3.51.4
-- 1.3.6.1.4.1.37950.1.1.5.12.8.3.51.4
-- 1.3.6.1.4.1.37950.1.1.5.12.8.3.51.4
		-- 1.3.6.1.4.1.37950.1.1.5.12.8.3.51.4
		upnpAction OBJECT-TYPE
			SYNTAX INTEGER
				{
				add(1),
				remove(2)
				}
			MAX-ACCESS read-write
			STATUS current
			DESCRIPTION
				"Description."
			::= { onuUPnP 4 }

		
--           1.3.6.1.4.1.37950.1.1.5.12.8.4
-- 1.3.6.1.4.1.37950.1.1.5.12.8.4
-- 1.3.6.1.4.1.37950.1.1.5.12.8.4
-- 1.3.6.1.4.1.37950.1.1.5.12.8.4
-- 1.3.6.1.4.1.37950.1.1.5.12.8.4
-- 1.3.6.1.4.1.37950.1.1.5.12.8.4
-- 1.3.6.1.4.1.37950.1.1.5.12.8.4
-- 1.3.6.1.4.1.37950.1.1.5.12.8.4
-- 1.3.6.1.4.1.37950.1.1.5.12.8.4
		-- 1.3.6.1.4.1.37950.1.1.5.12.8.4
		voipProfileEdit OBJECT IDENTIFIER ::= { onuProfileCfg 4 }

		
--          1.3.6.1.4.1.37950.1.1.5.12.8.4.1
-- 1.3.6.1.4.1.37950.1.1.5.12.8.4.1
-- 1.3.6.1.4.1.37950.1.1.5.12.8.4.1
-- 1.3.6.1.4.1.37950.1.1.5.12.8.4.1
-- 1.3.6.1.4.1.37950.1.1.5.12.8.4.1
-- 1.3.6.1.4.1.37950.1.1.5.12.8.4.1
-- 1.3.6.1.4.1.37950.1.1.5.12.8.4.1
-- 1.3.6.1.4.1.37950.1.1.5.12.8.4.1
-- 1.3.6.1.4.1.37950.1.1.5.12.8.4.1
		-- 1.3.6.1.4.1.37950.1.1.5.12.8.4.1
		voipProfileNo OBJECT-TYPE
			SYNTAX INTEGER (1..32767)
			MAX-ACCESS read-write
			STATUS current
			DESCRIPTION
				"Description."
			::= { voipProfileEdit 1 }

		
--          1.3.6.1.4.1.37950.1.1.5.12.8.4.2
-- 1.3.6.1.4.1.37950.1.1.5.12.8.4.2
-- 1.3.6.1.4.1.37950.1.1.5.12.8.4.2
-- 1.3.6.1.4.1.37950.1.1.5.12.8.4.2
-- 1.3.6.1.4.1.37950.1.1.5.12.8.4.2
-- 1.3.6.1.4.1.37950.1.1.5.12.8.4.2
-- 1.3.6.1.4.1.37950.1.1.5.12.8.4.2
-- 1.3.6.1.4.1.37950.1.1.5.12.8.4.2
-- 1.3.6.1.4.1.37950.1.1.5.12.8.4.2
		-- 1.3.6.1.4.1.37950.1.1.5.12.8.4.2
		onuPotsCountConfig OBJECT IDENTIFIER ::= { voipProfileEdit 2 }

		
--          1.3.6.1.4.1.37950.1.1.5.12.8.4.2.1
-- 1.3.6.1.4.1.37950.1.1.5.12.8.4.2.1
-- 1.3.6.1.4.1.37950.1.1.5.12.8.4.2.1
-- 1.3.6.1.4.1.37950.1.1.5.12.8.4.2.1
-- 1.3.6.1.4.1.37950.1.1.5.12.8.4.2.1
-- 1.3.6.1.4.1.37950.1.1.5.12.8.4.2.1
-- 1.3.6.1.4.1.37950.1.1.5.12.8.4.2.1
-- 1.3.6.1.4.1.37950.1.1.5.12.8.4.2.1
-- 1.3.6.1.4.1.37950.1.1.5.12.8.4.2.1
		-- 1.3.6.1.4.1.37950.1.1.5.12.8.4.2.1
		potsCount OBJECT-TYPE
			SYNTAX INTEGER (0..255)
			MAX-ACCESS read-write
			STATUS current
			DESCRIPTION
				"Description."
			::= { onuPotsCountConfig 1 }

		
--          1.3.6.1.4.1.37950.1.1.5.12.8.4.2.2
-- 1.3.6.1.4.1.37950.1.1.5.12.8.4.2.2
-- 1.3.6.1.4.1.37950.1.1.5.12.8.4.2.2
-- 1.3.6.1.4.1.37950.1.1.5.12.8.4.2.2
-- 1.3.6.1.4.1.37950.1.1.5.12.8.4.2.2
-- 1.3.6.1.4.1.37950.1.1.5.12.8.4.2.2
-- 1.3.6.1.4.1.37950.1.1.5.12.8.4.2.2
-- 1.3.6.1.4.1.37950.1.1.5.12.8.4.2.2
-- 1.3.6.1.4.1.37950.1.1.5.12.8.4.2.2
		-- 1.3.6.1.4.1.37950.1.1.5.12.8.4.2.2
		potsCountAction OBJECT-TYPE
			SYNTAX INTEGER
				{
				commit(1),
				remove(2)
				}
			MAX-ACCESS read-write
			STATUS current
			DESCRIPTION
				"Description."
			::= { onuPotsCountConfig 2 }

		
--          1.3.6.1.4.1.37950.1.1.5.12.8.4.3
-- 1.3.6.1.4.1.37950.1.1.5.12.8.4.3
-- 1.3.6.1.4.1.37950.1.1.5.12.8.4.3
-- 1.3.6.1.4.1.37950.1.1.5.12.8.4.3
-- 1.3.6.1.4.1.37950.1.1.5.12.8.4.3
-- 1.3.6.1.4.1.37950.1.1.5.12.8.4.3
-- 1.3.6.1.4.1.37950.1.1.5.12.8.4.3
-- 1.3.6.1.4.1.37950.1.1.5.12.8.4.3
-- 1.3.6.1.4.1.37950.1.1.5.12.8.4.3
		-- 1.3.6.1.4.1.37950.1.1.5.12.8.4.3
		voipGlobalConfig OBJECT IDENTIFIER ::= { voipProfileEdit 3 }

		
--          1.3.6.1.4.1.37950.1.1.5.12.8.4.3.1
-- 1.3.6.1.4.1.37950.1.1.5.12.8.4.3.1
-- 1.3.6.1.4.1.37950.1.1.5.12.8.4.3.1
-- 1.3.6.1.4.1.37950.1.1.5.12.8.4.3.1
-- 1.3.6.1.4.1.37950.1.1.5.12.8.4.3.1
-- 1.3.6.1.4.1.37950.1.1.5.12.8.4.3.1
-- 1.3.6.1.4.1.37950.1.1.5.12.8.4.3.1
-- 1.3.6.1.4.1.37950.1.1.5.12.8.4.3.1
-- 1.3.6.1.4.1.37950.1.1.5.12.8.4.3.1
		-- 1.3.6.1.4.1.37950.1.1.5.12.8.4.3.1
		ctcIpMode OBJECT-TYPE
			SYNTAX INTEGER
				{
				staticip(0),
				dhcp(1),
				pppoe(2)
				}
			MAX-ACCESS read-write
			STATUS current
			DESCRIPTION
				"Description."
			::= { voipGlobalConfig 1 }

		
--          1.3.6.1.4.1.37950.1.1.5.12.8.4.3.2
-- 1.3.6.1.4.1.37950.1.1.5.12.8.4.3.2
-- 1.3.6.1.4.1.37950.1.1.5.12.8.4.3.2
-- 1.3.6.1.4.1.37950.1.1.5.12.8.4.3.2
-- 1.3.6.1.4.1.37950.1.1.5.12.8.4.3.2
-- 1.3.6.1.4.1.37950.1.1.5.12.8.4.3.2
-- 1.3.6.1.4.1.37950.1.1.5.12.8.4.3.2
-- 1.3.6.1.4.1.37950.1.1.5.12.8.4.3.2
-- 1.3.6.1.4.1.37950.1.1.5.12.8.4.3.2
		-- 1.3.6.1.4.1.37950.1.1.5.12.8.4.3.2
		ctcStaticIpAddr OBJECT-TYPE
			SYNTAX IpAddress
			MAX-ACCESS read-write
			STATUS current
			DESCRIPTION
				"Description."
			::= { voipGlobalConfig 2 }

		
--          1.3.6.1.4.1.37950.1.1.5.12.8.4.3.3
-- 1.3.6.1.4.1.37950.1.1.5.12.8.4.3.3
-- 1.3.6.1.4.1.37950.1.1.5.12.8.4.3.3
-- 1.3.6.1.4.1.37950.1.1.5.12.8.4.3.3
-- 1.3.6.1.4.1.37950.1.1.5.12.8.4.3.3
-- 1.3.6.1.4.1.37950.1.1.5.12.8.4.3.3
-- 1.3.6.1.4.1.37950.1.1.5.12.8.4.3.3
-- 1.3.6.1.4.1.37950.1.1.5.12.8.4.3.3
-- 1.3.6.1.4.1.37950.1.1.5.12.8.4.3.3
		-- 1.3.6.1.4.1.37950.1.1.5.12.8.4.3.3
		ctcStaticIpMask OBJECT-TYPE
			SYNTAX IpAddress
			MAX-ACCESS read-write
			STATUS current
			DESCRIPTION
				"Description."
			::= { voipGlobalConfig 3 }

		
--          1.3.6.1.4.1.37950.1.1.5.12.8.4.3.4
-- 1.3.6.1.4.1.37950.1.1.5.12.8.4.3.4
-- 1.3.6.1.4.1.37950.1.1.5.12.8.4.3.4
-- 1.3.6.1.4.1.37950.1.1.5.12.8.4.3.4
-- 1.3.6.1.4.1.37950.1.1.5.12.8.4.3.4
-- 1.3.6.1.4.1.37950.1.1.5.12.8.4.3.4
-- 1.3.6.1.4.1.37950.1.1.5.12.8.4.3.4
-- 1.3.6.1.4.1.37950.1.1.5.12.8.4.3.4
-- 1.3.6.1.4.1.37950.1.1.5.12.8.4.3.4
		-- 1.3.6.1.4.1.37950.1.1.5.12.8.4.3.4
		ctcStaticIpGw OBJECT-TYPE
			SYNTAX IpAddress
			MAX-ACCESS read-write
			STATUS current
			DESCRIPTION
				"Description."
			::= { voipGlobalConfig 4 }

		
--          1.3.6.1.4.1.37950.1.1.5.12.8.4.3.5
-- 1.3.6.1.4.1.37950.1.1.5.12.8.4.3.5
-- 1.3.6.1.4.1.37950.1.1.5.12.8.4.3.5
-- 1.3.6.1.4.1.37950.1.1.5.12.8.4.3.5
-- 1.3.6.1.4.1.37950.1.1.5.12.8.4.3.5
-- 1.3.6.1.4.1.37950.1.1.5.12.8.4.3.5
-- 1.3.6.1.4.1.37950.1.1.5.12.8.4.3.5
-- 1.3.6.1.4.1.37950.1.1.5.12.8.4.3.5
-- 1.3.6.1.4.1.37950.1.1.5.12.8.4.3.5
		-- 1.3.6.1.4.1.37950.1.1.5.12.8.4.3.5
		ctcPppoeMode OBJECT-TYPE
			SYNTAX INTEGER
				{
				auto(1),
				chap(2),
				pap(3)
				}
			MAX-ACCESS read-write
			STATUS current
			DESCRIPTION
				"Description."
			::= { voipGlobalConfig 5 }

		
--          1.3.6.1.4.1.37950.1.1.5.12.8.4.3.6
-- 1.3.6.1.4.1.37950.1.1.5.12.8.4.3.6
-- 1.3.6.1.4.1.37950.1.1.5.12.8.4.3.6
-- 1.3.6.1.4.1.37950.1.1.5.12.8.4.3.6
-- 1.3.6.1.4.1.37950.1.1.5.12.8.4.3.6
-- 1.3.6.1.4.1.37950.1.1.5.12.8.4.3.6
-- 1.3.6.1.4.1.37950.1.1.5.12.8.4.3.6
-- 1.3.6.1.4.1.37950.1.1.5.12.8.4.3.6
-- 1.3.6.1.4.1.37950.1.1.5.12.8.4.3.6
		-- 1.3.6.1.4.1.37950.1.1.5.12.8.4.3.6
		ctcPppoeUsr OBJECT-TYPE
			SYNTAX OCTET STRING
			MAX-ACCESS read-write
			STATUS current
			DESCRIPTION
				"Description."
			::= { voipGlobalConfig 6 }

		
--          1.3.6.1.4.1.37950.1.1.5.12.8.4.3.7
-- 1.3.6.1.4.1.37950.1.1.5.12.8.4.3.7
-- 1.3.6.1.4.1.37950.1.1.5.12.8.4.3.7
-- 1.3.6.1.4.1.37950.1.1.5.12.8.4.3.7
-- 1.3.6.1.4.1.37950.1.1.5.12.8.4.3.7
-- 1.3.6.1.4.1.37950.1.1.5.12.8.4.3.7
-- 1.3.6.1.4.1.37950.1.1.5.12.8.4.3.7
-- 1.3.6.1.4.1.37950.1.1.5.12.8.4.3.7
-- 1.3.6.1.4.1.37950.1.1.5.12.8.4.3.7
		-- 1.3.6.1.4.1.37950.1.1.5.12.8.4.3.7
		ctcPppoePw OBJECT-TYPE
			SYNTAX OCTET STRING
			MAX-ACCESS read-write
			STATUS current
			DESCRIPTION
				"Description."
			::= { voipGlobalConfig 7 }

		
--          1.3.6.1.4.1.37950.1.1.5.12.8.4.3.8
-- 1.3.6.1.4.1.37950.1.1.5.12.8.4.3.8
-- 1.3.6.1.4.1.37950.1.1.5.12.8.4.3.8
-- 1.3.6.1.4.1.37950.1.1.5.12.8.4.3.8
-- 1.3.6.1.4.1.37950.1.1.5.12.8.4.3.8
-- 1.3.6.1.4.1.37950.1.1.5.12.8.4.3.8
-- 1.3.6.1.4.1.37950.1.1.5.12.8.4.3.8
-- 1.3.6.1.4.1.37950.1.1.5.12.8.4.3.8
-- 1.3.6.1.4.1.37950.1.1.5.12.8.4.3.8
		-- 1.3.6.1.4.1.37950.1.1.5.12.8.4.3.8
		voipVlanMode OBJECT-TYPE
			SYNTAX INTEGER
				{
				transparent(1),
				tag(2),
				vlan-stacking(3)
				}
			MAX-ACCESS read-write
			STATUS current
			DESCRIPTION
				"Description."
			::= { voipGlobalConfig 8 }

		
--          1.3.6.1.4.1.37950.1.1.5.12.8.4.3.9
-- 1.3.6.1.4.1.37950.1.1.5.12.8.4.3.9
-- 1.3.6.1.4.1.37950.1.1.5.12.8.4.3.9
-- 1.3.6.1.4.1.37950.1.1.5.12.8.4.3.9
-- 1.3.6.1.4.1.37950.1.1.5.12.8.4.3.9
-- 1.3.6.1.4.1.37950.1.1.5.12.8.4.3.9
-- 1.3.6.1.4.1.37950.1.1.5.12.8.4.3.9
-- 1.3.6.1.4.1.37950.1.1.5.12.8.4.3.9
-- 1.3.6.1.4.1.37950.1.1.5.12.8.4.3.9
		-- 1.3.6.1.4.1.37950.1.1.5.12.8.4.3.9
		voipCvlan OBJECT-TYPE
			SYNTAX INTEGER (0..4095)
			MAX-ACCESS read-write
			STATUS current
			DESCRIPTION
				"Description."
			::= { voipGlobalConfig 9 }

		
--          1.3.6.1.4.1.37950.1.1.5.12.8.4.3.10
-- 1.3.6.1.4.1.37950.1.1.5.12.8.4.3.10
-- 1.3.6.1.4.1.37950.1.1.5.12.8.4.3.10
-- 1.3.6.1.4.1.37950.1.1.5.12.8.4.3.10
-- 1.3.6.1.4.1.37950.1.1.5.12.8.4.3.10
-- 1.3.6.1.4.1.37950.1.1.5.12.8.4.3.10
-- 1.3.6.1.4.1.37950.1.1.5.12.8.4.3.10
-- 1.3.6.1.4.1.37950.1.1.5.12.8.4.3.10
-- 1.3.6.1.4.1.37950.1.1.5.12.8.4.3.10
		-- 1.3.6.1.4.1.37950.1.1.5.12.8.4.3.10
		voipSvlan OBJECT-TYPE
			SYNTAX INTEGER (0..4095)
			MAX-ACCESS read-write
			STATUS current
			DESCRIPTION
				"Description."
			DEFVAL { 0 }
			::= { voipGlobalConfig 10 }

		
--          1.3.6.1.4.1.37950.1.1.5.12.8.4.3.11
-- 1.3.6.1.4.1.37950.1.1.5.12.8.4.3.11
-- 1.3.6.1.4.1.37950.1.1.5.12.8.4.3.11
-- 1.3.6.1.4.1.37950.1.1.5.12.8.4.3.11
-- 1.3.6.1.4.1.37950.1.1.5.12.8.4.3.11
-- 1.3.6.1.4.1.37950.1.1.5.12.8.4.3.11
-- 1.3.6.1.4.1.37950.1.1.5.12.8.4.3.11
-- 1.3.6.1.4.1.37950.1.1.5.12.8.4.3.11
-- 1.3.6.1.4.1.37950.1.1.5.12.8.4.3.11
		-- 1.3.6.1.4.1.37950.1.1.5.12.8.4.3.11
		voipPri OBJECT-TYPE
			SYNTAX INTEGER (0..7)
			MAX-ACCESS read-write
			STATUS current
			DESCRIPTION
				"Description."
			DEFVAL { 5 }
			::= { voipGlobalConfig 11 }

		
--          1.3.6.1.4.1.37950.1.1.5.12.8.4.3.12
-- 1.3.6.1.4.1.37950.1.1.5.12.8.4.3.12
-- 1.3.6.1.4.1.37950.1.1.5.12.8.4.3.12
-- 1.3.6.1.4.1.37950.1.1.5.12.8.4.3.12
-- 1.3.6.1.4.1.37950.1.1.5.12.8.4.3.12
-- 1.3.6.1.4.1.37950.1.1.5.12.8.4.3.12
-- 1.3.6.1.4.1.37950.1.1.5.12.8.4.3.12
-- 1.3.6.1.4.1.37950.1.1.5.12.8.4.3.12
-- 1.3.6.1.4.1.37950.1.1.5.12.8.4.3.12
		-- 1.3.6.1.4.1.37950.1.1.5.12.8.4.3.12
		ctcVoipGlobalAction OBJECT-TYPE
			SYNTAX INTEGER
				{
				add(1),
				remove(2)
				}
			MAX-ACCESS read-write
			STATUS current
			DESCRIPTION
				"Description."
			DEFVAL { 1 }
			::= { voipGlobalConfig 12 }

		
--          1.3.6.1.4.1.37950.1.1.5.12.8.4.4
-- 1.3.6.1.4.1.37950.1.1.5.12.8.4.4
-- 1.3.6.1.4.1.37950.1.1.5.12.8.4.4
-- 1.3.6.1.4.1.37950.1.1.5.12.8.4.4
-- 1.3.6.1.4.1.37950.1.1.5.12.8.4.4
-- 1.3.6.1.4.1.37950.1.1.5.12.8.4.4
-- 1.3.6.1.4.1.37950.1.1.5.12.8.4.4
-- 1.3.6.1.4.1.37950.1.1.5.12.8.4.4
-- 1.3.6.1.4.1.37950.1.1.5.12.8.4.4
		-- 1.3.6.1.4.1.37950.1.1.5.12.8.4.4
		voipH248Config OBJECT IDENTIFIER ::= { voipProfileEdit 4 }

		
--          1.3.6.1.4.1.37950.1.1.5.12.8.4.4.1
-- 1.3.6.1.4.1.37950.1.1.5.12.8.4.4.1
-- 1.3.6.1.4.1.37950.1.1.5.12.8.4.4.1
-- 1.3.6.1.4.1.37950.1.1.5.12.8.4.4.1
-- 1.3.6.1.4.1.37950.1.1.5.12.8.4.4.1
-- 1.3.6.1.4.1.37950.1.1.5.12.8.4.4.1
-- 1.3.6.1.4.1.37950.1.1.5.12.8.4.4.1
-- 1.3.6.1.4.1.37950.1.1.5.12.8.4.4.1
-- 1.3.6.1.4.1.37950.1.1.5.12.8.4.4.1
		-- 1.3.6.1.4.1.37950.1.1.5.12.8.4.4.1
		h248ProParamConfig OBJECT IDENTIFIER ::= { voipH248Config 1 }

		
--          1.3.6.1.4.1.37950.1.1.5.12.8.4.4.1.1
-- 1.3.6.1.4.1.37950.1.1.5.12.8.4.4.1.1
-- 1.3.6.1.4.1.37950.1.1.5.12.8.4.4.1.1
-- 1.3.6.1.4.1.37950.1.1.5.12.8.4.4.1.1
-- 1.3.6.1.4.1.37950.1.1.5.12.8.4.4.1.1
-- 1.3.6.1.4.1.37950.1.1.5.12.8.4.4.1.1
-- 1.3.6.1.4.1.37950.1.1.5.12.8.4.4.1.1
-- 1.3.6.1.4.1.37950.1.1.5.12.8.4.4.1.1
-- 1.3.6.1.4.1.37950.1.1.5.12.8.4.4.1.1
		-- 1.3.6.1.4.1.37950.1.1.5.12.8.4.4.1.1
		ctcMgPort OBJECT-TYPE
			SYNTAX INTEGER (1..65535)
			MAX-ACCESS read-write
			STATUS current
			DESCRIPTION
				"Description."
			DEFVAL { 2944 }
			::= { h248ProParamConfig 1 }

		
--          1.3.6.1.4.1.37950.1.1.5.12.8.4.4.1.2
-- 1.3.6.1.4.1.37950.1.1.5.12.8.4.4.1.2
-- 1.3.6.1.4.1.37950.1.1.5.12.8.4.4.1.2
-- 1.3.6.1.4.1.37950.1.1.5.12.8.4.4.1.2
-- 1.3.6.1.4.1.37950.1.1.5.12.8.4.4.1.2
-- 1.3.6.1.4.1.37950.1.1.5.12.8.4.4.1.2
-- 1.3.6.1.4.1.37950.1.1.5.12.8.4.4.1.2
-- 1.3.6.1.4.1.37950.1.1.5.12.8.4.4.1.2
-- 1.3.6.1.4.1.37950.1.1.5.12.8.4.4.1.2
		-- 1.3.6.1.4.1.37950.1.1.5.12.8.4.4.1.2
		ctcMgcIp OBJECT-TYPE
			SYNTAX IpAddress
			MAX-ACCESS read-write
			STATUS current
			DESCRIPTION
				"Description."
			::= { h248ProParamConfig 2 }

		
--          1.3.6.1.4.1.37950.1.1.5.12.8.4.4.1.3
-- 1.3.6.1.4.1.37950.1.1.5.12.8.4.4.1.3
-- 1.3.6.1.4.1.37950.1.1.5.12.8.4.4.1.3
-- 1.3.6.1.4.1.37950.1.1.5.12.8.4.4.1.3
-- 1.3.6.1.4.1.37950.1.1.5.12.8.4.4.1.3
-- 1.3.6.1.4.1.37950.1.1.5.12.8.4.4.1.3
-- 1.3.6.1.4.1.37950.1.1.5.12.8.4.4.1.3
-- 1.3.6.1.4.1.37950.1.1.5.12.8.4.4.1.3
-- 1.3.6.1.4.1.37950.1.1.5.12.8.4.4.1.3
		-- 1.3.6.1.4.1.37950.1.1.5.12.8.4.4.1.3
		ctcMgComPort OBJECT-TYPE
			SYNTAX INTEGER (1..65535)
			MAX-ACCESS read-write
			STATUS current
			DESCRIPTION
				"Description."
			::= { h248ProParamConfig 3 }

		
--          1.3.6.1.4.1.37950.1.1.5.12.8.4.4.1.4
-- 1.3.6.1.4.1.37950.1.1.5.12.8.4.4.1.4
-- 1.3.6.1.4.1.37950.1.1.5.12.8.4.4.1.4
-- 1.3.6.1.4.1.37950.1.1.5.12.8.4.4.1.4
-- 1.3.6.1.4.1.37950.1.1.5.12.8.4.4.1.4
-- 1.3.6.1.4.1.37950.1.1.5.12.8.4.4.1.4
-- 1.3.6.1.4.1.37950.1.1.5.12.8.4.4.1.4
-- 1.3.6.1.4.1.37950.1.1.5.12.8.4.4.1.4
-- 1.3.6.1.4.1.37950.1.1.5.12.8.4.4.1.4
		-- 1.3.6.1.4.1.37950.1.1.5.12.8.4.4.1.4
		ctcBakMgcIp OBJECT-TYPE
			SYNTAX IpAddress
			MAX-ACCESS read-write
			STATUS current
			DESCRIPTION
				"Description."
			::= { h248ProParamConfig 4 }

		
--          1.3.6.1.4.1.37950.1.1.5.12.8.4.4.1.5
-- 1.3.6.1.4.1.37950.1.1.5.12.8.4.4.1.5
-- 1.3.6.1.4.1.37950.1.1.5.12.8.4.4.1.5
-- 1.3.6.1.4.1.37950.1.1.5.12.8.4.4.1.5
-- 1.3.6.1.4.1.37950.1.1.5.12.8.4.4.1.5
-- 1.3.6.1.4.1.37950.1.1.5.12.8.4.4.1.5
-- 1.3.6.1.4.1.37950.1.1.5.12.8.4.4.1.5
-- 1.3.6.1.4.1.37950.1.1.5.12.8.4.4.1.5
-- 1.3.6.1.4.1.37950.1.1.5.12.8.4.4.1.5
		-- 1.3.6.1.4.1.37950.1.1.5.12.8.4.4.1.5
		ctcBakMgcPort OBJECT-TYPE
			SYNTAX INTEGER (0..65535)
			MAX-ACCESS read-write
			STATUS current
			DESCRIPTION
				"Description."
			DEFVAL { 0 }
			::= { h248ProParamConfig 5 }

		
--          1.3.6.1.4.1.37950.1.1.5.12.8.4.4.1.6
-- 1.3.6.1.4.1.37950.1.1.5.12.8.4.4.1.6
-- 1.3.6.1.4.1.37950.1.1.5.12.8.4.4.1.6
-- 1.3.6.1.4.1.37950.1.1.5.12.8.4.4.1.6
-- 1.3.6.1.4.1.37950.1.1.5.12.8.4.4.1.6
-- 1.3.6.1.4.1.37950.1.1.5.12.8.4.4.1.6
-- 1.3.6.1.4.1.37950.1.1.5.12.8.4.4.1.6
-- 1.3.6.1.4.1.37950.1.1.5.12.8.4.4.1.6
-- 1.3.6.1.4.1.37950.1.1.5.12.8.4.4.1.6
		-- 1.3.6.1.4.1.37950.1.1.5.12.8.4.4.1.6
		ctcRegMode OBJECT-TYPE
			SYNTAX INTEGER
				{
				ip-addr(0),
				realm(1),
				device(2)
				}
			MAX-ACCESS read-write
			STATUS current
			DESCRIPTION
				"Description."
			DEFVAL { 0 }
			::= { h248ProParamConfig 6 }

		
--          1.3.6.1.4.1.37950.1.1.5.12.8.4.4.1.7
-- 1.3.6.1.4.1.37950.1.1.5.12.8.4.4.1.7
-- 1.3.6.1.4.1.37950.1.1.5.12.8.4.4.1.7
-- 1.3.6.1.4.1.37950.1.1.5.12.8.4.4.1.7
-- 1.3.6.1.4.1.37950.1.1.5.12.8.4.4.1.7
-- 1.3.6.1.4.1.37950.1.1.5.12.8.4.4.1.7
-- 1.3.6.1.4.1.37950.1.1.5.12.8.4.4.1.7
-- 1.3.6.1.4.1.37950.1.1.5.12.8.4.4.1.7
-- 1.3.6.1.4.1.37950.1.1.5.12.8.4.4.1.7
		-- 1.3.6.1.4.1.37950.1.1.5.12.8.4.4.1.7
		ctcMID OBJECT-TYPE
			SYNTAX OCTET STRING
			MAX-ACCESS read-write
			STATUS current
			DESCRIPTION
				"Description."
			::= { h248ProParamConfig 7 }

		
--          1.3.6.1.4.1.37950.1.1.5.12.8.4.4.1.8
-- 1.3.6.1.4.1.37950.1.1.5.12.8.4.4.1.8
-- 1.3.6.1.4.1.37950.1.1.5.12.8.4.4.1.8
-- 1.3.6.1.4.1.37950.1.1.5.12.8.4.4.1.8
-- 1.3.6.1.4.1.37950.1.1.5.12.8.4.4.1.8
-- 1.3.6.1.4.1.37950.1.1.5.12.8.4.4.1.8
-- 1.3.6.1.4.1.37950.1.1.5.12.8.4.4.1.8
-- 1.3.6.1.4.1.37950.1.1.5.12.8.4.4.1.8
-- 1.3.6.1.4.1.37950.1.1.5.12.8.4.4.1.8
		-- 1.3.6.1.4.1.37950.1.1.5.12.8.4.4.1.8
		ctcHeartbeatMode OBJECT-TYPE
			SYNTAX INTEGER
				{
				disable(0),
				h248(1)
				}
			MAX-ACCESS read-write
			STATUS current
			DESCRIPTION
				"Description."
			::= { h248ProParamConfig 8 }

		
--          1.3.6.1.4.1.37950.1.1.5.12.8.4.4.1.9
-- 1.3.6.1.4.1.37950.1.1.5.12.8.4.4.1.9
-- 1.3.6.1.4.1.37950.1.1.5.12.8.4.4.1.9
-- 1.3.6.1.4.1.37950.1.1.5.12.8.4.4.1.9
-- 1.3.6.1.4.1.37950.1.1.5.12.8.4.4.1.9
-- 1.3.6.1.4.1.37950.1.1.5.12.8.4.4.1.9
-- 1.3.6.1.4.1.37950.1.1.5.12.8.4.4.1.9
-- 1.3.6.1.4.1.37950.1.1.5.12.8.4.4.1.9
-- 1.3.6.1.4.1.37950.1.1.5.12.8.4.4.1.9
		-- 1.3.6.1.4.1.37950.1.1.5.12.8.4.4.1.9
		ctcHeartbeatCycle OBJECT-TYPE
			SYNTAX INTEGER (1..65535)
			MAX-ACCESS read-write
			STATUS current
			DESCRIPTION
				"Description."
			DEFVAL { 60 }
			::= { h248ProParamConfig 9 }

		
--          1.3.6.1.4.1.37950.1.1.5.12.8.4.4.1.10
-- 1.3.6.1.4.1.37950.1.1.5.12.8.4.4.1.10
-- 1.3.6.1.4.1.37950.1.1.5.12.8.4.4.1.10
-- 1.3.6.1.4.1.37950.1.1.5.12.8.4.4.1.10
-- 1.3.6.1.4.1.37950.1.1.5.12.8.4.4.1.10
-- 1.3.6.1.4.1.37950.1.1.5.12.8.4.4.1.10
-- 1.3.6.1.4.1.37950.1.1.5.12.8.4.4.1.10
-- 1.3.6.1.4.1.37950.1.1.5.12.8.4.4.1.10
-- 1.3.6.1.4.1.37950.1.1.5.12.8.4.4.1.10
		-- 1.3.6.1.4.1.37950.1.1.5.12.8.4.4.1.10
		ctcHeartbeatCount OBJECT-TYPE
			SYNTAX INTEGER (1..65535)
			MAX-ACCESS read-write
			STATUS current
			DESCRIPTION
				"Description."
			DEFVAL { 3 }
			::= { h248ProParamConfig 10 }

		
--          1.3.6.1.4.1.37950.1.1.5.12.8.4.4.1.11
-- 1.3.6.1.4.1.37950.1.1.5.12.8.4.4.1.11
-- 1.3.6.1.4.1.37950.1.1.5.12.8.4.4.1.11
-- 1.3.6.1.4.1.37950.1.1.5.12.8.4.4.1.11
-- 1.3.6.1.4.1.37950.1.1.5.12.8.4.4.1.11
-- 1.3.6.1.4.1.37950.1.1.5.12.8.4.4.1.11
-- 1.3.6.1.4.1.37950.1.1.5.12.8.4.4.1.11
-- 1.3.6.1.4.1.37950.1.1.5.12.8.4.4.1.11
-- 1.3.6.1.4.1.37950.1.1.5.12.8.4.4.1.11
		-- 1.3.6.1.4.1.37950.1.1.5.12.8.4.4.1.11
		ctcH248ProParamAction OBJECT-TYPE
			SYNTAX INTEGER
				{
				add(1),
				remove(2)
				}
			MAX-ACCESS read-write
			STATUS current
			DESCRIPTION
				"Description."
			::= { h248ProParamConfig 11 }

		
--          1.3.6.1.4.1.37950.1.1.5.12.8.4.4.2
-- 1.3.6.1.4.1.37950.1.1.5.12.8.4.4.2
-- 1.3.6.1.4.1.37950.1.1.5.12.8.4.4.2
-- 1.3.6.1.4.1.37950.1.1.5.12.8.4.4.2
-- 1.3.6.1.4.1.37950.1.1.5.12.8.4.4.2
-- 1.3.6.1.4.1.37950.1.1.5.12.8.4.4.2
-- 1.3.6.1.4.1.37950.1.1.5.12.8.4.4.2
-- 1.3.6.1.4.1.37950.1.1.5.12.8.4.4.2
-- 1.3.6.1.4.1.37950.1.1.5.12.8.4.4.2
		-- 1.3.6.1.4.1.37950.1.1.5.12.8.4.4.2
		h248RtpTidConfig OBJECT IDENTIFIER ::= { voipH248Config 2 }

		
--          1.3.6.1.4.1.37950.1.1.5.12.8.4.4.2.1
-- 1.3.6.1.4.1.37950.1.1.5.12.8.4.4.2.1
-- 1.3.6.1.4.1.37950.1.1.5.12.8.4.4.2.1
-- 1.3.6.1.4.1.37950.1.1.5.12.8.4.4.2.1
-- 1.3.6.1.4.1.37950.1.1.5.12.8.4.4.2.1
-- 1.3.6.1.4.1.37950.1.1.5.12.8.4.4.2.1
-- 1.3.6.1.4.1.37950.1.1.5.12.8.4.4.2.1
-- 1.3.6.1.4.1.37950.1.1.5.12.8.4.4.2.1
-- 1.3.6.1.4.1.37950.1.1.5.12.8.4.4.2.1
		-- 1.3.6.1.4.1.37950.1.1.5.12.8.4.4.2.1
		ctcRtpTidNumber OBJECT-TYPE
			SYNTAX INTEGER (0..255)
			MAX-ACCESS read-write
			STATUS current
			DESCRIPTION
				"Description."
			::= { h248RtpTidConfig 1 }

		
--          1.3.6.1.4.1.37950.1.1.5.12.8.4.4.2.2
-- 1.3.6.1.4.1.37950.1.1.5.12.8.4.4.2.2
-- 1.3.6.1.4.1.37950.1.1.5.12.8.4.4.2.2
-- 1.3.6.1.4.1.37950.1.1.5.12.8.4.4.2.2
-- 1.3.6.1.4.1.37950.1.1.5.12.8.4.4.2.2
-- 1.3.6.1.4.1.37950.1.1.5.12.8.4.4.2.2
-- 1.3.6.1.4.1.37950.1.1.5.12.8.4.4.2.2
-- 1.3.6.1.4.1.37950.1.1.5.12.8.4.4.2.2
-- 1.3.6.1.4.1.37950.1.1.5.12.8.4.4.2.2
		-- 1.3.6.1.4.1.37950.1.1.5.12.8.4.4.2.2
		ctcRtpTidPrefix OBJECT-TYPE
			SYNTAX OCTET STRING
			MAX-ACCESS read-write
			STATUS current
			DESCRIPTION
				"Description."
			::= { h248RtpTidConfig 2 }

		
--          1.3.6.1.4.1.37950.1.1.5.12.8.4.4.2.3
-- 1.3.6.1.4.1.37950.1.1.5.12.8.4.4.2.3
-- 1.3.6.1.4.1.37950.1.1.5.12.8.4.4.2.3
-- 1.3.6.1.4.1.37950.1.1.5.12.8.4.4.2.3
-- 1.3.6.1.4.1.37950.1.1.5.12.8.4.4.2.3
-- 1.3.6.1.4.1.37950.1.1.5.12.8.4.4.2.3
-- 1.3.6.1.4.1.37950.1.1.5.12.8.4.4.2.3
-- 1.3.6.1.4.1.37950.1.1.5.12.8.4.4.2.3
-- 1.3.6.1.4.1.37950.1.1.5.12.8.4.4.2.3
		-- 1.3.6.1.4.1.37950.1.1.5.12.8.4.4.2.3
		ctcDigitBegin0 OBJECT-TYPE
			SYNTAX Unsigned32 (0..4294967295)
			MAX-ACCESS read-write
			STATUS current
			DESCRIPTION
				"Description."
			::= { h248RtpTidConfig 3 }

		
--          1.3.6.1.4.1.37950.1.1.5.12.8.4.4.2.4
-- 1.3.6.1.4.1.37950.1.1.5.12.8.4.4.2.4
-- 1.3.6.1.4.1.37950.1.1.5.12.8.4.4.2.4
-- 1.3.6.1.4.1.37950.1.1.5.12.8.4.4.2.4
-- 1.3.6.1.4.1.37950.1.1.5.12.8.4.4.2.4
-- 1.3.6.1.4.1.37950.1.1.5.12.8.4.4.2.4
-- 1.3.6.1.4.1.37950.1.1.5.12.8.4.4.2.4
-- 1.3.6.1.4.1.37950.1.1.5.12.8.4.4.2.4
-- 1.3.6.1.4.1.37950.1.1.5.12.8.4.4.2.4
		-- 1.3.6.1.4.1.37950.1.1.5.12.8.4.4.2.4
		ctcDigitBegin1 OBJECT-TYPE
			SYNTAX Unsigned32 (0..4294967295)
			MAX-ACCESS read-write
			STATUS current
			DESCRIPTION
				"Description."
			::= { h248RtpTidConfig 4 }

		
--          1.3.6.1.4.1.37950.1.1.5.12.8.4.4.2.5
-- 1.3.6.1.4.1.37950.1.1.5.12.8.4.4.2.5
-- 1.3.6.1.4.1.37950.1.1.5.12.8.4.4.2.5
-- 1.3.6.1.4.1.37950.1.1.5.12.8.4.4.2.5
-- 1.3.6.1.4.1.37950.1.1.5.12.8.4.4.2.5
-- 1.3.6.1.4.1.37950.1.1.5.12.8.4.4.2.5
-- 1.3.6.1.4.1.37950.1.1.5.12.8.4.4.2.5
-- 1.3.6.1.4.1.37950.1.1.5.12.8.4.4.2.5
-- 1.3.6.1.4.1.37950.1.1.5.12.8.4.4.2.5
		-- 1.3.6.1.4.1.37950.1.1.5.12.8.4.4.2.5
		ctcRtpTidMode OBJECT-TYPE
			SYNTAX INTEGER
				{
				align(1),
				unalign(2)
				}
			MAX-ACCESS read-write
			STATUS current
			DESCRIPTION
				"Description."
			::= { h248RtpTidConfig 5 }

		
--          1.3.6.1.4.1.37950.1.1.5.12.8.4.4.2.6
-- 1.3.6.1.4.1.37950.1.1.5.12.8.4.4.2.6
-- 1.3.6.1.4.1.37950.1.1.5.12.8.4.4.2.6
-- 1.3.6.1.4.1.37950.1.1.5.12.8.4.4.2.6
-- 1.3.6.1.4.1.37950.1.1.5.12.8.4.4.2.6
-- 1.3.6.1.4.1.37950.1.1.5.12.8.4.4.2.6
-- 1.3.6.1.4.1.37950.1.1.5.12.8.4.4.2.6
-- 1.3.6.1.4.1.37950.1.1.5.12.8.4.4.2.6
-- 1.3.6.1.4.1.37950.1.1.5.12.8.4.4.2.6
		-- 1.3.6.1.4.1.37950.1.1.5.12.8.4.4.2.6
		ctcDigitLength OBJECT-TYPE
			SYNTAX INTEGER (0..255)
			MAX-ACCESS read-write
			STATUS current
			DESCRIPTION
				"Description."
			::= { h248RtpTidConfig 6 }

		
--          1.3.6.1.4.1.37950.1.1.5.12.8.4.4.2.7
-- 1.3.6.1.4.1.37950.1.1.5.12.8.4.4.2.7
-- 1.3.6.1.4.1.37950.1.1.5.12.8.4.4.2.7
-- 1.3.6.1.4.1.37950.1.1.5.12.8.4.4.2.7
-- 1.3.6.1.4.1.37950.1.1.5.12.8.4.4.2.7
-- 1.3.6.1.4.1.37950.1.1.5.12.8.4.4.2.7
-- 1.3.6.1.4.1.37950.1.1.5.12.8.4.4.2.7
-- 1.3.6.1.4.1.37950.1.1.5.12.8.4.4.2.7
-- 1.3.6.1.4.1.37950.1.1.5.12.8.4.4.2.7
		-- 1.3.6.1.4.1.37950.1.1.5.12.8.4.4.2.7
		ctcRtpTidAction OBJECT-TYPE
			SYNTAX INTEGER
				{
				add(1),
				remove(2)
				}
			MAX-ACCESS read-write
			STATUS current
			DESCRIPTION
				"Description."
			::= { h248RtpTidConfig 7 }

		
--          1.3.6.1.4.1.37950.1.1.5.12.8.4.4.3
-- 1.3.6.1.4.1.37950.1.1.5.12.8.4.4.3
-- 1.3.6.1.4.1.37950.1.1.5.12.8.4.4.3
-- 1.3.6.1.4.1.37950.1.1.5.12.8.4.4.3
-- 1.3.6.1.4.1.37950.1.1.5.12.8.4.4.3
-- 1.3.6.1.4.1.37950.1.1.5.12.8.4.4.3
-- 1.3.6.1.4.1.37950.1.1.5.12.8.4.4.3
-- 1.3.6.1.4.1.37950.1.1.5.12.8.4.4.3
-- 1.3.6.1.4.1.37950.1.1.5.12.8.4.4.3
		-- 1.3.6.1.4.1.37950.1.1.5.12.8.4.4.3
		h248UserTidConfig OBJECT IDENTIFIER ::= { voipH248Config 3 }

		
--          1.3.6.1.4.1.37950.1.1.5.12.8.4.4.3.1
-- 1.3.6.1.4.1.37950.1.1.5.12.8.4.4.3.1
-- 1.3.6.1.4.1.37950.1.1.5.12.8.4.4.3.1
-- 1.3.6.1.4.1.37950.1.1.5.12.8.4.4.3.1
-- 1.3.6.1.4.1.37950.1.1.5.12.8.4.4.3.1
-- 1.3.6.1.4.1.37950.1.1.5.12.8.4.4.3.1
-- 1.3.6.1.4.1.37950.1.1.5.12.8.4.4.3.1
-- 1.3.6.1.4.1.37950.1.1.5.12.8.4.4.3.1
-- 1.3.6.1.4.1.37950.1.1.5.12.8.4.4.3.1
		-- 1.3.6.1.4.1.37950.1.1.5.12.8.4.4.3.1
		ctcUserTidPotsNo OBJECT-TYPE
			SYNTAX INTEGER (1..255)
			MAX-ACCESS read-write
			STATUS current
			DESCRIPTION
				"Description."
			::= { h248UserTidConfig 1 }

		
--          1.3.6.1.4.1.37950.1.1.5.12.8.4.4.3.2
-- 1.3.6.1.4.1.37950.1.1.5.12.8.4.4.3.2
-- 1.3.6.1.4.1.37950.1.1.5.12.8.4.4.3.2
-- 1.3.6.1.4.1.37950.1.1.5.12.8.4.4.3.2
-- 1.3.6.1.4.1.37950.1.1.5.12.8.4.4.3.2
-- 1.3.6.1.4.1.37950.1.1.5.12.8.4.4.3.2
-- 1.3.6.1.4.1.37950.1.1.5.12.8.4.4.3.2
-- 1.3.6.1.4.1.37950.1.1.5.12.8.4.4.3.2
-- 1.3.6.1.4.1.37950.1.1.5.12.8.4.4.3.2
		-- 1.3.6.1.4.1.37950.1.1.5.12.8.4.4.3.2
		ctcUserTid OBJECT-TYPE
			SYNTAX OCTET STRING
			MAX-ACCESS read-write
			STATUS current
			DESCRIPTION
				"Description."
			::= { h248UserTidConfig 2 }

		
--          1.3.6.1.4.1.37950.1.1.5.12.8.4.4.3.3
-- 1.3.6.1.4.1.37950.1.1.5.12.8.4.4.3.3
-- 1.3.6.1.4.1.37950.1.1.5.12.8.4.4.3.3
-- 1.3.6.1.4.1.37950.1.1.5.12.8.4.4.3.3
-- 1.3.6.1.4.1.37950.1.1.5.12.8.4.4.3.3
-- 1.3.6.1.4.1.37950.1.1.5.12.8.4.4.3.3
-- 1.3.6.1.4.1.37950.1.1.5.12.8.4.4.3.3
-- 1.3.6.1.4.1.37950.1.1.5.12.8.4.4.3.3
-- 1.3.6.1.4.1.37950.1.1.5.12.8.4.4.3.3
		-- 1.3.6.1.4.1.37950.1.1.5.12.8.4.4.3.3
		ctcUserTidAction OBJECT-TYPE
			SYNTAX INTEGER
				{
				add(1),
				remove(2)
				}
			MAX-ACCESS read-write
			STATUS current
			DESCRIPTION
				"Description."
			::= { h248UserTidConfig 3 }

		
--          1.3.6.1.4.1.37950.1.1.5.12.8.4.5
-- 1.3.6.1.4.1.37950.1.1.5.12.8.4.5
-- 1.3.6.1.4.1.37950.1.1.5.12.8.4.5
-- 1.3.6.1.4.1.37950.1.1.5.12.8.4.5
-- 1.3.6.1.4.1.37950.1.1.5.12.8.4.5
-- 1.3.6.1.4.1.37950.1.1.5.12.8.4.5
-- 1.3.6.1.4.1.37950.1.1.5.12.8.4.5
-- 1.3.6.1.4.1.37950.1.1.5.12.8.4.5
-- 1.3.6.1.4.1.37950.1.1.5.12.8.4.5
		-- 1.3.6.1.4.1.37950.1.1.5.12.8.4.5
		voipSipConfig OBJECT IDENTIFIER ::= { voipProfileEdit 5 }

		
--          1.3.6.1.4.1.37950.1.1.5.12.8.4.5.1
-- 1.3.6.1.4.1.37950.1.1.5.12.8.4.5.1
-- 1.3.6.1.4.1.37950.1.1.5.12.8.4.5.1
-- 1.3.6.1.4.1.37950.1.1.5.12.8.4.5.1
-- 1.3.6.1.4.1.37950.1.1.5.12.8.4.5.1
-- 1.3.6.1.4.1.37950.1.1.5.12.8.4.5.1
-- 1.3.6.1.4.1.37950.1.1.5.12.8.4.5.1
-- 1.3.6.1.4.1.37950.1.1.5.12.8.4.5.1
-- 1.3.6.1.4.1.37950.1.1.5.12.8.4.5.1
		-- 1.3.6.1.4.1.37950.1.1.5.12.8.4.5.1
		sipProParamConfig OBJECT IDENTIFIER ::= { voipSipConfig 1 }

		
--          1.3.6.1.4.1.37950.1.1.5.12.8.4.5.1.1
-- 1.3.6.1.4.1.37950.1.1.5.12.8.4.5.1.1
-- 1.3.6.1.4.1.37950.1.1.5.12.8.4.5.1.1
-- 1.3.6.1.4.1.37950.1.1.5.12.8.4.5.1.1
-- 1.3.6.1.4.1.37950.1.1.5.12.8.4.5.1.1
-- 1.3.6.1.4.1.37950.1.1.5.12.8.4.5.1.1
-- 1.3.6.1.4.1.37950.1.1.5.12.8.4.5.1.1
-- 1.3.6.1.4.1.37950.1.1.5.12.8.4.5.1.1
-- 1.3.6.1.4.1.37950.1.1.5.12.8.4.5.1.1
		-- 1.3.6.1.4.1.37950.1.1.5.12.8.4.5.1.1
		ctcMgPortVal OBJECT-TYPE
			SYNTAX Integer32 (1..65535)
			MAX-ACCESS read-write
			STATUS current
			DESCRIPTION
				"Description."
			::= { sipProParamConfig 1 }

		
--          1.3.6.1.4.1.37950.1.1.5.12.8.4.5.1.2
-- 1.3.6.1.4.1.37950.1.1.5.12.8.4.5.1.2
-- 1.3.6.1.4.1.37950.1.1.5.12.8.4.5.1.2
-- 1.3.6.1.4.1.37950.1.1.5.12.8.4.5.1.2
-- 1.3.6.1.4.1.37950.1.1.5.12.8.4.5.1.2
-- 1.3.6.1.4.1.37950.1.1.5.12.8.4.5.1.2
-- 1.3.6.1.4.1.37950.1.1.5.12.8.4.5.1.2
-- 1.3.6.1.4.1.37950.1.1.5.12.8.4.5.1.2
-- 1.3.6.1.4.1.37950.1.1.5.12.8.4.5.1.2
		-- 1.3.6.1.4.1.37950.1.1.5.12.8.4.5.1.2
		ctcProxySrvIp OBJECT-TYPE
			SYNTAX IpAddress
			MAX-ACCESS read-write
			STATUS current
			DESCRIPTION
				"Description."
			::= { sipProParamConfig 2 }

		
--          1.3.6.1.4.1.37950.1.1.5.12.8.4.5.1.3
-- 1.3.6.1.4.1.37950.1.1.5.12.8.4.5.1.3
-- 1.3.6.1.4.1.37950.1.1.5.12.8.4.5.1.3
-- 1.3.6.1.4.1.37950.1.1.5.12.8.4.5.1.3
-- 1.3.6.1.4.1.37950.1.1.5.12.8.4.5.1.3
-- 1.3.6.1.4.1.37950.1.1.5.12.8.4.5.1.3
-- 1.3.6.1.4.1.37950.1.1.5.12.8.4.5.1.3
-- 1.3.6.1.4.1.37950.1.1.5.12.8.4.5.1.3
-- 1.3.6.1.4.1.37950.1.1.5.12.8.4.5.1.3
		-- 1.3.6.1.4.1.37950.1.1.5.12.8.4.5.1.3
		ctcProxySrvPort OBJECT-TYPE
			SYNTAX INTEGER (0..65535)
			MAX-ACCESS read-write
			STATUS current
			DESCRIPTION
				"Description."
			::= { sipProParamConfig 3 }

		
--          1.3.6.1.4.1.37950.1.1.5.12.8.4.5.1.4
-- 1.3.6.1.4.1.37950.1.1.5.12.8.4.5.1.4
-- 1.3.6.1.4.1.37950.1.1.5.12.8.4.5.1.4
-- 1.3.6.1.4.1.37950.1.1.5.12.8.4.5.1.4
-- 1.3.6.1.4.1.37950.1.1.5.12.8.4.5.1.4
-- 1.3.6.1.4.1.37950.1.1.5.12.8.4.5.1.4
-- 1.3.6.1.4.1.37950.1.1.5.12.8.4.5.1.4
-- 1.3.6.1.4.1.37950.1.1.5.12.8.4.5.1.4
-- 1.3.6.1.4.1.37950.1.1.5.12.8.4.5.1.4
		-- 1.3.6.1.4.1.37950.1.1.5.12.8.4.5.1.4
		ctcBakProxySrvIp OBJECT-TYPE
			SYNTAX IpAddress
			MAX-ACCESS read-write
			STATUS current
			DESCRIPTION
				"Description."
			::= { sipProParamConfig 4 }

		
--          1.3.6.1.4.1.37950.1.1.5.12.8.4.5.1.5
-- 1.3.6.1.4.1.37950.1.1.5.12.8.4.5.1.5
-- 1.3.6.1.4.1.37950.1.1.5.12.8.4.5.1.5
-- 1.3.6.1.4.1.37950.1.1.5.12.8.4.5.1.5
-- 1.3.6.1.4.1.37950.1.1.5.12.8.4.5.1.5
-- 1.3.6.1.4.1.37950.1.1.5.12.8.4.5.1.5
-- 1.3.6.1.4.1.37950.1.1.5.12.8.4.5.1.5
-- 1.3.6.1.4.1.37950.1.1.5.12.8.4.5.1.5
-- 1.3.6.1.4.1.37950.1.1.5.12.8.4.5.1.5
		-- 1.3.6.1.4.1.37950.1.1.5.12.8.4.5.1.5
		ctcBakProxySrvPort OBJECT-TYPE
			SYNTAX INTEGER (0..65535)
			MAX-ACCESS read-write
			STATUS current
			DESCRIPTION
				"Description."
			DEFVAL { 0 }
			::= { sipProParamConfig 5 }

		
--          1.3.6.1.4.1.37950.1.1.5.12.8.4.5.1.6
-- 1.3.6.1.4.1.37950.1.1.5.12.8.4.5.1.6
-- 1.3.6.1.4.1.37950.1.1.5.12.8.4.5.1.6
-- 1.3.6.1.4.1.37950.1.1.5.12.8.4.5.1.6
-- 1.3.6.1.4.1.37950.1.1.5.12.8.4.5.1.6
-- 1.3.6.1.4.1.37950.1.1.5.12.8.4.5.1.6
-- 1.3.6.1.4.1.37950.1.1.5.12.8.4.5.1.6
-- 1.3.6.1.4.1.37950.1.1.5.12.8.4.5.1.6
-- 1.3.6.1.4.1.37950.1.1.5.12.8.4.5.1.6
		-- 1.3.6.1.4.1.37950.1.1.5.12.8.4.5.1.6
		ctcRegSrvIp OBJECT-TYPE
			SYNTAX IpAddress
			MAX-ACCESS read-write
			STATUS current
			DESCRIPTION
				"Description."
			::= { sipProParamConfig 6 }

		
--          1.3.6.1.4.1.37950.1.1.5.12.8.4.5.1.7
-- 1.3.6.1.4.1.37950.1.1.5.12.8.4.5.1.7
-- 1.3.6.1.4.1.37950.1.1.5.12.8.4.5.1.7
-- 1.3.6.1.4.1.37950.1.1.5.12.8.4.5.1.7
-- 1.3.6.1.4.1.37950.1.1.5.12.8.4.5.1.7
-- 1.3.6.1.4.1.37950.1.1.5.12.8.4.5.1.7
-- 1.3.6.1.4.1.37950.1.1.5.12.8.4.5.1.7
-- 1.3.6.1.4.1.37950.1.1.5.12.8.4.5.1.7
-- 1.3.6.1.4.1.37950.1.1.5.12.8.4.5.1.7
		-- 1.3.6.1.4.1.37950.1.1.5.12.8.4.5.1.7
		ctcRegSrvPort OBJECT-TYPE
			SYNTAX INTEGER (0..65535)
			MAX-ACCESS read-write
			STATUS current
			DESCRIPTION
				"Description."
			::= { sipProParamConfig 7 }

		
--          1.3.6.1.4.1.37950.1.1.5.12.8.4.5.1.8
-- 1.3.6.1.4.1.37950.1.1.5.12.8.4.5.1.8
-- 1.3.6.1.4.1.37950.1.1.5.12.8.4.5.1.8
-- 1.3.6.1.4.1.37950.1.1.5.12.8.4.5.1.8
-- 1.3.6.1.4.1.37950.1.1.5.12.8.4.5.1.8
-- 1.3.6.1.4.1.37950.1.1.5.12.8.4.5.1.8
-- 1.3.6.1.4.1.37950.1.1.5.12.8.4.5.1.8
-- 1.3.6.1.4.1.37950.1.1.5.12.8.4.5.1.8
-- 1.3.6.1.4.1.37950.1.1.5.12.8.4.5.1.8
		-- 1.3.6.1.4.1.37950.1.1.5.12.8.4.5.1.8
		ctcBakRegSrvIp OBJECT-TYPE
			SYNTAX IpAddress
			MAX-ACCESS read-write
			STATUS current
			DESCRIPTION
				"Description."
			::= { sipProParamConfig 8 }

		
--          1.3.6.1.4.1.37950.1.1.5.12.8.4.5.1.9
-- 1.3.6.1.4.1.37950.1.1.5.12.8.4.5.1.9
-- 1.3.6.1.4.1.37950.1.1.5.12.8.4.5.1.9
-- 1.3.6.1.4.1.37950.1.1.5.12.8.4.5.1.9
-- 1.3.6.1.4.1.37950.1.1.5.12.8.4.5.1.9
-- 1.3.6.1.4.1.37950.1.1.5.12.8.4.5.1.9
-- 1.3.6.1.4.1.37950.1.1.5.12.8.4.5.1.9
-- 1.3.6.1.4.1.37950.1.1.5.12.8.4.5.1.9
-- 1.3.6.1.4.1.37950.1.1.5.12.8.4.5.1.9
		-- 1.3.6.1.4.1.37950.1.1.5.12.8.4.5.1.9
		ctcBakRegSrvPort OBJECT-TYPE
			SYNTAX INTEGER (0..65535)
			MAX-ACCESS read-write
			STATUS current
			DESCRIPTION
				"Description."
			DEFVAL { 0 }
			::= { sipProParamConfig 9 }

		
--          1.3.6.1.4.1.37950.1.1.5.12.8.4.5.1.10
-- 1.3.6.1.4.1.37950.1.1.5.12.8.4.5.1.10
-- 1.3.6.1.4.1.37950.1.1.5.12.8.4.5.1.10
-- 1.3.6.1.4.1.37950.1.1.5.12.8.4.5.1.10
-- 1.3.6.1.4.1.37950.1.1.5.12.8.4.5.1.10
-- 1.3.6.1.4.1.37950.1.1.5.12.8.4.5.1.10
-- 1.3.6.1.4.1.37950.1.1.5.12.8.4.5.1.10
-- 1.3.6.1.4.1.37950.1.1.5.12.8.4.5.1.10
-- 1.3.6.1.4.1.37950.1.1.5.12.8.4.5.1.10
		-- 1.3.6.1.4.1.37950.1.1.5.12.8.4.5.1.10
		ctcOutBoundServIp OBJECT-TYPE
			SYNTAX IpAddress
			MAX-ACCESS read-write
			STATUS current
			DESCRIPTION
				"Description."
			::= { sipProParamConfig 10 }

		
--          1.3.6.1.4.1.37950.1.1.5.12.8.4.5.1.11
-- 1.3.6.1.4.1.37950.1.1.5.12.8.4.5.1.11
-- 1.3.6.1.4.1.37950.1.1.5.12.8.4.5.1.11
-- 1.3.6.1.4.1.37950.1.1.5.12.8.4.5.1.11
-- 1.3.6.1.4.1.37950.1.1.5.12.8.4.5.1.11
-- 1.3.6.1.4.1.37950.1.1.5.12.8.4.5.1.11
-- 1.3.6.1.4.1.37950.1.1.5.12.8.4.5.1.11
-- 1.3.6.1.4.1.37950.1.1.5.12.8.4.5.1.11
-- 1.3.6.1.4.1.37950.1.1.5.12.8.4.5.1.11
		-- 1.3.6.1.4.1.37950.1.1.5.12.8.4.5.1.11
		ctcOutBoundServPort OBJECT-TYPE
			SYNTAX INTEGER (0..65535)
			MAX-ACCESS read-write
			STATUS current
			DESCRIPTION
				"Description."
			::= { sipProParamConfig 11 }

		
--          1.3.6.1.4.1.37950.1.1.5.12.8.4.5.1.12
-- 1.3.6.1.4.1.37950.1.1.5.12.8.4.5.1.12
-- 1.3.6.1.4.1.37950.1.1.5.12.8.4.5.1.12
-- 1.3.6.1.4.1.37950.1.1.5.12.8.4.5.1.12
-- 1.3.6.1.4.1.37950.1.1.5.12.8.4.5.1.12
-- 1.3.6.1.4.1.37950.1.1.5.12.8.4.5.1.12
-- 1.3.6.1.4.1.37950.1.1.5.12.8.4.5.1.12
-- 1.3.6.1.4.1.37950.1.1.5.12.8.4.5.1.12
-- 1.3.6.1.4.1.37950.1.1.5.12.8.4.5.1.12
		-- 1.3.6.1.4.1.37950.1.1.5.12.8.4.5.1.12
		ctcRegInterVal OBJECT-TYPE
			SYNTAX INTEGER (1..10000000)
			MAX-ACCESS read-write
			STATUS current
			DESCRIPTION
				"Description."
			DEFVAL { 0 }
			::= { sipProParamConfig 12 }

		
--          1.3.6.1.4.1.37950.1.1.5.12.8.4.5.1.13
-- 1.3.6.1.4.1.37950.1.1.5.12.8.4.5.1.13
-- 1.3.6.1.4.1.37950.1.1.5.12.8.4.5.1.13
-- 1.3.6.1.4.1.37950.1.1.5.12.8.4.5.1.13
-- 1.3.6.1.4.1.37950.1.1.5.12.8.4.5.1.13
-- 1.3.6.1.4.1.37950.1.1.5.12.8.4.5.1.13
-- 1.3.6.1.4.1.37950.1.1.5.12.8.4.5.1.13
-- 1.3.6.1.4.1.37950.1.1.5.12.8.4.5.1.13
-- 1.3.6.1.4.1.37950.1.1.5.12.8.4.5.1.13
		-- 1.3.6.1.4.1.37950.1.1.5.12.8.4.5.1.13
		ctcHbeartEn OBJECT-TYPE
			SYNTAX INTEGER
				{
				disable(0),
				enable(1)
				}
			MAX-ACCESS read-write
			STATUS current
			DESCRIPTION
				"Description."
			::= { sipProParamConfig 13 }

		
--          1.3.6.1.4.1.37950.1.1.5.12.8.4.5.1.14
-- 1.3.6.1.4.1.37950.1.1.5.12.8.4.5.1.14
-- 1.3.6.1.4.1.37950.1.1.5.12.8.4.5.1.14
-- 1.3.6.1.4.1.37950.1.1.5.12.8.4.5.1.14
-- 1.3.6.1.4.1.37950.1.1.5.12.8.4.5.1.14
-- 1.3.6.1.4.1.37950.1.1.5.12.8.4.5.1.14
-- 1.3.6.1.4.1.37950.1.1.5.12.8.4.5.1.14
-- 1.3.6.1.4.1.37950.1.1.5.12.8.4.5.1.14
-- 1.3.6.1.4.1.37950.1.1.5.12.8.4.5.1.14
		-- 1.3.6.1.4.1.37950.1.1.5.12.8.4.5.1.14
		ctcHbeatCycle OBJECT-TYPE
			SYNTAX INTEGER (1..65535)
			MAX-ACCESS read-write
			STATUS current
			DESCRIPTION
				"Description."
			DEFVAL { 60 }
			::= { sipProParamConfig 14 }

		
--          1.3.6.1.4.1.37950.1.1.5.12.8.4.5.1.15
-- 1.3.6.1.4.1.37950.1.1.5.12.8.4.5.1.15
-- 1.3.6.1.4.1.37950.1.1.5.12.8.4.5.1.15
-- 1.3.6.1.4.1.37950.1.1.5.12.8.4.5.1.15
-- 1.3.6.1.4.1.37950.1.1.5.12.8.4.5.1.15
-- 1.3.6.1.4.1.37950.1.1.5.12.8.4.5.1.15
-- 1.3.6.1.4.1.37950.1.1.5.12.8.4.5.1.15
-- 1.3.6.1.4.1.37950.1.1.5.12.8.4.5.1.15
-- 1.3.6.1.4.1.37950.1.1.5.12.8.4.5.1.15
		-- 1.3.6.1.4.1.37950.1.1.5.12.8.4.5.1.15
		ctcHbeatCount OBJECT-TYPE
			SYNTAX INTEGER (1..65535)
			MAX-ACCESS read-write
			STATUS current
			DESCRIPTION
				"Description."
			DEFVAL { 3 }
			::= { sipProParamConfig 15 }

		
--          1.3.6.1.4.1.37950.1.1.5.12.8.4.5.1.16
-- 1.3.6.1.4.1.37950.1.1.5.12.8.4.5.1.16
-- 1.3.6.1.4.1.37950.1.1.5.12.8.4.5.1.16
-- 1.3.6.1.4.1.37950.1.1.5.12.8.4.5.1.16
-- 1.3.6.1.4.1.37950.1.1.5.12.8.4.5.1.16
-- 1.3.6.1.4.1.37950.1.1.5.12.8.4.5.1.16
-- 1.3.6.1.4.1.37950.1.1.5.12.8.4.5.1.16
-- 1.3.6.1.4.1.37950.1.1.5.12.8.4.5.1.16
-- 1.3.6.1.4.1.37950.1.1.5.12.8.4.5.1.16
		-- 1.3.6.1.4.1.37950.1.1.5.12.8.4.5.1.16
		ctcRegSrvAction OBJECT-TYPE
			SYNTAX INTEGER
				{
				add(1),
				remove(2)
				}
			MAX-ACCESS read-write
			STATUS current
			DESCRIPTION
				"Description."
			::= { sipProParamConfig 16 }

		
--          1.3.6.1.4.1.37950.1.1.5.12.8.4.5.2
-- 1.3.6.1.4.1.37950.1.1.5.12.8.4.5.2
-- 1.3.6.1.4.1.37950.1.1.5.12.8.4.5.2
-- 1.3.6.1.4.1.37950.1.1.5.12.8.4.5.2
-- 1.3.6.1.4.1.37950.1.1.5.12.8.4.5.2
-- 1.3.6.1.4.1.37950.1.1.5.12.8.4.5.2
-- 1.3.6.1.4.1.37950.1.1.5.12.8.4.5.2
-- 1.3.6.1.4.1.37950.1.1.5.12.8.4.5.2
-- 1.3.6.1.4.1.37950.1.1.5.12.8.4.5.2
		-- 1.3.6.1.4.1.37950.1.1.5.12.8.4.5.2
		sipUserParamConfig OBJECT IDENTIFIER ::= { voipSipConfig 2 }

		
--          1.3.6.1.4.1.37950.1.1.5.12.8.4.5.2.1
-- 1.3.6.1.4.1.37950.1.1.5.12.8.4.5.2.1
-- 1.3.6.1.4.1.37950.1.1.5.12.8.4.5.2.1
-- 1.3.6.1.4.1.37950.1.1.5.12.8.4.5.2.1
-- 1.3.6.1.4.1.37950.1.1.5.12.8.4.5.2.1
-- 1.3.6.1.4.1.37950.1.1.5.12.8.4.5.2.1
-- 1.3.6.1.4.1.37950.1.1.5.12.8.4.5.2.1
-- 1.3.6.1.4.1.37950.1.1.5.12.8.4.5.2.1
-- 1.3.6.1.4.1.37950.1.1.5.12.8.4.5.2.1
		-- 1.3.6.1.4.1.37950.1.1.5.12.8.4.5.2.1
		ctcUserPotsNo OBJECT-TYPE
			SYNTAX INTEGER (1..255)
			MAX-ACCESS read-write
			STATUS current
			DESCRIPTION
				"Description."
			::= { sipUserParamConfig 1 }

		
--          1.3.6.1.4.1.37950.1.1.5.12.8.4.5.2.2
-- 1.3.6.1.4.1.37950.1.1.5.12.8.4.5.2.2
-- 1.3.6.1.4.1.37950.1.1.5.12.8.4.5.2.2
-- 1.3.6.1.4.1.37950.1.1.5.12.8.4.5.2.2
-- 1.3.6.1.4.1.37950.1.1.5.12.8.4.5.2.2
-- 1.3.6.1.4.1.37950.1.1.5.12.8.4.5.2.2
-- 1.3.6.1.4.1.37950.1.1.5.12.8.4.5.2.2
-- 1.3.6.1.4.1.37950.1.1.5.12.8.4.5.2.2
-- 1.3.6.1.4.1.37950.1.1.5.12.8.4.5.2.2
		-- 1.3.6.1.4.1.37950.1.1.5.12.8.4.5.2.2
		ctcUserAccount OBJECT-TYPE
			SYNTAX OCTET STRING
			MAX-ACCESS read-write
			STATUS current
			DESCRIPTION
				"Description."
			::= { sipUserParamConfig 2 }

		
--          1.3.6.1.4.1.37950.1.1.5.12.8.4.5.2.3
-- 1.3.6.1.4.1.37950.1.1.5.12.8.4.5.2.3
-- 1.3.6.1.4.1.37950.1.1.5.12.8.4.5.2.3
-- 1.3.6.1.4.1.37950.1.1.5.12.8.4.5.2.3
-- 1.3.6.1.4.1.37950.1.1.5.12.8.4.5.2.3
-- 1.3.6.1.4.1.37950.1.1.5.12.8.4.5.2.3
-- 1.3.6.1.4.1.37950.1.1.5.12.8.4.5.2.3
-- 1.3.6.1.4.1.37950.1.1.5.12.8.4.5.2.3
-- 1.3.6.1.4.1.37950.1.1.5.12.8.4.5.2.3
		-- 1.3.6.1.4.1.37950.1.1.5.12.8.4.5.2.3
		ctcUserName OBJECT-TYPE
			SYNTAX OCTET STRING
			MAX-ACCESS read-write
			STATUS current
			DESCRIPTION
				"Description."
			::= { sipUserParamConfig 3 }

		
--          1.3.6.1.4.1.37950.1.1.5.12.8.4.5.2.4
-- 1.3.6.1.4.1.37950.1.1.5.12.8.4.5.2.4
-- 1.3.6.1.4.1.37950.1.1.5.12.8.4.5.2.4
-- 1.3.6.1.4.1.37950.1.1.5.12.8.4.5.2.4
-- 1.3.6.1.4.1.37950.1.1.5.12.8.4.5.2.4
-- 1.3.6.1.4.1.37950.1.1.5.12.8.4.5.2.4
-- 1.3.6.1.4.1.37950.1.1.5.12.8.4.5.2.4
-- 1.3.6.1.4.1.37950.1.1.5.12.8.4.5.2.4
-- 1.3.6.1.4.1.37950.1.1.5.12.8.4.5.2.4
		-- 1.3.6.1.4.1.37950.1.1.5.12.8.4.5.2.4
		ctcUserPw OBJECT-TYPE
			SYNTAX OCTET STRING
			MAX-ACCESS read-write
			STATUS current
			DESCRIPTION
				"Description."
			::= { sipUserParamConfig 4 }

		
--          1.3.6.1.4.1.37950.1.1.5.12.8.4.5.2.5
-- 1.3.6.1.4.1.37950.1.1.5.12.8.4.5.2.5
-- 1.3.6.1.4.1.37950.1.1.5.12.8.4.5.2.5
-- 1.3.6.1.4.1.37950.1.1.5.12.8.4.5.2.5
-- 1.3.6.1.4.1.37950.1.1.5.12.8.4.5.2.5
-- 1.3.6.1.4.1.37950.1.1.5.12.8.4.5.2.5
-- 1.3.6.1.4.1.37950.1.1.5.12.8.4.5.2.5
-- 1.3.6.1.4.1.37950.1.1.5.12.8.4.5.2.5
-- 1.3.6.1.4.1.37950.1.1.5.12.8.4.5.2.5
		-- 1.3.6.1.4.1.37950.1.1.5.12.8.4.5.2.5
		ctcUserAction OBJECT-TYPE
			SYNTAX INTEGER
				{
				add(1),
				remove(2)
				}
			MAX-ACCESS read-write
			STATUS current
			DESCRIPTION
				"Description."
			::= { sipUserParamConfig 5 }

		
--          1.3.6.1.4.1.37950.1.1.5.12.8.4.5.3
-- 1.3.6.1.4.1.37950.1.1.5.12.8.4.5.3
-- 1.3.6.1.4.1.37950.1.1.5.12.8.4.5.3
-- 1.3.6.1.4.1.37950.1.1.5.12.8.4.5.3
-- 1.3.6.1.4.1.37950.1.1.5.12.8.4.5.3
-- 1.3.6.1.4.1.37950.1.1.5.12.8.4.5.3
-- 1.3.6.1.4.1.37950.1.1.5.12.8.4.5.3
-- 1.3.6.1.4.1.37950.1.1.5.12.8.4.5.3
-- 1.3.6.1.4.1.37950.1.1.5.12.8.4.5.3
		-- 1.3.6.1.4.1.37950.1.1.5.12.8.4.5.3
		sipDigitConfig OBJECT IDENTIFIER ::= { voipSipConfig 3 }

		
--          1.3.6.1.4.1.37950.1.1.5.12.8.4.5.3.1
-- 1.3.6.1.4.1.37950.1.1.5.12.8.4.5.3.1
-- 1.3.6.1.4.1.37950.1.1.5.12.8.4.5.3.1
-- 1.3.6.1.4.1.37950.1.1.5.12.8.4.5.3.1
-- 1.3.6.1.4.1.37950.1.1.5.12.8.4.5.3.1
-- 1.3.6.1.4.1.37950.1.1.5.12.8.4.5.3.1
-- 1.3.6.1.4.1.37950.1.1.5.12.8.4.5.3.1
-- 1.3.6.1.4.1.37950.1.1.5.12.8.4.5.3.1
-- 1.3.6.1.4.1.37950.1.1.5.12.8.4.5.3.1
		-- 1.3.6.1.4.1.37950.1.1.5.12.8.4.5.3.1
		ctcDigitNum OBJECT-TYPE
			SYNTAX Integer32 (1..255)
			MAX-ACCESS read-write
			STATUS current
			DESCRIPTION
				"Description."
			::= { sipDigitConfig 1 }

		
--          1.3.6.1.4.1.37950.1.1.5.12.8.4.5.3.2
-- 1.3.6.1.4.1.37950.1.1.5.12.8.4.5.3.2
-- 1.3.6.1.4.1.37950.1.1.5.12.8.4.5.3.2
-- 1.3.6.1.4.1.37950.1.1.5.12.8.4.5.3.2
-- 1.3.6.1.4.1.37950.1.1.5.12.8.4.5.3.2
-- 1.3.6.1.4.1.37950.1.1.5.12.8.4.5.3.2
-- 1.3.6.1.4.1.37950.1.1.5.12.8.4.5.3.2
-- 1.3.6.1.4.1.37950.1.1.5.12.8.4.5.3.2
-- 1.3.6.1.4.1.37950.1.1.5.12.8.4.5.3.2
		-- 1.3.6.1.4.1.37950.1.1.5.12.8.4.5.3.2
		ctcDigitNumBlock OBJECT-TYPE
			SYNTAX Integer32 (0..255)
			MAX-ACCESS read-write
			STATUS current
			DESCRIPTION
				"Description."
			::= { sipDigitConfig 2 }

		
--          1.3.6.1.4.1.37950.1.1.5.12.8.4.5.3.3
-- 1.3.6.1.4.1.37950.1.1.5.12.8.4.5.3.3
-- 1.3.6.1.4.1.37950.1.1.5.12.8.4.5.3.3
-- 1.3.6.1.4.1.37950.1.1.5.12.8.4.5.3.3
-- 1.3.6.1.4.1.37950.1.1.5.12.8.4.5.3.3
-- 1.3.6.1.4.1.37950.1.1.5.12.8.4.5.3.3
-- 1.3.6.1.4.1.37950.1.1.5.12.8.4.5.3.3
-- 1.3.6.1.4.1.37950.1.1.5.12.8.4.5.3.3
-- 1.3.6.1.4.1.37950.1.1.5.12.8.4.5.3.3
		-- 1.3.6.1.4.1.37950.1.1.5.12.8.4.5.3.3
		ctcDigitMap OBJECT-TYPE
			SYNTAX OCTET STRING
			MAX-ACCESS read-write
			STATUS current
			DESCRIPTION
				"Description."
			::= { sipDigitConfig 3 }

		
--          1.3.6.1.4.1.37950.1.1.5.12.8.4.5.3.4
-- 1.3.6.1.4.1.37950.1.1.5.12.8.4.5.3.4
-- 1.3.6.1.4.1.37950.1.1.5.12.8.4.5.3.4
-- 1.3.6.1.4.1.37950.1.1.5.12.8.4.5.3.4
-- 1.3.6.1.4.1.37950.1.1.5.12.8.4.5.3.4
-- 1.3.6.1.4.1.37950.1.1.5.12.8.4.5.3.4
-- 1.3.6.1.4.1.37950.1.1.5.12.8.4.5.3.4
-- 1.3.6.1.4.1.37950.1.1.5.12.8.4.5.3.4
-- 1.3.6.1.4.1.37950.1.1.5.12.8.4.5.3.4
		-- 1.3.6.1.4.1.37950.1.1.5.12.8.4.5.3.4
		ctcDigitMapAction OBJECT-TYPE
			SYNTAX INTEGER
				{
				add(1),
				commit(2)
				}
			MAX-ACCESS read-write
			STATUS current
			DESCRIPTION
				"Description."
			::= { sipDigitConfig 4 }

		
--          1.3.6.1.4.1.37950.1.1.5.12.8.4.6
-- 1.3.6.1.4.1.37950.1.1.5.12.8.4.6
-- 1.3.6.1.4.1.37950.1.1.5.12.8.4.6
-- 1.3.6.1.4.1.37950.1.1.5.12.8.4.6
-- 1.3.6.1.4.1.37950.1.1.5.12.8.4.6
-- 1.3.6.1.4.1.37950.1.1.5.12.8.4.6
-- 1.3.6.1.4.1.37950.1.1.5.12.8.4.6
-- 1.3.6.1.4.1.37950.1.1.5.12.8.4.6
-- 1.3.6.1.4.1.37950.1.1.5.12.8.4.6
		-- 1.3.6.1.4.1.37950.1.1.5.12.8.4.6
		voipFaxModemCfg OBJECT IDENTIFIER ::= { voipProfileEdit 6 }

		
--          1.3.6.1.4.1.37950.1.1.5.12.8.4.6.1
-- 1.3.6.1.4.1.37950.1.1.5.12.8.4.6.1
-- 1.3.6.1.4.1.37950.1.1.5.12.8.4.6.1
-- 1.3.6.1.4.1.37950.1.1.5.12.8.4.6.1
-- 1.3.6.1.4.1.37950.1.1.5.12.8.4.6.1
-- 1.3.6.1.4.1.37950.1.1.5.12.8.4.6.1
-- 1.3.6.1.4.1.37950.1.1.5.12.8.4.6.1
-- 1.3.6.1.4.1.37950.1.1.5.12.8.4.6.1
-- 1.3.6.1.4.1.37950.1.1.5.12.8.4.6.1
		-- 1.3.6.1.4.1.37950.1.1.5.12.8.4.6.1
		ctcT38En OBJECT-TYPE
			SYNTAX INTEGER
				{
				disable(0),
				enable(1)
				}
			MAX-ACCESS read-write
			STATUS current
			DESCRIPTION
				"Description."
			::= { voipFaxModemCfg 1 }

		
--          1.3.6.1.4.1.37950.1.1.5.12.8.4.6.2
-- 1.3.6.1.4.1.37950.1.1.5.12.8.4.6.2
-- 1.3.6.1.4.1.37950.1.1.5.12.8.4.6.2
-- 1.3.6.1.4.1.37950.1.1.5.12.8.4.6.2
-- 1.3.6.1.4.1.37950.1.1.5.12.8.4.6.2
-- 1.3.6.1.4.1.37950.1.1.5.12.8.4.6.2
-- 1.3.6.1.4.1.37950.1.1.5.12.8.4.6.2
-- 1.3.6.1.4.1.37950.1.1.5.12.8.4.6.2
-- 1.3.6.1.4.1.37950.1.1.5.12.8.4.6.2
		-- 1.3.6.1.4.1.37950.1.1.5.12.8.4.6.2
		ctcControl OBJECT-TYPE
			SYNTAX INTEGER
				{
				negotiation(1),
				autovbd(2)
				}
			MAX-ACCESS read-write
			STATUS current
			DESCRIPTION
				"Description."
			::= { voipFaxModemCfg 2 }

		
--          1.3.6.1.4.1.37950.1.1.5.12.8.4.6.3
-- 1.3.6.1.4.1.37950.1.1.5.12.8.4.6.3
-- 1.3.6.1.4.1.37950.1.1.5.12.8.4.6.3
-- 1.3.6.1.4.1.37950.1.1.5.12.8.4.6.3
-- 1.3.6.1.4.1.37950.1.1.5.12.8.4.6.3
-- 1.3.6.1.4.1.37950.1.1.5.12.8.4.6.3
-- 1.3.6.1.4.1.37950.1.1.5.12.8.4.6.3
-- 1.3.6.1.4.1.37950.1.1.5.12.8.4.6.3
-- 1.3.6.1.4.1.37950.1.1.5.12.8.4.6.3
		-- 1.3.6.1.4.1.37950.1.1.5.12.8.4.6.3
		ctcFaxModemAction OBJECT-TYPE
			SYNTAX INTEGER
				{
				add(1),
				remove(2)
				}
			MAX-ACCESS read-write
			STATUS current
			DESCRIPTION
				"Description."
			::= { voipFaxModemCfg 3 }

		
--          1.3.6.1.4.1.37950.1.1.5.12.8.4.7
-- 1.3.6.1.4.1.37950.1.1.5.12.8.4.7
-- 1.3.6.1.4.1.37950.1.1.5.12.8.4.7
-- 1.3.6.1.4.1.37950.1.1.5.12.8.4.7
-- 1.3.6.1.4.1.37950.1.1.5.12.8.4.7
-- 1.3.6.1.4.1.37950.1.1.5.12.8.4.7
-- 1.3.6.1.4.1.37950.1.1.5.12.8.4.7
-- 1.3.6.1.4.1.37950.1.1.5.12.8.4.7
-- 1.3.6.1.4.1.37950.1.1.5.12.8.4.7
		-- 1.3.6.1.4.1.37950.1.1.5.12.8.4.7
		voipPotsManage OBJECT IDENTIFIER ::= { voipProfileEdit 7 }

		
--          1.3.6.1.4.1.37950.1.1.5.12.8.4.7.1
-- 1.3.6.1.4.1.37950.1.1.5.12.8.4.7.1
-- 1.3.6.1.4.1.37950.1.1.5.12.8.4.7.1
-- 1.3.6.1.4.1.37950.1.1.5.12.8.4.7.1
-- 1.3.6.1.4.1.37950.1.1.5.12.8.4.7.1
-- 1.3.6.1.4.1.37950.1.1.5.12.8.4.7.1
-- 1.3.6.1.4.1.37950.1.1.5.12.8.4.7.1
-- 1.3.6.1.4.1.37950.1.1.5.12.8.4.7.1
-- 1.3.6.1.4.1.37950.1.1.5.12.8.4.7.1
		-- 1.3.6.1.4.1.37950.1.1.5.12.8.4.7.1
		ctcPotsNo OBJECT-TYPE
			SYNTAX Integer32 (1..255)
			MAX-ACCESS read-write
			STATUS current
			DESCRIPTION
				"Description."
			::= { voipPotsManage 1 }

		
--          1.3.6.1.4.1.37950.1.1.5.12.8.4.7.2
-- 1.3.6.1.4.1.37950.1.1.5.12.8.4.7.2
-- 1.3.6.1.4.1.37950.1.1.5.12.8.4.7.2
-- 1.3.6.1.4.1.37950.1.1.5.12.8.4.7.2
-- 1.3.6.1.4.1.37950.1.1.5.12.8.4.7.2
-- 1.3.6.1.4.1.37950.1.1.5.12.8.4.7.2
-- 1.3.6.1.4.1.37950.1.1.5.12.8.4.7.2
-- 1.3.6.1.4.1.37950.1.1.5.12.8.4.7.2
-- 1.3.6.1.4.1.37950.1.1.5.12.8.4.7.2
		-- 1.3.6.1.4.1.37950.1.1.5.12.8.4.7.2
		ctcPotsEnable OBJECT-TYPE
			SYNTAX INTEGER
				{
				disable(0),
				enable(1)
				}
			MAX-ACCESS read-write
			STATUS current
			DESCRIPTION
				"Description."
			::= { voipPotsManage 2 }

		
--          1.3.6.1.4.1.37950.1.1.5.12.8.4.7.3
-- 1.3.6.1.4.1.37950.1.1.5.12.8.4.7.3
-- 1.3.6.1.4.1.37950.1.1.5.12.8.4.7.3
-- 1.3.6.1.4.1.37950.1.1.5.12.8.4.7.3
-- 1.3.6.1.4.1.37950.1.1.5.12.8.4.7.3
-- 1.3.6.1.4.1.37950.1.1.5.12.8.4.7.3
-- 1.3.6.1.4.1.37950.1.1.5.12.8.4.7.3
-- 1.3.6.1.4.1.37950.1.1.5.12.8.4.7.3
-- 1.3.6.1.4.1.37950.1.1.5.12.8.4.7.3
		-- 1.3.6.1.4.1.37950.1.1.5.12.8.4.7.3
		ctcPotsMgAction OBJECT-TYPE
			SYNTAX INTEGER
				{
				add(1),
				remove(2)
				}
			MAX-ACCESS read-write
			STATUS current
			DESCRIPTION
				"Description."
			::= { voipPotsManage 3 }

		
--          1.3.6.1.4.1.37950.1.1.5.12.8.4.8
-- 1.3.6.1.4.1.37950.1.1.5.12.8.4.8
-- 1.3.6.1.4.1.37950.1.1.5.12.8.4.8
-- 1.3.6.1.4.1.37950.1.1.5.12.8.4.8
-- 1.3.6.1.4.1.37950.1.1.5.12.8.4.8
-- 1.3.6.1.4.1.37950.1.1.5.12.8.4.8
-- 1.3.6.1.4.1.37950.1.1.5.12.8.4.8
-- 1.3.6.1.4.1.37950.1.1.5.12.8.4.8
-- 1.3.6.1.4.1.37950.1.1.5.12.8.4.8
		-- 1.3.6.1.4.1.37950.1.1.5.12.8.4.8
		voipTimerConfig OBJECT IDENTIFIER ::= { voipProfileEdit 8 }

		
--          1.3.6.1.4.1.37950.1.1.5.12.8.4.8.1
-- 1.3.6.1.4.1.37950.1.1.5.12.8.4.8.1
-- 1.3.6.1.4.1.37950.1.1.5.12.8.4.8.1
-- 1.3.6.1.4.1.37950.1.1.5.12.8.4.8.1
-- 1.3.6.1.4.1.37950.1.1.5.12.8.4.8.1
-- 1.3.6.1.4.1.37950.1.1.5.12.8.4.8.1
-- 1.3.6.1.4.1.37950.1.1.5.12.8.4.8.1
-- 1.3.6.1.4.1.37950.1.1.5.12.8.4.8.1
-- 1.3.6.1.4.1.37950.1.1.5.12.8.4.8.1
		-- 1.3.6.1.4.1.37950.1.1.5.12.8.4.8.1
		maxWaitTime OBJECT-TYPE
			SYNTAX Integer32 (0..254)
			MAX-ACCESS read-write
			STATUS current
			DESCRIPTION
				"Description."
			::= { voipTimerConfig 1 }

		
--          1.3.6.1.4.1.37950.1.1.5.12.8.4.8.2
-- 1.3.6.1.4.1.37950.1.1.5.12.8.4.8.2
-- 1.3.6.1.4.1.37950.1.1.5.12.8.4.8.2
-- 1.3.6.1.4.1.37950.1.1.5.12.8.4.8.2
-- 1.3.6.1.4.1.37950.1.1.5.12.8.4.8.2
-- 1.3.6.1.4.1.37950.1.1.5.12.8.4.8.2
-- 1.3.6.1.4.1.37950.1.1.5.12.8.4.8.2
-- 1.3.6.1.4.1.37950.1.1.5.12.8.4.8.2
-- 1.3.6.1.4.1.37950.1.1.5.12.8.4.8.2
		-- 1.3.6.1.4.1.37950.1.1.5.12.8.4.8.2
		startTimer OBJECT-TYPE
			SYNTAX Integer32
			MAX-ACCESS read-write
			STATUS current
			DESCRIPTION
				"Description."
			::= { voipTimerConfig 2 }

		
--          1.3.6.1.4.1.37950.1.1.5.12.8.4.8.3
-- 1.3.6.1.4.1.37950.1.1.5.12.8.4.8.3
-- 1.3.6.1.4.1.37950.1.1.5.12.8.4.8.3
-- 1.3.6.1.4.1.37950.1.1.5.12.8.4.8.3
-- 1.3.6.1.4.1.37950.1.1.5.12.8.4.8.3
-- 1.3.6.1.4.1.37950.1.1.5.12.8.4.8.3
-- 1.3.6.1.4.1.37950.1.1.5.12.8.4.8.3
-- 1.3.6.1.4.1.37950.1.1.5.12.8.4.8.3
-- 1.3.6.1.4.1.37950.1.1.5.12.8.4.8.3
		-- 1.3.6.1.4.1.37950.1.1.5.12.8.4.8.3
		longTimer OBJECT-TYPE
			SYNTAX Integer32 (1..65535)
			MAX-ACCESS read-write
			STATUS current
			DESCRIPTION
				"Description."
			::= { voipTimerConfig 3 }

		
--          1.3.6.1.4.1.37950.1.1.5.12.8.4.8.4
-- 1.3.6.1.4.1.37950.1.1.5.12.8.4.8.4
-- 1.3.6.1.4.1.37950.1.1.5.12.8.4.8.4
-- 1.3.6.1.4.1.37950.1.1.5.12.8.4.8.4
-- 1.3.6.1.4.1.37950.1.1.5.12.8.4.8.4
-- 1.3.6.1.4.1.37950.1.1.5.12.8.4.8.4
-- 1.3.6.1.4.1.37950.1.1.5.12.8.4.8.4
-- 1.3.6.1.4.1.37950.1.1.5.12.8.4.8.4
-- 1.3.6.1.4.1.37950.1.1.5.12.8.4.8.4
		-- 1.3.6.1.4.1.37950.1.1.5.12.8.4.8.4
		shortTimer OBJECT-TYPE
			SYNTAX Integer32 (1..65535)
			MAX-ACCESS read-write
			STATUS current
			DESCRIPTION
				"Description."
			::= { voipTimerConfig 4 }

		
--          1.3.6.1.4.1.37950.1.1.5.12.8.4.8.5
-- 1.3.6.1.4.1.37950.1.1.5.12.8.4.8.5
-- 1.3.6.1.4.1.37950.1.1.5.12.8.4.8.5
-- 1.3.6.1.4.1.37950.1.1.5.12.8.4.8.5
-- 1.3.6.1.4.1.37950.1.1.5.12.8.4.8.5
-- 1.3.6.1.4.1.37950.1.1.5.12.8.4.8.5
-- 1.3.6.1.4.1.37950.1.1.5.12.8.4.8.5
-- 1.3.6.1.4.1.37950.1.1.5.12.8.4.8.5
-- 1.3.6.1.4.1.37950.1.1.5.12.8.4.8.5
		-- 1.3.6.1.4.1.37950.1.1.5.12.8.4.8.5
		digitmapNotify OBJECT-TYPE
			SYNTAX INTEGER
				{
				disable(0),
				enable(1)
				}
			MAX-ACCESS read-write
			STATUS current
			DESCRIPTION
				"Description."
			::= { voipTimerConfig 5 }

		
--          1.3.6.1.4.1.37950.1.1.5.12.8.4.8.6
-- 1.3.6.1.4.1.37950.1.1.5.12.8.4.8.6
-- 1.3.6.1.4.1.37950.1.1.5.12.8.4.8.6
-- 1.3.6.1.4.1.37950.1.1.5.12.8.4.8.6
-- 1.3.6.1.4.1.37950.1.1.5.12.8.4.8.6
-- 1.3.6.1.4.1.37950.1.1.5.12.8.4.8.6
-- 1.3.6.1.4.1.37950.1.1.5.12.8.4.8.6
-- 1.3.6.1.4.1.37950.1.1.5.12.8.4.8.6
-- 1.3.6.1.4.1.37950.1.1.5.12.8.4.8.6
		-- 1.3.6.1.4.1.37950.1.1.5.12.8.4.8.6
		voipTimerAction OBJECT-TYPE
			SYNTAX INTEGER
				{
				add(1),
				remove(2)
				}
			MAX-ACCESS read-write
			STATUS current
			DESCRIPTION
				"Description."
			::= { voipTimerConfig 6 }

		
--          1.3.6.1.4.1.37950.1.1.5.12.8.4.9
-- 1.3.6.1.4.1.37950.1.1.5.12.8.4.9
-- 1.3.6.1.4.1.37950.1.1.5.12.8.4.9
-- 1.3.6.1.4.1.37950.1.1.5.12.8.4.9
-- 1.3.6.1.4.1.37950.1.1.5.12.8.4.9
-- 1.3.6.1.4.1.37950.1.1.5.12.8.4.9
-- 1.3.6.1.4.1.37950.1.1.5.12.8.4.9
-- 1.3.6.1.4.1.37950.1.1.5.12.8.4.9
-- 1.3.6.1.4.1.37950.1.1.5.12.8.4.9
		-- 1.3.6.1.4.1.37950.1.1.5.12.8.4.9
		voipPotsParameter OBJECT IDENTIFIER ::= { voipProfileEdit 9 }

		
--          1.3.6.1.4.1.37950.1.1.5.12.8.4.9.1
-- 1.3.6.1.4.1.37950.1.1.5.12.8.4.9.1
-- 1.3.6.1.4.1.37950.1.1.5.12.8.4.9.1
-- 1.3.6.1.4.1.37950.1.1.5.12.8.4.9.1
-- 1.3.6.1.4.1.37950.1.1.5.12.8.4.9.1
-- 1.3.6.1.4.1.37950.1.1.5.12.8.4.9.1
-- 1.3.6.1.4.1.37950.1.1.5.12.8.4.9.1
-- 1.3.6.1.4.1.37950.1.1.5.12.8.4.9.1
-- 1.3.6.1.4.1.37950.1.1.5.12.8.4.9.1
		-- 1.3.6.1.4.1.37950.1.1.5.12.8.4.9.1
		priPotsPtNo OBJECT-TYPE
			SYNTAX Integer32 (1..255)
			MAX-ACCESS read-write
			STATUS current
			DESCRIPTION
				"Description."
			::= { voipPotsParameter 1 }

		
--          1.3.6.1.4.1.37950.1.1.5.12.8.4.9.2
-- 1.3.6.1.4.1.37950.1.1.5.12.8.4.9.2
-- 1.3.6.1.4.1.37950.1.1.5.12.8.4.9.2
-- 1.3.6.1.4.1.37950.1.1.5.12.8.4.9.2
-- 1.3.6.1.4.1.37950.1.1.5.12.8.4.9.2
-- 1.3.6.1.4.1.37950.1.1.5.12.8.4.9.2
-- 1.3.6.1.4.1.37950.1.1.5.12.8.4.9.2
-- 1.3.6.1.4.1.37950.1.1.5.12.8.4.9.2
-- 1.3.6.1.4.1.37950.1.1.5.12.8.4.9.2
		-- 1.3.6.1.4.1.37950.1.1.5.12.8.4.9.2
		priVad OBJECT-TYPE
			SYNTAX INTEGER
				{
				disable(0),
				enable(1)
				}
			MAX-ACCESS read-write
			STATUS current
			DESCRIPTION
				"Description."
			::= { voipPotsParameter 2 }

		
--          1.3.6.1.4.1.37950.1.1.5.12.8.4.9.3
-- 1.3.6.1.4.1.37950.1.1.5.12.8.4.9.3
-- 1.3.6.1.4.1.37950.1.1.5.12.8.4.9.3
-- 1.3.6.1.4.1.37950.1.1.5.12.8.4.9.3
-- 1.3.6.1.4.1.37950.1.1.5.12.8.4.9.3
-- 1.3.6.1.4.1.37950.1.1.5.12.8.4.9.3
-- 1.3.6.1.4.1.37950.1.1.5.12.8.4.9.3
-- 1.3.6.1.4.1.37950.1.1.5.12.8.4.9.3
-- 1.3.6.1.4.1.37950.1.1.5.12.8.4.9.3
		-- 1.3.6.1.4.1.37950.1.1.5.12.8.4.9.3
		priEchoCancel OBJECT-TYPE
			SYNTAX INTEGER
				{
				disable(0),
				enable(1)
				}
			MAX-ACCESS read-write
			STATUS current
			DESCRIPTION
				"Description."
			::= { voipPotsParameter 3 }

		
--          1.3.6.1.4.1.37950.1.1.5.12.8.4.9.4
-- 1.3.6.1.4.1.37950.1.1.5.12.8.4.9.4
-- 1.3.6.1.4.1.37950.1.1.5.12.8.4.9.4
-- 1.3.6.1.4.1.37950.1.1.5.12.8.4.9.4
-- 1.3.6.1.4.1.37950.1.1.5.12.8.4.9.4
-- 1.3.6.1.4.1.37950.1.1.5.12.8.4.9.4
-- 1.3.6.1.4.1.37950.1.1.5.12.8.4.9.4
-- 1.3.6.1.4.1.37950.1.1.5.12.8.4.9.4
-- 1.3.6.1.4.1.37950.1.1.5.12.8.4.9.4
		-- 1.3.6.1.4.1.37950.1.1.5.12.8.4.9.4
		priInputGain OBJECT-TYPE
			SYNTAX Integer32 (-32..32)
			MAX-ACCESS read-write
			STATUS current
			DESCRIPTION
				"Description."
			::= { voipPotsParameter 4 }

		
--          1.3.6.1.4.1.37950.1.1.5.12.8.4.9.5
-- 1.3.6.1.4.1.37950.1.1.5.12.8.4.9.5
-- 1.3.6.1.4.1.37950.1.1.5.12.8.4.9.5
-- 1.3.6.1.4.1.37950.1.1.5.12.8.4.9.5
-- 1.3.6.1.4.1.37950.1.1.5.12.8.4.9.5
-- 1.3.6.1.4.1.37950.1.1.5.12.8.4.9.5
-- 1.3.6.1.4.1.37950.1.1.5.12.8.4.9.5
-- 1.3.6.1.4.1.37950.1.1.5.12.8.4.9.5
-- 1.3.6.1.4.1.37950.1.1.5.12.8.4.9.5
		-- 1.3.6.1.4.1.37950.1.1.5.12.8.4.9.5
		priOutputGain OBJECT-TYPE
			SYNTAX Integer32 (-32..32)
			MAX-ACCESS read-write
			STATUS current
			DESCRIPTION
				"Description."
			::= { voipPotsParameter 5 }

		
--          1.3.6.1.4.1.37950.1.1.5.12.8.4.9.6
-- 1.3.6.1.4.1.37950.1.1.5.12.8.4.9.6
-- 1.3.6.1.4.1.37950.1.1.5.12.8.4.9.6
-- 1.3.6.1.4.1.37950.1.1.5.12.8.4.9.6
-- 1.3.6.1.4.1.37950.1.1.5.12.8.4.9.6
-- 1.3.6.1.4.1.37950.1.1.5.12.8.4.9.6
-- 1.3.6.1.4.1.37950.1.1.5.12.8.4.9.6
-- 1.3.6.1.4.1.37950.1.1.5.12.8.4.9.6
-- 1.3.6.1.4.1.37950.1.1.5.12.8.4.9.6
		-- 1.3.6.1.4.1.37950.1.1.5.12.8.4.9.6
		priDtmfMode OBJECT-TYPE
			SYNTAX INTEGER
				{
				transparent(0),
				rfc2833(1),
				rfc2833-redundancy(2),
				outband(3)
				}
			MAX-ACCESS read-write
			STATUS current
			DESCRIPTION
				"Description."
			::= { voipPotsParameter 6 }

		
--          1.3.6.1.4.1.37950.1.1.5.12.8.4.9.7
-- 1.3.6.1.4.1.37950.1.1.5.12.8.4.9.7
-- 1.3.6.1.4.1.37950.1.1.5.12.8.4.9.7
-- 1.3.6.1.4.1.37950.1.1.5.12.8.4.9.7
-- 1.3.6.1.4.1.37950.1.1.5.12.8.4.9.7
-- 1.3.6.1.4.1.37950.1.1.5.12.8.4.9.7
-- 1.3.6.1.4.1.37950.1.1.5.12.8.4.9.7
-- 1.3.6.1.4.1.37950.1.1.5.12.8.4.9.7
-- 1.3.6.1.4.1.37950.1.1.5.12.8.4.9.7
		-- 1.3.6.1.4.1.37950.1.1.5.12.8.4.9.7
		priPotsParameterAction OBJECT-TYPE
			SYNTAX INTEGER
				{
				add(1),
				remove(2)
				}
			MAX-ACCESS read-write
			STATUS current
			DESCRIPTION
				"Description."
			::= { voipPotsParameter 7 }

		
--          1.3.6.1.4.1.37950.1.1.5.12.8.4.10
-- 1.3.6.1.4.1.37950.1.1.5.12.8.4.10
-- 1.3.6.1.4.1.37950.1.1.5.12.8.4.10
-- 1.3.6.1.4.1.37950.1.1.5.12.8.4.10
-- 1.3.6.1.4.1.37950.1.1.5.12.8.4.10
-- 1.3.6.1.4.1.37950.1.1.5.12.8.4.10
-- 1.3.6.1.4.1.37950.1.1.5.12.8.4.10
-- 1.3.6.1.4.1.37950.1.1.5.12.8.4.10
-- 1.3.6.1.4.1.37950.1.1.5.12.8.4.10
		-- 1.3.6.1.4.1.37950.1.1.5.12.8.4.10
		onuVoipParam OBJECT IDENTIFIER ::= { voipProfileEdit 10 }

		
--          1.3.6.1.4.1.37950.1.1.5.12.8.4.10.1
-- 1.3.6.1.4.1.37950.1.1.5.12.8.4.10.1
-- 1.3.6.1.4.1.37950.1.1.5.12.8.4.10.1
-- 1.3.6.1.4.1.37950.1.1.5.12.8.4.10.1
-- 1.3.6.1.4.1.37950.1.1.5.12.8.4.10.1
-- 1.3.6.1.4.1.37950.1.1.5.12.8.4.10.1
-- 1.3.6.1.4.1.37950.1.1.5.12.8.4.10.1
-- 1.3.6.1.4.1.37950.1.1.5.12.8.4.10.1
-- 1.3.6.1.4.1.37950.1.1.5.12.8.4.10.1
		-- 1.3.6.1.4.1.37950.1.1.5.12.8.4.10.1
		ipMode OBJECT-TYPE
			SYNTAX INTEGER
				{
				static(1),
				dhcp(2),
				pppoe(3)
				}
			MAX-ACCESS read-write
			STATUS current
			DESCRIPTION
				"Description."
			::= { onuVoipParam 1 }

		
--          1.3.6.1.4.1.37950.1.1.5.12.8.4.10.2
-- 1.3.6.1.4.1.37950.1.1.5.12.8.4.10.2
-- 1.3.6.1.4.1.37950.1.1.5.12.8.4.10.2
-- 1.3.6.1.4.1.37950.1.1.5.12.8.4.10.2
-- 1.3.6.1.4.1.37950.1.1.5.12.8.4.10.2
-- 1.3.6.1.4.1.37950.1.1.5.12.8.4.10.2
-- 1.3.6.1.4.1.37950.1.1.5.12.8.4.10.2
-- 1.3.6.1.4.1.37950.1.1.5.12.8.4.10.2
-- 1.3.6.1.4.1.37950.1.1.5.12.8.4.10.2
		-- 1.3.6.1.4.1.37950.1.1.5.12.8.4.10.2
		ip OBJECT-TYPE
			SYNTAX IpAddress
			MAX-ACCESS read-write
			STATUS current
			DESCRIPTION
				"Description."
			::= { onuVoipParam 2 }

		
--          1.3.6.1.4.1.37950.1.1.5.12.8.4.10.3
-- 1.3.6.1.4.1.37950.1.1.5.12.8.4.10.3
-- 1.3.6.1.4.1.37950.1.1.5.12.8.4.10.3
-- 1.3.6.1.4.1.37950.1.1.5.12.8.4.10.3
-- 1.3.6.1.4.1.37950.1.1.5.12.8.4.10.3
-- 1.3.6.1.4.1.37950.1.1.5.12.8.4.10.3
-- 1.3.6.1.4.1.37950.1.1.5.12.8.4.10.3
-- 1.3.6.1.4.1.37950.1.1.5.12.8.4.10.3
-- 1.3.6.1.4.1.37950.1.1.5.12.8.4.10.3
		-- 1.3.6.1.4.1.37950.1.1.5.12.8.4.10.3
		mask OBJECT-TYPE
			SYNTAX IpAddress
			MAX-ACCESS read-write
			STATUS current
			DESCRIPTION
				"Description."
			::= { onuVoipParam 3 }

		
--          1.3.6.1.4.1.37950.1.1.5.12.8.4.10.4
-- 1.3.6.1.4.1.37950.1.1.5.12.8.4.10.4
-- 1.3.6.1.4.1.37950.1.1.5.12.8.4.10.4
-- 1.3.6.1.4.1.37950.1.1.5.12.8.4.10.4
-- 1.3.6.1.4.1.37950.1.1.5.12.8.4.10.4
-- 1.3.6.1.4.1.37950.1.1.5.12.8.4.10.4
-- 1.3.6.1.4.1.37950.1.1.5.12.8.4.10.4
-- 1.3.6.1.4.1.37950.1.1.5.12.8.4.10.4
-- 1.3.6.1.4.1.37950.1.1.5.12.8.4.10.4
		-- 1.3.6.1.4.1.37950.1.1.5.12.8.4.10.4
		gw OBJECT-TYPE
			SYNTAX IpAddress
			MAX-ACCESS read-write
			STATUS current
			DESCRIPTION
				"Description."
			::= { onuVoipParam 4 }

		
--          1.3.6.1.4.1.37950.1.1.5.12.8.4.10.5
-- 1.3.6.1.4.1.37950.1.1.5.12.8.4.10.5
-- 1.3.6.1.4.1.37950.1.1.5.12.8.4.10.5
-- 1.3.6.1.4.1.37950.1.1.5.12.8.4.10.5
-- 1.3.6.1.4.1.37950.1.1.5.12.8.4.10.5
-- 1.3.6.1.4.1.37950.1.1.5.12.8.4.10.5
-- 1.3.6.1.4.1.37950.1.1.5.12.8.4.10.5
-- 1.3.6.1.4.1.37950.1.1.5.12.8.4.10.5
-- 1.3.6.1.4.1.37950.1.1.5.12.8.4.10.5
		-- 1.3.6.1.4.1.37950.1.1.5.12.8.4.10.5
		rtpIp OBJECT-TYPE
			SYNTAX IpAddress
			MAX-ACCESS read-write
			STATUS current
			DESCRIPTION
				"Description."
			::= { onuVoipParam 5 }

		
--          1.3.6.1.4.1.37950.1.1.5.12.8.4.10.6
-- 1.3.6.1.4.1.37950.1.1.5.12.8.4.10.6
-- 1.3.6.1.4.1.37950.1.1.5.12.8.4.10.6
-- 1.3.6.1.4.1.37950.1.1.5.12.8.4.10.6
-- 1.3.6.1.4.1.37950.1.1.5.12.8.4.10.6
-- 1.3.6.1.4.1.37950.1.1.5.12.8.4.10.6
-- 1.3.6.1.4.1.37950.1.1.5.12.8.4.10.6
-- 1.3.6.1.4.1.37950.1.1.5.12.8.4.10.6
-- 1.3.6.1.4.1.37950.1.1.5.12.8.4.10.6
		-- 1.3.6.1.4.1.37950.1.1.5.12.8.4.10.6
		rtpMask OBJECT-TYPE
			SYNTAX IpAddress
			MAX-ACCESS read-write
			STATUS current
			DESCRIPTION
				"Description."
			::= { onuVoipParam 6 }

		
--          1.3.6.1.4.1.37950.1.1.5.12.8.4.10.7
-- 1.3.6.1.4.1.37950.1.1.5.12.8.4.10.7
-- 1.3.6.1.4.1.37950.1.1.5.12.8.4.10.7
-- 1.3.6.1.4.1.37950.1.1.5.12.8.4.10.7
-- 1.3.6.1.4.1.37950.1.1.5.12.8.4.10.7
-- 1.3.6.1.4.1.37950.1.1.5.12.8.4.10.7
-- 1.3.6.1.4.1.37950.1.1.5.12.8.4.10.7
-- 1.3.6.1.4.1.37950.1.1.5.12.8.4.10.7
-- 1.3.6.1.4.1.37950.1.1.5.12.8.4.10.7
		-- 1.3.6.1.4.1.37950.1.1.5.12.8.4.10.7
		rtpGw OBJECT-TYPE
			SYNTAX IpAddress
			MAX-ACCESS read-write
			STATUS current
			DESCRIPTION
				"Description."
			::= { onuVoipParam 7 }

		
--          1.3.6.1.4.1.37950.1.1.5.12.8.4.10.8
-- 1.3.6.1.4.1.37950.1.1.5.12.8.4.10.8
-- 1.3.6.1.4.1.37950.1.1.5.12.8.4.10.8
-- 1.3.6.1.4.1.37950.1.1.5.12.8.4.10.8
-- 1.3.6.1.4.1.37950.1.1.5.12.8.4.10.8
-- 1.3.6.1.4.1.37950.1.1.5.12.8.4.10.8
-- 1.3.6.1.4.1.37950.1.1.5.12.8.4.10.8
-- 1.3.6.1.4.1.37950.1.1.5.12.8.4.10.8
-- 1.3.6.1.4.1.37950.1.1.5.12.8.4.10.8
		-- 1.3.6.1.4.1.37950.1.1.5.12.8.4.10.8
		dnsMaster OBJECT-TYPE
			SYNTAX IpAddress
			MAX-ACCESS read-write
			STATUS current
			DESCRIPTION
				"Description."
			::= { onuVoipParam 8 }

		
--          1.3.6.1.4.1.37950.1.1.5.12.8.4.10.9
-- 1.3.6.1.4.1.37950.1.1.5.12.8.4.10.9
-- 1.3.6.1.4.1.37950.1.1.5.12.8.4.10.9
-- 1.3.6.1.4.1.37950.1.1.5.12.8.4.10.9
-- 1.3.6.1.4.1.37950.1.1.5.12.8.4.10.9
-- 1.3.6.1.4.1.37950.1.1.5.12.8.4.10.9
-- 1.3.6.1.4.1.37950.1.1.5.12.8.4.10.9
-- 1.3.6.1.4.1.37950.1.1.5.12.8.4.10.9
-- 1.3.6.1.4.1.37950.1.1.5.12.8.4.10.9
		-- 1.3.6.1.4.1.37950.1.1.5.12.8.4.10.9
		dnsSlave OBJECT-TYPE
			SYNTAX IpAddress
			MAX-ACCESS read-write
			STATUS current
			DESCRIPTION
				"Description."
			::= { onuVoipParam 9 }

		
--          1.3.6.1.4.1.37950.1.1.5.12.8.4.10.10
-- 1.3.6.1.4.1.37950.1.1.5.12.8.4.10.10
-- 1.3.6.1.4.1.37950.1.1.5.12.8.4.10.10
-- 1.3.6.1.4.1.37950.1.1.5.12.8.4.10.10
-- 1.3.6.1.4.1.37950.1.1.5.12.8.4.10.10
-- 1.3.6.1.4.1.37950.1.1.5.12.8.4.10.10
-- 1.3.6.1.4.1.37950.1.1.5.12.8.4.10.10
-- 1.3.6.1.4.1.37950.1.1.5.12.8.4.10.10
-- 1.3.6.1.4.1.37950.1.1.5.12.8.4.10.10
		-- 1.3.6.1.4.1.37950.1.1.5.12.8.4.10.10
		dhcpOption60Enable OBJECT-TYPE
			SYNTAX INTEGER
				{
				disable(0),
				enable(1)
				}
			MAX-ACCESS read-write
			STATUS current
			DESCRIPTION
				"Description."
			::= { onuVoipParam 10 }

		
--          1.3.6.1.4.1.37950.1.1.5.12.8.4.10.11
-- 1.3.6.1.4.1.37950.1.1.5.12.8.4.10.11
-- 1.3.6.1.4.1.37950.1.1.5.12.8.4.10.11
-- 1.3.6.1.4.1.37950.1.1.5.12.8.4.10.11
-- 1.3.6.1.4.1.37950.1.1.5.12.8.4.10.11
-- 1.3.6.1.4.1.37950.1.1.5.12.8.4.10.11
-- 1.3.6.1.4.1.37950.1.1.5.12.8.4.10.11
-- 1.3.6.1.4.1.37950.1.1.5.12.8.4.10.11
-- 1.3.6.1.4.1.37950.1.1.5.12.8.4.10.11
		-- 1.3.6.1.4.1.37950.1.1.5.12.8.4.10.11
		dhcpOption60Base OBJECT-TYPE
			SYNTAX OCTET STRING
			MAX-ACCESS read-write
			STATUS current
			DESCRIPTION
				"Description."
			::= { onuVoipParam 11 }

		
--          1.3.6.1.4.1.37950.1.1.5.12.8.4.10.12
-- 1.3.6.1.4.1.37950.1.1.5.12.8.4.10.12
-- 1.3.6.1.4.1.37950.1.1.5.12.8.4.10.12
-- 1.3.6.1.4.1.37950.1.1.5.12.8.4.10.12
-- 1.3.6.1.4.1.37950.1.1.5.12.8.4.10.12
-- 1.3.6.1.4.1.37950.1.1.5.12.8.4.10.12
-- 1.3.6.1.4.1.37950.1.1.5.12.8.4.10.12
-- 1.3.6.1.4.1.37950.1.1.5.12.8.4.10.12
-- 1.3.6.1.4.1.37950.1.1.5.12.8.4.10.12
		-- 1.3.6.1.4.1.37950.1.1.5.12.8.4.10.12
		dhcpOption60Value OBJECT-TYPE
			SYNTAX OCTET STRING
			MAX-ACCESS read-write
			STATUS current
			DESCRIPTION
				"Description."
			::= { onuVoipParam 12 }

		
--          1.3.6.1.4.1.37950.1.1.5.12.8.4.10.13
-- 1.3.6.1.4.1.37950.1.1.5.12.8.4.10.13
-- 1.3.6.1.4.1.37950.1.1.5.12.8.4.10.13
-- 1.3.6.1.4.1.37950.1.1.5.12.8.4.10.13
-- 1.3.6.1.4.1.37950.1.1.5.12.8.4.10.13
-- 1.3.6.1.4.1.37950.1.1.5.12.8.4.10.13
-- 1.3.6.1.4.1.37950.1.1.5.12.8.4.10.13
-- 1.3.6.1.4.1.37950.1.1.5.12.8.4.10.13
-- 1.3.6.1.4.1.37950.1.1.5.12.8.4.10.13
		-- 1.3.6.1.4.1.37950.1.1.5.12.8.4.10.13
		pppoeMode OBJECT-TYPE
			SYNTAX INTEGER
				{
				auto(0),
				chap(1),
				pap(2)
				}
			MAX-ACCESS read-write
			STATUS current
			DESCRIPTION
				"Description."
			::= { onuVoipParam 13 }

		
--          1.3.6.1.4.1.37950.1.1.5.12.8.4.10.14
-- 1.3.6.1.4.1.37950.1.1.5.12.8.4.10.14
-- 1.3.6.1.4.1.37950.1.1.5.12.8.4.10.14
-- 1.3.6.1.4.1.37950.1.1.5.12.8.4.10.14
-- 1.3.6.1.4.1.37950.1.1.5.12.8.4.10.14
-- 1.3.6.1.4.1.37950.1.1.5.12.8.4.10.14
-- 1.3.6.1.4.1.37950.1.1.5.12.8.4.10.14
-- 1.3.6.1.4.1.37950.1.1.5.12.8.4.10.14
-- 1.3.6.1.4.1.37950.1.1.5.12.8.4.10.14
		-- 1.3.6.1.4.1.37950.1.1.5.12.8.4.10.14
		pppoeUsername OBJECT-TYPE
			SYNTAX OCTET STRING
			MAX-ACCESS read-write
			STATUS current
			DESCRIPTION
				"Description."
			::= { onuVoipParam 14 }

		
--          1.3.6.1.4.1.37950.1.1.5.12.8.4.10.15
-- 1.3.6.1.4.1.37950.1.1.5.12.8.4.10.15
-- 1.3.6.1.4.1.37950.1.1.5.12.8.4.10.15
-- 1.3.6.1.4.1.37950.1.1.5.12.8.4.10.15
-- 1.3.6.1.4.1.37950.1.1.5.12.8.4.10.15
-- 1.3.6.1.4.1.37950.1.1.5.12.8.4.10.15
-- 1.3.6.1.4.1.37950.1.1.5.12.8.4.10.15
-- 1.3.6.1.4.1.37950.1.1.5.12.8.4.10.15
-- 1.3.6.1.4.1.37950.1.1.5.12.8.4.10.15
		-- 1.3.6.1.4.1.37950.1.1.5.12.8.4.10.15
		pppoePassword OBJECT-TYPE
			SYNTAX OCTET STRING
			MAX-ACCESS read-write
			STATUS current
			DESCRIPTION
				"Description."
			::= { onuVoipParam 15 }

		
--          1.3.6.1.4.1.37950.1.1.5.12.8.4.10.16
-- 1.3.6.1.4.1.37950.1.1.5.12.8.4.10.16
-- 1.3.6.1.4.1.37950.1.1.5.12.8.4.10.16
-- 1.3.6.1.4.1.37950.1.1.5.12.8.4.10.16
-- 1.3.6.1.4.1.37950.1.1.5.12.8.4.10.16
-- 1.3.6.1.4.1.37950.1.1.5.12.8.4.10.16
-- 1.3.6.1.4.1.37950.1.1.5.12.8.4.10.16
-- 1.3.6.1.4.1.37950.1.1.5.12.8.4.10.16
-- 1.3.6.1.4.1.37950.1.1.5.12.8.4.10.16
		-- 1.3.6.1.4.1.37950.1.1.5.12.8.4.10.16
		svlanTpid OBJECT-TYPE
			SYNTAX Integer32
			MAX-ACCESS read-write
			STATUS current
			DESCRIPTION
				"Description."
			::= { onuVoipParam 16 }

		
--          1.3.6.1.4.1.37950.1.1.5.12.8.4.10.17
-- 1.3.6.1.4.1.37950.1.1.5.12.8.4.10.17
-- 1.3.6.1.4.1.37950.1.1.5.12.8.4.10.17
-- 1.3.6.1.4.1.37950.1.1.5.12.8.4.10.17
-- 1.3.6.1.4.1.37950.1.1.5.12.8.4.10.17
-- 1.3.6.1.4.1.37950.1.1.5.12.8.4.10.17
-- 1.3.6.1.4.1.37950.1.1.5.12.8.4.10.17
-- 1.3.6.1.4.1.37950.1.1.5.12.8.4.10.17
-- 1.3.6.1.4.1.37950.1.1.5.12.8.4.10.17
		-- 1.3.6.1.4.1.37950.1.1.5.12.8.4.10.17
		svlanId OBJECT-TYPE
			SYNTAX Integer32 (0..4095)
			MAX-ACCESS read-write
			STATUS current
			DESCRIPTION
				"Description."
			::= { onuVoipParam 17 }

		
--          1.3.6.1.4.1.37950.1.1.5.12.8.4.10.18
-- 1.3.6.1.4.1.37950.1.1.5.12.8.4.10.18
-- 1.3.6.1.4.1.37950.1.1.5.12.8.4.10.18
-- 1.3.6.1.4.1.37950.1.1.5.12.8.4.10.18
-- 1.3.6.1.4.1.37950.1.1.5.12.8.4.10.18
-- 1.3.6.1.4.1.37950.1.1.5.12.8.4.10.18
-- 1.3.6.1.4.1.37950.1.1.5.12.8.4.10.18
-- 1.3.6.1.4.1.37950.1.1.5.12.8.4.10.18
-- 1.3.6.1.4.1.37950.1.1.5.12.8.4.10.18
		-- 1.3.6.1.4.1.37950.1.1.5.12.8.4.10.18
		svlanCos OBJECT-TYPE
			SYNTAX Integer32 (0..7)
			MAX-ACCESS read-write
			STATUS current
			DESCRIPTION
				"Description."
			::= { onuVoipParam 18 }

		
--          1.3.6.1.4.1.37950.1.1.5.12.8.4.10.19
-- 1.3.6.1.4.1.37950.1.1.5.12.8.4.10.19
-- 1.3.6.1.4.1.37950.1.1.5.12.8.4.10.19
-- 1.3.6.1.4.1.37950.1.1.5.12.8.4.10.19
-- 1.3.6.1.4.1.37950.1.1.5.12.8.4.10.19
-- 1.3.6.1.4.1.37950.1.1.5.12.8.4.10.19
-- 1.3.6.1.4.1.37950.1.1.5.12.8.4.10.19
-- 1.3.6.1.4.1.37950.1.1.5.12.8.4.10.19
-- 1.3.6.1.4.1.37950.1.1.5.12.8.4.10.19
		-- 1.3.6.1.4.1.37950.1.1.5.12.8.4.10.19
		cvlanTpid OBJECT-TYPE
			SYNTAX Integer32
			MAX-ACCESS read-write
			STATUS current
			DESCRIPTION
				"Description."
			::= { onuVoipParam 19 }

		
--          1.3.6.1.4.1.37950.1.1.5.12.8.4.10.20
-- 1.3.6.1.4.1.37950.1.1.5.12.8.4.10.20
-- 1.3.6.1.4.1.37950.1.1.5.12.8.4.10.20
-- 1.3.6.1.4.1.37950.1.1.5.12.8.4.10.20
-- 1.3.6.1.4.1.37950.1.1.5.12.8.4.10.20
-- 1.3.6.1.4.1.37950.1.1.5.12.8.4.10.20
-- 1.3.6.1.4.1.37950.1.1.5.12.8.4.10.20
-- 1.3.6.1.4.1.37950.1.1.5.12.8.4.10.20
-- 1.3.6.1.4.1.37950.1.1.5.12.8.4.10.20
		-- 1.3.6.1.4.1.37950.1.1.5.12.8.4.10.20
		cvlanId OBJECT-TYPE
			SYNTAX Integer32 (0..4095)
			MAX-ACCESS read-write
			STATUS current
			DESCRIPTION
				"Description."
			::= { onuVoipParam 20 }

		
--          1.3.6.1.4.1.37950.1.1.5.12.8.4.10.21
-- 1.3.6.1.4.1.37950.1.1.5.12.8.4.10.21
-- 1.3.6.1.4.1.37950.1.1.5.12.8.4.10.21
-- 1.3.6.1.4.1.37950.1.1.5.12.8.4.10.21
-- 1.3.6.1.4.1.37950.1.1.5.12.8.4.10.21
-- 1.3.6.1.4.1.37950.1.1.5.12.8.4.10.21
-- 1.3.6.1.4.1.37950.1.1.5.12.8.4.10.21
-- 1.3.6.1.4.1.37950.1.1.5.12.8.4.10.21
-- 1.3.6.1.4.1.37950.1.1.5.12.8.4.10.21
		-- 1.3.6.1.4.1.37950.1.1.5.12.8.4.10.21
		cvlanCos OBJECT-TYPE
			SYNTAX Integer32 (0..7)
			MAX-ACCESS read-write
			STATUS current
			DESCRIPTION
				"Description."
			::= { onuVoipParam 21 }

		
--          1.3.6.1.4.1.37950.1.1.5.12.8.4.10.22
-- 1.3.6.1.4.1.37950.1.1.5.12.8.4.10.22
-- 1.3.6.1.4.1.37950.1.1.5.12.8.4.10.22
-- 1.3.6.1.4.1.37950.1.1.5.12.8.4.10.22
-- 1.3.6.1.4.1.37950.1.1.5.12.8.4.10.22
-- 1.3.6.1.4.1.37950.1.1.5.12.8.4.10.22
-- 1.3.6.1.4.1.37950.1.1.5.12.8.4.10.22
-- 1.3.6.1.4.1.37950.1.1.5.12.8.4.10.22
-- 1.3.6.1.4.1.37950.1.1.5.12.8.4.10.22
		-- 1.3.6.1.4.1.37950.1.1.5.12.8.4.10.22
		rtpSVlanTpid OBJECT-TYPE
			SYNTAX Integer32
			MAX-ACCESS read-write
			STATUS current
			DESCRIPTION
				"Description."
			::= { onuVoipParam 22 }

		
--          1.3.6.1.4.1.37950.1.1.5.12.8.4.10.23
-- 1.3.6.1.4.1.37950.1.1.5.12.8.4.10.23
-- 1.3.6.1.4.1.37950.1.1.5.12.8.4.10.23
-- 1.3.6.1.4.1.37950.1.1.5.12.8.4.10.23
-- 1.3.6.1.4.1.37950.1.1.5.12.8.4.10.23
-- 1.3.6.1.4.1.37950.1.1.5.12.8.4.10.23
-- 1.3.6.1.4.1.37950.1.1.5.12.8.4.10.23
-- 1.3.6.1.4.1.37950.1.1.5.12.8.4.10.23
-- 1.3.6.1.4.1.37950.1.1.5.12.8.4.10.23
		-- 1.3.6.1.4.1.37950.1.1.5.12.8.4.10.23
		rtpSVlanId OBJECT-TYPE
			SYNTAX Integer32 (0..4095)
			MAX-ACCESS read-write
			STATUS current
			DESCRIPTION
				"Description."
			::= { onuVoipParam 23 }

		
--          1.3.6.1.4.1.37950.1.1.5.12.8.4.10.24
-- 1.3.6.1.4.1.37950.1.1.5.12.8.4.10.24
-- 1.3.6.1.4.1.37950.1.1.5.12.8.4.10.24
-- 1.3.6.1.4.1.37950.1.1.5.12.8.4.10.24
-- 1.3.6.1.4.1.37950.1.1.5.12.8.4.10.24
-- 1.3.6.1.4.1.37950.1.1.5.12.8.4.10.24
-- 1.3.6.1.4.1.37950.1.1.5.12.8.4.10.24
-- 1.3.6.1.4.1.37950.1.1.5.12.8.4.10.24
-- 1.3.6.1.4.1.37950.1.1.5.12.8.4.10.24
		-- 1.3.6.1.4.1.37950.1.1.5.12.8.4.10.24
		rtpSVlanCos OBJECT-TYPE
			SYNTAX Integer32 (0..7)
			MAX-ACCESS read-write
			STATUS current
			DESCRIPTION
				"Description."
			::= { onuVoipParam 24 }

		
--          1.3.6.1.4.1.37950.1.1.5.12.8.4.10.25
-- 1.3.6.1.4.1.37950.1.1.5.12.8.4.10.25
-- 1.3.6.1.4.1.37950.1.1.5.12.8.4.10.25
-- 1.3.6.1.4.1.37950.1.1.5.12.8.4.10.25
-- 1.3.6.1.4.1.37950.1.1.5.12.8.4.10.25
-- 1.3.6.1.4.1.37950.1.1.5.12.8.4.10.25
-- 1.3.6.1.4.1.37950.1.1.5.12.8.4.10.25
-- 1.3.6.1.4.1.37950.1.1.5.12.8.4.10.25
-- 1.3.6.1.4.1.37950.1.1.5.12.8.4.10.25
		-- 1.3.6.1.4.1.37950.1.1.5.12.8.4.10.25
		rtpCVlanTpid OBJECT-TYPE
			SYNTAX Integer32
			MAX-ACCESS read-write
			STATUS current
			DESCRIPTION
				"Description."
			::= { onuVoipParam 25 }

		
--          1.3.6.1.4.1.37950.1.1.5.12.8.4.10.26
-- 1.3.6.1.4.1.37950.1.1.5.12.8.4.10.26
-- 1.3.6.1.4.1.37950.1.1.5.12.8.4.10.26
-- 1.3.6.1.4.1.37950.1.1.5.12.8.4.10.26
-- 1.3.6.1.4.1.37950.1.1.5.12.8.4.10.26
-- 1.3.6.1.4.1.37950.1.1.5.12.8.4.10.26
-- 1.3.6.1.4.1.37950.1.1.5.12.8.4.10.26
-- 1.3.6.1.4.1.37950.1.1.5.12.8.4.10.26
-- 1.3.6.1.4.1.37950.1.1.5.12.8.4.10.26
		-- 1.3.6.1.4.1.37950.1.1.5.12.8.4.10.26
		rtpCVlanId OBJECT-TYPE
			SYNTAX Integer32 (0..4095)
			MAX-ACCESS read-write
			STATUS current
			DESCRIPTION
				"Description."
			::= { onuVoipParam 26 }

		
--          1.3.6.1.4.1.37950.1.1.5.12.8.4.10.27
-- 1.3.6.1.4.1.37950.1.1.5.12.8.4.10.27
-- 1.3.6.1.4.1.37950.1.1.5.12.8.4.10.27
-- 1.3.6.1.4.1.37950.1.1.5.12.8.4.10.27
-- 1.3.6.1.4.1.37950.1.1.5.12.8.4.10.27
-- 1.3.6.1.4.1.37950.1.1.5.12.8.4.10.27
-- 1.3.6.1.4.1.37950.1.1.5.12.8.4.10.27
-- 1.3.6.1.4.1.37950.1.1.5.12.8.4.10.27
-- 1.3.6.1.4.1.37950.1.1.5.12.8.4.10.27
		-- 1.3.6.1.4.1.37950.1.1.5.12.8.4.10.27
		rtpCVlanCos OBJECT-TYPE
			SYNTAX Integer32 (0..7)
			MAX-ACCESS read-write
			STATUS current
			DESCRIPTION
				"Description."
			::= { onuVoipParam 27 }

		
--          1.3.6.1.4.1.37950.1.1.5.12.8.4.10.28
-- 1.3.6.1.4.1.37950.1.1.5.12.8.4.10.28
-- 1.3.6.1.4.1.37950.1.1.5.12.8.4.10.28
-- 1.3.6.1.4.1.37950.1.1.5.12.8.4.10.28
-- 1.3.6.1.4.1.37950.1.1.5.12.8.4.10.28
-- 1.3.6.1.4.1.37950.1.1.5.12.8.4.10.28
-- 1.3.6.1.4.1.37950.1.1.5.12.8.4.10.28
-- 1.3.6.1.4.1.37950.1.1.5.12.8.4.10.28
-- 1.3.6.1.4.1.37950.1.1.5.12.8.4.10.28
		-- 1.3.6.1.4.1.37950.1.1.5.12.8.4.10.28
		voipParamAction OBJECT-TYPE
			SYNTAX INTEGER
				{
				commit(1),
				remove(2)
				}
			MAX-ACCESS read-write
			STATUS current
			DESCRIPTION
				"Description."
			::= { onuVoipParam 28 }

		
--          1.3.6.1.4.1.37950.1.1.5.12.8.4.11
-- 1.3.6.1.4.1.37950.1.1.5.12.8.4.11
-- 1.3.6.1.4.1.37950.1.1.5.12.8.4.11
-- 1.3.6.1.4.1.37950.1.1.5.12.8.4.11
-- 1.3.6.1.4.1.37950.1.1.5.12.8.4.11
-- 1.3.6.1.4.1.37950.1.1.5.12.8.4.11
-- 1.3.6.1.4.1.37950.1.1.5.12.8.4.11
-- 1.3.6.1.4.1.37950.1.1.5.12.8.4.11
-- 1.3.6.1.4.1.37950.1.1.5.12.8.4.11
		-- 1.3.6.1.4.1.37950.1.1.5.12.8.4.11
		onuSipParam OBJECT IDENTIFIER ::= { voipProfileEdit 11 }

		
--          1.3.6.1.4.1.37950.1.1.5.12.8.4.11.1
-- 1.3.6.1.4.1.37950.1.1.5.12.8.4.11.1
-- 1.3.6.1.4.1.37950.1.1.5.12.8.4.11.1
-- 1.3.6.1.4.1.37950.1.1.5.12.8.4.11.1
-- 1.3.6.1.4.1.37950.1.1.5.12.8.4.11.1
-- 1.3.6.1.4.1.37950.1.1.5.12.8.4.11.1
-- 1.3.6.1.4.1.37950.1.1.5.12.8.4.11.1
-- 1.3.6.1.4.1.37950.1.1.5.12.8.4.11.1
-- 1.3.6.1.4.1.37950.1.1.5.12.8.4.11.1
		-- 1.3.6.1.4.1.37950.1.1.5.12.8.4.11.1
		proxyServName OBJECT-TYPE
			SYNTAX OCTET STRING
			MAX-ACCESS read-write
			STATUS current
			DESCRIPTION
				"Description."
			::= { onuSipParam 1 }

		
--          1.3.6.1.4.1.37950.1.1.5.12.8.4.11.2
-- 1.3.6.1.4.1.37950.1.1.5.12.8.4.11.2
-- 1.3.6.1.4.1.37950.1.1.5.12.8.4.11.2
-- 1.3.6.1.4.1.37950.1.1.5.12.8.4.11.2
-- 1.3.6.1.4.1.37950.1.1.5.12.8.4.11.2
-- 1.3.6.1.4.1.37950.1.1.5.12.8.4.11.2
-- 1.3.6.1.4.1.37950.1.1.5.12.8.4.11.2
-- 1.3.6.1.4.1.37950.1.1.5.12.8.4.11.2
-- 1.3.6.1.4.1.37950.1.1.5.12.8.4.11.2
		-- 1.3.6.1.4.1.37950.1.1.5.12.8.4.11.2
		proxyServPort OBJECT-TYPE
			SYNTAX Integer32 (0..65535)
			MAX-ACCESS read-write
			STATUS current
			DESCRIPTION
				"Description."
			::= { onuSipParam 2 }

		
--          1.3.6.1.4.1.37950.1.1.5.12.8.4.11.3
-- 1.3.6.1.4.1.37950.1.1.5.12.8.4.11.3
-- 1.3.6.1.4.1.37950.1.1.5.12.8.4.11.3
-- 1.3.6.1.4.1.37950.1.1.5.12.8.4.11.3
-- 1.3.6.1.4.1.37950.1.1.5.12.8.4.11.3
-- 1.3.6.1.4.1.37950.1.1.5.12.8.4.11.3
-- 1.3.6.1.4.1.37950.1.1.5.12.8.4.11.3
-- 1.3.6.1.4.1.37950.1.1.5.12.8.4.11.3
-- 1.3.6.1.4.1.37950.1.1.5.12.8.4.11.3
		-- 1.3.6.1.4.1.37950.1.1.5.12.8.4.11.3
		bakProxyServName OBJECT-TYPE
			SYNTAX OCTET STRING
			MAX-ACCESS read-write
			STATUS current
			DESCRIPTION
				"Description."
			::= { onuSipParam 3 }

		
--          1.3.6.1.4.1.37950.1.1.5.12.8.4.11.4
-- 1.3.6.1.4.1.37950.1.1.5.12.8.4.11.4
-- 1.3.6.1.4.1.37950.1.1.5.12.8.4.11.4
-- 1.3.6.1.4.1.37950.1.1.5.12.8.4.11.4
-- 1.3.6.1.4.1.37950.1.1.5.12.8.4.11.4
-- 1.3.6.1.4.1.37950.1.1.5.12.8.4.11.4
-- 1.3.6.1.4.1.37950.1.1.5.12.8.4.11.4
-- 1.3.6.1.4.1.37950.1.1.5.12.8.4.11.4
-- 1.3.6.1.4.1.37950.1.1.5.12.8.4.11.4
		-- 1.3.6.1.4.1.37950.1.1.5.12.8.4.11.4
		bakProxyServPort OBJECT-TYPE
			SYNTAX Integer32 (0..65535)
			MAX-ACCESS read-write
			STATUS current
			DESCRIPTION
				"Description."
			::= { onuSipParam 4 }

		
--          1.3.6.1.4.1.37950.1.1.5.12.8.4.11.5
-- 1.3.6.1.4.1.37950.1.1.5.12.8.4.11.5
-- 1.3.6.1.4.1.37950.1.1.5.12.8.4.11.5
-- 1.3.6.1.4.1.37950.1.1.5.12.8.4.11.5
-- 1.3.6.1.4.1.37950.1.1.5.12.8.4.11.5
-- 1.3.6.1.4.1.37950.1.1.5.12.8.4.11.5
-- 1.3.6.1.4.1.37950.1.1.5.12.8.4.11.5
-- 1.3.6.1.4.1.37950.1.1.5.12.8.4.11.5
-- 1.3.6.1.4.1.37950.1.1.5.12.8.4.11.5
		-- 1.3.6.1.4.1.37950.1.1.5.12.8.4.11.5
		regServName OBJECT-TYPE
			SYNTAX OCTET STRING
			MAX-ACCESS read-write
			STATUS current
			DESCRIPTION
				"Description."
			::= { onuSipParam 5 }

		
--          1.3.6.1.4.1.37950.1.1.5.12.8.4.11.6
-- 1.3.6.1.4.1.37950.1.1.5.12.8.4.11.6
-- 1.3.6.1.4.1.37950.1.1.5.12.8.4.11.6
-- 1.3.6.1.4.1.37950.1.1.5.12.8.4.11.6
-- 1.3.6.1.4.1.37950.1.1.5.12.8.4.11.6
-- 1.3.6.1.4.1.37950.1.1.5.12.8.4.11.6
-- 1.3.6.1.4.1.37950.1.1.5.12.8.4.11.6
-- 1.3.6.1.4.1.37950.1.1.5.12.8.4.11.6
-- 1.3.6.1.4.1.37950.1.1.5.12.8.4.11.6
		-- 1.3.6.1.4.1.37950.1.1.5.12.8.4.11.6
		regServPort OBJECT-TYPE
			SYNTAX Integer32 (0..65535)
			MAX-ACCESS read-write
			STATUS current
			DESCRIPTION
				"Description."
			::= { onuSipParam 6 }

		
--          1.3.6.1.4.1.37950.1.1.5.12.8.4.11.7
-- 1.3.6.1.4.1.37950.1.1.5.12.8.4.11.7
-- 1.3.6.1.4.1.37950.1.1.5.12.8.4.11.7
-- 1.3.6.1.4.1.37950.1.1.5.12.8.4.11.7
-- 1.3.6.1.4.1.37950.1.1.5.12.8.4.11.7
-- 1.3.6.1.4.1.37950.1.1.5.12.8.4.11.7
-- 1.3.6.1.4.1.37950.1.1.5.12.8.4.11.7
-- 1.3.6.1.4.1.37950.1.1.5.12.8.4.11.7
-- 1.3.6.1.4.1.37950.1.1.5.12.8.4.11.7
		-- 1.3.6.1.4.1.37950.1.1.5.12.8.4.11.7
		bakRegServName OBJECT-TYPE
			SYNTAX OCTET STRING
			MAX-ACCESS read-write
			STATUS current
			DESCRIPTION
				"Description."
			::= { onuSipParam 7 }

		
--          1.3.6.1.4.1.37950.1.1.5.12.8.4.11.8
-- 1.3.6.1.4.1.37950.1.1.5.12.8.4.11.8
-- 1.3.6.1.4.1.37950.1.1.5.12.8.4.11.8
-- 1.3.6.1.4.1.37950.1.1.5.12.8.4.11.8
-- 1.3.6.1.4.1.37950.1.1.5.12.8.4.11.8
-- 1.3.6.1.4.1.37950.1.1.5.12.8.4.11.8
-- 1.3.6.1.4.1.37950.1.1.5.12.8.4.11.8
-- 1.3.6.1.4.1.37950.1.1.5.12.8.4.11.8
-- 1.3.6.1.4.1.37950.1.1.5.12.8.4.11.8
		-- 1.3.6.1.4.1.37950.1.1.5.12.8.4.11.8
		bakRegServPort OBJECT-TYPE
			SYNTAX Integer32 (0..65535)
			MAX-ACCESS read-write
			STATUS current
			DESCRIPTION
				"Description."
			::= { onuSipParam 8 }

		
--          1.3.6.1.4.1.37950.1.1.5.12.8.4.11.9
-- 1.3.6.1.4.1.37950.1.1.5.12.8.4.11.9
-- 1.3.6.1.4.1.37950.1.1.5.12.8.4.11.9
-- 1.3.6.1.4.1.37950.1.1.5.12.8.4.11.9
-- 1.3.6.1.4.1.37950.1.1.5.12.8.4.11.9
-- 1.3.6.1.4.1.37950.1.1.5.12.8.4.11.9
-- 1.3.6.1.4.1.37950.1.1.5.12.8.4.11.9
-- 1.3.6.1.4.1.37950.1.1.5.12.8.4.11.9
-- 1.3.6.1.4.1.37950.1.1.5.12.8.4.11.9
		-- 1.3.6.1.4.1.37950.1.1.5.12.8.4.11.9
		outBndServName OBJECT-TYPE
			SYNTAX OCTET STRING
			MAX-ACCESS read-write
			STATUS current
			DESCRIPTION
				"Description."
			::= { onuSipParam 9 }

		
--          1.3.6.1.4.1.37950.1.1.5.12.8.4.11.10
-- 1.3.6.1.4.1.37950.1.1.5.12.8.4.11.10
-- 1.3.6.1.4.1.37950.1.1.5.12.8.4.11.10
-- 1.3.6.1.4.1.37950.1.1.5.12.8.4.11.10
-- 1.3.6.1.4.1.37950.1.1.5.12.8.4.11.10
-- 1.3.6.1.4.1.37950.1.1.5.12.8.4.11.10
-- 1.3.6.1.4.1.37950.1.1.5.12.8.4.11.10
-- 1.3.6.1.4.1.37950.1.1.5.12.8.4.11.10
-- 1.3.6.1.4.1.37950.1.1.5.12.8.4.11.10
		-- 1.3.6.1.4.1.37950.1.1.5.12.8.4.11.10
		outBndServPort OBJECT-TYPE
			SYNTAX Integer32 (0..65535)
			MAX-ACCESS read-write
			STATUS current
			DESCRIPTION
				"Description."
			::= { onuSipParam 10 }

		
--          1.3.6.1.4.1.37950.1.1.5.12.8.4.11.11
-- 1.3.6.1.4.1.37950.1.1.5.12.8.4.11.11
-- 1.3.6.1.4.1.37950.1.1.5.12.8.4.11.11
-- 1.3.6.1.4.1.37950.1.1.5.12.8.4.11.11
-- 1.3.6.1.4.1.37950.1.1.5.12.8.4.11.11
-- 1.3.6.1.4.1.37950.1.1.5.12.8.4.11.11
-- 1.3.6.1.4.1.37950.1.1.5.12.8.4.11.11
-- 1.3.6.1.4.1.37950.1.1.5.12.8.4.11.11
-- 1.3.6.1.4.1.37950.1.1.5.12.8.4.11.11
		-- 1.3.6.1.4.1.37950.1.1.5.12.8.4.11.11
		sipParamMgPort OBJECT-TYPE
			SYNTAX Integer32 (0..65535)
			MAX-ACCESS read-write
			STATUS current
			DESCRIPTION
				"Description."
			::= { onuSipParam 11 }

		
--          1.3.6.1.4.1.37950.1.1.5.12.8.4.11.12
-- 1.3.6.1.4.1.37950.1.1.5.12.8.4.11.12
-- 1.3.6.1.4.1.37950.1.1.5.12.8.4.11.12
-- 1.3.6.1.4.1.37950.1.1.5.12.8.4.11.12
-- 1.3.6.1.4.1.37950.1.1.5.12.8.4.11.12
-- 1.3.6.1.4.1.37950.1.1.5.12.8.4.11.12
-- 1.3.6.1.4.1.37950.1.1.5.12.8.4.11.12
-- 1.3.6.1.4.1.37950.1.1.5.12.8.4.11.12
-- 1.3.6.1.4.1.37950.1.1.5.12.8.4.11.12
		-- 1.3.6.1.4.1.37950.1.1.5.12.8.4.11.12
		regInterval OBJECT-TYPE
			SYNTAX Integer32 (0..10000000)
			MAX-ACCESS read-write
			STATUS current
			DESCRIPTION
				"Description."
			::= { onuSipParam 12 }

		
--          1.3.6.1.4.1.37950.1.1.5.12.8.4.11.13
-- 1.3.6.1.4.1.37950.1.1.5.12.8.4.11.13
-- 1.3.6.1.4.1.37950.1.1.5.12.8.4.11.13
-- 1.3.6.1.4.1.37950.1.1.5.12.8.4.11.13
-- 1.3.6.1.4.1.37950.1.1.5.12.8.4.11.13
-- 1.3.6.1.4.1.37950.1.1.5.12.8.4.11.13
-- 1.3.6.1.4.1.37950.1.1.5.12.8.4.11.13
-- 1.3.6.1.4.1.37950.1.1.5.12.8.4.11.13
-- 1.3.6.1.4.1.37950.1.1.5.12.8.4.11.13
		-- 1.3.6.1.4.1.37950.1.1.5.12.8.4.11.13
		hBeatCfg OBJECT-TYPE
			SYNTAX INTEGER
				{
				disable(0),
				active(1),
				passive(2)
				}
			MAX-ACCESS read-write
			STATUS current
			DESCRIPTION
				"Description."
			::= { onuSipParam 13 }

		
--          1.3.6.1.4.1.37950.1.1.5.12.8.4.11.14
-- 1.3.6.1.4.1.37950.1.1.5.12.8.4.11.14
-- 1.3.6.1.4.1.37950.1.1.5.12.8.4.11.14
-- 1.3.6.1.4.1.37950.1.1.5.12.8.4.11.14
-- 1.3.6.1.4.1.37950.1.1.5.12.8.4.11.14
-- 1.3.6.1.4.1.37950.1.1.5.12.8.4.11.14
-- 1.3.6.1.4.1.37950.1.1.5.12.8.4.11.14
-- 1.3.6.1.4.1.37950.1.1.5.12.8.4.11.14
-- 1.3.6.1.4.1.37950.1.1.5.12.8.4.11.14
		-- 1.3.6.1.4.1.37950.1.1.5.12.8.4.11.14
		hBeatCycle OBJECT-TYPE
			SYNTAX Integer32 (1..65525)
			MAX-ACCESS read-write
			STATUS current
			DESCRIPTION
				"Description."
			::= { onuSipParam 14 }

		
--          1.3.6.1.4.1.37950.1.1.5.12.8.4.11.15
-- 1.3.6.1.4.1.37950.1.1.5.12.8.4.11.15
-- 1.3.6.1.4.1.37950.1.1.5.12.8.4.11.15
-- 1.3.6.1.4.1.37950.1.1.5.12.8.4.11.15
-- 1.3.6.1.4.1.37950.1.1.5.12.8.4.11.15
-- 1.3.6.1.4.1.37950.1.1.5.12.8.4.11.15
-- 1.3.6.1.4.1.37950.1.1.5.12.8.4.11.15
-- 1.3.6.1.4.1.37950.1.1.5.12.8.4.11.15
-- 1.3.6.1.4.1.37950.1.1.5.12.8.4.11.15
		-- 1.3.6.1.4.1.37950.1.1.5.12.8.4.11.15
		hBeatCount OBJECT-TYPE
			SYNTAX Integer32 (1..65535)
			MAX-ACCESS read-write
			STATUS current
			DESCRIPTION
				"Description."
			::= { onuSipParam 15 }

		
--          1.3.6.1.4.1.37950.1.1.5.12.8.4.11.16
-- 1.3.6.1.4.1.37950.1.1.5.12.8.4.11.16
-- 1.3.6.1.4.1.37950.1.1.5.12.8.4.11.16
-- 1.3.6.1.4.1.37950.1.1.5.12.8.4.11.16
-- 1.3.6.1.4.1.37950.1.1.5.12.8.4.11.16
-- 1.3.6.1.4.1.37950.1.1.5.12.8.4.11.16
-- 1.3.6.1.4.1.37950.1.1.5.12.8.4.11.16
-- 1.3.6.1.4.1.37950.1.1.5.12.8.4.11.16
-- 1.3.6.1.4.1.37950.1.1.5.12.8.4.11.16
		-- 1.3.6.1.4.1.37950.1.1.5.12.8.4.11.16
		sipGloParamAction OBJECT-TYPE
			SYNTAX INTEGER
				{
				commit(1),
				remove(2)
				}
			MAX-ACCESS read-write
			STATUS current
			DESCRIPTION
				"Description."
			::= { onuSipParam 16 }

		
--          1.3.6.1.4.1.37950.1.1.5.12.8.5
-- 1.3.6.1.4.1.37950.1.1.5.12.8.5
-- 1.3.6.1.4.1.37950.1.1.5.12.8.5
-- 1.3.6.1.4.1.37950.1.1.5.12.8.5
-- 1.3.6.1.4.1.37950.1.1.5.12.8.5
-- 1.3.6.1.4.1.37950.1.1.5.12.8.5
-- 1.3.6.1.4.1.37950.1.1.5.12.8.5
-- 1.3.6.1.4.1.37950.1.1.5.12.8.5
-- 1.3.6.1.4.1.37950.1.1.5.12.8.5
		-- 1.3.6.1.4.1.37950.1.1.5.12.8.5
		alarmProfileEdit OBJECT IDENTIFIER ::= { onuProfileCfg 5 }

		
--          1.3.6.1.4.1.37950.1.1.5.12.8.5.2
-- 1.3.6.1.4.1.37950.1.1.5.12.8.5.2
-- 1.3.6.1.4.1.37950.1.1.5.12.8.5.2
-- 1.3.6.1.4.1.37950.1.1.5.12.8.5.2
-- 1.3.6.1.4.1.37950.1.1.5.12.8.5.2
-- 1.3.6.1.4.1.37950.1.1.5.12.8.5.2
-- 1.3.6.1.4.1.37950.1.1.5.12.8.5.2
-- 1.3.6.1.4.1.37950.1.1.5.12.8.5.2
-- 1.3.6.1.4.1.37950.1.1.5.12.8.5.2
		-- 1.3.6.1.4.1.37950.1.1.5.12.8.5.2
		alarmProfileNo OBJECT-TYPE
			SYNTAX INTEGER (1..32767)
			MAX-ACCESS read-write
			STATUS current
			DESCRIPTION
				"Description."
			::= { alarmProfileEdit 2 }

		
--          1.3.6.1.4.1.37950.1.1.5.12.8.5.3
-- 1.3.6.1.4.1.37950.1.1.5.12.8.5.3
-- 1.3.6.1.4.1.37950.1.1.5.12.8.5.3
-- 1.3.6.1.4.1.37950.1.1.5.12.8.5.3
-- 1.3.6.1.4.1.37950.1.1.5.12.8.5.3
-- 1.3.6.1.4.1.37950.1.1.5.12.8.5.3
-- 1.3.6.1.4.1.37950.1.1.5.12.8.5.3
-- 1.3.6.1.4.1.37950.1.1.5.12.8.5.3
-- 1.3.6.1.4.1.37950.1.1.5.12.8.5.3
		-- 1.3.6.1.4.1.37950.1.1.5.12.8.5.3
		alarmOnuConfig OBJECT IDENTIFIER ::= { alarmProfileEdit 3 }

		
--          1.3.6.1.4.1.37950.1.1.5.12.8.5.3.1
-- 1.3.6.1.4.1.37950.1.1.5.12.8.5.3.1
-- 1.3.6.1.4.1.37950.1.1.5.12.8.5.3.1
-- 1.3.6.1.4.1.37950.1.1.5.12.8.5.3.1
-- 1.3.6.1.4.1.37950.1.1.5.12.8.5.3.1
-- 1.3.6.1.4.1.37950.1.1.5.12.8.5.3.1
-- 1.3.6.1.4.1.37950.1.1.5.12.8.5.3.1
-- 1.3.6.1.4.1.37950.1.1.5.12.8.5.3.1
-- 1.3.6.1.4.1.37950.1.1.5.12.8.5.3.1
		-- 1.3.6.1.4.1.37950.1.1.5.12.8.5.3.1
		alarmOnuTpye OBJECT-TYPE
			SYNTAX INTEGER
				{
				equipmemAlarm(1),
				powerAlarm(2),
				batteryMiss(3),
				batteryFail(4),
				physicalLntrusion(5),
				selfTestFail(6),
				iadConFail(7),
				ponIfSwitch(8),
				sleepStatusUpdate(9)
				}
			MAX-ACCESS read-write
			STATUS current
			DESCRIPTION
				"Description."
			::= { alarmOnuConfig 1 }

		
--          1.3.6.1.4.1.37950.1.1.5.12.8.5.3.2
-- 1.3.6.1.4.1.37950.1.1.5.12.8.5.3.2
-- 1.3.6.1.4.1.37950.1.1.5.12.8.5.3.2
-- 1.3.6.1.4.1.37950.1.1.5.12.8.5.3.2
-- 1.3.6.1.4.1.37950.1.1.5.12.8.5.3.2
-- 1.3.6.1.4.1.37950.1.1.5.12.8.5.3.2
-- 1.3.6.1.4.1.37950.1.1.5.12.8.5.3.2
-- 1.3.6.1.4.1.37950.1.1.5.12.8.5.3.2
-- 1.3.6.1.4.1.37950.1.1.5.12.8.5.3.2
		-- 1.3.6.1.4.1.37950.1.1.5.12.8.5.3.2
		alarmOnuEn OBJECT-TYPE
			SYNTAX INTEGER
				{
				disable(0),
				enable(1)
				}
			MAX-ACCESS read-write
			STATUS current
			DESCRIPTION
				"Description."
			::= { alarmOnuConfig 2 }

		
--          1.3.6.1.4.1.37950.1.1.5.12.8.5.3.3
-- 1.3.6.1.4.1.37950.1.1.5.12.8.5.3.3
-- 1.3.6.1.4.1.37950.1.1.5.12.8.5.3.3
-- 1.3.6.1.4.1.37950.1.1.5.12.8.5.3.3
-- 1.3.6.1.4.1.37950.1.1.5.12.8.5.3.3
-- 1.3.6.1.4.1.37950.1.1.5.12.8.5.3.3
-- 1.3.6.1.4.1.37950.1.1.5.12.8.5.3.3
-- 1.3.6.1.4.1.37950.1.1.5.12.8.5.3.3
-- 1.3.6.1.4.1.37950.1.1.5.12.8.5.3.3
		-- 1.3.6.1.4.1.37950.1.1.5.12.8.5.3.3
		alarmOnuAction OBJECT-TYPE
			SYNTAX INTEGER
				{
				add(1),
				commit(2)
				}
			MAX-ACCESS read-write
			STATUS current
			DESCRIPTION
				"Description."
			::= { alarmOnuConfig 3 }

		
--          1.3.6.1.4.1.37950.1.1.5.12.8.5.4
-- 1.3.6.1.4.1.37950.1.1.5.12.8.5.4
-- 1.3.6.1.4.1.37950.1.1.5.12.8.5.4
-- 1.3.6.1.4.1.37950.1.1.5.12.8.5.4
-- 1.3.6.1.4.1.37950.1.1.5.12.8.5.4
-- 1.3.6.1.4.1.37950.1.1.5.12.8.5.4
-- 1.3.6.1.4.1.37950.1.1.5.12.8.5.4
-- 1.3.6.1.4.1.37950.1.1.5.12.8.5.4
-- 1.3.6.1.4.1.37950.1.1.5.12.8.5.4
		-- 1.3.6.1.4.1.37950.1.1.5.12.8.5.4
		onuTempAlarm OBJECT IDENTIFIER ::= { alarmProfileEdit 4 }

		
--          1.3.6.1.4.1.37950.1.1.5.12.8.5.4.1
-- 1.3.6.1.4.1.37950.1.1.5.12.8.5.4.1
-- 1.3.6.1.4.1.37950.1.1.5.12.8.5.4.1
-- 1.3.6.1.4.1.37950.1.1.5.12.8.5.4.1
-- 1.3.6.1.4.1.37950.1.1.5.12.8.5.4.1
-- 1.3.6.1.4.1.37950.1.1.5.12.8.5.4.1
-- 1.3.6.1.4.1.37950.1.1.5.12.8.5.4.1
-- 1.3.6.1.4.1.37950.1.1.5.12.8.5.4.1
-- 1.3.6.1.4.1.37950.1.1.5.12.8.5.4.1
		-- 1.3.6.1.4.1.37950.1.1.5.12.8.5.4.1
		onuTempAlarmType OBJECT-TYPE
			SYNTAX INTEGER
				{
				onuTempHighAarm(1),
				onuTempLowAlarm(2)
				}
			MAX-ACCESS read-write
			STATUS current
			DESCRIPTION
				"Description."
			::= { onuTempAlarm 1 }

		
--          1.3.6.1.4.1.37950.1.1.5.12.8.5.4.2
-- 1.3.6.1.4.1.37950.1.1.5.12.8.5.4.2
-- 1.3.6.1.4.1.37950.1.1.5.12.8.5.4.2
-- 1.3.6.1.4.1.37950.1.1.5.12.8.5.4.2
-- 1.3.6.1.4.1.37950.1.1.5.12.8.5.4.2
-- 1.3.6.1.4.1.37950.1.1.5.12.8.5.4.2
-- 1.3.6.1.4.1.37950.1.1.5.12.8.5.4.2
-- 1.3.6.1.4.1.37950.1.1.5.12.8.5.4.2
-- 1.3.6.1.4.1.37950.1.1.5.12.8.5.4.2
		-- 1.3.6.1.4.1.37950.1.1.5.12.8.5.4.2
		onuTempAlarmEn OBJECT-TYPE
			SYNTAX INTEGER
				{
				disable(0),
				enable(1)
				}
			MAX-ACCESS read-write
			STATUS current
			DESCRIPTION
				"Description."
			::= { onuTempAlarm 2 }

		
--          1.3.6.1.4.1.37950.1.1.5.12.8.5.4.3
-- 1.3.6.1.4.1.37950.1.1.5.12.8.5.4.3
-- 1.3.6.1.4.1.37950.1.1.5.12.8.5.4.3
-- 1.3.6.1.4.1.37950.1.1.5.12.8.5.4.3
-- 1.3.6.1.4.1.37950.1.1.5.12.8.5.4.3
-- 1.3.6.1.4.1.37950.1.1.5.12.8.5.4.3
-- 1.3.6.1.4.1.37950.1.1.5.12.8.5.4.3
-- 1.3.6.1.4.1.37950.1.1.5.12.8.5.4.3
-- 1.3.6.1.4.1.37950.1.1.5.12.8.5.4.3
		-- 1.3.6.1.4.1.37950.1.1.5.12.8.5.4.3
		onuTempAlarmThld OBJECT-TYPE
			SYNTAX INTEGER (-1280..1280)
			MAX-ACCESS read-write
			STATUS current
			DESCRIPTION
				"Description."
			::= { onuTempAlarm 3 }

		
--          1.3.6.1.4.1.37950.1.1.5.12.8.5.4.4
-- 1.3.6.1.4.1.37950.1.1.5.12.8.5.4.4
-- 1.3.6.1.4.1.37950.1.1.5.12.8.5.4.4
-- 1.3.6.1.4.1.37950.1.1.5.12.8.5.4.4
-- 1.3.6.1.4.1.37950.1.1.5.12.8.5.4.4
-- 1.3.6.1.4.1.37950.1.1.5.12.8.5.4.4
-- 1.3.6.1.4.1.37950.1.1.5.12.8.5.4.4
-- 1.3.6.1.4.1.37950.1.1.5.12.8.5.4.4
-- 1.3.6.1.4.1.37950.1.1.5.12.8.5.4.4
		-- 1.3.6.1.4.1.37950.1.1.5.12.8.5.4.4
		onuTempClearThld OBJECT-TYPE
			SYNTAX INTEGER (-1280..1280)
			MAX-ACCESS read-write
			STATUS current
			DESCRIPTION
				"Description."
			::= { onuTempAlarm 4 }

		
--          1.3.6.1.4.1.37950.1.1.5.12.8.5.4.5
-- 1.3.6.1.4.1.37950.1.1.5.12.8.5.4.5
-- 1.3.6.1.4.1.37950.1.1.5.12.8.5.4.5
-- 1.3.6.1.4.1.37950.1.1.5.12.8.5.4.5
-- 1.3.6.1.4.1.37950.1.1.5.12.8.5.4.5
-- 1.3.6.1.4.1.37950.1.1.5.12.8.5.4.5
-- 1.3.6.1.4.1.37950.1.1.5.12.8.5.4.5
-- 1.3.6.1.4.1.37950.1.1.5.12.8.5.4.5
-- 1.3.6.1.4.1.37950.1.1.5.12.8.5.4.5
		-- 1.3.6.1.4.1.37950.1.1.5.12.8.5.4.5
		onuTempAlarmAction OBJECT-TYPE
			SYNTAX INTEGER
				{
				add(1),
				commit(2)
				}
			MAX-ACCESS read-write
			STATUS current
			DESCRIPTION
				"Description."
			::= { onuTempAlarm 5 }

		
--          1.3.6.1.4.1.37950.1.1.5.12.8.5.5
-- 1.3.6.1.4.1.37950.1.1.5.12.8.5.5
-- 1.3.6.1.4.1.37950.1.1.5.12.8.5.5
-- 1.3.6.1.4.1.37950.1.1.5.12.8.5.5
-- 1.3.6.1.4.1.37950.1.1.5.12.8.5.5
-- 1.3.6.1.4.1.37950.1.1.5.12.8.5.5
-- 1.3.6.1.4.1.37950.1.1.5.12.8.5.5
-- 1.3.6.1.4.1.37950.1.1.5.12.8.5.5
-- 1.3.6.1.4.1.37950.1.1.5.12.8.5.5
		-- 1.3.6.1.4.1.37950.1.1.5.12.8.5.5
		onuVccLowAlarm OBJECT IDENTIFIER ::= { alarmProfileEdit 5 }

		
--          1.3.6.1.4.1.37950.1.1.5.12.8.5.5.1
-- 1.3.6.1.4.1.37950.1.1.5.12.8.5.5.1
-- 1.3.6.1.4.1.37950.1.1.5.12.8.5.5.1
-- 1.3.6.1.4.1.37950.1.1.5.12.8.5.5.1
-- 1.3.6.1.4.1.37950.1.1.5.12.8.5.5.1
-- 1.3.6.1.4.1.37950.1.1.5.12.8.5.5.1
-- 1.3.6.1.4.1.37950.1.1.5.12.8.5.5.1
-- 1.3.6.1.4.1.37950.1.1.5.12.8.5.5.1
-- 1.3.6.1.4.1.37950.1.1.5.12.8.5.5.1
		-- 1.3.6.1.4.1.37950.1.1.5.12.8.5.5.1
		onuVccAlarmEn OBJECT-TYPE
			SYNTAX INTEGER
				{
				disable(0),
				enable(1)
				}
			MAX-ACCESS read-write
			STATUS current
			DESCRIPTION
				"Description."
			::= { onuVccLowAlarm 1 }

		
--          1.3.6.1.4.1.37950.1.1.5.12.8.5.5.2
-- 1.3.6.1.4.1.37950.1.1.5.12.8.5.5.2
-- 1.3.6.1.4.1.37950.1.1.5.12.8.5.5.2
-- 1.3.6.1.4.1.37950.1.1.5.12.8.5.5.2
-- 1.3.6.1.4.1.37950.1.1.5.12.8.5.5.2
-- 1.3.6.1.4.1.37950.1.1.5.12.8.5.5.2
-- 1.3.6.1.4.1.37950.1.1.5.12.8.5.5.2
-- 1.3.6.1.4.1.37950.1.1.5.12.8.5.5.2
-- 1.3.6.1.4.1.37950.1.1.5.12.8.5.5.2
		-- 1.3.6.1.4.1.37950.1.1.5.12.8.5.5.2
		onuVccAlarmThld OBJECT-TYPE
			SYNTAX INTEGER (0..65535)
			MAX-ACCESS read-write
			STATUS current
			DESCRIPTION
				"Description."
			::= { onuVccLowAlarm 2 }

		
--          1.3.6.1.4.1.37950.1.1.5.12.8.5.5.3
-- 1.3.6.1.4.1.37950.1.1.5.12.8.5.5.3
-- 1.3.6.1.4.1.37950.1.1.5.12.8.5.5.3
-- 1.3.6.1.4.1.37950.1.1.5.12.8.5.5.3
-- 1.3.6.1.4.1.37950.1.1.5.12.8.5.5.3
-- 1.3.6.1.4.1.37950.1.1.5.12.8.5.5.3
-- 1.3.6.1.4.1.37950.1.1.5.12.8.5.5.3
-- 1.3.6.1.4.1.37950.1.1.5.12.8.5.5.3
-- 1.3.6.1.4.1.37950.1.1.5.12.8.5.5.3
		-- 1.3.6.1.4.1.37950.1.1.5.12.8.5.5.3
		onuVccClearThld OBJECT-TYPE
			SYNTAX INTEGER (0..65535)
			MAX-ACCESS read-write
			STATUS current
			DESCRIPTION
				"Description."
			::= { onuVccLowAlarm 3 }

		
--          1.3.6.1.4.1.37950.1.1.5.12.8.5.5.4
-- 1.3.6.1.4.1.37950.1.1.5.12.8.5.5.4
-- 1.3.6.1.4.1.37950.1.1.5.12.8.5.5.4
-- 1.3.6.1.4.1.37950.1.1.5.12.8.5.5.4
-- 1.3.6.1.4.1.37950.1.1.5.12.8.5.5.4
-- 1.3.6.1.4.1.37950.1.1.5.12.8.5.5.4
-- 1.3.6.1.4.1.37950.1.1.5.12.8.5.5.4
-- 1.3.6.1.4.1.37950.1.1.5.12.8.5.5.4
-- 1.3.6.1.4.1.37950.1.1.5.12.8.5.5.4
		-- 1.3.6.1.4.1.37950.1.1.5.12.8.5.5.4
		onuVccAlarmAction OBJECT-TYPE
			SYNTAX INTEGER
				{
				add(1),
				delete(2)
				}
			MAX-ACCESS read-write
			STATUS current
			DESCRIPTION
				"Description."
			::= { onuVccLowAlarm 4 }

		
--          1.3.6.1.4.1.37950.1.1.5.12.8.5.6
-- 1.3.6.1.4.1.37950.1.1.5.12.8.5.6
-- 1.3.6.1.4.1.37950.1.1.5.12.8.5.6
-- 1.3.6.1.4.1.37950.1.1.5.12.8.5.6
-- 1.3.6.1.4.1.37950.1.1.5.12.8.5.6
-- 1.3.6.1.4.1.37950.1.1.5.12.8.5.6
-- 1.3.6.1.4.1.37950.1.1.5.12.8.5.6
-- 1.3.6.1.4.1.37950.1.1.5.12.8.5.6
-- 1.3.6.1.4.1.37950.1.1.5.12.8.5.6
		-- 1.3.6.1.4.1.37950.1.1.5.12.8.5.6
		ponVccAlarm OBJECT IDENTIFIER ::= { alarmProfileEdit 6 }

		
--          1.3.6.1.4.1.37950.1.1.5.12.8.5.6.1
-- 1.3.6.1.4.1.37950.1.1.5.12.8.5.6.1
-- 1.3.6.1.4.1.37950.1.1.5.12.8.5.6.1
-- 1.3.6.1.4.1.37950.1.1.5.12.8.5.6.1
-- 1.3.6.1.4.1.37950.1.1.5.12.8.5.6.1
-- 1.3.6.1.4.1.37950.1.1.5.12.8.5.6.1
-- 1.3.6.1.4.1.37950.1.1.5.12.8.5.6.1
-- 1.3.6.1.4.1.37950.1.1.5.12.8.5.6.1
-- 1.3.6.1.4.1.37950.1.1.5.12.8.5.6.1
		-- 1.3.6.1.4.1.37950.1.1.5.12.8.5.6.1
		ponVccAlarmType OBJECT-TYPE
			SYNTAX INTEGER
				{
				vccHighAlarm(1),
				vccLowAlarm(2),
				vccHighWarn(3),
				vccLowWarn(4)
				}
			MAX-ACCESS read-write
			STATUS current
			DESCRIPTION
				"Description."
			::= { ponVccAlarm 1 }

		
--          1.3.6.1.4.1.37950.1.1.5.12.8.5.6.2
-- 1.3.6.1.4.1.37950.1.1.5.12.8.5.6.2
-- 1.3.6.1.4.1.37950.1.1.5.12.8.5.6.2
-- 1.3.6.1.4.1.37950.1.1.5.12.8.5.6.2
-- 1.3.6.1.4.1.37950.1.1.5.12.8.5.6.2
-- 1.3.6.1.4.1.37950.1.1.5.12.8.5.6.2
-- 1.3.6.1.4.1.37950.1.1.5.12.8.5.6.2
-- 1.3.6.1.4.1.37950.1.1.5.12.8.5.6.2
-- 1.3.6.1.4.1.37950.1.1.5.12.8.5.6.2
		-- 1.3.6.1.4.1.37950.1.1.5.12.8.5.6.2
		ponVccAlarmTypeEn OBJECT-TYPE
			SYNTAX INTEGER
				{
				disable(0),
				enable(1)
				}
			MAX-ACCESS read-write
			STATUS current
			DESCRIPTION
				"Description."
			::= { ponVccAlarm 2 }

		
--          1.3.6.1.4.1.37950.1.1.5.12.8.5.6.3
-- 1.3.6.1.4.1.37950.1.1.5.12.8.5.6.3
-- 1.3.6.1.4.1.37950.1.1.5.12.8.5.6.3
-- 1.3.6.1.4.1.37950.1.1.5.12.8.5.6.3
-- 1.3.6.1.4.1.37950.1.1.5.12.8.5.6.3
-- 1.3.6.1.4.1.37950.1.1.5.12.8.5.6.3
-- 1.3.6.1.4.1.37950.1.1.5.12.8.5.6.3
-- 1.3.6.1.4.1.37950.1.1.5.12.8.5.6.3
-- 1.3.6.1.4.1.37950.1.1.5.12.8.5.6.3
		-- 1.3.6.1.4.1.37950.1.1.5.12.8.5.6.3
		ponVccAlarmThld OBJECT-TYPE
			SYNTAX INTEGER (0..65)
			MAX-ACCESS read-write
			STATUS current
			DESCRIPTION
				"Description."
			::= { ponVccAlarm 3 }

		
--          1.3.6.1.4.1.37950.1.1.5.12.8.5.6.4
-- 1.3.6.1.4.1.37950.1.1.5.12.8.5.6.4
-- 1.3.6.1.4.1.37950.1.1.5.12.8.5.6.4
-- 1.3.6.1.4.1.37950.1.1.5.12.8.5.6.4
-- 1.3.6.1.4.1.37950.1.1.5.12.8.5.6.4
-- 1.3.6.1.4.1.37950.1.1.5.12.8.5.6.4
-- 1.3.6.1.4.1.37950.1.1.5.12.8.5.6.4
-- 1.3.6.1.4.1.37950.1.1.5.12.8.5.6.4
-- 1.3.6.1.4.1.37950.1.1.5.12.8.5.6.4
		-- 1.3.6.1.4.1.37950.1.1.5.12.8.5.6.4
		ponVccClearThld OBJECT-TYPE
			SYNTAX INTEGER (0..65)
			MAX-ACCESS read-write
			STATUS current
			DESCRIPTION
				"Description."
			::= { ponVccAlarm 4 }

		
--          1.3.6.1.4.1.37950.1.1.5.12.8.5.6.5
-- 1.3.6.1.4.1.37950.1.1.5.12.8.5.6.5
-- 1.3.6.1.4.1.37950.1.1.5.12.8.5.6.5
-- 1.3.6.1.4.1.37950.1.1.5.12.8.5.6.5
-- 1.3.6.1.4.1.37950.1.1.5.12.8.5.6.5
-- 1.3.6.1.4.1.37950.1.1.5.12.8.5.6.5
-- 1.3.6.1.4.1.37950.1.1.5.12.8.5.6.5
-- 1.3.6.1.4.1.37950.1.1.5.12.8.5.6.5
-- 1.3.6.1.4.1.37950.1.1.5.12.8.5.6.5
		-- 1.3.6.1.4.1.37950.1.1.5.12.8.5.6.5
		ponVccAlarmAction OBJECT-TYPE
			SYNTAX INTEGER
				{
				add(1),
				delete(2)
				}
			MAX-ACCESS read-write
			STATUS current
			DESCRIPTION
				"Description."
			::= { ponVccAlarm 5 }

		
--          1.3.6.1.4.1.37950.1.1.5.12.8.5.7
-- 1.3.6.1.4.1.37950.1.1.5.12.8.5.7
-- 1.3.6.1.4.1.37950.1.1.5.12.8.5.7
-- 1.3.6.1.4.1.37950.1.1.5.12.8.5.7
-- 1.3.6.1.4.1.37950.1.1.5.12.8.5.7
-- 1.3.6.1.4.1.37950.1.1.5.12.8.5.7
-- 1.3.6.1.4.1.37950.1.1.5.12.8.5.7
-- 1.3.6.1.4.1.37950.1.1.5.12.8.5.7
-- 1.3.6.1.4.1.37950.1.1.5.12.8.5.7
		-- 1.3.6.1.4.1.37950.1.1.5.12.8.5.7
		ponBiasAlarm OBJECT IDENTIFIER ::= { alarmProfileEdit 7 }

		
--          1.3.6.1.4.1.37950.1.1.5.12.8.5.7.1
-- 1.3.6.1.4.1.37950.1.1.5.12.8.5.7.1
-- 1.3.6.1.4.1.37950.1.1.5.12.8.5.7.1
-- 1.3.6.1.4.1.37950.1.1.5.12.8.5.7.1
-- 1.3.6.1.4.1.37950.1.1.5.12.8.5.7.1
-- 1.3.6.1.4.1.37950.1.1.5.12.8.5.7.1
-- 1.3.6.1.4.1.37950.1.1.5.12.8.5.7.1
-- 1.3.6.1.4.1.37950.1.1.5.12.8.5.7.1
-- 1.3.6.1.4.1.37950.1.1.5.12.8.5.7.1
		-- 1.3.6.1.4.1.37950.1.1.5.12.8.5.7.1
		ponBiasAlarmType OBJECT-TYPE
			SYNTAX INTEGER
				{
				txBiasHighAlarm(1),
				txBiasLowAlarm(2),
				txBiasHighWarn(3),
				txBiasLowWarn(4)
				}
			MAX-ACCESS read-write
			STATUS current
			DESCRIPTION
				"Description."
			::= { ponBiasAlarm 1 }

		
--          1.3.6.1.4.1.37950.1.1.5.12.8.5.7.2
-- 1.3.6.1.4.1.37950.1.1.5.12.8.5.7.2
-- 1.3.6.1.4.1.37950.1.1.5.12.8.5.7.2
-- 1.3.6.1.4.1.37950.1.1.5.12.8.5.7.2
-- 1.3.6.1.4.1.37950.1.1.5.12.8.5.7.2
-- 1.3.6.1.4.1.37950.1.1.5.12.8.5.7.2
-- 1.3.6.1.4.1.37950.1.1.5.12.8.5.7.2
-- 1.3.6.1.4.1.37950.1.1.5.12.8.5.7.2
-- 1.3.6.1.4.1.37950.1.1.5.12.8.5.7.2
		-- 1.3.6.1.4.1.37950.1.1.5.12.8.5.7.2
		ponBiasAlarmTypeEn OBJECT-TYPE
			SYNTAX INTEGER
				{
				disable(0),
				enable(1)
				}
			MAX-ACCESS read-write
			STATUS current
			DESCRIPTION
				"Description."
			::= { ponBiasAlarm 2 }

		
--          1.3.6.1.4.1.37950.1.1.5.12.8.5.7.3
-- 1.3.6.1.4.1.37950.1.1.5.12.8.5.7.3
-- 1.3.6.1.4.1.37950.1.1.5.12.8.5.7.3
-- 1.3.6.1.4.1.37950.1.1.5.12.8.5.7.3
-- 1.3.6.1.4.1.37950.1.1.5.12.8.5.7.3
-- 1.3.6.1.4.1.37950.1.1.5.12.8.5.7.3
-- 1.3.6.1.4.1.37950.1.1.5.12.8.5.7.3
-- 1.3.6.1.4.1.37950.1.1.5.12.8.5.7.3
-- 1.3.6.1.4.1.37950.1.1.5.12.8.5.7.3
		-- 1.3.6.1.4.1.37950.1.1.5.12.8.5.7.3
		ponBiasAlarmThld OBJECT-TYPE
			SYNTAX INTEGER (0..1310)
			MAX-ACCESS read-write
			STATUS current
			DESCRIPTION
				"Description."
			::= { ponBiasAlarm 3 }

		
--          1.3.6.1.4.1.37950.1.1.5.12.8.5.7.4
-- 1.3.6.1.4.1.37950.1.1.5.12.8.5.7.4
-- 1.3.6.1.4.1.37950.1.1.5.12.8.5.7.4
-- 1.3.6.1.4.1.37950.1.1.5.12.8.5.7.4
-- 1.3.6.1.4.1.37950.1.1.5.12.8.5.7.4
-- 1.3.6.1.4.1.37950.1.1.5.12.8.5.7.4
-- 1.3.6.1.4.1.37950.1.1.5.12.8.5.7.4
-- 1.3.6.1.4.1.37950.1.1.5.12.8.5.7.4
-- 1.3.6.1.4.1.37950.1.1.5.12.8.5.7.4
		-- 1.3.6.1.4.1.37950.1.1.5.12.8.5.7.4
		ponBiasClearThld OBJECT-TYPE
			SYNTAX INTEGER (0..1310)
			MAX-ACCESS read-write
			STATUS current
			DESCRIPTION
				"Description."
			::= { ponBiasAlarm 4 }

		
--          1.3.6.1.4.1.37950.1.1.5.12.8.5.7.5
-- 1.3.6.1.4.1.37950.1.1.5.12.8.5.7.5
-- 1.3.6.1.4.1.37950.1.1.5.12.8.5.7.5
-- 1.3.6.1.4.1.37950.1.1.5.12.8.5.7.5
-- 1.3.6.1.4.1.37950.1.1.5.12.8.5.7.5
-- 1.3.6.1.4.1.37950.1.1.5.12.8.5.7.5
-- 1.3.6.1.4.1.37950.1.1.5.12.8.5.7.5
-- 1.3.6.1.4.1.37950.1.1.5.12.8.5.7.5
-- 1.3.6.1.4.1.37950.1.1.5.12.8.5.7.5
		-- 1.3.6.1.4.1.37950.1.1.5.12.8.5.7.5
		ponBiasAlarmAction OBJECT-TYPE
			SYNTAX INTEGER
				{
				add(1),
				delete(2)
				}
			MAX-ACCESS read-write
			STATUS current
			DESCRIPTION
				"Description."
			::= { ponBiasAlarm 5 }

		
--          1.3.6.1.4.1.37950.1.1.5.12.8.5.8
-- 1.3.6.1.4.1.37950.1.1.5.12.8.5.8
-- 1.3.6.1.4.1.37950.1.1.5.12.8.5.8
-- 1.3.6.1.4.1.37950.1.1.5.12.8.5.8
-- 1.3.6.1.4.1.37950.1.1.5.12.8.5.8
-- 1.3.6.1.4.1.37950.1.1.5.12.8.5.8
-- 1.3.6.1.4.1.37950.1.1.5.12.8.5.8
-- 1.3.6.1.4.1.37950.1.1.5.12.8.5.8
-- 1.3.6.1.4.1.37950.1.1.5.12.8.5.8
		-- 1.3.6.1.4.1.37950.1.1.5.12.8.5.8
		ponPowerAlarm OBJECT IDENTIFIER ::= { alarmProfileEdit 8 }

		
--          1.3.6.1.4.1.37950.1.1.5.12.8.5.8.1
-- 1.3.6.1.4.1.37950.1.1.5.12.8.5.8.1
-- 1.3.6.1.4.1.37950.1.1.5.12.8.5.8.1
-- 1.3.6.1.4.1.37950.1.1.5.12.8.5.8.1
-- 1.3.6.1.4.1.37950.1.1.5.12.8.5.8.1
-- 1.3.6.1.4.1.37950.1.1.5.12.8.5.8.1
-- 1.3.6.1.4.1.37950.1.1.5.12.8.5.8.1
-- 1.3.6.1.4.1.37950.1.1.5.12.8.5.8.1
-- 1.3.6.1.4.1.37950.1.1.5.12.8.5.8.1
		-- 1.3.6.1.4.1.37950.1.1.5.12.8.5.8.1
		ponPowerAlarmType OBJECT-TYPE
			SYNTAX INTEGER
				{
				rxPowerHighAlarm(1),
				rxPowerLowAlarm(2),
				txPowerHighAlarm(3),
				txPowerLowAlarm(4),
				rxPowerHighWarn(5),
				rxPowerLowWarn(6),
				txPowerHighWarn(7),
				txPowerLowWarn(8)
				}
			MAX-ACCESS read-write
			STATUS current
			DESCRIPTION
				"Description."
			::= { ponPowerAlarm 1 }

		
--          1.3.6.1.4.1.37950.1.1.5.12.8.5.8.2
-- 1.3.6.1.4.1.37950.1.1.5.12.8.5.8.2
-- 1.3.6.1.4.1.37950.1.1.5.12.8.5.8.2
-- 1.3.6.1.4.1.37950.1.1.5.12.8.5.8.2
-- 1.3.6.1.4.1.37950.1.1.5.12.8.5.8.2
-- 1.3.6.1.4.1.37950.1.1.5.12.8.5.8.2
-- 1.3.6.1.4.1.37950.1.1.5.12.8.5.8.2
-- 1.3.6.1.4.1.37950.1.1.5.12.8.5.8.2
-- 1.3.6.1.4.1.37950.1.1.5.12.8.5.8.2
		-- 1.3.6.1.4.1.37950.1.1.5.12.8.5.8.2
		ponPowerAlarmTypeEn OBJECT-TYPE
			SYNTAX INTEGER
				{
				disable(0),
				enable(1)
				}
			MAX-ACCESS read-write
			STATUS current
			DESCRIPTION
				"Description."
			::= { ponPowerAlarm 2 }

		
--          1.3.6.1.4.1.37950.1.1.5.12.8.5.8.3
-- 1.3.6.1.4.1.37950.1.1.5.12.8.5.8.3
-- 1.3.6.1.4.1.37950.1.1.5.12.8.5.8.3
-- 1.3.6.1.4.1.37950.1.1.5.12.8.5.8.3
-- 1.3.6.1.4.1.37950.1.1.5.12.8.5.8.3
-- 1.3.6.1.4.1.37950.1.1.5.12.8.5.8.3
-- 1.3.6.1.4.1.37950.1.1.5.12.8.5.8.3
-- 1.3.6.1.4.1.37950.1.1.5.12.8.5.8.3
-- 1.3.6.1.4.1.37950.1.1.5.12.8.5.8.3
		-- 1.3.6.1.4.1.37950.1.1.5.12.8.5.8.3
		ponPowerAlarmThld OBJECT-TYPE
			SYNTAX INTEGER (-400..82)
			MAX-ACCESS read-write
			STATUS current
			DESCRIPTION
				"Description."
			::= { ponPowerAlarm 3 }

		
--          1.3.6.1.4.1.37950.1.1.5.12.8.5.8.4
-- 1.3.6.1.4.1.37950.1.1.5.12.8.5.8.4
-- 1.3.6.1.4.1.37950.1.1.5.12.8.5.8.4
-- 1.3.6.1.4.1.37950.1.1.5.12.8.5.8.4
-- 1.3.6.1.4.1.37950.1.1.5.12.8.5.8.4
-- 1.3.6.1.4.1.37950.1.1.5.12.8.5.8.4
-- 1.3.6.1.4.1.37950.1.1.5.12.8.5.8.4
-- 1.3.6.1.4.1.37950.1.1.5.12.8.5.8.4
-- 1.3.6.1.4.1.37950.1.1.5.12.8.5.8.4
		-- 1.3.6.1.4.1.37950.1.1.5.12.8.5.8.4
		ponPowerClearThld OBJECT-TYPE
			SYNTAX INTEGER (-400..82)
			MAX-ACCESS read-write
			STATUS current
			DESCRIPTION
				"Description."
			::= { ponPowerAlarm 4 }

		
--          1.3.6.1.4.1.37950.1.1.5.12.8.5.8.5
-- 1.3.6.1.4.1.37950.1.1.5.12.8.5.8.5
-- 1.3.6.1.4.1.37950.1.1.5.12.8.5.8.5
-- 1.3.6.1.4.1.37950.1.1.5.12.8.5.8.5
-- 1.3.6.1.4.1.37950.1.1.5.12.8.5.8.5
-- 1.3.6.1.4.1.37950.1.1.5.12.8.5.8.5
-- 1.3.6.1.4.1.37950.1.1.5.12.8.5.8.5
-- 1.3.6.1.4.1.37950.1.1.5.12.8.5.8.5
-- 1.3.6.1.4.1.37950.1.1.5.12.8.5.8.5
		-- 1.3.6.1.4.1.37950.1.1.5.12.8.5.8.5
		ponPowerAlarmAction OBJECT-TYPE
			SYNTAX INTEGER
				{
				add(1),
				delete(2)
				}
			MAX-ACCESS read-write
			STATUS current
			DESCRIPTION
				"Description."
			::= { ponPowerAlarm 5 }

		
--          1.3.6.1.4.1.37950.1.1.5.12.8.5.9
-- 1.3.6.1.4.1.37950.1.1.5.12.8.5.9
-- 1.3.6.1.4.1.37950.1.1.5.12.8.5.9
-- 1.3.6.1.4.1.37950.1.1.5.12.8.5.9
-- 1.3.6.1.4.1.37950.1.1.5.12.8.5.9
-- 1.3.6.1.4.1.37950.1.1.5.12.8.5.9
-- 1.3.6.1.4.1.37950.1.1.5.12.8.5.9
-- 1.3.6.1.4.1.37950.1.1.5.12.8.5.9
-- 1.3.6.1.4.1.37950.1.1.5.12.8.5.9
		-- 1.3.6.1.4.1.37950.1.1.5.12.8.5.9
		ponTempAlarm OBJECT IDENTIFIER ::= { alarmProfileEdit 9 }

		
--          1.3.6.1.4.1.37950.1.1.5.12.8.5.9.1
-- 1.3.6.1.4.1.37950.1.1.5.12.8.5.9.1
-- 1.3.6.1.4.1.37950.1.1.5.12.8.5.9.1
-- 1.3.6.1.4.1.37950.1.1.5.12.8.5.9.1
-- 1.3.6.1.4.1.37950.1.1.5.12.8.5.9.1
-- 1.3.6.1.4.1.37950.1.1.5.12.8.5.9.1
-- 1.3.6.1.4.1.37950.1.1.5.12.8.5.9.1
-- 1.3.6.1.4.1.37950.1.1.5.12.8.5.9.1
-- 1.3.6.1.4.1.37950.1.1.5.12.8.5.9.1
		-- 1.3.6.1.4.1.37950.1.1.5.12.8.5.9.1
		ponTempAlarmType OBJECT-TYPE
			SYNTAX INTEGER
				{
				tempHighAlarm(1),
				tempLowAlarm(2),
				tempHighWarn(3),
				tempLowWarn(4)
				}
			MAX-ACCESS read-write
			STATUS current
			DESCRIPTION
				"Description."
			::= { ponTempAlarm 1 }

		
--          1.3.6.1.4.1.37950.1.1.5.12.8.5.9.2
-- 1.3.6.1.4.1.37950.1.1.5.12.8.5.9.2
-- 1.3.6.1.4.1.37950.1.1.5.12.8.5.9.2
-- 1.3.6.1.4.1.37950.1.1.5.12.8.5.9.2
-- 1.3.6.1.4.1.37950.1.1.5.12.8.5.9.2
-- 1.3.6.1.4.1.37950.1.1.5.12.8.5.9.2
-- 1.3.6.1.4.1.37950.1.1.5.12.8.5.9.2
-- 1.3.6.1.4.1.37950.1.1.5.12.8.5.9.2
-- 1.3.6.1.4.1.37950.1.1.5.12.8.5.9.2
		-- 1.3.6.1.4.1.37950.1.1.5.12.8.5.9.2
		ponTempAlarmTypeEn OBJECT-TYPE
			SYNTAX INTEGER
				{
				disable(0),
				enable(1)
				}
			MAX-ACCESS read-write
			STATUS current
			DESCRIPTION
				"Description."
			::= { ponTempAlarm 2 }

		
--          1.3.6.1.4.1.37950.1.1.5.12.8.5.9.3
-- 1.3.6.1.4.1.37950.1.1.5.12.8.5.9.3
-- 1.3.6.1.4.1.37950.1.1.5.12.8.5.9.3
-- 1.3.6.1.4.1.37950.1.1.5.12.8.5.9.3
-- 1.3.6.1.4.1.37950.1.1.5.12.8.5.9.3
-- 1.3.6.1.4.1.37950.1.1.5.12.8.5.9.3
-- 1.3.6.1.4.1.37950.1.1.5.12.8.5.9.3
-- 1.3.6.1.4.1.37950.1.1.5.12.8.5.9.3
-- 1.3.6.1.4.1.37950.1.1.5.12.8.5.9.3
		-- 1.3.6.1.4.1.37950.1.1.5.12.8.5.9.3
		ponTempAlarmThld OBJECT-TYPE
			SYNTAX INTEGER (-1280..1280)
			MAX-ACCESS read-write
			STATUS current
			DESCRIPTION
				"Description."
			::= { ponTempAlarm 3 }

		
--          1.3.6.1.4.1.37950.1.1.5.12.8.5.9.4
-- 1.3.6.1.4.1.37950.1.1.5.12.8.5.9.4
-- 1.3.6.1.4.1.37950.1.1.5.12.8.5.9.4
-- 1.3.6.1.4.1.37950.1.1.5.12.8.5.9.4
-- 1.3.6.1.4.1.37950.1.1.5.12.8.5.9.4
-- 1.3.6.1.4.1.37950.1.1.5.12.8.5.9.4
-- 1.3.6.1.4.1.37950.1.1.5.12.8.5.9.4
-- 1.3.6.1.4.1.37950.1.1.5.12.8.5.9.4
-- 1.3.6.1.4.1.37950.1.1.5.12.8.5.9.4
		-- 1.3.6.1.4.1.37950.1.1.5.12.8.5.9.4
		ponTempClearThld OBJECT-TYPE
			SYNTAX INTEGER (-1280..1280)
			MAX-ACCESS read-write
			STATUS current
			DESCRIPTION
				"Description."
			::= { ponTempAlarm 4 }

		
--          1.3.6.1.4.1.37950.1.1.5.12.8.5.9.5
-- 1.3.6.1.4.1.37950.1.1.5.12.8.5.9.5
-- 1.3.6.1.4.1.37950.1.1.5.12.8.5.9.5
-- 1.3.6.1.4.1.37950.1.1.5.12.8.5.9.5
-- 1.3.6.1.4.1.37950.1.1.5.12.8.5.9.5
-- 1.3.6.1.4.1.37950.1.1.5.12.8.5.9.5
-- 1.3.6.1.4.1.37950.1.1.5.12.8.5.9.5
-- 1.3.6.1.4.1.37950.1.1.5.12.8.5.9.5
-- 1.3.6.1.4.1.37950.1.1.5.12.8.5.9.5
		-- 1.3.6.1.4.1.37950.1.1.5.12.8.5.9.5
		ponTempAlarmAction OBJECT-TYPE
			SYNTAX INTEGER
				{
				add(1),
				delete(2)
				}
			MAX-ACCESS read-write
			STATUS current
			DESCRIPTION
				"Description."
			::= { ponTempAlarm 5 }

		
--          1.3.6.1.4.1.37950.1.1.5.12.8.5.10
-- 1.3.6.1.4.1.37950.1.1.5.12.8.5.10
-- 1.3.6.1.4.1.37950.1.1.5.12.8.5.10
-- 1.3.6.1.4.1.37950.1.1.5.12.8.5.10
-- 1.3.6.1.4.1.37950.1.1.5.12.8.5.10
-- 1.3.6.1.4.1.37950.1.1.5.12.8.5.10
-- 1.3.6.1.4.1.37950.1.1.5.12.8.5.10
-- 1.3.6.1.4.1.37950.1.1.5.12.8.5.10
-- 1.3.6.1.4.1.37950.1.1.5.12.8.5.10
		-- 1.3.6.1.4.1.37950.1.1.5.12.8.5.10
		ponStatAlarm OBJECT IDENTIFIER ::= { alarmProfileEdit 10 }

		
--          1.3.6.1.4.1.37950.1.1.5.12.8.5.10.1
-- 1.3.6.1.4.1.37950.1.1.5.12.8.5.10.1
-- 1.3.6.1.4.1.37950.1.1.5.12.8.5.10.1
-- 1.3.6.1.4.1.37950.1.1.5.12.8.5.10.1
-- 1.3.6.1.4.1.37950.1.1.5.12.8.5.10.1
-- 1.3.6.1.4.1.37950.1.1.5.12.8.5.10.1
-- 1.3.6.1.4.1.37950.1.1.5.12.8.5.10.1
-- 1.3.6.1.4.1.37950.1.1.5.12.8.5.10.1
-- 1.3.6.1.4.1.37950.1.1.5.12.8.5.10.1
		-- 1.3.6.1.4.1.37950.1.1.5.12.8.5.10.1
		ponStatAlarmType OBJECT-TYPE
			SYNTAX INTEGER
				{
				downstreamDropEventsAlarm(1),
				upstreamDropEventsAlarm(2),
				downstreamCRCErrorFramesAlarm(3),
				upstreamCRCErrorFramesAlarm(4),
				downstreamUndersizeFramesAlarm(5),
				upstreamUndersizeFramesAlarm(6),
				downstreamOversizeFramesAlarm(7),
				upstreamOversizeFramesAlarm(8),
				downstreamFragmentsAlarm(9),
				upstreamFragmentsAlarm(10),
				downstreamJabbersAlarm(11),
				upstreamJabbersAlarm(12),
				downstreamDiscardsAlarm(13),
				upstreamDiscardsAlarm(14),
				downstreamErrorsAlarm(15),
				upstreamErrorsAlarm(16),
				downstreamDropEventsWarning(17),
				upstreamDropEventsWarning(18),
				downstreamCRCErrorFramesWarning(19),
				upstreamCRCErrorFramesWarning(20),
				downstreamUndersizeFramesWarning(21),
				upstreamUndersizeFramesWarning(22),
				downstreamOversizeFramesWarning(23),
				upstreamOversizeFramesWarning(24),
				downstreamFragmentsWarning(25),
				upstreamFragmentsWarning(26),
				downstreamJabbersWarning(27),
				upstreamJabbersWarning(28),
				downstreamDiscardsWarning(29),
				upstreamDiscardsWarning(30),
				downstreamErrorsWarning(31),
				upstreamErrorsWarning(32)
				}
			MAX-ACCESS read-write
			STATUS current
			DESCRIPTION
				"Description."
			::= { ponStatAlarm 1 }

		
--          1.3.6.1.4.1.37950.1.1.5.12.8.5.10.2
-- 1.3.6.1.4.1.37950.1.1.5.12.8.5.10.2
-- 1.3.6.1.4.1.37950.1.1.5.12.8.5.10.2
-- 1.3.6.1.4.1.37950.1.1.5.12.8.5.10.2
-- 1.3.6.1.4.1.37950.1.1.5.12.8.5.10.2
-- 1.3.6.1.4.1.37950.1.1.5.12.8.5.10.2
-- 1.3.6.1.4.1.37950.1.1.5.12.8.5.10.2
-- 1.3.6.1.4.1.37950.1.1.5.12.8.5.10.2
-- 1.3.6.1.4.1.37950.1.1.5.12.8.5.10.2
		-- 1.3.6.1.4.1.37950.1.1.5.12.8.5.10.2
		ponStatAlarmTypeEn OBJECT-TYPE
			SYNTAX INTEGER
				{
				disable(0),
				enable(1)
				}
			MAX-ACCESS read-write
			STATUS current
			DESCRIPTION
				"Description."
			::= { ponStatAlarm 2 }

		
--          1.3.6.1.4.1.37950.1.1.5.12.8.5.10.3
-- 1.3.6.1.4.1.37950.1.1.5.12.8.5.10.3
-- 1.3.6.1.4.1.37950.1.1.5.12.8.5.10.3
-- 1.3.6.1.4.1.37950.1.1.5.12.8.5.10.3
-- 1.3.6.1.4.1.37950.1.1.5.12.8.5.10.3
-- 1.3.6.1.4.1.37950.1.1.5.12.8.5.10.3
-- 1.3.6.1.4.1.37950.1.1.5.12.8.5.10.3
-- 1.3.6.1.4.1.37950.1.1.5.12.8.5.10.3
-- 1.3.6.1.4.1.37950.1.1.5.12.8.5.10.3
		-- 1.3.6.1.4.1.37950.1.1.5.12.8.5.10.3
		ponStatAlarmThld OBJECT-TYPE
			SYNTAX INTEGER (0..65535)
			MAX-ACCESS read-write
			STATUS current
			DESCRIPTION
				"Description."
			::= { ponStatAlarm 3 }

		
--          1.3.6.1.4.1.37950.1.1.5.12.8.5.10.4
-- 1.3.6.1.4.1.37950.1.1.5.12.8.5.10.4
-- 1.3.6.1.4.1.37950.1.1.5.12.8.5.10.4
-- 1.3.6.1.4.1.37950.1.1.5.12.8.5.10.4
-- 1.3.6.1.4.1.37950.1.1.5.12.8.5.10.4
-- 1.3.6.1.4.1.37950.1.1.5.12.8.5.10.4
-- 1.3.6.1.4.1.37950.1.1.5.12.8.5.10.4
-- 1.3.6.1.4.1.37950.1.1.5.12.8.5.10.4
-- 1.3.6.1.4.1.37950.1.1.5.12.8.5.10.4
		-- 1.3.6.1.4.1.37950.1.1.5.12.8.5.10.4
		ponStatAlarmAction OBJECT-TYPE
			SYNTAX INTEGER
				{
				add(1),
				delete(2)
				}
			MAX-ACCESS read-write
			STATUS current
			DESCRIPTION
				"Description."
			::= { ponStatAlarm 4 }

		
--          1.3.6.1.4.1.37950.1.1.5.12.8.5.11
-- 1.3.6.1.4.1.37950.1.1.5.12.8.5.11
-- 1.3.6.1.4.1.37950.1.1.5.12.8.5.11
-- 1.3.6.1.4.1.37950.1.1.5.12.8.5.11
-- 1.3.6.1.4.1.37950.1.1.5.12.8.5.11
-- 1.3.6.1.4.1.37950.1.1.5.12.8.5.11
-- 1.3.6.1.4.1.37950.1.1.5.12.8.5.11
-- 1.3.6.1.4.1.37950.1.1.5.12.8.5.11
-- 1.3.6.1.4.1.37950.1.1.5.12.8.5.11
		-- 1.3.6.1.4.1.37950.1.1.5.12.8.5.11
		portAlarmStatus OBJECT IDENTIFIER ::= { alarmProfileEdit 11 }

		
--          1.3.6.1.4.1.37950.1.1.5.12.8.5.11.1
-- 1.3.6.1.4.1.37950.1.1.5.12.8.5.11.1
-- 1.3.6.1.4.1.37950.1.1.5.12.8.5.11.1
-- 1.3.6.1.4.1.37950.1.1.5.12.8.5.11.1
-- 1.3.6.1.4.1.37950.1.1.5.12.8.5.11.1
-- 1.3.6.1.4.1.37950.1.1.5.12.8.5.11.1
-- 1.3.6.1.4.1.37950.1.1.5.12.8.5.11.1
-- 1.3.6.1.4.1.37950.1.1.5.12.8.5.11.1
-- 1.3.6.1.4.1.37950.1.1.5.12.8.5.11.1
		-- 1.3.6.1.4.1.37950.1.1.5.12.8.5.11.1
		portAlarmEthNo OBJECT-TYPE
			SYNTAX INTEGER (1..255)
			MAX-ACCESS read-write
			STATUS current
			DESCRIPTION
				"Description."
			::= { portAlarmStatus 1 }

		
--          1.3.6.1.4.1.37950.1.1.5.12.8.5.11.2
-- 1.3.6.1.4.1.37950.1.1.5.12.8.5.11.2
-- 1.3.6.1.4.1.37950.1.1.5.12.8.5.11.2
-- 1.3.6.1.4.1.37950.1.1.5.12.8.5.11.2
-- 1.3.6.1.4.1.37950.1.1.5.12.8.5.11.2
-- 1.3.6.1.4.1.37950.1.1.5.12.8.5.11.2
-- 1.3.6.1.4.1.37950.1.1.5.12.8.5.11.2
-- 1.3.6.1.4.1.37950.1.1.5.12.8.5.11.2
-- 1.3.6.1.4.1.37950.1.1.5.12.8.5.11.2
		-- 1.3.6.1.4.1.37950.1.1.5.12.8.5.11.2
		portAlarmStatusType OBJECT-TYPE
			SYNTAX INTEGER
				{
				ethPortAutoNegFailure(1),
				ethPortLos(2),
				ethPortFailure(3),
				ethPortLoopback(4),
				ethPortCongestion(5)
				}
			MAX-ACCESS read-write
			STATUS current
			DESCRIPTION
				"Description."
			::= { portAlarmStatus 2 }

		
--          1.3.6.1.4.1.37950.1.1.5.12.8.5.11.3
-- 1.3.6.1.4.1.37950.1.1.5.12.8.5.11.3
-- 1.3.6.1.4.1.37950.1.1.5.12.8.5.11.3
-- 1.3.6.1.4.1.37950.1.1.5.12.8.5.11.3
-- 1.3.6.1.4.1.37950.1.1.5.12.8.5.11.3
-- 1.3.6.1.4.1.37950.1.1.5.12.8.5.11.3
-- 1.3.6.1.4.1.37950.1.1.5.12.8.5.11.3
-- 1.3.6.1.4.1.37950.1.1.5.12.8.5.11.3
-- 1.3.6.1.4.1.37950.1.1.5.12.8.5.11.3
		-- 1.3.6.1.4.1.37950.1.1.5.12.8.5.11.3
		portAlarmStatusEn OBJECT-TYPE
			SYNTAX INTEGER
				{
				disable(0),
				enable(1)
				}
			MAX-ACCESS read-write
			STATUS current
			DESCRIPTION
				"Description."
			::= { portAlarmStatus 3 }

		
--          1.3.6.1.4.1.37950.1.1.5.12.8.5.11.4
-- 1.3.6.1.4.1.37950.1.1.5.12.8.5.11.4
-- 1.3.6.1.4.1.37950.1.1.5.12.8.5.11.4
-- 1.3.6.1.4.1.37950.1.1.5.12.8.5.11.4
-- 1.3.6.1.4.1.37950.1.1.5.12.8.5.11.4
-- 1.3.6.1.4.1.37950.1.1.5.12.8.5.11.4
-- 1.3.6.1.4.1.37950.1.1.5.12.8.5.11.4
-- 1.3.6.1.4.1.37950.1.1.5.12.8.5.11.4
-- 1.3.6.1.4.1.37950.1.1.5.12.8.5.11.4
		-- 1.3.6.1.4.1.37950.1.1.5.12.8.5.11.4
		portAlarmStatusAction OBJECT-TYPE
			SYNTAX INTEGER
				{
				add(1),
				delete(2)
				}
			MAX-ACCESS read-write
			STATUS current
			DESCRIPTION
				"Description."
			::= { portAlarmStatus 4 }

		
--          1.3.6.1.4.1.37950.1.1.5.12.8.5.12
-- 1.3.6.1.4.1.37950.1.1.5.12.8.5.12
-- 1.3.6.1.4.1.37950.1.1.5.12.8.5.12
-- 1.3.6.1.4.1.37950.1.1.5.12.8.5.12
-- 1.3.6.1.4.1.37950.1.1.5.12.8.5.12
-- 1.3.6.1.4.1.37950.1.1.5.12.8.5.12
-- 1.3.6.1.4.1.37950.1.1.5.12.8.5.12
-- 1.3.6.1.4.1.37950.1.1.5.12.8.5.12
-- 1.3.6.1.4.1.37950.1.1.5.12.8.5.12
		-- 1.3.6.1.4.1.37950.1.1.5.12.8.5.12
		portStatAlarm OBJECT IDENTIFIER ::= { alarmProfileEdit 12 }

		
--          1.3.6.1.4.1.37950.1.1.5.12.8.5.12.1
-- 1.3.6.1.4.1.37950.1.1.5.12.8.5.12.1
-- 1.3.6.1.4.1.37950.1.1.5.12.8.5.12.1
-- 1.3.6.1.4.1.37950.1.1.5.12.8.5.12.1
-- 1.3.6.1.4.1.37950.1.1.5.12.8.5.12.1
-- 1.3.6.1.4.1.37950.1.1.5.12.8.5.12.1
-- 1.3.6.1.4.1.37950.1.1.5.12.8.5.12.1
-- 1.3.6.1.4.1.37950.1.1.5.12.8.5.12.1
-- 1.3.6.1.4.1.37950.1.1.5.12.8.5.12.1
		-- 1.3.6.1.4.1.37950.1.1.5.12.8.5.12.1
		portStatAlarmEthNo OBJECT-TYPE
			SYNTAX INTEGER (1..255)
			MAX-ACCESS read-write
			STATUS current
			DESCRIPTION
				"Description."
			::= { portStatAlarm 1 }

		
--          1.3.6.1.4.1.37950.1.1.5.12.8.5.12.2
-- 1.3.6.1.4.1.37950.1.1.5.12.8.5.12.2
-- 1.3.6.1.4.1.37950.1.1.5.12.8.5.12.2
-- 1.3.6.1.4.1.37950.1.1.5.12.8.5.12.2
-- 1.3.6.1.4.1.37950.1.1.5.12.8.5.12.2
-- 1.3.6.1.4.1.37950.1.1.5.12.8.5.12.2
-- 1.3.6.1.4.1.37950.1.1.5.12.8.5.12.2
-- 1.3.6.1.4.1.37950.1.1.5.12.8.5.12.2
-- 1.3.6.1.4.1.37950.1.1.5.12.8.5.12.2
		-- 1.3.6.1.4.1.37950.1.1.5.12.8.5.12.2
		portStatAlarmType OBJECT-TYPE
			SYNTAX INTEGER
				{
				downstreamDropEventsAlarm(1),
				upstreamDropEventsAlarm(2),
				downstreamCRCErrorFramesAlarm(3),
				upstreamCRCErrorFramesAlarm(4),
				downstreamUndersizeFramesAlarm(5),
				upstreamUndersizeFramesAlarm(6),
				downstreamOversizeFramesAlarm(7),
				upstreamOversizeFramesAlarm(8),
				downstreamFragmentsAlarm(9),
				upstreamFragmentsAlarm(10),
				downstreamJabbersAlarm(11),
				upstreamJabbersAlarm(12),
				downstreamDiscardsAlarm(13),
				upstreamDiscardsAlarm(14),
				downstreamErrorsAlarm(15),
				upstreamErrorsAlarm(16),
				statusChangeTimesAlarm(17),
				downstreamDropEventsWarning(18),
				upstreamDropEventsWarning(19),
				downstreamCRCErrorFramesWarning(20),
				upstreamCRCErrorFramesWarning(21),
				downstreamUndersizeFramesWarning(22),
				upstreamUndersizeFramesWarning(23),
				downstreamOversizeFramesWarning(24),
				upstreamOversizeFramesWarning(25),
				upstreamFragmentsWarning(27),
				downstreamJabbersWarning(28),
				upstreamJabbersWarning(29),
				downstreamDiscardsWarning(30),
				upstreamDiscardsWarning(31),
				downstreamErrorsWarning(32),
				upstreamErrorsWarning(33),
				statusChangeTimesWarning(34)
				}
			MAX-ACCESS read-write
			STATUS current
			DESCRIPTION
				"Description."
			::= { portStatAlarm 2 }

		
--          1.3.6.1.4.1.37950.1.1.5.12.8.5.12.3
-- 1.3.6.1.4.1.37950.1.1.5.12.8.5.12.3
-- 1.3.6.1.4.1.37950.1.1.5.12.8.5.12.3
-- 1.3.6.1.4.1.37950.1.1.5.12.8.5.12.3
-- 1.3.6.1.4.1.37950.1.1.5.12.8.5.12.3
-- 1.3.6.1.4.1.37950.1.1.5.12.8.5.12.3
-- 1.3.6.1.4.1.37950.1.1.5.12.8.5.12.3
-- 1.3.6.1.4.1.37950.1.1.5.12.8.5.12.3
-- 1.3.6.1.4.1.37950.1.1.5.12.8.5.12.3
		-- 1.3.6.1.4.1.37950.1.1.5.12.8.5.12.3
		portStatAlarmTypeEn OBJECT-TYPE
			SYNTAX INTEGER
				{
				disable(0),
				enable(1)
				}
			MAX-ACCESS read-write
			STATUS current
			DESCRIPTION
				"Description."
			::= { portStatAlarm 3 }

		
--          1.3.6.1.4.1.37950.1.1.5.12.8.5.12.4
-- 1.3.6.1.4.1.37950.1.1.5.12.8.5.12.4
-- 1.3.6.1.4.1.37950.1.1.5.12.8.5.12.4
-- 1.3.6.1.4.1.37950.1.1.5.12.8.5.12.4
-- 1.3.6.1.4.1.37950.1.1.5.12.8.5.12.4
-- 1.3.6.1.4.1.37950.1.1.5.12.8.5.12.4
-- 1.3.6.1.4.1.37950.1.1.5.12.8.5.12.4
-- 1.3.6.1.4.1.37950.1.1.5.12.8.5.12.4
-- 1.3.6.1.4.1.37950.1.1.5.12.8.5.12.4
		-- 1.3.6.1.4.1.37950.1.1.5.12.8.5.12.4
		portStatAlarmTld OBJECT-TYPE
			SYNTAX INTEGER (0..65535)
			MAX-ACCESS read-write
			STATUS current
			DESCRIPTION
				"Description."
			::= { portStatAlarm 4 }

		
--          1.3.6.1.4.1.37950.1.1.5.12.8.5.12.5
-- 1.3.6.1.4.1.37950.1.1.5.12.8.5.12.5
-- 1.3.6.1.4.1.37950.1.1.5.12.8.5.12.5
-- 1.3.6.1.4.1.37950.1.1.5.12.8.5.12.5
-- 1.3.6.1.4.1.37950.1.1.5.12.8.5.12.5
-- 1.3.6.1.4.1.37950.1.1.5.12.8.5.12.5
-- 1.3.6.1.4.1.37950.1.1.5.12.8.5.12.5
-- 1.3.6.1.4.1.37950.1.1.5.12.8.5.12.5
-- 1.3.6.1.4.1.37950.1.1.5.12.8.5.12.5
		-- 1.3.6.1.4.1.37950.1.1.5.12.8.5.12.5
		portStatAlarmAction OBJECT-TYPE
			SYNTAX INTEGER
				{
				add(1),
				delete(2)
				}
			MAX-ACCESS read-write
			STATUS current
			DESCRIPTION
				"Description."
			::= { portStatAlarm 5 }

		
--          1.3.6.1.4.1.37950.1.1.5.12.8.5.13
-- 1.3.6.1.4.1.37950.1.1.5.12.8.5.13
-- 1.3.6.1.4.1.37950.1.1.5.12.8.5.13
-- 1.3.6.1.4.1.37950.1.1.5.12.8.5.13
-- 1.3.6.1.4.1.37950.1.1.5.12.8.5.13
-- 1.3.6.1.4.1.37950.1.1.5.12.8.5.13
-- 1.3.6.1.4.1.37950.1.1.5.12.8.5.13
-- 1.3.6.1.4.1.37950.1.1.5.12.8.5.13
-- 1.3.6.1.4.1.37950.1.1.5.12.8.5.13
		-- 1.3.6.1.4.1.37950.1.1.5.12.8.5.13
		potsAlarmStatus OBJECT IDENTIFIER ::= { alarmProfileEdit 13 }

		
--          1.3.6.1.4.1.37950.1.1.5.12.8.5.13.1
-- 1.3.6.1.4.1.37950.1.1.5.12.8.5.13.1
-- 1.3.6.1.4.1.37950.1.1.5.12.8.5.13.1
-- 1.3.6.1.4.1.37950.1.1.5.12.8.5.13.1
-- 1.3.6.1.4.1.37950.1.1.5.12.8.5.13.1
-- 1.3.6.1.4.1.37950.1.1.5.12.8.5.13.1
-- 1.3.6.1.4.1.37950.1.1.5.12.8.5.13.1
-- 1.3.6.1.4.1.37950.1.1.5.12.8.5.13.1
-- 1.3.6.1.4.1.37950.1.1.5.12.8.5.13.1
		-- 1.3.6.1.4.1.37950.1.1.5.12.8.5.13.1
		potsAlarmPotsNo OBJECT-TYPE
			SYNTAX INTEGER (1..64)
			MAX-ACCESS read-write
			STATUS current
			DESCRIPTION
				"Description."
			::= { potsAlarmStatus 1 }

		
--          1.3.6.1.4.1.37950.1.1.5.12.8.5.13.2
-- 1.3.6.1.4.1.37950.1.1.5.12.8.5.13.2
-- 1.3.6.1.4.1.37950.1.1.5.12.8.5.13.2
-- 1.3.6.1.4.1.37950.1.1.5.12.8.5.13.2
-- 1.3.6.1.4.1.37950.1.1.5.12.8.5.13.2
-- 1.3.6.1.4.1.37950.1.1.5.12.8.5.13.2
-- 1.3.6.1.4.1.37950.1.1.5.12.8.5.13.2
-- 1.3.6.1.4.1.37950.1.1.5.12.8.5.13.2
-- 1.3.6.1.4.1.37950.1.1.5.12.8.5.13.2
		-- 1.3.6.1.4.1.37950.1.1.5.12.8.5.13.2
		potsPortFailAlarmEn OBJECT-TYPE
			SYNTAX INTEGER
				{
				disable(0),
				enable(1)
				}
			MAX-ACCESS read-write
			STATUS current
			DESCRIPTION
				"Description."
			::= { potsAlarmStatus 2 }

		
--          1.3.6.1.4.1.37950.1.1.5.12.8.5.13.3
-- 1.3.6.1.4.1.37950.1.1.5.12.8.5.13.3
-- 1.3.6.1.4.1.37950.1.1.5.12.8.5.13.3
-- 1.3.6.1.4.1.37950.1.1.5.12.8.5.13.3
-- 1.3.6.1.4.1.37950.1.1.5.12.8.5.13.3
-- 1.3.6.1.4.1.37950.1.1.5.12.8.5.13.3
-- 1.3.6.1.4.1.37950.1.1.5.12.8.5.13.3
-- 1.3.6.1.4.1.37950.1.1.5.12.8.5.13.3
-- 1.3.6.1.4.1.37950.1.1.5.12.8.5.13.3
		-- 1.3.6.1.4.1.37950.1.1.5.12.8.5.13.3
		potsAlarmStatusAction OBJECT-TYPE
			SYNTAX INTEGER
				{
				add(1),
				delete(2)
				}
			MAX-ACCESS read-write
			STATUS current
			DESCRIPTION
				"Description."
			::= { potsAlarmStatus 3 }

		
--          1.3.6.1.4.1.37950.1.1.5.12.8.5.14
-- 1.3.6.1.4.1.37950.1.1.5.12.8.5.14
-- 1.3.6.1.4.1.37950.1.1.5.12.8.5.14
-- 1.3.6.1.4.1.37950.1.1.5.12.8.5.14
-- 1.3.6.1.4.1.37950.1.1.5.12.8.5.14
-- 1.3.6.1.4.1.37950.1.1.5.12.8.5.14
-- 1.3.6.1.4.1.37950.1.1.5.12.8.5.14
-- 1.3.6.1.4.1.37950.1.1.5.12.8.5.14
-- 1.3.6.1.4.1.37950.1.1.5.12.8.5.14
		-- 1.3.6.1.4.1.37950.1.1.5.12.8.5.14
		e1AlarmStatus OBJECT IDENTIFIER ::= { alarmProfileEdit 14 }

		
--          1.3.6.1.4.1.37950.1.1.5.12.8.5.14.1
-- 1.3.6.1.4.1.37950.1.1.5.12.8.5.14.1
-- 1.3.6.1.4.1.37950.1.1.5.12.8.5.14.1
-- 1.3.6.1.4.1.37950.1.1.5.12.8.5.14.1
-- 1.3.6.1.4.1.37950.1.1.5.12.8.5.14.1
-- 1.3.6.1.4.1.37950.1.1.5.12.8.5.14.1
-- 1.3.6.1.4.1.37950.1.1.5.12.8.5.14.1
-- 1.3.6.1.4.1.37950.1.1.5.12.8.5.14.1
-- 1.3.6.1.4.1.37950.1.1.5.12.8.5.14.1
		-- 1.3.6.1.4.1.37950.1.1.5.12.8.5.14.1
		e1AlarmE1No OBJECT-TYPE
			SYNTAX INTEGER (1..16)
			MAX-ACCESS read-write
			STATUS current
			DESCRIPTION
				"Description."
			::= { e1AlarmStatus 1 }

		
--          1.3.6.1.4.1.37950.1.1.5.12.8.5.14.2
-- 1.3.6.1.4.1.37950.1.1.5.12.8.5.14.2
-- 1.3.6.1.4.1.37950.1.1.5.12.8.5.14.2
-- 1.3.6.1.4.1.37950.1.1.5.12.8.5.14.2
-- 1.3.6.1.4.1.37950.1.1.5.12.8.5.14.2
-- 1.3.6.1.4.1.37950.1.1.5.12.8.5.14.2
-- 1.3.6.1.4.1.37950.1.1.5.12.8.5.14.2
-- 1.3.6.1.4.1.37950.1.1.5.12.8.5.14.2
-- 1.3.6.1.4.1.37950.1.1.5.12.8.5.14.2
		-- 1.3.6.1.4.1.37950.1.1.5.12.8.5.14.2
		e1AlarmType OBJECT-TYPE
			SYNTAX INTEGER
				{
				e1PortFailure(1),
				e1TimingUnlock(2),
				e1Los(3)
				}
			MAX-ACCESS read-write
			STATUS current
			DESCRIPTION
				"Description."
			::= { e1AlarmStatus 2 }

		
--          1.3.6.1.4.1.37950.1.1.5.12.8.5.14.3
-- 1.3.6.1.4.1.37950.1.1.5.12.8.5.14.3
-- 1.3.6.1.4.1.37950.1.1.5.12.8.5.14.3
-- 1.3.6.1.4.1.37950.1.1.5.12.8.5.14.3
-- 1.3.6.1.4.1.37950.1.1.5.12.8.5.14.3
-- 1.3.6.1.4.1.37950.1.1.5.12.8.5.14.3
-- 1.3.6.1.4.1.37950.1.1.5.12.8.5.14.3
-- 1.3.6.1.4.1.37950.1.1.5.12.8.5.14.3
-- 1.3.6.1.4.1.37950.1.1.5.12.8.5.14.3
		-- 1.3.6.1.4.1.37950.1.1.5.12.8.5.14.3
		e1AlarmTypeEn OBJECT-TYPE
			SYNTAX INTEGER
				{
				disable(0),
				enable(1)
				}
			MAX-ACCESS read-write
			STATUS current
			DESCRIPTION
				"Description."
			::= { e1AlarmStatus 3 }

		
--          1.3.6.1.4.1.37950.1.1.5.12.8.5.14.4
-- 1.3.6.1.4.1.37950.1.1.5.12.8.5.14.4
-- 1.3.6.1.4.1.37950.1.1.5.12.8.5.14.4
-- 1.3.6.1.4.1.37950.1.1.5.12.8.5.14.4
-- 1.3.6.1.4.1.37950.1.1.5.12.8.5.14.4
-- 1.3.6.1.4.1.37950.1.1.5.12.8.5.14.4
-- 1.3.6.1.4.1.37950.1.1.5.12.8.5.14.4
-- 1.3.6.1.4.1.37950.1.1.5.12.8.5.14.4
-- 1.3.6.1.4.1.37950.1.1.5.12.8.5.14.4
		-- 1.3.6.1.4.1.37950.1.1.5.12.8.5.14.4
		e1AlarmStatusAction OBJECT-TYPE
			SYNTAX INTEGER
				{
				add(1),
				delete(2)
				}
			MAX-ACCESS read-write
			STATUS current
			DESCRIPTION
				"Description."
			::= { e1AlarmStatus 4 }

		
--          1.3.6.1.4.1.37950.1.1.5.12.8.6
-- 1.3.6.1.4.1.37950.1.1.5.12.8.6
-- 1.3.6.1.4.1.37950.1.1.5.12.8.6
-- 1.3.6.1.4.1.37950.1.1.5.12.8.6
-- 1.3.6.1.4.1.37950.1.1.5.12.8.6
-- 1.3.6.1.4.1.37950.1.1.5.12.8.6
-- 1.3.6.1.4.1.37950.1.1.5.12.8.6
-- 1.3.6.1.4.1.37950.1.1.5.12.8.6
-- 1.3.6.1.4.1.37950.1.1.5.12.8.6
		-- 1.3.6.1.4.1.37950.1.1.5.12.8.6
		profileManualBind OBJECT IDENTIFIER ::= { onuProfileCfg 6 }

		
--          1.3.6.1.4.1.37950.1.1.5.12.8.6.1
-- 1.3.6.1.4.1.37950.1.1.5.12.8.6.1
-- 1.3.6.1.4.1.37950.1.1.5.12.8.6.1
-- 1.3.6.1.4.1.37950.1.1.5.12.8.6.1
-- 1.3.6.1.4.1.37950.1.1.5.12.8.6.1
-- 1.3.6.1.4.1.37950.1.1.5.12.8.6.1
-- 1.3.6.1.4.1.37950.1.1.5.12.8.6.1
-- 1.3.6.1.4.1.37950.1.1.5.12.8.6.1
-- 1.3.6.1.4.1.37950.1.1.5.12.8.6.1
		-- 1.3.6.1.4.1.37950.1.1.5.12.8.6.1
		profileBindTpye OBJECT-TYPE
			SYNTAX INTEGER
				{
				dba(1),
				srv(2),
				voip(3),
				alarm(4)
				}
			MAX-ACCESS read-write
			STATUS current
			DESCRIPTION
				"Description."
			::= { profileManualBind 1 }

		
--          1.3.6.1.4.1.37950.1.1.5.12.8.6.2
-- 1.3.6.1.4.1.37950.1.1.5.12.8.6.2
-- 1.3.6.1.4.1.37950.1.1.5.12.8.6.2
-- 1.3.6.1.4.1.37950.1.1.5.12.8.6.2
-- 1.3.6.1.4.1.37950.1.1.5.12.8.6.2
-- 1.3.6.1.4.1.37950.1.1.5.12.8.6.2
-- 1.3.6.1.4.1.37950.1.1.5.12.8.6.2
-- 1.3.6.1.4.1.37950.1.1.5.12.8.6.2
-- 1.3.6.1.4.1.37950.1.1.5.12.8.6.2
		-- 1.3.6.1.4.1.37950.1.1.5.12.8.6.2
		profileBindPon OBJECT-TYPE
			SYNTAX Integer32 (1..16)
			MAX-ACCESS read-write
			STATUS current
			DESCRIPTION
				"Description."
			::= { profileManualBind 2 }

		
--          1.3.6.1.4.1.37950.1.1.5.12.8.6.3
-- 1.3.6.1.4.1.37950.1.1.5.12.8.6.3
-- 1.3.6.1.4.1.37950.1.1.5.12.8.6.3
-- 1.3.6.1.4.1.37950.1.1.5.12.8.6.3
-- 1.3.6.1.4.1.37950.1.1.5.12.8.6.3
-- 1.3.6.1.4.1.37950.1.1.5.12.8.6.3
-- 1.3.6.1.4.1.37950.1.1.5.12.8.6.3
-- 1.3.6.1.4.1.37950.1.1.5.12.8.6.3
-- 1.3.6.1.4.1.37950.1.1.5.12.8.6.3
		-- 1.3.6.1.4.1.37950.1.1.5.12.8.6.3
		profileBindOnu OBJECT-TYPE
			SYNTAX Integer32 (1..65535)
			MAX-ACCESS read-write
			STATUS current
			DESCRIPTION
				"Description."
			::= { profileManualBind 3 }

		
--          1.3.6.1.4.1.37950.1.1.5.12.8.6.4
-- 1.3.6.1.4.1.37950.1.1.5.12.8.6.4
-- 1.3.6.1.4.1.37950.1.1.5.12.8.6.4
-- 1.3.6.1.4.1.37950.1.1.5.12.8.6.4
-- 1.3.6.1.4.1.37950.1.1.5.12.8.6.4
-- 1.3.6.1.4.1.37950.1.1.5.12.8.6.4
-- 1.3.6.1.4.1.37950.1.1.5.12.8.6.4
-- 1.3.6.1.4.1.37950.1.1.5.12.8.6.4
-- 1.3.6.1.4.1.37950.1.1.5.12.8.6.4
		-- 1.3.6.1.4.1.37950.1.1.5.12.8.6.4
		profileBindId OBJECT-TYPE
			SYNTAX Integer32 (0..32767)
			MAX-ACCESS read-write
			STATUS current
			DESCRIPTION
				"Description."
			::= { profileManualBind 4 }

		
--          1.3.6.1.4.1.37950.1.1.5.12.8.6.5
-- 1.3.6.1.4.1.37950.1.1.5.12.8.6.5
-- 1.3.6.1.4.1.37950.1.1.5.12.8.6.5
-- 1.3.6.1.4.1.37950.1.1.5.12.8.6.5
-- 1.3.6.1.4.1.37950.1.1.5.12.8.6.5
-- 1.3.6.1.4.1.37950.1.1.5.12.8.6.5
-- 1.3.6.1.4.1.37950.1.1.5.12.8.6.5
-- 1.3.6.1.4.1.37950.1.1.5.12.8.6.5
-- 1.3.6.1.4.1.37950.1.1.5.12.8.6.5
		-- 1.3.6.1.4.1.37950.1.1.5.12.8.6.5
		profileBindAction OBJECT-TYPE
			SYNTAX INTEGER { commit(1) }
			MAX-ACCESS read-write
			STATUS current
			DESCRIPTION
				"Description."
			::= { profileManualBind 5 }

		
--          1.3.6.1.4.1.37950.1.1.5.12.8.7
-- 1.3.6.1.4.1.37950.1.1.5.12.8.7
-- 1.3.6.1.4.1.37950.1.1.5.12.8.7
-- 1.3.6.1.4.1.37950.1.1.5.12.8.7
-- 1.3.6.1.4.1.37950.1.1.5.12.8.7
-- 1.3.6.1.4.1.37950.1.1.5.12.8.7
-- 1.3.6.1.4.1.37950.1.1.5.12.8.7
-- 1.3.6.1.4.1.37950.1.1.5.12.8.7
-- 1.3.6.1.4.1.37950.1.1.5.12.8.7
		-- 1.3.6.1.4.1.37950.1.1.5.12.8.7
		profileAutoBind OBJECT IDENTIFIER ::= { onuProfileCfg 7 }

		
--          1.3.6.1.4.1.37950.1.1.5.12.8.7.1
-- 1.3.6.1.4.1.37950.1.1.5.12.8.7.1
-- 1.3.6.1.4.1.37950.1.1.5.12.8.7.1
-- 1.3.6.1.4.1.37950.1.1.5.12.8.7.1
-- 1.3.6.1.4.1.37950.1.1.5.12.8.7.1
-- 1.3.6.1.4.1.37950.1.1.5.12.8.7.1
-- 1.3.6.1.4.1.37950.1.1.5.12.8.7.1
-- 1.3.6.1.4.1.37950.1.1.5.12.8.7.1
-- 1.3.6.1.4.1.37950.1.1.5.12.8.7.1
		-- 1.3.6.1.4.1.37950.1.1.5.12.8.7.1
		profileAutoBindDba OBJECT-TYPE
			SYNTAX Integer32 (0..32767)
			MAX-ACCESS read-write
			STATUS current
			DESCRIPTION
				"Description."
			::= { profileAutoBind 1 }

		
--          1.3.6.1.4.1.37950.1.1.5.12.8.7.2
-- 1.3.6.1.4.1.37950.1.1.5.12.8.7.2
-- 1.3.6.1.4.1.37950.1.1.5.12.8.7.2
-- 1.3.6.1.4.1.37950.1.1.5.12.8.7.2
-- 1.3.6.1.4.1.37950.1.1.5.12.8.7.2
-- 1.3.6.1.4.1.37950.1.1.5.12.8.7.2
-- 1.3.6.1.4.1.37950.1.1.5.12.8.7.2
-- 1.3.6.1.4.1.37950.1.1.5.12.8.7.2
-- 1.3.6.1.4.1.37950.1.1.5.12.8.7.2
		-- 1.3.6.1.4.1.37950.1.1.5.12.8.7.2
		profileAutoBindSrv OBJECT-TYPE
			SYNTAX Integer32 (0..32767)
			MAX-ACCESS read-write
			STATUS current
			DESCRIPTION
				"Description."
			::= { profileAutoBind 2 }

		
--          1.3.6.1.4.1.37950.1.1.5.12.8.7.3
-- 1.3.6.1.4.1.37950.1.1.5.12.8.7.3
-- 1.3.6.1.4.1.37950.1.1.5.12.8.7.3
-- 1.3.6.1.4.1.37950.1.1.5.12.8.7.3
-- 1.3.6.1.4.1.37950.1.1.5.12.8.7.3
-- 1.3.6.1.4.1.37950.1.1.5.12.8.7.3
-- 1.3.6.1.4.1.37950.1.1.5.12.8.7.3
-- 1.3.6.1.4.1.37950.1.1.5.12.8.7.3
-- 1.3.6.1.4.1.37950.1.1.5.12.8.7.3
		-- 1.3.6.1.4.1.37950.1.1.5.12.8.7.3
		profileAutoBindVoip OBJECT-TYPE
			SYNTAX Integer32 (0..32767)
			MAX-ACCESS read-write
			STATUS current
			DESCRIPTION
				"Description."
			::= { profileAutoBind 3 }

		
--          1.3.6.1.4.1.37950.1.1.5.12.8.7.4
-- 1.3.6.1.4.1.37950.1.1.5.12.8.7.4
-- 1.3.6.1.4.1.37950.1.1.5.12.8.7.4
-- 1.3.6.1.4.1.37950.1.1.5.12.8.7.4
-- 1.3.6.1.4.1.37950.1.1.5.12.8.7.4
-- 1.3.6.1.4.1.37950.1.1.5.12.8.7.4
-- 1.3.6.1.4.1.37950.1.1.5.12.8.7.4
-- 1.3.6.1.4.1.37950.1.1.5.12.8.7.4
-- 1.3.6.1.4.1.37950.1.1.5.12.8.7.4
		-- 1.3.6.1.4.1.37950.1.1.5.12.8.7.4
		profileAutoBindAlarm OBJECT-TYPE
			SYNTAX Integer32 (0..32767)
			MAX-ACCESS read-write
			STATUS current
			DESCRIPTION
				"Description."
			::= { profileAutoBind 4 }

		
--          1.3.6.1.4.1.37950.1.1.5.12.8.7.5
-- 1.3.6.1.4.1.37950.1.1.5.12.8.7.5
-- 1.3.6.1.4.1.37950.1.1.5.12.8.7.5
-- 1.3.6.1.4.1.37950.1.1.5.12.8.7.5
-- 1.3.6.1.4.1.37950.1.1.5.12.8.7.5
-- 1.3.6.1.4.1.37950.1.1.5.12.8.7.5
-- 1.3.6.1.4.1.37950.1.1.5.12.8.7.5
-- 1.3.6.1.4.1.37950.1.1.5.12.8.7.5
-- 1.3.6.1.4.1.37950.1.1.5.12.8.7.5
		-- 1.3.6.1.4.1.37950.1.1.5.12.8.7.5
		profileOnuType OBJECT-TYPE
			SYNTAX OCTET STRING
			MAX-ACCESS read-write
			STATUS current
			DESCRIPTION
				"Description."
			::= { profileAutoBind 5 }

		
--          1.3.6.1.4.1.37950.1.1.5.12.8.7.6
-- 1.3.6.1.4.1.37950.1.1.5.12.8.7.6
-- 1.3.6.1.4.1.37950.1.1.5.12.8.7.6
-- 1.3.6.1.4.1.37950.1.1.5.12.8.7.6
-- 1.3.6.1.4.1.37950.1.1.5.12.8.7.6
-- 1.3.6.1.4.1.37950.1.1.5.12.8.7.6
-- 1.3.6.1.4.1.37950.1.1.5.12.8.7.6
-- 1.3.6.1.4.1.37950.1.1.5.12.8.7.6
-- 1.3.6.1.4.1.37950.1.1.5.12.8.7.6
		-- 1.3.6.1.4.1.37950.1.1.5.12.8.7.6
		profileAutoBindAction OBJECT-TYPE
			SYNTAX INTEGER
				{
				add(1),
				delete(2)
				}
			MAX-ACCESS read-write
			STATUS current
			DESCRIPTION
				"Description."
			::= { profileAutoBind 6 }

		
--          1.3.6.1.4.1.37950.1.1.5.12.8.8
-- 1.3.6.1.4.1.37950.1.1.5.12.8.8
-- 1.3.6.1.4.1.37950.1.1.5.12.8.8
-- 1.3.6.1.4.1.37950.1.1.5.12.8.8
-- 1.3.6.1.4.1.37950.1.1.5.12.8.8
-- 1.3.6.1.4.1.37950.1.1.5.12.8.8
-- 1.3.6.1.4.1.37950.1.1.5.12.8.8
-- 1.3.6.1.4.1.37950.1.1.5.12.8.8
-- 1.3.6.1.4.1.37950.1.1.5.12.8.8
		-- 1.3.6.1.4.1.37950.1.1.5.12.8.8
		profileDescrEdit OBJECT IDENTIFIER ::= { onuProfileCfg 8 }

		
--          1.3.6.1.4.1.37950.1.1.5.12.8.8.1
-- 1.3.6.1.4.1.37950.1.1.5.12.8.8.1
-- 1.3.6.1.4.1.37950.1.1.5.12.8.8.1
-- 1.3.6.1.4.1.37950.1.1.5.12.8.8.1
-- 1.3.6.1.4.1.37950.1.1.5.12.8.8.1
-- 1.3.6.1.4.1.37950.1.1.5.12.8.8.1
-- 1.3.6.1.4.1.37950.1.1.5.12.8.8.1
-- 1.3.6.1.4.1.37950.1.1.5.12.8.8.1
-- 1.3.6.1.4.1.37950.1.1.5.12.8.8.1
		-- 1.3.6.1.4.1.37950.1.1.5.12.8.8.1
		profileDescrType OBJECT-TYPE
			SYNTAX INTEGER
				{
				dba(1),
				srv(2),
				voip(3),
				alarm(4)
				}
			MAX-ACCESS read-write
			STATUS current
			DESCRIPTION
				"Description."
			::= { profileDescrEdit 1 }

		
--          1.3.6.1.4.1.37950.1.1.5.12.8.8.2
-- 1.3.6.1.4.1.37950.1.1.5.12.8.8.2
-- 1.3.6.1.4.1.37950.1.1.5.12.8.8.2
-- 1.3.6.1.4.1.37950.1.1.5.12.8.8.2
-- 1.3.6.1.4.1.37950.1.1.5.12.8.8.2
-- 1.3.6.1.4.1.37950.1.1.5.12.8.8.2
-- 1.3.6.1.4.1.37950.1.1.5.12.8.8.2
-- 1.3.6.1.4.1.37950.1.1.5.12.8.8.2
-- 1.3.6.1.4.1.37950.1.1.5.12.8.8.2
		-- 1.3.6.1.4.1.37950.1.1.5.12.8.8.2
		profileDescrId OBJECT-TYPE
			SYNTAX Integer32 (1..32767)
			MAX-ACCESS read-write
			STATUS current
			DESCRIPTION
				"Description."
			::= { profileDescrEdit 2 }

		
--          1.3.6.1.4.1.37950.1.1.5.12.8.8.3
-- 1.3.6.1.4.1.37950.1.1.5.12.8.8.3
-- 1.3.6.1.4.1.37950.1.1.5.12.8.8.3
-- 1.3.6.1.4.1.37950.1.1.5.12.8.8.3
-- 1.3.6.1.4.1.37950.1.1.5.12.8.8.3
-- 1.3.6.1.4.1.37950.1.1.5.12.8.8.3
-- 1.3.6.1.4.1.37950.1.1.5.12.8.8.3
-- 1.3.6.1.4.1.37950.1.1.5.12.8.8.3
-- 1.3.6.1.4.1.37950.1.1.5.12.8.8.3
		-- 1.3.6.1.4.1.37950.1.1.5.12.8.8.3
		profileDescrStr OBJECT-TYPE
			SYNTAX OCTET STRING
			MAX-ACCESS read-write
			STATUS current
			DESCRIPTION
				"Description."
			::= { profileDescrEdit 3 }

		
--          1.3.6.1.4.1.37950.1.1.5.12.8.8.4
-- 1.3.6.1.4.1.37950.1.1.5.12.8.8.4
-- 1.3.6.1.4.1.37950.1.1.5.12.8.8.4
-- 1.3.6.1.4.1.37950.1.1.5.12.8.8.4
-- 1.3.6.1.4.1.37950.1.1.5.12.8.8.4
-- 1.3.6.1.4.1.37950.1.1.5.12.8.8.4
-- 1.3.6.1.4.1.37950.1.1.5.12.8.8.4
-- 1.3.6.1.4.1.37950.1.1.5.12.8.8.4
-- 1.3.6.1.4.1.37950.1.1.5.12.8.8.4
		-- 1.3.6.1.4.1.37950.1.1.5.12.8.8.4
		profileDescrAction OBJECT-TYPE
			SYNTAX INTEGER
				{
				submit(1),
				delete(2)
				}
			MAX-ACCESS read-write
			STATUS current
			DESCRIPTION
				"Description."
			::= { profileDescrEdit 4 }

		
--          1.3.6.1.4.1.37950.1.1.5.12.9
-- 1.3.6.1.4.1.37950.1.1.5.12.9
-- 1.3.6.1.4.1.37950.1.1.5.12.9
-- 1.3.6.1.4.1.37950.1.1.5.12.9
-- 1.3.6.1.4.1.37950.1.1.5.12.9
-- 1.3.6.1.4.1.37950.1.1.5.12.9
-- 1.3.6.1.4.1.37950.1.1.5.12.9
-- 1.3.6.1.4.1.37950.1.1.5.12.9
-- 1.3.6.1.4.1.37950.1.1.5.12.9
		-- 1.3.6.1.4.1.37950.1.1.5.12.9
		onuProfileShow OBJECT IDENTIFIER ::= { v1600dOnuMgmt 9 }

		
--          1.3.6.1.4.1.37950.1.1.5.12.9.1
-- 1.3.6.1.4.1.37950.1.1.5.12.9.1
-- 1.3.6.1.4.1.37950.1.1.5.12.9.1
-- 1.3.6.1.4.1.37950.1.1.5.12.9.1
-- 1.3.6.1.4.1.37950.1.1.5.12.9.1
-- 1.3.6.1.4.1.37950.1.1.5.12.9.1
-- 1.3.6.1.4.1.37950.1.1.5.12.9.1
-- 1.3.6.1.4.1.37950.1.1.5.12.9.1
-- 1.3.6.1.4.1.37950.1.1.5.12.9.1
		-- 1.3.6.1.4.1.37950.1.1.5.12.9.1
		dbaProfileShow OBJECT IDENTIFIER ::= { onuProfileShow 1 }

		
--          1.3.6.1.4.1.37950.1.1.5.12.9.1.1
-- 1.3.6.1.4.1.37950.1.1.5.12.9.1.1
-- 1.3.6.1.4.1.37950.1.1.5.12.9.1.1
-- 1.3.6.1.4.1.37950.1.1.5.12.9.1.1
-- 1.3.6.1.4.1.37950.1.1.5.12.9.1.1
-- 1.3.6.1.4.1.37950.1.1.5.12.9.1.1
-- 1.3.6.1.4.1.37950.1.1.5.12.9.1.1
-- 1.3.6.1.4.1.37950.1.1.5.12.9.1.1
-- 1.3.6.1.4.1.37950.1.1.5.12.9.1.1
		-- 1.3.6.1.4.1.37950.1.1.5.12.9.1.1
		upsteamPFTable OBJECT-TYPE
			SYNTAX SEQUENCE OF UpsteamPFEntry
			MAX-ACCESS not-accessible
			STATUS current
			DESCRIPTION
				"Description."
			::= { dbaProfileShow 1 }

		
--          1.3.6.1.4.1.37950.1.1.5.12.9.1.1.1
-- 1.3.6.1.4.1.37950.1.1.5.12.9.1.1.1
-- 1.3.6.1.4.1.37950.1.1.5.12.9.1.1.1
-- 1.3.6.1.4.1.37950.1.1.5.12.9.1.1.1
-- 1.3.6.1.4.1.37950.1.1.5.12.9.1.1.1
-- 1.3.6.1.4.1.37950.1.1.5.12.9.1.1.1
-- 1.3.6.1.4.1.37950.1.1.5.12.9.1.1.1
-- 1.3.6.1.4.1.37950.1.1.5.12.9.1.1.1
-- 1.3.6.1.4.1.37950.1.1.5.12.9.1.1.1
		-- 1.3.6.1.4.1.37950.1.1.5.12.9.1.1.1
		upsteamPFEntry OBJECT-TYPE
			SYNTAX UpsteamPFEntry
			MAX-ACCESS not-accessible
			STATUS current
			DESCRIPTION
				"Description."
			INDEX { upstreamDbaId }
			::= { upsteamPFTable 1 }

		
		UpsteamPFEntry ::=
			SEQUENCE { 
				upstreamDbaId
					Integer32,
				upstreamFirS
					Integer32,
				upstreamCirS
					Integer32,
				upstreamPirS
					Integer32,
				upstreamWeightS
					Integer32
			 }

--          1.3.6.1.4.1.37950.1.1.5.12.9.1.1.1.1
-- 1.3.6.1.4.1.37950.1.1.5.12.9.1.1.1.1
-- 1.3.6.1.4.1.37950.1.1.5.12.9.1.1.1.1
-- 1.3.6.1.4.1.37950.1.1.5.12.9.1.1.1.1
-- 1.3.6.1.4.1.37950.1.1.5.12.9.1.1.1.1
-- 1.3.6.1.4.1.37950.1.1.5.12.9.1.1.1.1
-- 1.3.6.1.4.1.37950.1.1.5.12.9.1.1.1.1
-- 1.3.6.1.4.1.37950.1.1.5.12.9.1.1.1.1
-- 1.3.6.1.4.1.37950.1.1.5.12.9.1.1.1.1
		-- 1.3.6.1.4.1.37950.1.1.5.12.9.1.1.1.1
		upstreamDbaId OBJECT-TYPE
			SYNTAX Integer32
			MAX-ACCESS read-only
			STATUS current
			DESCRIPTION
				"Description."
			::= { upsteamPFEntry 1 }

		
--          1.3.6.1.4.1.37950.1.1.5.12.9.1.1.1.2
-- 1.3.6.1.4.1.37950.1.1.5.12.9.1.1.1.2
-- 1.3.6.1.4.1.37950.1.1.5.12.9.1.1.1.2
-- 1.3.6.1.4.1.37950.1.1.5.12.9.1.1.1.2
-- 1.3.6.1.4.1.37950.1.1.5.12.9.1.1.1.2
-- 1.3.6.1.4.1.37950.1.1.5.12.9.1.1.1.2
-- 1.3.6.1.4.1.37950.1.1.5.12.9.1.1.1.2
-- 1.3.6.1.4.1.37950.1.1.5.12.9.1.1.1.2
-- 1.3.6.1.4.1.37950.1.1.5.12.9.1.1.1.2
		-- 1.3.6.1.4.1.37950.1.1.5.12.9.1.1.1.2
		upstreamFirS OBJECT-TYPE
			SYNTAX Integer32 (0..950000)
			MAX-ACCESS read-only
			STATUS current
			DESCRIPTION
				"Description."
			::= { upsteamPFEntry 2 }

		
--          1.3.6.1.4.1.37950.1.1.5.12.9.1.1.1.3
-- 1.3.6.1.4.1.37950.1.1.5.12.9.1.1.1.3
-- 1.3.6.1.4.1.37950.1.1.5.12.9.1.1.1.3
-- 1.3.6.1.4.1.37950.1.1.5.12.9.1.1.1.3
-- 1.3.6.1.4.1.37950.1.1.5.12.9.1.1.1.3
-- 1.3.6.1.4.1.37950.1.1.5.12.9.1.1.1.3
-- 1.3.6.1.4.1.37950.1.1.5.12.9.1.1.1.3
-- 1.3.6.1.4.1.37950.1.1.5.12.9.1.1.1.3
-- 1.3.6.1.4.1.37950.1.1.5.12.9.1.1.1.3
		-- 1.3.6.1.4.1.37950.1.1.5.12.9.1.1.1.3
		upstreamCirS OBJECT-TYPE
			SYNTAX Integer32 (1..950000)
			MAX-ACCESS read-only
			STATUS current
			DESCRIPTION
				"Description."
			::= { upsteamPFEntry 3 }

		
--          1.3.6.1.4.1.37950.1.1.5.12.9.1.1.1.4
-- 1.3.6.1.4.1.37950.1.1.5.12.9.1.1.1.4
-- 1.3.6.1.4.1.37950.1.1.5.12.9.1.1.1.4
-- 1.3.6.1.4.1.37950.1.1.5.12.9.1.1.1.4
-- 1.3.6.1.4.1.37950.1.1.5.12.9.1.1.1.4
-- 1.3.6.1.4.1.37950.1.1.5.12.9.1.1.1.4
-- 1.3.6.1.4.1.37950.1.1.5.12.9.1.1.1.4
-- 1.3.6.1.4.1.37950.1.1.5.12.9.1.1.1.4
-- 1.3.6.1.4.1.37950.1.1.5.12.9.1.1.1.4
		-- 1.3.6.1.4.1.37950.1.1.5.12.9.1.1.1.4
		upstreamPirS OBJECT-TYPE
			SYNTAX Integer32 (512..1000000)
			MAX-ACCESS read-only
			STATUS current
			DESCRIPTION
				"Description."
			::= { upsteamPFEntry 4 }

		
--          1.3.6.1.4.1.37950.1.1.5.12.9.1.1.1.5
-- 1.3.6.1.4.1.37950.1.1.5.12.9.1.1.1.5
-- 1.3.6.1.4.1.37950.1.1.5.12.9.1.1.1.5
-- 1.3.6.1.4.1.37950.1.1.5.12.9.1.1.1.5
-- 1.3.6.1.4.1.37950.1.1.5.12.9.1.1.1.5
-- 1.3.6.1.4.1.37950.1.1.5.12.9.1.1.1.5
-- 1.3.6.1.4.1.37950.1.1.5.12.9.1.1.1.5
-- 1.3.6.1.4.1.37950.1.1.5.12.9.1.1.1.5
-- 1.3.6.1.4.1.37950.1.1.5.12.9.1.1.1.5
		-- 1.3.6.1.4.1.37950.1.1.5.12.9.1.1.1.5
		upstreamWeightS OBJECT-TYPE
			SYNTAX Integer32 (1..20)
			MAX-ACCESS read-only
			STATUS current
			DESCRIPTION
				"Description."
			::= { upsteamPFEntry 5 }

		
--          1.3.6.1.4.1.37950.1.1.5.12.9.1.2
-- 1.3.6.1.4.1.37950.1.1.5.12.9.1.2
-- 1.3.6.1.4.1.37950.1.1.5.12.9.1.2
-- 1.3.6.1.4.1.37950.1.1.5.12.9.1.2
-- 1.3.6.1.4.1.37950.1.1.5.12.9.1.2
-- 1.3.6.1.4.1.37950.1.1.5.12.9.1.2
-- 1.3.6.1.4.1.37950.1.1.5.12.9.1.2
-- 1.3.6.1.4.1.37950.1.1.5.12.9.1.2
-- 1.3.6.1.4.1.37950.1.1.5.12.9.1.2
		-- 1.3.6.1.4.1.37950.1.1.5.12.9.1.2
		dnstreamPFTable OBJECT-TYPE
			SYNTAX SEQUENCE OF DnstreamPFEntry
			MAX-ACCESS not-accessible
			STATUS current
			DESCRIPTION
				"Description."
			::= { dbaProfileShow 2 }

		
--          1.3.6.1.4.1.37950.1.1.5.12.9.1.2.1
-- 1.3.6.1.4.1.37950.1.1.5.12.9.1.2.1
-- 1.3.6.1.4.1.37950.1.1.5.12.9.1.2.1
-- 1.3.6.1.4.1.37950.1.1.5.12.9.1.2.1
-- 1.3.6.1.4.1.37950.1.1.5.12.9.1.2.1
-- 1.3.6.1.4.1.37950.1.1.5.12.9.1.2.1
-- 1.3.6.1.4.1.37950.1.1.5.12.9.1.2.1
-- 1.3.6.1.4.1.37950.1.1.5.12.9.1.2.1
-- 1.3.6.1.4.1.37950.1.1.5.12.9.1.2.1
		-- 1.3.6.1.4.1.37950.1.1.5.12.9.1.2.1
		dnstreamPFEntry OBJECT-TYPE
			SYNTAX DnstreamPFEntry
			MAX-ACCESS not-accessible
			STATUS current
			DESCRIPTION
				"Description."
			INDEX { dnstreamDbaId }
			::= { dnstreamPFTable 1 }

		
		DnstreamPFEntry ::=
			SEQUENCE { 
				dnstreamDbaId
					Integer32,
				dnstreamPirS
					Integer32,
				dnstreamWeightS
					Integer32
			 }

--          1.3.6.1.4.1.37950.1.1.5.12.9.1.2.1.1
-- 1.3.6.1.4.1.37950.1.1.5.12.9.1.2.1.1
-- 1.3.6.1.4.1.37950.1.1.5.12.9.1.2.1.1
-- 1.3.6.1.4.1.37950.1.1.5.12.9.1.2.1.1
-- 1.3.6.1.4.1.37950.1.1.5.12.9.1.2.1.1
-- 1.3.6.1.4.1.37950.1.1.5.12.9.1.2.1.1
-- 1.3.6.1.4.1.37950.1.1.5.12.9.1.2.1.1
-- 1.3.6.1.4.1.37950.1.1.5.12.9.1.2.1.1
-- 1.3.6.1.4.1.37950.1.1.5.12.9.1.2.1.1
		-- 1.3.6.1.4.1.37950.1.1.5.12.9.1.2.1.1
		dnstreamDbaId OBJECT-TYPE
			SYNTAX Integer32
			MAX-ACCESS read-only
			STATUS current
			DESCRIPTION
				"Description."
			::= { dnstreamPFEntry 1 }

		
--          1.3.6.1.4.1.37950.1.1.5.12.9.1.2.1.2
-- 1.3.6.1.4.1.37950.1.1.5.12.9.1.2.1.2
-- 1.3.6.1.4.1.37950.1.1.5.12.9.1.2.1.2
-- 1.3.6.1.4.1.37950.1.1.5.12.9.1.2.1.2
-- 1.3.6.1.4.1.37950.1.1.5.12.9.1.2.1.2
-- 1.3.6.1.4.1.37950.1.1.5.12.9.1.2.1.2
-- 1.3.6.1.4.1.37950.1.1.5.12.9.1.2.1.2
-- 1.3.6.1.4.1.37950.1.1.5.12.9.1.2.1.2
-- 1.3.6.1.4.1.37950.1.1.5.12.9.1.2.1.2
		-- 1.3.6.1.4.1.37950.1.1.5.12.9.1.2.1.2
		dnstreamPirS OBJECT-TYPE
			SYNTAX Integer32 (0..1000000)
			MAX-ACCESS read-only
			STATUS current
			DESCRIPTION
				"Description."
			::= { dnstreamPFEntry 2 }

		
--          1.3.6.1.4.1.37950.1.1.5.12.9.1.2.1.3
-- 1.3.6.1.4.1.37950.1.1.5.12.9.1.2.1.3
-- 1.3.6.1.4.1.37950.1.1.5.12.9.1.2.1.3
-- 1.3.6.1.4.1.37950.1.1.5.12.9.1.2.1.3
-- 1.3.6.1.4.1.37950.1.1.5.12.9.1.2.1.3
-- 1.3.6.1.4.1.37950.1.1.5.12.9.1.2.1.3
-- 1.3.6.1.4.1.37950.1.1.5.12.9.1.2.1.3
-- 1.3.6.1.4.1.37950.1.1.5.12.9.1.2.1.3
-- 1.3.6.1.4.1.37950.1.1.5.12.9.1.2.1.3
		-- 1.3.6.1.4.1.37950.1.1.5.12.9.1.2.1.3
		dnstreamWeightS OBJECT-TYPE
			SYNTAX Integer32 (1..16)
			MAX-ACCESS read-only
			STATUS current
			DESCRIPTION
				"Description."
			::= { dnstreamPFEntry 3 }

		
--          1.3.6.1.4.1.37950.1.1.5.12.9.2
-- 1.3.6.1.4.1.37950.1.1.5.12.9.2
-- 1.3.6.1.4.1.37950.1.1.5.12.9.2
-- 1.3.6.1.4.1.37950.1.1.5.12.9.2
-- 1.3.6.1.4.1.37950.1.1.5.12.9.2
-- 1.3.6.1.4.1.37950.1.1.5.12.9.2
-- 1.3.6.1.4.1.37950.1.1.5.12.9.2
-- 1.3.6.1.4.1.37950.1.1.5.12.9.2
-- 1.3.6.1.4.1.37950.1.1.5.12.9.2
		-- 1.3.6.1.4.1.37950.1.1.5.12.9.2
		srvProfileShow OBJECT IDENTIFIER ::= { onuProfileShow 2 }

		
--          1.3.6.1.4.1.37950.1.1.5.12.9.2.1
-- 1.3.6.1.4.1.37950.1.1.5.12.9.2.1
-- 1.3.6.1.4.1.37950.1.1.5.12.9.2.1
-- 1.3.6.1.4.1.37950.1.1.5.12.9.2.1
-- 1.3.6.1.4.1.37950.1.1.5.12.9.2.1
-- 1.3.6.1.4.1.37950.1.1.5.12.9.2.1
-- 1.3.6.1.4.1.37950.1.1.5.12.9.2.1
-- 1.3.6.1.4.1.37950.1.1.5.12.9.2.1
-- 1.3.6.1.4.1.37950.1.1.5.12.9.2.1
		-- 1.3.6.1.4.1.37950.1.1.5.12.9.2.1
		onuLanCountPFTable OBJECT-TYPE
			SYNTAX SEQUENCE OF OnuLanCountPFEntry
			MAX-ACCESS not-accessible
			STATUS current
			DESCRIPTION
				"Description."
			::= { srvProfileShow 1 }

		
--          1.3.6.1.4.1.37950.1.1.5.12.9.2.1.1
-- 1.3.6.1.4.1.37950.1.1.5.12.9.2.1.1
-- 1.3.6.1.4.1.37950.1.1.5.12.9.2.1.1
-- 1.3.6.1.4.1.37950.1.1.5.12.9.2.1.1
-- 1.3.6.1.4.1.37950.1.1.5.12.9.2.1.1
-- 1.3.6.1.4.1.37950.1.1.5.12.9.2.1.1
-- 1.3.6.1.4.1.37950.1.1.5.12.9.2.1.1
-- 1.3.6.1.4.1.37950.1.1.5.12.9.2.1.1
-- 1.3.6.1.4.1.37950.1.1.5.12.9.2.1.1
		-- 1.3.6.1.4.1.37950.1.1.5.12.9.2.1.1
		onuLanCountPFEntry OBJECT-TYPE
			SYNTAX OnuLanCountPFEntry
			MAX-ACCESS not-accessible
			STATUS current
			DESCRIPTION
				"Description."
			INDEX { onuLanCountSrvId }
			::= { onuLanCountPFTable 1 }

		
		OnuLanCountPFEntry ::=
			SEQUENCE { 
				onuLanCountSrvId
					Integer32,
				onuLanCountS
					INTEGER
			 }

--          1.3.6.1.4.1.37950.1.1.5.12.9.2.1.1.1
-- 1.3.6.1.4.1.37950.1.1.5.12.9.2.1.1.1
-- 1.3.6.1.4.1.37950.1.1.5.12.9.2.1.1.1
-- 1.3.6.1.4.1.37950.1.1.5.12.9.2.1.1.1
-- 1.3.6.1.4.1.37950.1.1.5.12.9.2.1.1.1
-- 1.3.6.1.4.1.37950.1.1.5.12.9.2.1.1.1
-- 1.3.6.1.4.1.37950.1.1.5.12.9.2.1.1.1
-- 1.3.6.1.4.1.37950.1.1.5.12.9.2.1.1.1
-- 1.3.6.1.4.1.37950.1.1.5.12.9.2.1.1.1
		-- 1.3.6.1.4.1.37950.1.1.5.12.9.2.1.1.1
		onuLanCountSrvId OBJECT-TYPE
			SYNTAX Integer32 (0..65535)
			MAX-ACCESS read-only
			STATUS current
			DESCRIPTION
				"Description."
			::= { onuLanCountPFEntry 1 }

		
--          1.3.6.1.4.1.37950.1.1.5.12.9.2.1.1.2
-- 1.3.6.1.4.1.37950.1.1.5.12.9.2.1.1.2
-- 1.3.6.1.4.1.37950.1.1.5.12.9.2.1.1.2
-- 1.3.6.1.4.1.37950.1.1.5.12.9.2.1.1.2
-- 1.3.6.1.4.1.37950.1.1.5.12.9.2.1.1.2
-- 1.3.6.1.4.1.37950.1.1.5.12.9.2.1.1.2
-- 1.3.6.1.4.1.37950.1.1.5.12.9.2.1.1.2
-- 1.3.6.1.4.1.37950.1.1.5.12.9.2.1.1.2
-- 1.3.6.1.4.1.37950.1.1.5.12.9.2.1.1.2
		-- 1.3.6.1.4.1.37950.1.1.5.12.9.2.1.1.2
		onuLanCountS OBJECT-TYPE
			SYNTAX INTEGER (0..255)
			MAX-ACCESS read-only
			STATUS current
			DESCRIPTION
				"Description."
			::= { onuLanCountPFEntry 2 }

		
--          1.3.6.1.4.1.37950.1.1.5.12.9.2.2
-- 1.3.6.1.4.1.37950.1.1.5.12.9.2.2
-- 1.3.6.1.4.1.37950.1.1.5.12.9.2.2
-- 1.3.6.1.4.1.37950.1.1.5.12.9.2.2
-- 1.3.6.1.4.1.37950.1.1.5.12.9.2.2
-- 1.3.6.1.4.1.37950.1.1.5.12.9.2.2
-- 1.3.6.1.4.1.37950.1.1.5.12.9.2.2
-- 1.3.6.1.4.1.37950.1.1.5.12.9.2.2
-- 1.3.6.1.4.1.37950.1.1.5.12.9.2.2
		-- 1.3.6.1.4.1.37950.1.1.5.12.9.2.2
		onuFastleavePFTable OBJECT-TYPE
			SYNTAX SEQUENCE OF OnuFastleavePFEntry
			MAX-ACCESS not-accessible
			STATUS current
			DESCRIPTION
				"Description."
			::= { srvProfileShow 2 }

		
--          1.3.6.1.4.1.37950.1.1.5.12.9.2.2.1
-- 1.3.6.1.4.1.37950.1.1.5.12.9.2.2.1
-- 1.3.6.1.4.1.37950.1.1.5.12.9.2.2.1
-- 1.3.6.1.4.1.37950.1.1.5.12.9.2.2.1
-- 1.3.6.1.4.1.37950.1.1.5.12.9.2.2.1
-- 1.3.6.1.4.1.37950.1.1.5.12.9.2.2.1
-- 1.3.6.1.4.1.37950.1.1.5.12.9.2.2.1
-- 1.3.6.1.4.1.37950.1.1.5.12.9.2.2.1
-- 1.3.6.1.4.1.37950.1.1.5.12.9.2.2.1
		-- 1.3.6.1.4.1.37950.1.1.5.12.9.2.2.1
		onuFastleavePFEntry OBJECT-TYPE
			SYNTAX OnuFastleavePFEntry
			MAX-ACCESS not-accessible
			STATUS current
			DESCRIPTION
				"Description."
			INDEX { onuFastleaveSrvId }
			::= { onuFastleavePFTable 1 }

		
		OnuFastleavePFEntry ::=
			SEQUENCE { 
				onuFastleaveSrvId
					Integer32,
				onuFastleaveEnableS
					INTEGER
			 }

--          1.3.6.1.4.1.37950.1.1.5.12.9.2.2.1.1
-- 1.3.6.1.4.1.37950.1.1.5.12.9.2.2.1.1
-- 1.3.6.1.4.1.37950.1.1.5.12.9.2.2.1.1
-- 1.3.6.1.4.1.37950.1.1.5.12.9.2.2.1.1
-- 1.3.6.1.4.1.37950.1.1.5.12.9.2.2.1.1
-- 1.3.6.1.4.1.37950.1.1.5.12.9.2.2.1.1
-- 1.3.6.1.4.1.37950.1.1.5.12.9.2.2.1.1
-- 1.3.6.1.4.1.37950.1.1.5.12.9.2.2.1.1
-- 1.3.6.1.4.1.37950.1.1.5.12.9.2.2.1.1
		-- 1.3.6.1.4.1.37950.1.1.5.12.9.2.2.1.1
		onuFastleaveSrvId OBJECT-TYPE
			SYNTAX Integer32 (0..65535)
			MAX-ACCESS read-only
			STATUS current
			DESCRIPTION
				"Description."
			::= { onuFastleavePFEntry 1 }

		
--          1.3.6.1.4.1.37950.1.1.5.12.9.2.2.1.2
-- 1.3.6.1.4.1.37950.1.1.5.12.9.2.2.1.2
-- 1.3.6.1.4.1.37950.1.1.5.12.9.2.2.1.2
-- 1.3.6.1.4.1.37950.1.1.5.12.9.2.2.1.2
-- 1.3.6.1.4.1.37950.1.1.5.12.9.2.2.1.2
-- 1.3.6.1.4.1.37950.1.1.5.12.9.2.2.1.2
-- 1.3.6.1.4.1.37950.1.1.5.12.9.2.2.1.2
-- 1.3.6.1.4.1.37950.1.1.5.12.9.2.2.1.2
-- 1.3.6.1.4.1.37950.1.1.5.12.9.2.2.1.2
		-- 1.3.6.1.4.1.37950.1.1.5.12.9.2.2.1.2
		onuFastleaveEnableS OBJECT-TYPE
			SYNTAX INTEGER
				{
				disable(0),
				enable(1)
				}
			MAX-ACCESS read-only
			STATUS current
			DESCRIPTION
				"Description."
			::= { onuFastleavePFEntry 2 }

		
--          1.3.6.1.4.1.37950.1.1.5.12.9.2.3
-- 1.3.6.1.4.1.37950.1.1.5.12.9.2.3
-- 1.3.6.1.4.1.37950.1.1.5.12.9.2.3
-- 1.3.6.1.4.1.37950.1.1.5.12.9.2.3
-- 1.3.6.1.4.1.37950.1.1.5.12.9.2.3
-- 1.3.6.1.4.1.37950.1.1.5.12.9.2.3
-- 1.3.6.1.4.1.37950.1.1.5.12.9.2.3
-- 1.3.6.1.4.1.37950.1.1.5.12.9.2.3
-- 1.3.6.1.4.1.37950.1.1.5.12.9.2.3
		-- 1.3.6.1.4.1.37950.1.1.5.12.9.2.3
		onuFecModePFTable OBJECT-TYPE
			SYNTAX SEQUENCE OF OnuFecModePFEntry
			MAX-ACCESS not-accessible
			STATUS current
			DESCRIPTION
				"Description."
			::= { srvProfileShow 3 }

		
--          1.3.6.1.4.1.37950.1.1.5.12.9.2.3.1
-- 1.3.6.1.4.1.37950.1.1.5.12.9.2.3.1
-- 1.3.6.1.4.1.37950.1.1.5.12.9.2.3.1
-- 1.3.6.1.4.1.37950.1.1.5.12.9.2.3.1
-- 1.3.6.1.4.1.37950.1.1.5.12.9.2.3.1
-- 1.3.6.1.4.1.37950.1.1.5.12.9.2.3.1
-- 1.3.6.1.4.1.37950.1.1.5.12.9.2.3.1
-- 1.3.6.1.4.1.37950.1.1.5.12.9.2.3.1
-- 1.3.6.1.4.1.37950.1.1.5.12.9.2.3.1
		-- 1.3.6.1.4.1.37950.1.1.5.12.9.2.3.1
		onuFecModePFEntry OBJECT-TYPE
			SYNTAX OnuFecModePFEntry
			MAX-ACCESS not-accessible
			STATUS current
			DESCRIPTION
				"Description."
			INDEX { onuFecModeSrvId }
			::= { onuFecModePFTable 1 }

		
		OnuFecModePFEntry ::=
			SEQUENCE { 
				onuFecModeSrvId
					Integer32,
				onuFecModeEnableS
					INTEGER
			 }

--          1.3.6.1.4.1.37950.1.1.5.12.9.2.3.1.1
-- 1.3.6.1.4.1.37950.1.1.5.12.9.2.3.1.1
-- 1.3.6.1.4.1.37950.1.1.5.12.9.2.3.1.1
-- 1.3.6.1.4.1.37950.1.1.5.12.9.2.3.1.1
-- 1.3.6.1.4.1.37950.1.1.5.12.9.2.3.1.1
-- 1.3.6.1.4.1.37950.1.1.5.12.9.2.3.1.1
-- 1.3.6.1.4.1.37950.1.1.5.12.9.2.3.1.1
-- 1.3.6.1.4.1.37950.1.1.5.12.9.2.3.1.1
-- 1.3.6.1.4.1.37950.1.1.5.12.9.2.3.1.1
		-- 1.3.6.1.4.1.37950.1.1.5.12.9.2.3.1.1
		onuFecModeSrvId OBJECT-TYPE
			SYNTAX Integer32 (0..65535)
			MAX-ACCESS read-only
			STATUS current
			DESCRIPTION
				"Description."
			::= { onuFecModePFEntry 1 }

		
--          1.3.6.1.4.1.37950.1.1.5.12.9.2.3.1.2
-- 1.3.6.1.4.1.37950.1.1.5.12.9.2.3.1.2
-- 1.3.6.1.4.1.37950.1.1.5.12.9.2.3.1.2
-- 1.3.6.1.4.1.37950.1.1.5.12.9.2.3.1.2
-- 1.3.6.1.4.1.37950.1.1.5.12.9.2.3.1.2
-- 1.3.6.1.4.1.37950.1.1.5.12.9.2.3.1.2
-- 1.3.6.1.4.1.37950.1.1.5.12.9.2.3.1.2
-- 1.3.6.1.4.1.37950.1.1.5.12.9.2.3.1.2
-- 1.3.6.1.4.1.37950.1.1.5.12.9.2.3.1.2
		-- 1.3.6.1.4.1.37950.1.1.5.12.9.2.3.1.2
		onuFecModeEnableS OBJECT-TYPE
			SYNTAX INTEGER
				{
				disable(0),
				enable(1)
				}
			MAX-ACCESS read-only
			STATUS current
			DESCRIPTION
				"Description."
			::= { onuFecModePFEntry 2 }

		
--          1.3.6.1.4.1.37950.1.1.5.12.9.2.4
-- 1.3.6.1.4.1.37950.1.1.5.12.9.2.4
-- 1.3.6.1.4.1.37950.1.1.5.12.9.2.4
-- 1.3.6.1.4.1.37950.1.1.5.12.9.2.4
-- 1.3.6.1.4.1.37950.1.1.5.12.9.2.4
-- 1.3.6.1.4.1.37950.1.1.5.12.9.2.4
-- 1.3.6.1.4.1.37950.1.1.5.12.9.2.4
-- 1.3.6.1.4.1.37950.1.1.5.12.9.2.4
-- 1.3.6.1.4.1.37950.1.1.5.12.9.2.4
		-- 1.3.6.1.4.1.37950.1.1.5.12.9.2.4
		ctcMcModePFTable OBJECT-TYPE
			SYNTAX SEQUENCE OF CtcMcModePFEntry
			MAX-ACCESS not-accessible
			STATUS current
			DESCRIPTION
				"Description."
			::= { srvProfileShow 4 }

		
--          1.3.6.1.4.1.37950.1.1.5.12.9.2.4.1
-- 1.3.6.1.4.1.37950.1.1.5.12.9.2.4.1
-- 1.3.6.1.4.1.37950.1.1.5.12.9.2.4.1
-- 1.3.6.1.4.1.37950.1.1.5.12.9.2.4.1
-- 1.3.6.1.4.1.37950.1.1.5.12.9.2.4.1
-- 1.3.6.1.4.1.37950.1.1.5.12.9.2.4.1
-- 1.3.6.1.4.1.37950.1.1.5.12.9.2.4.1
-- 1.3.6.1.4.1.37950.1.1.5.12.9.2.4.1
-- 1.3.6.1.4.1.37950.1.1.5.12.9.2.4.1
		-- 1.3.6.1.4.1.37950.1.1.5.12.9.2.4.1
		ctcMcModePFEntry OBJECT-TYPE
			SYNTAX CtcMcModePFEntry
			MAX-ACCESS not-accessible
			STATUS current
			DESCRIPTION
				"Description."
			INDEX { ctcMcModeSrvId }
			::= { ctcMcModePFTable 1 }

		
		CtcMcModePFEntry ::=
			SEQUENCE { 
				ctcMcModeSrvId
					Integer32,
				ctcMcModeS
					INTEGER
			 }

--          1.3.6.1.4.1.37950.1.1.5.12.9.2.4.1.1
-- 1.3.6.1.4.1.37950.1.1.5.12.9.2.4.1.1
-- 1.3.6.1.4.1.37950.1.1.5.12.9.2.4.1.1
-- 1.3.6.1.4.1.37950.1.1.5.12.9.2.4.1.1
-- 1.3.6.1.4.1.37950.1.1.5.12.9.2.4.1.1
-- 1.3.6.1.4.1.37950.1.1.5.12.9.2.4.1.1
-- 1.3.6.1.4.1.37950.1.1.5.12.9.2.4.1.1
-- 1.3.6.1.4.1.37950.1.1.5.12.9.2.4.1.1
-- 1.3.6.1.4.1.37950.1.1.5.12.9.2.4.1.1
		-- 1.3.6.1.4.1.37950.1.1.5.12.9.2.4.1.1
		ctcMcModeSrvId OBJECT-TYPE
			SYNTAX Integer32 (0..65535)
			MAX-ACCESS read-only
			STATUS current
			DESCRIPTION
				"Description."
			::= { ctcMcModePFEntry 1 }

		
--          1.3.6.1.4.1.37950.1.1.5.12.9.2.4.1.2
-- 1.3.6.1.4.1.37950.1.1.5.12.9.2.4.1.2
-- 1.3.6.1.4.1.37950.1.1.5.12.9.2.4.1.2
-- 1.3.6.1.4.1.37950.1.1.5.12.9.2.4.1.2
-- 1.3.6.1.4.1.37950.1.1.5.12.9.2.4.1.2
-- 1.3.6.1.4.1.37950.1.1.5.12.9.2.4.1.2
-- 1.3.6.1.4.1.37950.1.1.5.12.9.2.4.1.2
-- 1.3.6.1.4.1.37950.1.1.5.12.9.2.4.1.2
-- 1.3.6.1.4.1.37950.1.1.5.12.9.2.4.1.2
		-- 1.3.6.1.4.1.37950.1.1.5.12.9.2.4.1.2
		ctcMcModeS OBJECT-TYPE
			SYNTAX INTEGER
				{
				snooping(1),
				control(2)
				}
			MAX-ACCESS read-only
			STATUS current
			DESCRIPTION
				"Description."
			::= { ctcMcModePFEntry 2 }

		
--          1.3.6.1.4.1.37950.1.1.5.12.9.2.5
-- 1.3.6.1.4.1.37950.1.1.5.12.9.2.5
-- 1.3.6.1.4.1.37950.1.1.5.12.9.2.5
-- 1.3.6.1.4.1.37950.1.1.5.12.9.2.5
-- 1.3.6.1.4.1.37950.1.1.5.12.9.2.5
-- 1.3.6.1.4.1.37950.1.1.5.12.9.2.5
-- 1.3.6.1.4.1.37950.1.1.5.12.9.2.5
-- 1.3.6.1.4.1.37950.1.1.5.12.9.2.5
-- 1.3.6.1.4.1.37950.1.1.5.12.9.2.5
		-- 1.3.6.1.4.1.37950.1.1.5.12.9.2.5
		ctcMultiLlidPFTable OBJECT-TYPE
			SYNTAX SEQUENCE OF CtcMultiLlidPFEntry
			MAX-ACCESS not-accessible
			STATUS current
			DESCRIPTION
				"Description."
			::= { srvProfileShow 5 }

		
--          1.3.6.1.4.1.37950.1.1.5.12.9.2.5.1
-- 1.3.6.1.4.1.37950.1.1.5.12.9.2.5.1
-- 1.3.6.1.4.1.37950.1.1.5.12.9.2.5.1
-- 1.3.6.1.4.1.37950.1.1.5.12.9.2.5.1
-- 1.3.6.1.4.1.37950.1.1.5.12.9.2.5.1
-- 1.3.6.1.4.1.37950.1.1.5.12.9.2.5.1
-- 1.3.6.1.4.1.37950.1.1.5.12.9.2.5.1
-- 1.3.6.1.4.1.37950.1.1.5.12.9.2.5.1
-- 1.3.6.1.4.1.37950.1.1.5.12.9.2.5.1
		-- 1.3.6.1.4.1.37950.1.1.5.12.9.2.5.1
		ctcMultiLlidPFEntry OBJECT-TYPE
			SYNTAX CtcMultiLlidPFEntry
			MAX-ACCESS not-accessible
			STATUS current
			DESCRIPTION
				"Description."
			INDEX { ctcMultiLlidSrvId }
			::= { ctcMultiLlidPFTable 1 }

		
		CtcMultiLlidPFEntry ::=
			SEQUENCE { 
				ctcMultiLlidSrvId
					Integer32,
				ctcMultiLlidS
					INTEGER
			 }

--          1.3.6.1.4.1.37950.1.1.5.12.9.2.5.1.1
-- 1.3.6.1.4.1.37950.1.1.5.12.9.2.5.1.1
-- 1.3.6.1.4.1.37950.1.1.5.12.9.2.5.1.1
-- 1.3.6.1.4.1.37950.1.1.5.12.9.2.5.1.1
-- 1.3.6.1.4.1.37950.1.1.5.12.9.2.5.1.1
-- 1.3.6.1.4.1.37950.1.1.5.12.9.2.5.1.1
-- 1.3.6.1.4.1.37950.1.1.5.12.9.2.5.1.1
-- 1.3.6.1.4.1.37950.1.1.5.12.9.2.5.1.1
-- 1.3.6.1.4.1.37950.1.1.5.12.9.2.5.1.1
		-- 1.3.6.1.4.1.37950.1.1.5.12.9.2.5.1.1
		ctcMultiLlidSrvId OBJECT-TYPE
			SYNTAX Integer32 (0..65535)
			MAX-ACCESS read-only
			STATUS current
			DESCRIPTION
				"Description."
			::= { ctcMultiLlidPFEntry 1 }

		
--          1.3.6.1.4.1.37950.1.1.5.12.9.2.5.1.2
-- 1.3.6.1.4.1.37950.1.1.5.12.9.2.5.1.2
-- 1.3.6.1.4.1.37950.1.1.5.12.9.2.5.1.2
-- 1.3.6.1.4.1.37950.1.1.5.12.9.2.5.1.2
-- 1.3.6.1.4.1.37950.1.1.5.12.9.2.5.1.2
-- 1.3.6.1.4.1.37950.1.1.5.12.9.2.5.1.2
-- 1.3.6.1.4.1.37950.1.1.5.12.9.2.5.1.2
-- 1.3.6.1.4.1.37950.1.1.5.12.9.2.5.1.2
-- 1.3.6.1.4.1.37950.1.1.5.12.9.2.5.1.2
		-- 1.3.6.1.4.1.37950.1.1.5.12.9.2.5.1.2
		ctcMultiLlidS OBJECT-TYPE
			SYNTAX INTEGER (0..8)
			MAX-ACCESS read-only
			STATUS current
			DESCRIPTION
				"Description."
			::= { ctcMultiLlidPFEntry 2 }

		
--          1.3.6.1.4.1.37950.1.1.5.12.9.2.6
-- 1.3.6.1.4.1.37950.1.1.5.12.9.2.6
-- 1.3.6.1.4.1.37950.1.1.5.12.9.2.6
-- 1.3.6.1.4.1.37950.1.1.5.12.9.2.6
-- 1.3.6.1.4.1.37950.1.1.5.12.9.2.6
-- 1.3.6.1.4.1.37950.1.1.5.12.9.2.6
-- 1.3.6.1.4.1.37950.1.1.5.12.9.2.6
-- 1.3.6.1.4.1.37950.1.1.5.12.9.2.6
-- 1.3.6.1.4.1.37950.1.1.5.12.9.2.6
		-- 1.3.6.1.4.1.37950.1.1.5.12.9.2.6
		ctcActivePonPFTable OBJECT-TYPE
			SYNTAX SEQUENCE OF CtcActivePonPFEntry
			MAX-ACCESS not-accessible
			STATUS current
			DESCRIPTION
				"Description."
			::= { srvProfileShow 6 }

		
--          1.3.6.1.4.1.37950.1.1.5.12.9.2.6.1
-- 1.3.6.1.4.1.37950.1.1.5.12.9.2.6.1
-- 1.3.6.1.4.1.37950.1.1.5.12.9.2.6.1
-- 1.3.6.1.4.1.37950.1.1.5.12.9.2.6.1
-- 1.3.6.1.4.1.37950.1.1.5.12.9.2.6.1
-- 1.3.6.1.4.1.37950.1.1.5.12.9.2.6.1
-- 1.3.6.1.4.1.37950.1.1.5.12.9.2.6.1
-- 1.3.6.1.4.1.37950.1.1.5.12.9.2.6.1
-- 1.3.6.1.4.1.37950.1.1.5.12.9.2.6.1
		-- 1.3.6.1.4.1.37950.1.1.5.12.9.2.6.1
		ctcActivePonPFEntry OBJECT-TYPE
			SYNTAX CtcActivePonPFEntry
			MAX-ACCESS not-accessible
			STATUS current
			DESCRIPTION
				"Description."
			INDEX { ctcActivePonSrvId }
			::= { ctcActivePonPFTable 1 }

		
		CtcActivePonPFEntry ::=
			SEQUENCE { 
				ctcActivePonSrvId
					Integer32,
				ctcActivePonS
					INTEGER
			 }

--          1.3.6.1.4.1.37950.1.1.5.12.9.2.6.1.1
-- 1.3.6.1.4.1.37950.1.1.5.12.9.2.6.1.1
-- 1.3.6.1.4.1.37950.1.1.5.12.9.2.6.1.1
-- 1.3.6.1.4.1.37950.1.1.5.12.9.2.6.1.1
-- 1.3.6.1.4.1.37950.1.1.5.12.9.2.6.1.1
-- 1.3.6.1.4.1.37950.1.1.5.12.9.2.6.1.1
-- 1.3.6.1.4.1.37950.1.1.5.12.9.2.6.1.1
-- 1.3.6.1.4.1.37950.1.1.5.12.9.2.6.1.1
-- 1.3.6.1.4.1.37950.1.1.5.12.9.2.6.1.1
		-- 1.3.6.1.4.1.37950.1.1.5.12.9.2.6.1.1
		ctcActivePonSrvId OBJECT-TYPE
			SYNTAX Integer32 (0..65535)
			MAX-ACCESS read-only
			STATUS current
			DESCRIPTION
				"Description."
			::= { ctcActivePonPFEntry 1 }

		
--          1.3.6.1.4.1.37950.1.1.5.12.9.2.6.1.2
-- 1.3.6.1.4.1.37950.1.1.5.12.9.2.6.1.2
-- 1.3.6.1.4.1.37950.1.1.5.12.9.2.6.1.2
-- 1.3.6.1.4.1.37950.1.1.5.12.9.2.6.1.2
-- 1.3.6.1.4.1.37950.1.1.5.12.9.2.6.1.2
-- 1.3.6.1.4.1.37950.1.1.5.12.9.2.6.1.2
-- 1.3.6.1.4.1.37950.1.1.5.12.9.2.6.1.2
-- 1.3.6.1.4.1.37950.1.1.5.12.9.2.6.1.2
-- 1.3.6.1.4.1.37950.1.1.5.12.9.2.6.1.2
		-- 1.3.6.1.4.1.37950.1.1.5.12.9.2.6.1.2
		ctcActivePonS OBJECT-TYPE
			SYNTAX INTEGER (0..8)
			MAX-ACCESS read-only
			STATUS current
			DESCRIPTION
				"Description."
			::= { ctcActivePonPFEntry 2 }

		
--          1.3.6.1.4.1.37950.1.1.5.12.9.2.7
-- 1.3.6.1.4.1.37950.1.1.5.12.9.2.7
-- 1.3.6.1.4.1.37950.1.1.5.12.9.2.7
-- 1.3.6.1.4.1.37950.1.1.5.12.9.2.7
-- 1.3.6.1.4.1.37950.1.1.5.12.9.2.7
-- 1.3.6.1.4.1.37950.1.1.5.12.9.2.7
-- 1.3.6.1.4.1.37950.1.1.5.12.9.2.7
-- 1.3.6.1.4.1.37950.1.1.5.12.9.2.7
-- 1.3.6.1.4.1.37950.1.1.5.12.9.2.7
		-- 1.3.6.1.4.1.37950.1.1.5.12.9.2.7
		ctcHoldoverPFTable OBJECT-TYPE
			SYNTAX SEQUENCE OF CtcHoldoverPFEntry
			MAX-ACCESS not-accessible
			STATUS current
			DESCRIPTION
				"Description."
			::= { srvProfileShow 7 }

		
--          1.3.6.1.4.1.37950.1.1.5.12.9.2.7.1
-- 1.3.6.1.4.1.37950.1.1.5.12.9.2.7.1
-- 1.3.6.1.4.1.37950.1.1.5.12.9.2.7.1
-- 1.3.6.1.4.1.37950.1.1.5.12.9.2.7.1
-- 1.3.6.1.4.1.37950.1.1.5.12.9.2.7.1
-- 1.3.6.1.4.1.37950.1.1.5.12.9.2.7.1
-- 1.3.6.1.4.1.37950.1.1.5.12.9.2.7.1
-- 1.3.6.1.4.1.37950.1.1.5.12.9.2.7.1
-- 1.3.6.1.4.1.37950.1.1.5.12.9.2.7.1
		-- 1.3.6.1.4.1.37950.1.1.5.12.9.2.7.1
		ctcHoldoverPFEntry OBJECT-TYPE
			SYNTAX CtcHoldoverPFEntry
			MAX-ACCESS not-accessible
			STATUS current
			DESCRIPTION
				"Description."
			INDEX { ctcHoldoverSrvId }
			::= { ctcHoldoverPFTable 1 }

		
		CtcHoldoverPFEntry ::=
			SEQUENCE { 
				ctcHoldoverSrvId
					Integer32,
				ctcHoldoverS
					Integer32
			 }

--          1.3.6.1.4.1.37950.1.1.5.12.9.2.7.1.1
-- 1.3.6.1.4.1.37950.1.1.5.12.9.2.7.1.1
-- 1.3.6.1.4.1.37950.1.1.5.12.9.2.7.1.1
-- 1.3.6.1.4.1.37950.1.1.5.12.9.2.7.1.1
-- 1.3.6.1.4.1.37950.1.1.5.12.9.2.7.1.1
-- 1.3.6.1.4.1.37950.1.1.5.12.9.2.7.1.1
-- 1.3.6.1.4.1.37950.1.1.5.12.9.2.7.1.1
-- 1.3.6.1.4.1.37950.1.1.5.12.9.2.7.1.1
-- 1.3.6.1.4.1.37950.1.1.5.12.9.2.7.1.1
		-- 1.3.6.1.4.1.37950.1.1.5.12.9.2.7.1.1
		ctcHoldoverSrvId OBJECT-TYPE
			SYNTAX Integer32 (0..65535)
			MAX-ACCESS read-only
			STATUS current
			DESCRIPTION
				"Description."
			::= { ctcHoldoverPFEntry 1 }

		
--          1.3.6.1.4.1.37950.1.1.5.12.9.2.7.1.2
-- 1.3.6.1.4.1.37950.1.1.5.12.9.2.7.1.2
-- 1.3.6.1.4.1.37950.1.1.5.12.9.2.7.1.2
-- 1.3.6.1.4.1.37950.1.1.5.12.9.2.7.1.2
-- 1.3.6.1.4.1.37950.1.1.5.12.9.2.7.1.2
-- 1.3.6.1.4.1.37950.1.1.5.12.9.2.7.1.2
-- 1.3.6.1.4.1.37950.1.1.5.12.9.2.7.1.2
-- 1.3.6.1.4.1.37950.1.1.5.12.9.2.7.1.2
-- 1.3.6.1.4.1.37950.1.1.5.12.9.2.7.1.2
		-- 1.3.6.1.4.1.37950.1.1.5.12.9.2.7.1.2
		ctcHoldoverS OBJECT-TYPE
			SYNTAX Integer32 (0..65535)
			MAX-ACCESS read-only
			STATUS current
			DESCRIPTION
				"Description."
			::= { ctcHoldoverPFEntry 2 }

		
--          1.3.6.1.4.1.37950.1.1.5.12.9.2.8
-- 1.3.6.1.4.1.37950.1.1.5.12.9.2.8
-- 1.3.6.1.4.1.37950.1.1.5.12.9.2.8
-- 1.3.6.1.4.1.37950.1.1.5.12.9.2.8
-- 1.3.6.1.4.1.37950.1.1.5.12.9.2.8
-- 1.3.6.1.4.1.37950.1.1.5.12.9.2.8
-- 1.3.6.1.4.1.37950.1.1.5.12.9.2.8
-- 1.3.6.1.4.1.37950.1.1.5.12.9.2.8
-- 1.3.6.1.4.1.37950.1.1.5.12.9.2.8
		-- 1.3.6.1.4.1.37950.1.1.5.12.9.2.8
		onuMgmtIpPFTable OBJECT-TYPE
			SYNTAX SEQUENCE OF OnuMgmtIpPFEntry
			MAX-ACCESS not-accessible
			STATUS current
			DESCRIPTION
				"Description."
			::= { srvProfileShow 8 }

		
--          1.3.6.1.4.1.37950.1.1.5.12.9.2.8.1
-- 1.3.6.1.4.1.37950.1.1.5.12.9.2.8.1
-- 1.3.6.1.4.1.37950.1.1.5.12.9.2.8.1
-- 1.3.6.1.4.1.37950.1.1.5.12.9.2.8.1
-- 1.3.6.1.4.1.37950.1.1.5.12.9.2.8.1
-- 1.3.6.1.4.1.37950.1.1.5.12.9.2.8.1
-- 1.3.6.1.4.1.37950.1.1.5.12.9.2.8.1
-- 1.3.6.1.4.1.37950.1.1.5.12.9.2.8.1
-- 1.3.6.1.4.1.37950.1.1.5.12.9.2.8.1
		-- 1.3.6.1.4.1.37950.1.1.5.12.9.2.8.1
		onuMgmtIpPFEntry OBJECT-TYPE
			SYNTAX OnuMgmtIpPFEntry
			MAX-ACCESS not-accessible
			STATUS current
			DESCRIPTION
				"Description."
			INDEX { onuMgmtIpSrvId }
			::= { onuMgmtIpPFTable 1 }

		
		OnuMgmtIpPFEntry ::=
			SEQUENCE { 
				onuMgmtIpSrvId
					Integer32,
				onuMgmtIpAddrS
					IpAddress,
				onuMgmtIpMaskS
					IpAddress,
				onuMgmtIpGwS
					IpAddress,
				onuMgmtIpCvlanS
					INTEGER,
				onuMgmtIpSvlanS
					INTEGER,
				onuMgmtIpPriS
					INTEGER
			 }

--          1.3.6.1.4.1.37950.1.1.5.12.9.2.8.1.1
-- 1.3.6.1.4.1.37950.1.1.5.12.9.2.8.1.1
-- 1.3.6.1.4.1.37950.1.1.5.12.9.2.8.1.1
-- 1.3.6.1.4.1.37950.1.1.5.12.9.2.8.1.1
-- 1.3.6.1.4.1.37950.1.1.5.12.9.2.8.1.1
-- 1.3.6.1.4.1.37950.1.1.5.12.9.2.8.1.1
-- 1.3.6.1.4.1.37950.1.1.5.12.9.2.8.1.1
-- 1.3.6.1.4.1.37950.1.1.5.12.9.2.8.1.1
-- 1.3.6.1.4.1.37950.1.1.5.12.9.2.8.1.1
		-- 1.3.6.1.4.1.37950.1.1.5.12.9.2.8.1.1
		onuMgmtIpSrvId OBJECT-TYPE
			SYNTAX Integer32 (0..65535)
			MAX-ACCESS read-only
			STATUS current
			DESCRIPTION
				"Description."
			::= { onuMgmtIpPFEntry 1 }

		
--          1.3.6.1.4.1.37950.1.1.5.12.9.2.8.1.2
-- 1.3.6.1.4.1.37950.1.1.5.12.9.2.8.1.2
-- 1.3.6.1.4.1.37950.1.1.5.12.9.2.8.1.2
-- 1.3.6.1.4.1.37950.1.1.5.12.9.2.8.1.2
-- 1.3.6.1.4.1.37950.1.1.5.12.9.2.8.1.2
-- 1.3.6.1.4.1.37950.1.1.5.12.9.2.8.1.2
-- 1.3.6.1.4.1.37950.1.1.5.12.9.2.8.1.2
-- 1.3.6.1.4.1.37950.1.1.5.12.9.2.8.1.2
-- 1.3.6.1.4.1.37950.1.1.5.12.9.2.8.1.2
		-- 1.3.6.1.4.1.37950.1.1.5.12.9.2.8.1.2
		onuMgmtIpAddrS OBJECT-TYPE
			SYNTAX IpAddress
			MAX-ACCESS read-only
			STATUS current
			DESCRIPTION
				"Description."
			::= { onuMgmtIpPFEntry 2 }

		
--          1.3.6.1.4.1.37950.1.1.5.12.9.2.8.1.3
-- 1.3.6.1.4.1.37950.1.1.5.12.9.2.8.1.3
-- 1.3.6.1.4.1.37950.1.1.5.12.9.2.8.1.3
-- 1.3.6.1.4.1.37950.1.1.5.12.9.2.8.1.3
-- 1.3.6.1.4.1.37950.1.1.5.12.9.2.8.1.3
-- 1.3.6.1.4.1.37950.1.1.5.12.9.2.8.1.3
-- 1.3.6.1.4.1.37950.1.1.5.12.9.2.8.1.3
-- 1.3.6.1.4.1.37950.1.1.5.12.9.2.8.1.3
-- 1.3.6.1.4.1.37950.1.1.5.12.9.2.8.1.3
		-- 1.3.6.1.4.1.37950.1.1.5.12.9.2.8.1.3
		onuMgmtIpMaskS OBJECT-TYPE
			SYNTAX IpAddress
			MAX-ACCESS read-only
			STATUS current
			DESCRIPTION
				"Description."
			::= { onuMgmtIpPFEntry 3 }

		
--          1.3.6.1.4.1.37950.1.1.5.12.9.2.8.1.4
-- 1.3.6.1.4.1.37950.1.1.5.12.9.2.8.1.4
-- 1.3.6.1.4.1.37950.1.1.5.12.9.2.8.1.4
-- 1.3.6.1.4.1.37950.1.1.5.12.9.2.8.1.4
-- 1.3.6.1.4.1.37950.1.1.5.12.9.2.8.1.4
-- 1.3.6.1.4.1.37950.1.1.5.12.9.2.8.1.4
-- 1.3.6.1.4.1.37950.1.1.5.12.9.2.8.1.4
-- 1.3.6.1.4.1.37950.1.1.5.12.9.2.8.1.4
-- 1.3.6.1.4.1.37950.1.1.5.12.9.2.8.1.4
		-- 1.3.6.1.4.1.37950.1.1.5.12.9.2.8.1.4
		onuMgmtIpGwS OBJECT-TYPE
			SYNTAX IpAddress
			MAX-ACCESS read-only
			STATUS current
			DESCRIPTION
				"Description."
			::= { onuMgmtIpPFEntry 4 }

		
--          1.3.6.1.4.1.37950.1.1.5.12.9.2.8.1.5
-- 1.3.6.1.4.1.37950.1.1.5.12.9.2.8.1.5
-- 1.3.6.1.4.1.37950.1.1.5.12.9.2.8.1.5
-- 1.3.6.1.4.1.37950.1.1.5.12.9.2.8.1.5
-- 1.3.6.1.4.1.37950.1.1.5.12.9.2.8.1.5
-- 1.3.6.1.4.1.37950.1.1.5.12.9.2.8.1.5
-- 1.3.6.1.4.1.37950.1.1.5.12.9.2.8.1.5
-- 1.3.6.1.4.1.37950.1.1.5.12.9.2.8.1.5
-- 1.3.6.1.4.1.37950.1.1.5.12.9.2.8.1.5
		-- 1.3.6.1.4.1.37950.1.1.5.12.9.2.8.1.5
		onuMgmtIpCvlanS OBJECT-TYPE
			SYNTAX INTEGER (0..4095)
			MAX-ACCESS read-only
			STATUS current
			DESCRIPTION
				"Description."
			::= { onuMgmtIpPFEntry 5 }

		
--          1.3.6.1.4.1.37950.1.1.5.12.9.2.8.1.6
-- 1.3.6.1.4.1.37950.1.1.5.12.9.2.8.1.6
-- 1.3.6.1.4.1.37950.1.1.5.12.9.2.8.1.6
-- 1.3.6.1.4.1.37950.1.1.5.12.9.2.8.1.6
-- 1.3.6.1.4.1.37950.1.1.5.12.9.2.8.1.6
-- 1.3.6.1.4.1.37950.1.1.5.12.9.2.8.1.6
-- 1.3.6.1.4.1.37950.1.1.5.12.9.2.8.1.6
-- 1.3.6.1.4.1.37950.1.1.5.12.9.2.8.1.6
-- 1.3.6.1.4.1.37950.1.1.5.12.9.2.8.1.6
		-- 1.3.6.1.4.1.37950.1.1.5.12.9.2.8.1.6
		onuMgmtIpSvlanS OBJECT-TYPE
			SYNTAX INTEGER (0..4095)
			MAX-ACCESS read-only
			STATUS current
			DESCRIPTION
				"Description."
			::= { onuMgmtIpPFEntry 6 }

		
--          1.3.6.1.4.1.37950.1.1.5.12.9.2.8.1.7
-- 1.3.6.1.4.1.37950.1.1.5.12.9.2.8.1.7
-- 1.3.6.1.4.1.37950.1.1.5.12.9.2.8.1.7
-- 1.3.6.1.4.1.37950.1.1.5.12.9.2.8.1.7
-- 1.3.6.1.4.1.37950.1.1.5.12.9.2.8.1.7
-- 1.3.6.1.4.1.37950.1.1.5.12.9.2.8.1.7
-- 1.3.6.1.4.1.37950.1.1.5.12.9.2.8.1.7
-- 1.3.6.1.4.1.37950.1.1.5.12.9.2.8.1.7
-- 1.3.6.1.4.1.37950.1.1.5.12.9.2.8.1.7
		-- 1.3.6.1.4.1.37950.1.1.5.12.9.2.8.1.7
		onuMgmtIpPriS OBJECT-TYPE
			SYNTAX INTEGER (-1..7)
			MAX-ACCESS read-only
			STATUS current
			DESCRIPTION
				"Description."
			::= { onuMgmtIpPFEntry 7 }

		
--          1.3.6.1.4.1.37950.1.1.5.12.9.2.9
-- 1.3.6.1.4.1.37950.1.1.5.12.9.2.9
-- 1.3.6.1.4.1.37950.1.1.5.12.9.2.9
-- 1.3.6.1.4.1.37950.1.1.5.12.9.2.9
-- 1.3.6.1.4.1.37950.1.1.5.12.9.2.9
-- 1.3.6.1.4.1.37950.1.1.5.12.9.2.9
-- 1.3.6.1.4.1.37950.1.1.5.12.9.2.9
-- 1.3.6.1.4.1.37950.1.1.5.12.9.2.9
-- 1.3.6.1.4.1.37950.1.1.5.12.9.2.9
		-- 1.3.6.1.4.1.37950.1.1.5.12.9.2.9
		onuSnmpProPFTable OBJECT-TYPE
			SYNTAX SEQUENCE OF OnuSnmpProPFEntry
			MAX-ACCESS not-accessible
			STATUS current
			DESCRIPTION
				"Description."
			::= { srvProfileShow 9 }

		
--          1.3.6.1.4.1.37950.1.1.5.12.9.2.9.1
-- 1.3.6.1.4.1.37950.1.1.5.12.9.2.9.1
-- 1.3.6.1.4.1.37950.1.1.5.12.9.2.9.1
-- 1.3.6.1.4.1.37950.1.1.5.12.9.2.9.1
-- 1.3.6.1.4.1.37950.1.1.5.12.9.2.9.1
-- 1.3.6.1.4.1.37950.1.1.5.12.9.2.9.1
-- 1.3.6.1.4.1.37950.1.1.5.12.9.2.9.1
-- 1.3.6.1.4.1.37950.1.1.5.12.9.2.9.1
-- 1.3.6.1.4.1.37950.1.1.5.12.9.2.9.1
		-- 1.3.6.1.4.1.37950.1.1.5.12.9.2.9.1
		onuSnmpProPFEntry OBJECT-TYPE
			SYNTAX OnuSnmpProPFEntry
			MAX-ACCESS not-accessible
			STATUS current
			DESCRIPTION
				"Description."
			INDEX { onuSnmpProSrvId }
			::= { onuSnmpProPFTable 1 }

		
		OnuSnmpProPFEntry ::=
			SEQUENCE { 
				onuSnmpProSrvId
					Integer32,
				onuSnmpProHostS
					IpAddress,
				onuSnmpProTrapPortS
					INTEGER,
				onuSnmpProPortS
					INTEGER,
				onuSnmpProNameS
					OCTET STRING,
				onuSnmpProComRdS
					OCTET STRING,
				onuSnmpProComWrS
					OCTET STRING
			 }

--          1.3.6.1.4.1.37950.1.1.5.12.9.2.9.1.1
-- 1.3.6.1.4.1.37950.1.1.5.12.9.2.9.1.1
-- 1.3.6.1.4.1.37950.1.1.5.12.9.2.9.1.1
-- 1.3.6.1.4.1.37950.1.1.5.12.9.2.9.1.1
-- 1.3.6.1.4.1.37950.1.1.5.12.9.2.9.1.1
-- 1.3.6.1.4.1.37950.1.1.5.12.9.2.9.1.1
-- 1.3.6.1.4.1.37950.1.1.5.12.9.2.9.1.1
-- 1.3.6.1.4.1.37950.1.1.5.12.9.2.9.1.1
-- 1.3.6.1.4.1.37950.1.1.5.12.9.2.9.1.1
		-- 1.3.6.1.4.1.37950.1.1.5.12.9.2.9.1.1
		onuSnmpProSrvId OBJECT-TYPE
			SYNTAX Integer32 (0..65535)
			MAX-ACCESS read-only
			STATUS current
			DESCRIPTION
				"Description."
			::= { onuSnmpProPFEntry 1 }

		
--          1.3.6.1.4.1.37950.1.1.5.12.9.2.9.1.2
-- 1.3.6.1.4.1.37950.1.1.5.12.9.2.9.1.2
-- 1.3.6.1.4.1.37950.1.1.5.12.9.2.9.1.2
-- 1.3.6.1.4.1.37950.1.1.5.12.9.2.9.1.2
-- 1.3.6.1.4.1.37950.1.1.5.12.9.2.9.1.2
-- 1.3.6.1.4.1.37950.1.1.5.12.9.2.9.1.2
-- 1.3.6.1.4.1.37950.1.1.5.12.9.2.9.1.2
-- 1.3.6.1.4.1.37950.1.1.5.12.9.2.9.1.2
-- 1.3.6.1.4.1.37950.1.1.5.12.9.2.9.1.2
		-- 1.3.6.1.4.1.37950.1.1.5.12.9.2.9.1.2
		onuSnmpProHostS OBJECT-TYPE
			SYNTAX IpAddress
			MAX-ACCESS read-only
			STATUS current
			DESCRIPTION
				"Description."
			::= { onuSnmpProPFEntry 2 }

		
--          1.3.6.1.4.1.37950.1.1.5.12.9.2.9.1.3
-- 1.3.6.1.4.1.37950.1.1.5.12.9.2.9.1.3
-- 1.3.6.1.4.1.37950.1.1.5.12.9.2.9.1.3
-- 1.3.6.1.4.1.37950.1.1.5.12.9.2.9.1.3
-- 1.3.6.1.4.1.37950.1.1.5.12.9.2.9.1.3
-- 1.3.6.1.4.1.37950.1.1.5.12.9.2.9.1.3
-- 1.3.6.1.4.1.37950.1.1.5.12.9.2.9.1.3
-- 1.3.6.1.4.1.37950.1.1.5.12.9.2.9.1.3
-- 1.3.6.1.4.1.37950.1.1.5.12.9.2.9.1.3
		-- 1.3.6.1.4.1.37950.1.1.5.12.9.2.9.1.3
		onuSnmpProTrapPortS OBJECT-TYPE
			SYNTAX INTEGER (0..65535)
			MAX-ACCESS read-only
			STATUS current
			DESCRIPTION
				"Description."
			::= { onuSnmpProPFEntry 3 }

		
--          1.3.6.1.4.1.37950.1.1.5.12.9.2.9.1.4
-- 1.3.6.1.4.1.37950.1.1.5.12.9.2.9.1.4
-- 1.3.6.1.4.1.37950.1.1.5.12.9.2.9.1.4
-- 1.3.6.1.4.1.37950.1.1.5.12.9.2.9.1.4
-- 1.3.6.1.4.1.37950.1.1.5.12.9.2.9.1.4
-- 1.3.6.1.4.1.37950.1.1.5.12.9.2.9.1.4
-- 1.3.6.1.4.1.37950.1.1.5.12.9.2.9.1.4
-- 1.3.6.1.4.1.37950.1.1.5.12.9.2.9.1.4
-- 1.3.6.1.4.1.37950.1.1.5.12.9.2.9.1.4
		-- 1.3.6.1.4.1.37950.1.1.5.12.9.2.9.1.4
		onuSnmpProPortS OBJECT-TYPE
			SYNTAX INTEGER (1..65535)
			MAX-ACCESS read-only
			STATUS current
			DESCRIPTION
				"Description."
			::= { onuSnmpProPFEntry 4 }

		
--          1.3.6.1.4.1.37950.1.1.5.12.9.2.9.1.5
-- 1.3.6.1.4.1.37950.1.1.5.12.9.2.9.1.5
-- 1.3.6.1.4.1.37950.1.1.5.12.9.2.9.1.5
-- 1.3.6.1.4.1.37950.1.1.5.12.9.2.9.1.5
-- 1.3.6.1.4.1.37950.1.1.5.12.9.2.9.1.5
-- 1.3.6.1.4.1.37950.1.1.5.12.9.2.9.1.5
-- 1.3.6.1.4.1.37950.1.1.5.12.9.2.9.1.5
-- 1.3.6.1.4.1.37950.1.1.5.12.9.2.9.1.5
-- 1.3.6.1.4.1.37950.1.1.5.12.9.2.9.1.5
		-- 1.3.6.1.4.1.37950.1.1.5.12.9.2.9.1.5
		onuSnmpProNameS OBJECT-TYPE
			SYNTAX OCTET STRING
			MAX-ACCESS read-only
			STATUS current
			DESCRIPTION
				"Description."
			::= { onuSnmpProPFEntry 5 }

		
--          1.3.6.1.4.1.37950.1.1.5.12.9.2.9.1.6
-- 1.3.6.1.4.1.37950.1.1.5.12.9.2.9.1.6
-- 1.3.6.1.4.1.37950.1.1.5.12.9.2.9.1.6
-- 1.3.6.1.4.1.37950.1.1.5.12.9.2.9.1.6
-- 1.3.6.1.4.1.37950.1.1.5.12.9.2.9.1.6
-- 1.3.6.1.4.1.37950.1.1.5.12.9.2.9.1.6
-- 1.3.6.1.4.1.37950.1.1.5.12.9.2.9.1.6
-- 1.3.6.1.4.1.37950.1.1.5.12.9.2.9.1.6
-- 1.3.6.1.4.1.37950.1.1.5.12.9.2.9.1.6
		-- 1.3.6.1.4.1.37950.1.1.5.12.9.2.9.1.6
		onuSnmpProComRdS OBJECT-TYPE
			SYNTAX OCTET STRING
			MAX-ACCESS read-only
			STATUS current
			DESCRIPTION
				"Description."
			::= { onuSnmpProPFEntry 6 }

		
--          1.3.6.1.4.1.37950.1.1.5.12.9.2.9.1.7
-- 1.3.6.1.4.1.37950.1.1.5.12.9.2.9.1.7
-- 1.3.6.1.4.1.37950.1.1.5.12.9.2.9.1.7
-- 1.3.6.1.4.1.37950.1.1.5.12.9.2.9.1.7
-- 1.3.6.1.4.1.37950.1.1.5.12.9.2.9.1.7
-- 1.3.6.1.4.1.37950.1.1.5.12.9.2.9.1.7
-- 1.3.6.1.4.1.37950.1.1.5.12.9.2.9.1.7
-- 1.3.6.1.4.1.37950.1.1.5.12.9.2.9.1.7
-- 1.3.6.1.4.1.37950.1.1.5.12.9.2.9.1.7
		-- 1.3.6.1.4.1.37950.1.1.5.12.9.2.9.1.7
		onuSnmpProComWrS OBJECT-TYPE
			SYNTAX OCTET STRING
			MAX-ACCESS read-only
			STATUS current
			DESCRIPTION
				"Description."
			::= { onuSnmpProPFEntry 7 }

		
--          1.3.6.1.4.1.37950.1.1.5.12.9.2.10
-- 1.3.6.1.4.1.37950.1.1.5.12.9.2.10
-- 1.3.6.1.4.1.37950.1.1.5.12.9.2.10
-- 1.3.6.1.4.1.37950.1.1.5.12.9.2.10
-- 1.3.6.1.4.1.37950.1.1.5.12.9.2.10
-- 1.3.6.1.4.1.37950.1.1.5.12.9.2.10
-- 1.3.6.1.4.1.37950.1.1.5.12.9.2.10
-- 1.3.6.1.4.1.37950.1.1.5.12.9.2.10
-- 1.3.6.1.4.1.37950.1.1.5.12.9.2.10
		-- 1.3.6.1.4.1.37950.1.1.5.12.9.2.10
		onuSlaPFTable OBJECT-TYPE
			SYNTAX SEQUENCE OF OnuSlaPFEntry
			MAX-ACCESS not-accessible
			STATUS current
			DESCRIPTION
				"Description."
			::= { srvProfileShow 10 }

		
--          1.3.6.1.4.1.37950.1.1.5.12.9.2.10.1
-- 1.3.6.1.4.1.37950.1.1.5.12.9.2.10.1
-- 1.3.6.1.4.1.37950.1.1.5.12.9.2.10.1
-- 1.3.6.1.4.1.37950.1.1.5.12.9.2.10.1
-- 1.3.6.1.4.1.37950.1.1.5.12.9.2.10.1
-- 1.3.6.1.4.1.37950.1.1.5.12.9.2.10.1
-- 1.3.6.1.4.1.37950.1.1.5.12.9.2.10.1
-- 1.3.6.1.4.1.37950.1.1.5.12.9.2.10.1
-- 1.3.6.1.4.1.37950.1.1.5.12.9.2.10.1
		-- 1.3.6.1.4.1.37950.1.1.5.12.9.2.10.1
		onuSlaPFEntry OBJECT-TYPE
			SYNTAX OnuSlaPFEntry
			MAX-ACCESS not-accessible
			STATUS current
			DESCRIPTION
				"Description."
			INDEX { onuSlaSrvId }
			::= { onuSlaPFTable 1 }

		
		OnuSlaPFEntry ::=
			SEQUENCE { 
				onuSlaSrvId
					Integer32,
				onuSlaEnableS
					INTEGER
			 }

--          1.3.6.1.4.1.37950.1.1.5.12.9.2.10.1.1
-- 1.3.6.1.4.1.37950.1.1.5.12.9.2.10.1.1
-- 1.3.6.1.4.1.37950.1.1.5.12.9.2.10.1.1
-- 1.3.6.1.4.1.37950.1.1.5.12.9.2.10.1.1
-- 1.3.6.1.4.1.37950.1.1.5.12.9.2.10.1.1
-- 1.3.6.1.4.1.37950.1.1.5.12.9.2.10.1.1
-- 1.3.6.1.4.1.37950.1.1.5.12.9.2.10.1.1
-- 1.3.6.1.4.1.37950.1.1.5.12.9.2.10.1.1
-- 1.3.6.1.4.1.37950.1.1.5.12.9.2.10.1.1
		-- 1.3.6.1.4.1.37950.1.1.5.12.9.2.10.1.1
		onuSlaSrvId OBJECT-TYPE
			SYNTAX Integer32 (0..65535)
			MAX-ACCESS read-only
			STATUS current
			DESCRIPTION
				"Description."
			::= { onuSlaPFEntry 1 }

		
--          1.3.6.1.4.1.37950.1.1.5.12.9.2.10.1.2
-- 1.3.6.1.4.1.37950.1.1.5.12.9.2.10.1.2
-- 1.3.6.1.4.1.37950.1.1.5.12.9.2.10.1.2
-- 1.3.6.1.4.1.37950.1.1.5.12.9.2.10.1.2
-- 1.3.6.1.4.1.37950.1.1.5.12.9.2.10.1.2
-- 1.3.6.1.4.1.37950.1.1.5.12.9.2.10.1.2
-- 1.3.6.1.4.1.37950.1.1.5.12.9.2.10.1.2
-- 1.3.6.1.4.1.37950.1.1.5.12.9.2.10.1.2
-- 1.3.6.1.4.1.37950.1.1.5.12.9.2.10.1.2
		-- 1.3.6.1.4.1.37950.1.1.5.12.9.2.10.1.2
		onuSlaEnableS OBJECT-TYPE
			SYNTAX INTEGER
				{
				disable(0),
				enable(1)
				}
			MAX-ACCESS read-only
			STATUS current
			DESCRIPTION
				"Description."
			::= { onuSlaPFEntry 2 }

		
--          1.3.6.1.4.1.37950.1.1.5.12.9.2.11
-- 1.3.6.1.4.1.37950.1.1.5.12.9.2.11
-- 1.3.6.1.4.1.37950.1.1.5.12.9.2.11
-- 1.3.6.1.4.1.37950.1.1.5.12.9.2.11
-- 1.3.6.1.4.1.37950.1.1.5.12.9.2.11
-- 1.3.6.1.4.1.37950.1.1.5.12.9.2.11
-- 1.3.6.1.4.1.37950.1.1.5.12.9.2.11
-- 1.3.6.1.4.1.37950.1.1.5.12.9.2.11
-- 1.3.6.1.4.1.37950.1.1.5.12.9.2.11
		-- 1.3.6.1.4.1.37950.1.1.5.12.9.2.11
		onuCtcPausePFTable OBJECT-TYPE
			SYNTAX SEQUENCE OF OnuCtcPausePFEntry
			MAX-ACCESS not-accessible
			STATUS current
			DESCRIPTION
				"Description."
			::= { srvProfileShow 11 }

		
--          1.3.6.1.4.1.37950.1.1.5.12.9.2.11.1
-- 1.3.6.1.4.1.37950.1.1.5.12.9.2.11.1
-- 1.3.6.1.4.1.37950.1.1.5.12.9.2.11.1
-- 1.3.6.1.4.1.37950.1.1.5.12.9.2.11.1
-- 1.3.6.1.4.1.37950.1.1.5.12.9.2.11.1
-- 1.3.6.1.4.1.37950.1.1.5.12.9.2.11.1
-- 1.3.6.1.4.1.37950.1.1.5.12.9.2.11.1
-- 1.3.6.1.4.1.37950.1.1.5.12.9.2.11.1
-- 1.3.6.1.4.1.37950.1.1.5.12.9.2.11.1
		-- 1.3.6.1.4.1.37950.1.1.5.12.9.2.11.1
		onuCtcPausePFEntry OBJECT-TYPE
			SYNTAX OnuCtcPausePFEntry
			MAX-ACCESS not-accessible
			STATUS current
			DESCRIPTION
				"Description."
			INDEX { onuCtcPauseSrvId, pausePortIndexS }
			::= { onuCtcPausePFTable 1 }

		
		OnuCtcPausePFEntry ::=
			SEQUENCE { 
				onuCtcPauseSrvId
					Integer32,
				pausePortIndexS
					INTEGER,
				onuCtcPauseEnS
					INTEGER
			 }

--          1.3.6.1.4.1.37950.1.1.5.12.9.2.11.1.1
-- 1.3.6.1.4.1.37950.1.1.5.12.9.2.11.1.1
-- 1.3.6.1.4.1.37950.1.1.5.12.9.2.11.1.1
-- 1.3.6.1.4.1.37950.1.1.5.12.9.2.11.1.1
-- 1.3.6.1.4.1.37950.1.1.5.12.9.2.11.1.1
-- 1.3.6.1.4.1.37950.1.1.5.12.9.2.11.1.1
-- 1.3.6.1.4.1.37950.1.1.5.12.9.2.11.1.1
-- 1.3.6.1.4.1.37950.1.1.5.12.9.2.11.1.1
-- 1.3.6.1.4.1.37950.1.1.5.12.9.2.11.1.1
		-- 1.3.6.1.4.1.37950.1.1.5.12.9.2.11.1.1
		onuCtcPauseSrvId OBJECT-TYPE
			SYNTAX Integer32 (0..65536)
			MAX-ACCESS read-only
			STATUS current
			DESCRIPTION
				"Description."
			::= { onuCtcPausePFEntry 1 }

		
--          1.3.6.1.4.1.37950.1.1.5.12.9.2.11.1.2
-- 1.3.6.1.4.1.37950.1.1.5.12.9.2.11.1.2
-- 1.3.6.1.4.1.37950.1.1.5.12.9.2.11.1.2
-- 1.3.6.1.4.1.37950.1.1.5.12.9.2.11.1.2
-- 1.3.6.1.4.1.37950.1.1.5.12.9.2.11.1.2
-- 1.3.6.1.4.1.37950.1.1.5.12.9.2.11.1.2
-- 1.3.6.1.4.1.37950.1.1.5.12.9.2.11.1.2
-- 1.3.6.1.4.1.37950.1.1.5.12.9.2.11.1.2
-- 1.3.6.1.4.1.37950.1.1.5.12.9.2.11.1.2
		-- 1.3.6.1.4.1.37950.1.1.5.12.9.2.11.1.2
		pausePortIndexS OBJECT-TYPE
			SYNTAX INTEGER (1..255)
			MAX-ACCESS read-only
			STATUS current
			DESCRIPTION
				"Description."
			::= { onuCtcPausePFEntry 2 }

		
--          1.3.6.1.4.1.37950.1.1.5.12.9.2.11.1.3
-- 1.3.6.1.4.1.37950.1.1.5.12.9.2.11.1.3
-- 1.3.6.1.4.1.37950.1.1.5.12.9.2.11.1.3
-- 1.3.6.1.4.1.37950.1.1.5.12.9.2.11.1.3
-- 1.3.6.1.4.1.37950.1.1.5.12.9.2.11.1.3
-- 1.3.6.1.4.1.37950.1.1.5.12.9.2.11.1.3
-- 1.3.6.1.4.1.37950.1.1.5.12.9.2.11.1.3
-- 1.3.6.1.4.1.37950.1.1.5.12.9.2.11.1.3
-- 1.3.6.1.4.1.37950.1.1.5.12.9.2.11.1.3
		-- 1.3.6.1.4.1.37950.1.1.5.12.9.2.11.1.3
		onuCtcPauseEnS OBJECT-TYPE
			SYNTAX INTEGER
				{
				disable(0),
				enable(1)
				}
			MAX-ACCESS read-only
			STATUS current
			DESCRIPTION
				"Description."
			::= { onuCtcPausePFEntry 3 }

		
--          1.3.6.1.4.1.37950.1.1.5.12.9.2.12
-- 1.3.6.1.4.1.37950.1.1.5.12.9.2.12
-- 1.3.6.1.4.1.37950.1.1.5.12.9.2.12
-- 1.3.6.1.4.1.37950.1.1.5.12.9.2.12
-- 1.3.6.1.4.1.37950.1.1.5.12.9.2.12
-- 1.3.6.1.4.1.37950.1.1.5.12.9.2.12
-- 1.3.6.1.4.1.37950.1.1.5.12.9.2.12
-- 1.3.6.1.4.1.37950.1.1.5.12.9.2.12
-- 1.3.6.1.4.1.37950.1.1.5.12.9.2.12
		-- 1.3.6.1.4.1.37950.1.1.5.12.9.2.12
		onuCtcLoopdetectPFTable OBJECT-TYPE
			SYNTAX SEQUENCE OF OnuCtcLoopdetectPFEntry
			MAX-ACCESS not-accessible
			STATUS current
			DESCRIPTION
				"Description."
			::= { srvProfileShow 12 }

		
--          1.3.6.1.4.1.37950.1.1.5.12.9.2.12.1
-- 1.3.6.1.4.1.37950.1.1.5.12.9.2.12.1
-- 1.3.6.1.4.1.37950.1.1.5.12.9.2.12.1
-- 1.3.6.1.4.1.37950.1.1.5.12.9.2.12.1
-- 1.3.6.1.4.1.37950.1.1.5.12.9.2.12.1
-- 1.3.6.1.4.1.37950.1.1.5.12.9.2.12.1
-- 1.3.6.1.4.1.37950.1.1.5.12.9.2.12.1
-- 1.3.6.1.4.1.37950.1.1.5.12.9.2.12.1
-- 1.3.6.1.4.1.37950.1.1.5.12.9.2.12.1
		-- 1.3.6.1.4.1.37950.1.1.5.12.9.2.12.1
		onuCtcLoopdetectPFEntry OBJECT-TYPE
			SYNTAX OnuCtcLoopdetectPFEntry
			MAX-ACCESS not-accessible
			STATUS current
			DESCRIPTION
				"Description."
			INDEX { onuCtcLoopdetectSrvId, loopdetectPortIndexS }
			::= { onuCtcLoopdetectPFTable 1 }

		
		OnuCtcLoopdetectPFEntry ::=
			SEQUENCE { 
				onuCtcLoopdetectSrvId
					Integer32,
				loopdetectPortIndexS
					INTEGER,
				onuCtcLoopdetectEnS
					INTEGER
			 }

--          1.3.6.1.4.1.37950.1.1.5.12.9.2.12.1.1
-- 1.3.6.1.4.1.37950.1.1.5.12.9.2.12.1.1
-- 1.3.6.1.4.1.37950.1.1.5.12.9.2.12.1.1
-- 1.3.6.1.4.1.37950.1.1.5.12.9.2.12.1.1
-- 1.3.6.1.4.1.37950.1.1.5.12.9.2.12.1.1
-- 1.3.6.1.4.1.37950.1.1.5.12.9.2.12.1.1
-- 1.3.6.1.4.1.37950.1.1.5.12.9.2.12.1.1
-- 1.3.6.1.4.1.37950.1.1.5.12.9.2.12.1.1
-- 1.3.6.1.4.1.37950.1.1.5.12.9.2.12.1.1
		-- 1.3.6.1.4.1.37950.1.1.5.12.9.2.12.1.1
		onuCtcLoopdetectSrvId OBJECT-TYPE
			SYNTAX Integer32 (0..65535)
			MAX-ACCESS read-only
			STATUS current
			DESCRIPTION
				"Description."
			::= { onuCtcLoopdetectPFEntry 1 }

		
--          1.3.6.1.4.1.37950.1.1.5.12.9.2.12.1.2
-- 1.3.6.1.4.1.37950.1.1.5.12.9.2.12.1.2
-- 1.3.6.1.4.1.37950.1.1.5.12.9.2.12.1.2
-- 1.3.6.1.4.1.37950.1.1.5.12.9.2.12.1.2
-- 1.3.6.1.4.1.37950.1.1.5.12.9.2.12.1.2
-- 1.3.6.1.4.1.37950.1.1.5.12.9.2.12.1.2
-- 1.3.6.1.4.1.37950.1.1.5.12.9.2.12.1.2
-- 1.3.6.1.4.1.37950.1.1.5.12.9.2.12.1.2
-- 1.3.6.1.4.1.37950.1.1.5.12.9.2.12.1.2
		-- 1.3.6.1.4.1.37950.1.1.5.12.9.2.12.1.2
		loopdetectPortIndexS OBJECT-TYPE
			SYNTAX INTEGER (1..255)
			MAX-ACCESS read-only
			STATUS current
			DESCRIPTION
				"Description."
			::= { onuCtcLoopdetectPFEntry 2 }

		
--          1.3.6.1.4.1.37950.1.1.5.12.9.2.12.1.3
-- 1.3.6.1.4.1.37950.1.1.5.12.9.2.12.1.3
-- 1.3.6.1.4.1.37950.1.1.5.12.9.2.12.1.3
-- 1.3.6.1.4.1.37950.1.1.5.12.9.2.12.1.3
-- 1.3.6.1.4.1.37950.1.1.5.12.9.2.12.1.3
-- 1.3.6.1.4.1.37950.1.1.5.12.9.2.12.1.3
-- 1.3.6.1.4.1.37950.1.1.5.12.9.2.12.1.3
-- 1.3.6.1.4.1.37950.1.1.5.12.9.2.12.1.3
-- 1.3.6.1.4.1.37950.1.1.5.12.9.2.12.1.3
		-- 1.3.6.1.4.1.37950.1.1.5.12.9.2.12.1.3
		onuCtcLoopdetectEnS OBJECT-TYPE
			SYNTAX INTEGER
				{
				disable(0),
				enable(1)
				}
			MAX-ACCESS read-only
			STATUS current
			DESCRIPTION
				"Description."
			::= { onuCtcLoopdetectPFEntry 3 }

		
--          1.3.6.1.4.1.37950.1.1.5.12.9.2.13
-- 1.3.6.1.4.1.37950.1.1.5.12.9.2.13
-- 1.3.6.1.4.1.37950.1.1.5.12.9.2.13
-- 1.3.6.1.4.1.37950.1.1.5.12.9.2.13
-- 1.3.6.1.4.1.37950.1.1.5.12.9.2.13
-- 1.3.6.1.4.1.37950.1.1.5.12.9.2.13
-- 1.3.6.1.4.1.37950.1.1.5.12.9.2.13
-- 1.3.6.1.4.1.37950.1.1.5.12.9.2.13
-- 1.3.6.1.4.1.37950.1.1.5.12.9.2.13
		-- 1.3.6.1.4.1.37950.1.1.5.12.9.2.13
		onuMcTagstripPFTable OBJECT-TYPE
			SYNTAX SEQUENCE OF OnuMcTagstripPFEntry
			MAX-ACCESS not-accessible
			STATUS current
			DESCRIPTION
				"Description."
			::= { srvProfileShow 13 }

		
--          1.3.6.1.4.1.37950.1.1.5.12.9.2.13.1
-- 1.3.6.1.4.1.37950.1.1.5.12.9.2.13.1
-- 1.3.6.1.4.1.37950.1.1.5.12.9.2.13.1
-- 1.3.6.1.4.1.37950.1.1.5.12.9.2.13.1
-- 1.3.6.1.4.1.37950.1.1.5.12.9.2.13.1
-- 1.3.6.1.4.1.37950.1.1.5.12.9.2.13.1
-- 1.3.6.1.4.1.37950.1.1.5.12.9.2.13.1
-- 1.3.6.1.4.1.37950.1.1.5.12.9.2.13.1
-- 1.3.6.1.4.1.37950.1.1.5.12.9.2.13.1
		-- 1.3.6.1.4.1.37950.1.1.5.12.9.2.13.1
		onuMcTagstripPFEntry OBJECT-TYPE
			SYNTAX OnuMcTagstripPFEntry
			MAX-ACCESS not-accessible
			STATUS current
			DESCRIPTION
				"Description."
			INDEX { onuMcTagstripSrvId, tagstripPortIndexS }
			::= { onuMcTagstripPFTable 1 }

		
		OnuMcTagstripPFEntry ::=
			SEQUENCE { 
				onuMcTagstripSrvId
					Integer32,
				tagstripPortIndexS
					INTEGER,
				onuMcTagstripEnS
					INTEGER
			 }

--          1.3.6.1.4.1.37950.1.1.5.12.9.2.13.1.1
-- 1.3.6.1.4.1.37950.1.1.5.12.9.2.13.1.1
-- 1.3.6.1.4.1.37950.1.1.5.12.9.2.13.1.1
-- 1.3.6.1.4.1.37950.1.1.5.12.9.2.13.1.1
-- 1.3.6.1.4.1.37950.1.1.5.12.9.2.13.1.1
-- 1.3.6.1.4.1.37950.1.1.5.12.9.2.13.1.1
-- 1.3.6.1.4.1.37950.1.1.5.12.9.2.13.1.1
-- 1.3.6.1.4.1.37950.1.1.5.12.9.2.13.1.1
-- 1.3.6.1.4.1.37950.1.1.5.12.9.2.13.1.1
		-- 1.3.6.1.4.1.37950.1.1.5.12.9.2.13.1.1
		onuMcTagstripSrvId OBJECT-TYPE
			SYNTAX Integer32 (0..65535)
			MAX-ACCESS read-only
			STATUS current
			DESCRIPTION
				"Description."
			::= { onuMcTagstripPFEntry 1 }

		
--          1.3.6.1.4.1.37950.1.1.5.12.9.2.13.1.2
-- 1.3.6.1.4.1.37950.1.1.5.12.9.2.13.1.2
-- 1.3.6.1.4.1.37950.1.1.5.12.9.2.13.1.2
-- 1.3.6.1.4.1.37950.1.1.5.12.9.2.13.1.2
-- 1.3.6.1.4.1.37950.1.1.5.12.9.2.13.1.2
-- 1.3.6.1.4.1.37950.1.1.5.12.9.2.13.1.2
-- 1.3.6.1.4.1.37950.1.1.5.12.9.2.13.1.2
-- 1.3.6.1.4.1.37950.1.1.5.12.9.2.13.1.2
-- 1.3.6.1.4.1.37950.1.1.5.12.9.2.13.1.2
		-- 1.3.6.1.4.1.37950.1.1.5.12.9.2.13.1.2
		tagstripPortIndexS OBJECT-TYPE
			SYNTAX INTEGER (1..255)
			MAX-ACCESS read-only
			STATUS current
			DESCRIPTION
				"Description."
			::= { onuMcTagstripPFEntry 2 }

		
--          1.3.6.1.4.1.37950.1.1.5.12.9.2.13.1.3
-- 1.3.6.1.4.1.37950.1.1.5.12.9.2.13.1.3
-- 1.3.6.1.4.1.37950.1.1.5.12.9.2.13.1.3
-- 1.3.6.1.4.1.37950.1.1.5.12.9.2.13.1.3
-- 1.3.6.1.4.1.37950.1.1.5.12.9.2.13.1.3
-- 1.3.6.1.4.1.37950.1.1.5.12.9.2.13.1.3
-- 1.3.6.1.4.1.37950.1.1.5.12.9.2.13.1.3
-- 1.3.6.1.4.1.37950.1.1.5.12.9.2.13.1.3
-- 1.3.6.1.4.1.37950.1.1.5.12.9.2.13.1.3
		-- 1.3.6.1.4.1.37950.1.1.5.12.9.2.13.1.3
		onuMcTagstripEnS OBJECT-TYPE
			SYNTAX INTEGER
				{
				disable(0),
				enable(1)
				}
			MAX-ACCESS read-only
			STATUS current
			DESCRIPTION
				"Description."
			::= { onuMcTagstripPFEntry 3 }

		
--          1.3.6.1.4.1.37950.1.1.5.12.9.2.14
-- 1.3.6.1.4.1.37950.1.1.5.12.9.2.14
-- 1.3.6.1.4.1.37950.1.1.5.12.9.2.14
-- 1.3.6.1.4.1.37950.1.1.5.12.9.2.14
-- 1.3.6.1.4.1.37950.1.1.5.12.9.2.14
-- 1.3.6.1.4.1.37950.1.1.5.12.9.2.14
-- 1.3.6.1.4.1.37950.1.1.5.12.9.2.14
-- 1.3.6.1.4.1.37950.1.1.5.12.9.2.14
-- 1.3.6.1.4.1.37950.1.1.5.12.9.2.14
		-- 1.3.6.1.4.1.37950.1.1.5.12.9.2.14
		onuMcVlanTransPFTable OBJECT-TYPE
			SYNTAX SEQUENCE OF OnuMcVlanTransPFEntry
			MAX-ACCESS not-accessible
			STATUS current
			DESCRIPTION
				"Description."
			::= { srvProfileShow 14 }

		
--          1.3.6.1.4.1.37950.1.1.5.12.9.2.14.1
-- 1.3.6.1.4.1.37950.1.1.5.12.9.2.14.1
-- 1.3.6.1.4.1.37950.1.1.5.12.9.2.14.1
-- 1.3.6.1.4.1.37950.1.1.5.12.9.2.14.1
-- 1.3.6.1.4.1.37950.1.1.5.12.9.2.14.1
-- 1.3.6.1.4.1.37950.1.1.5.12.9.2.14.1
-- 1.3.6.1.4.1.37950.1.1.5.12.9.2.14.1
-- 1.3.6.1.4.1.37950.1.1.5.12.9.2.14.1
-- 1.3.6.1.4.1.37950.1.1.5.12.9.2.14.1
		-- 1.3.6.1.4.1.37950.1.1.5.12.9.2.14.1
		onuMcVlanTransPFEntry OBJECT-TYPE
			SYNTAX OnuMcVlanTransPFEntry
			MAX-ACCESS not-accessible
			STATUS current
			DESCRIPTION
				"Description."
			INDEX { onuMcVlanTransnSrvId, mcVlanTransPortIndexS }
			::= { onuMcVlanTransPFTable 1 }

		
		OnuMcVlanTransPFEntry ::=
			SEQUENCE { 
				onuMcVlanTransnSrvId
					Integer32,
				mcVlanTransPortIndexS
					INTEGER,
				onuMcVlanTransVlanStrS
					OCTET STRING
			 }

--          1.3.6.1.4.1.37950.1.1.5.12.9.2.14.1.1
-- 1.3.6.1.4.1.37950.1.1.5.12.9.2.14.1.1
-- 1.3.6.1.4.1.37950.1.1.5.12.9.2.14.1.1
-- 1.3.6.1.4.1.37950.1.1.5.12.9.2.14.1.1
-- 1.3.6.1.4.1.37950.1.1.5.12.9.2.14.1.1
-- 1.3.6.1.4.1.37950.1.1.5.12.9.2.14.1.1
-- 1.3.6.1.4.1.37950.1.1.5.12.9.2.14.1.1
-- 1.3.6.1.4.1.37950.1.1.5.12.9.2.14.1.1
-- 1.3.6.1.4.1.37950.1.1.5.12.9.2.14.1.1
		-- 1.3.6.1.4.1.37950.1.1.5.12.9.2.14.1.1
		onuMcVlanTransnSrvId OBJECT-TYPE
			SYNTAX Integer32 (0..65535)
			MAX-ACCESS read-only
			STATUS current
			DESCRIPTION
				"Description."
			::= { onuMcVlanTransPFEntry 1 }

		
--          1.3.6.1.4.1.37950.1.1.5.12.9.2.14.1.2
-- 1.3.6.1.4.1.37950.1.1.5.12.9.2.14.1.2
-- 1.3.6.1.4.1.37950.1.1.5.12.9.2.14.1.2
-- 1.3.6.1.4.1.37950.1.1.5.12.9.2.14.1.2
-- 1.3.6.1.4.1.37950.1.1.5.12.9.2.14.1.2
-- 1.3.6.1.4.1.37950.1.1.5.12.9.2.14.1.2
-- 1.3.6.1.4.1.37950.1.1.5.12.9.2.14.1.2
-- 1.3.6.1.4.1.37950.1.1.5.12.9.2.14.1.2
-- 1.3.6.1.4.1.37950.1.1.5.12.9.2.14.1.2
		-- 1.3.6.1.4.1.37950.1.1.5.12.9.2.14.1.2
		mcVlanTransPortIndexS OBJECT-TYPE
			SYNTAX INTEGER (1..255)
			MAX-ACCESS read-only
			STATUS current
			DESCRIPTION
				"Description."
			::= { onuMcVlanTransPFEntry 2 }

		
--          1.3.6.1.4.1.37950.1.1.5.12.9.2.14.1.3
-- 1.3.6.1.4.1.37950.1.1.5.12.9.2.14.1.3
-- 1.3.6.1.4.1.37950.1.1.5.12.9.2.14.1.3
-- 1.3.6.1.4.1.37950.1.1.5.12.9.2.14.1.3
-- 1.3.6.1.4.1.37950.1.1.5.12.9.2.14.1.3
-- 1.3.6.1.4.1.37950.1.1.5.12.9.2.14.1.3
-- 1.3.6.1.4.1.37950.1.1.5.12.9.2.14.1.3
-- 1.3.6.1.4.1.37950.1.1.5.12.9.2.14.1.3
-- 1.3.6.1.4.1.37950.1.1.5.12.9.2.14.1.3
		-- 1.3.6.1.4.1.37950.1.1.5.12.9.2.14.1.3
		onuMcVlanTransVlanStrS OBJECT-TYPE
			SYNTAX OCTET STRING
			MAX-ACCESS read-only
			STATUS current
			DESCRIPTION
				"Description."
			::= { onuMcVlanTransPFEntry 3 }

		
--          1.3.6.1.4.1.37950.1.1.5.12.9.2.15
-- 1.3.6.1.4.1.37950.1.1.5.12.9.2.15
-- 1.3.6.1.4.1.37950.1.1.5.12.9.2.15
-- 1.3.6.1.4.1.37950.1.1.5.12.9.2.15
-- 1.3.6.1.4.1.37950.1.1.5.12.9.2.15
-- 1.3.6.1.4.1.37950.1.1.5.12.9.2.15
-- 1.3.6.1.4.1.37950.1.1.5.12.9.2.15
-- 1.3.6.1.4.1.37950.1.1.5.12.9.2.15
-- 1.3.6.1.4.1.37950.1.1.5.12.9.2.15
		-- 1.3.6.1.4.1.37950.1.1.5.12.9.2.15
		onuPortPhyAdminPFTable OBJECT-TYPE
			SYNTAX SEQUENCE OF OnuPortPhyAdminPFEntry
			MAX-ACCESS not-accessible
			STATUS current
			DESCRIPTION
				"Description."
			::= { srvProfileShow 15 }

		
--          1.3.6.1.4.1.37950.1.1.5.12.9.2.15.1
-- 1.3.6.1.4.1.37950.1.1.5.12.9.2.15.1
-- 1.3.6.1.4.1.37950.1.1.5.12.9.2.15.1
-- 1.3.6.1.4.1.37950.1.1.5.12.9.2.15.1
-- 1.3.6.1.4.1.37950.1.1.5.12.9.2.15.1
-- 1.3.6.1.4.1.37950.1.1.5.12.9.2.15.1
-- 1.3.6.1.4.1.37950.1.1.5.12.9.2.15.1
-- 1.3.6.1.4.1.37950.1.1.5.12.9.2.15.1
-- 1.3.6.1.4.1.37950.1.1.5.12.9.2.15.1
		-- 1.3.6.1.4.1.37950.1.1.5.12.9.2.15.1
		onuPortPhyAdminPFEntry OBJECT-TYPE
			SYNTAX OnuPortPhyAdminPFEntry
			MAX-ACCESS not-accessible
			STATUS current
			DESCRIPTION
				"Description."
			INDEX { onuPortPhyAdminSrvId, adminPortIndexS }
			::= { onuPortPhyAdminPFTable 1 }

		
		OnuPortPhyAdminPFEntry ::=
			SEQUENCE { 
				onuPortPhyAdminSrvId
					Integer32,
				adminPortIndexS
					INTEGER,
				onuPortPhyAdminEnS
					INTEGER
			 }

--          1.3.6.1.4.1.37950.1.1.5.12.9.2.15.1.1
-- 1.3.6.1.4.1.37950.1.1.5.12.9.2.15.1.1
-- 1.3.6.1.4.1.37950.1.1.5.12.9.2.15.1.1
-- 1.3.6.1.4.1.37950.1.1.5.12.9.2.15.1.1
-- 1.3.6.1.4.1.37950.1.1.5.12.9.2.15.1.1
-- 1.3.6.1.4.1.37950.1.1.5.12.9.2.15.1.1
-- 1.3.6.1.4.1.37950.1.1.5.12.9.2.15.1.1
-- 1.3.6.1.4.1.37950.1.1.5.12.9.2.15.1.1
-- 1.3.6.1.4.1.37950.1.1.5.12.9.2.15.1.1
		-- 1.3.6.1.4.1.37950.1.1.5.12.9.2.15.1.1
		onuPortPhyAdminSrvId OBJECT-TYPE
			SYNTAX Integer32 (0..65535)
			MAX-ACCESS read-only
			STATUS current
			DESCRIPTION
				"Description."
			::= { onuPortPhyAdminPFEntry 1 }

		
--          1.3.6.1.4.1.37950.1.1.5.12.9.2.15.1.2
-- 1.3.6.1.4.1.37950.1.1.5.12.9.2.15.1.2
-- 1.3.6.1.4.1.37950.1.1.5.12.9.2.15.1.2
-- 1.3.6.1.4.1.37950.1.1.5.12.9.2.15.1.2
-- 1.3.6.1.4.1.37950.1.1.5.12.9.2.15.1.2
-- 1.3.6.1.4.1.37950.1.1.5.12.9.2.15.1.2
-- 1.3.6.1.4.1.37950.1.1.5.12.9.2.15.1.2
-- 1.3.6.1.4.1.37950.1.1.5.12.9.2.15.1.2
-- 1.3.6.1.4.1.37950.1.1.5.12.9.2.15.1.2
		-- 1.3.6.1.4.1.37950.1.1.5.12.9.2.15.1.2
		adminPortIndexS OBJECT-TYPE
			SYNTAX INTEGER (1..255)
			MAX-ACCESS read-only
			STATUS current
			DESCRIPTION
				"Description."
			::= { onuPortPhyAdminPFEntry 2 }

		
--          1.3.6.1.4.1.37950.1.1.5.12.9.2.15.1.3
-- 1.3.6.1.4.1.37950.1.1.5.12.9.2.15.1.3
-- 1.3.6.1.4.1.37950.1.1.5.12.9.2.15.1.3
-- 1.3.6.1.4.1.37950.1.1.5.12.9.2.15.1.3
-- 1.3.6.1.4.1.37950.1.1.5.12.9.2.15.1.3
-- 1.3.6.1.4.1.37950.1.1.5.12.9.2.15.1.3
-- 1.3.6.1.4.1.37950.1.1.5.12.9.2.15.1.3
-- 1.3.6.1.4.1.37950.1.1.5.12.9.2.15.1.3
-- 1.3.6.1.4.1.37950.1.1.5.12.9.2.15.1.3
		-- 1.3.6.1.4.1.37950.1.1.5.12.9.2.15.1.3
		onuPortPhyAdminEnS OBJECT-TYPE
			SYNTAX INTEGER
				{
				disable(0),
				enable(1)
				}
			MAX-ACCESS read-only
			STATUS current
			DESCRIPTION
				"Description."
			::= { onuPortPhyAdminPFEntry 3 }

		
--          1.3.6.1.4.1.37950.1.1.5.12.9.2.16
-- 1.3.6.1.4.1.37950.1.1.5.12.9.2.16
-- 1.3.6.1.4.1.37950.1.1.5.12.9.2.16
-- 1.3.6.1.4.1.37950.1.1.5.12.9.2.16
-- 1.3.6.1.4.1.37950.1.1.5.12.9.2.16
-- 1.3.6.1.4.1.37950.1.1.5.12.9.2.16
-- 1.3.6.1.4.1.37950.1.1.5.12.9.2.16
-- 1.3.6.1.4.1.37950.1.1.5.12.9.2.16
-- 1.3.6.1.4.1.37950.1.1.5.12.9.2.16
		-- 1.3.6.1.4.1.37950.1.1.5.12.9.2.16
		portAutoNegPFTable OBJECT-TYPE
			SYNTAX SEQUENCE OF PortAutoNegPFEntry
			MAX-ACCESS not-accessible
			STATUS current
			DESCRIPTION
				"Description."
			::= { srvProfileShow 16 }

		
--          1.3.6.1.4.1.37950.1.1.5.12.9.2.16.1
-- 1.3.6.1.4.1.37950.1.1.5.12.9.2.16.1
-- 1.3.6.1.4.1.37950.1.1.5.12.9.2.16.1
-- 1.3.6.1.4.1.37950.1.1.5.12.9.2.16.1
-- 1.3.6.1.4.1.37950.1.1.5.12.9.2.16.1
-- 1.3.6.1.4.1.37950.1.1.5.12.9.2.16.1
-- 1.3.6.1.4.1.37950.1.1.5.12.9.2.16.1
-- 1.3.6.1.4.1.37950.1.1.5.12.9.2.16.1
-- 1.3.6.1.4.1.37950.1.1.5.12.9.2.16.1
		-- 1.3.6.1.4.1.37950.1.1.5.12.9.2.16.1
		portAutoNegPFEntry OBJECT-TYPE
			SYNTAX PortAutoNegPFEntry
			MAX-ACCESS not-accessible
			STATUS current
			DESCRIPTION
				"Description."
			INDEX { portAutoNegSrvId, autoNegPortIndexS }
			::= { portAutoNegPFTable 1 }

		
		PortAutoNegPFEntry ::=
			SEQUENCE { 
				portAutoNegSrvId
					Integer32,
				autoNegPortIndexS
					INTEGER,
				portAutoNegEnS
					INTEGER
			 }

--          1.3.6.1.4.1.37950.1.1.5.12.9.2.16.1.1
-- 1.3.6.1.4.1.37950.1.1.5.12.9.2.16.1.1
-- 1.3.6.1.4.1.37950.1.1.5.12.9.2.16.1.1
-- 1.3.6.1.4.1.37950.1.1.5.12.9.2.16.1.1
-- 1.3.6.1.4.1.37950.1.1.5.12.9.2.16.1.1
-- 1.3.6.1.4.1.37950.1.1.5.12.9.2.16.1.1
-- 1.3.6.1.4.1.37950.1.1.5.12.9.2.16.1.1
-- 1.3.6.1.4.1.37950.1.1.5.12.9.2.16.1.1
-- 1.3.6.1.4.1.37950.1.1.5.12.9.2.16.1.1
		-- 1.3.6.1.4.1.37950.1.1.5.12.9.2.16.1.1
		portAutoNegSrvId OBJECT-TYPE
			SYNTAX Integer32 (0..65535)
			MAX-ACCESS read-only
			STATUS current
			DESCRIPTION
				"Description."
			::= { portAutoNegPFEntry 1 }

		
--          1.3.6.1.4.1.37950.1.1.5.12.9.2.16.1.2
-- 1.3.6.1.4.1.37950.1.1.5.12.9.2.16.1.2
-- 1.3.6.1.4.1.37950.1.1.5.12.9.2.16.1.2
-- 1.3.6.1.4.1.37950.1.1.5.12.9.2.16.1.2
-- 1.3.6.1.4.1.37950.1.1.5.12.9.2.16.1.2
-- 1.3.6.1.4.1.37950.1.1.5.12.9.2.16.1.2
-- 1.3.6.1.4.1.37950.1.1.5.12.9.2.16.1.2
-- 1.3.6.1.4.1.37950.1.1.5.12.9.2.16.1.2
-- 1.3.6.1.4.1.37950.1.1.5.12.9.2.16.1.2
		-- 1.3.6.1.4.1.37950.1.1.5.12.9.2.16.1.2
		autoNegPortIndexS OBJECT-TYPE
			SYNTAX INTEGER (1..255)
			MAX-ACCESS read-only
			STATUS current
			DESCRIPTION
				"Description."
			::= { portAutoNegPFEntry 2 }

		
--          1.3.6.1.4.1.37950.1.1.5.12.9.2.16.1.3
-- 1.3.6.1.4.1.37950.1.1.5.12.9.2.16.1.3
-- 1.3.6.1.4.1.37950.1.1.5.12.9.2.16.1.3
-- 1.3.6.1.4.1.37950.1.1.5.12.9.2.16.1.3
-- 1.3.6.1.4.1.37950.1.1.5.12.9.2.16.1.3
-- 1.3.6.1.4.1.37950.1.1.5.12.9.2.16.1.3
-- 1.3.6.1.4.1.37950.1.1.5.12.9.2.16.1.3
-- 1.3.6.1.4.1.37950.1.1.5.12.9.2.16.1.3
-- 1.3.6.1.4.1.37950.1.1.5.12.9.2.16.1.3
		-- 1.3.6.1.4.1.37950.1.1.5.12.9.2.16.1.3
		portAutoNegEnS OBJECT-TYPE
			SYNTAX INTEGER
				{
				disable(0),
				enable(1)
				}
			MAX-ACCESS read-only
			STATUS current
			DESCRIPTION
				"Description."
			::= { portAutoNegPFEntry 3 }

		
--          1.3.6.1.4.1.37950.1.1.5.12.9.2.17
-- 1.3.6.1.4.1.37950.1.1.5.12.9.2.17
-- 1.3.6.1.4.1.37950.1.1.5.12.9.2.17
-- 1.3.6.1.4.1.37950.1.1.5.12.9.2.17
-- 1.3.6.1.4.1.37950.1.1.5.12.9.2.17
-- 1.3.6.1.4.1.37950.1.1.5.12.9.2.17
-- 1.3.6.1.4.1.37950.1.1.5.12.9.2.17
-- 1.3.6.1.4.1.37950.1.1.5.12.9.2.17
-- 1.3.6.1.4.1.37950.1.1.5.12.9.2.17
		-- 1.3.6.1.4.1.37950.1.1.5.12.9.2.17
		maxIgmpGrpPFTable OBJECT-TYPE
			SYNTAX SEQUENCE OF MaxIgmpGrpPFEntry
			MAX-ACCESS not-accessible
			STATUS current
			DESCRIPTION
				"Description."
			::= { srvProfileShow 17 }

		
--          1.3.6.1.4.1.37950.1.1.5.12.9.2.17.1
-- 1.3.6.1.4.1.37950.1.1.5.12.9.2.17.1
-- 1.3.6.1.4.1.37950.1.1.5.12.9.2.17.1
-- 1.3.6.1.4.1.37950.1.1.5.12.9.2.17.1
-- 1.3.6.1.4.1.37950.1.1.5.12.9.2.17.1
-- 1.3.6.1.4.1.37950.1.1.5.12.9.2.17.1
-- 1.3.6.1.4.1.37950.1.1.5.12.9.2.17.1
-- 1.3.6.1.4.1.37950.1.1.5.12.9.2.17.1
-- 1.3.6.1.4.1.37950.1.1.5.12.9.2.17.1
		-- 1.3.6.1.4.1.37950.1.1.5.12.9.2.17.1
		maxIgmpGrpPFEntry OBJECT-TYPE
			SYNTAX MaxIgmpGrpPFEntry
			MAX-ACCESS not-accessible
			STATUS current
			DESCRIPTION
				"Description."
			INDEX { maxIgmpGrpSrvId, maxIgmpPortIndexS }
			::= { maxIgmpGrpPFTable 1 }

		
		MaxIgmpGrpPFEntry ::=
			SEQUENCE { 
				maxIgmpGrpSrvId
					Integer32,
				maxIgmpPortIndexS
					INTEGER,
				maxIgmpGrpS
					Integer32
			 }

--          1.3.6.1.4.1.37950.1.1.5.12.9.2.17.1.1
-- 1.3.6.1.4.1.37950.1.1.5.12.9.2.17.1.1
-- 1.3.6.1.4.1.37950.1.1.5.12.9.2.17.1.1
-- 1.3.6.1.4.1.37950.1.1.5.12.9.2.17.1.1
-- 1.3.6.1.4.1.37950.1.1.5.12.9.2.17.1.1
-- 1.3.6.1.4.1.37950.1.1.5.12.9.2.17.1.1
-- 1.3.6.1.4.1.37950.1.1.5.12.9.2.17.1.1
-- 1.3.6.1.4.1.37950.1.1.5.12.9.2.17.1.1
-- 1.3.6.1.4.1.37950.1.1.5.12.9.2.17.1.1
		-- 1.3.6.1.4.1.37950.1.1.5.12.9.2.17.1.1
		maxIgmpGrpSrvId OBJECT-TYPE
			SYNTAX Integer32 (0..65535)
			MAX-ACCESS read-only
			STATUS current
			DESCRIPTION
				"Description."
			::= { maxIgmpGrpPFEntry 1 }

		
--          1.3.6.1.4.1.37950.1.1.5.12.9.2.17.1.2
-- 1.3.6.1.4.1.37950.1.1.5.12.9.2.17.1.2
-- 1.3.6.1.4.1.37950.1.1.5.12.9.2.17.1.2
-- 1.3.6.1.4.1.37950.1.1.5.12.9.2.17.1.2
-- 1.3.6.1.4.1.37950.1.1.5.12.9.2.17.1.2
-- 1.3.6.1.4.1.37950.1.1.5.12.9.2.17.1.2
-- 1.3.6.1.4.1.37950.1.1.5.12.9.2.17.1.2
-- 1.3.6.1.4.1.37950.1.1.5.12.9.2.17.1.2
-- 1.3.6.1.4.1.37950.1.1.5.12.9.2.17.1.2
		-- 1.3.6.1.4.1.37950.1.1.5.12.9.2.17.1.2
		maxIgmpPortIndexS OBJECT-TYPE
			SYNTAX INTEGER (1..255)
			MAX-ACCESS read-only
			STATUS current
			DESCRIPTION
				"Description."
			::= { maxIgmpGrpPFEntry 2 }

		
--          1.3.6.1.4.1.37950.1.1.5.12.9.2.17.1.3
-- 1.3.6.1.4.1.37950.1.1.5.12.9.2.17.1.3
-- 1.3.6.1.4.1.37950.1.1.5.12.9.2.17.1.3
-- 1.3.6.1.4.1.37950.1.1.5.12.9.2.17.1.3
-- 1.3.6.1.4.1.37950.1.1.5.12.9.2.17.1.3
-- 1.3.6.1.4.1.37950.1.1.5.12.9.2.17.1.3
-- 1.3.6.1.4.1.37950.1.1.5.12.9.2.17.1.3
-- 1.3.6.1.4.1.37950.1.1.5.12.9.2.17.1.3
-- 1.3.6.1.4.1.37950.1.1.5.12.9.2.17.1.3
		-- 1.3.6.1.4.1.37950.1.1.5.12.9.2.17.1.3
		maxIgmpGrpS OBJECT-TYPE
			SYNTAX Integer32
			MAX-ACCESS read-only
			STATUS current
			DESCRIPTION
				"Description."
			::= { maxIgmpGrpPFEntry 3 }

		
--          1.3.6.1.4.1.37950.1.1.5.12.9.2.18
-- 1.3.6.1.4.1.37950.1.1.5.12.9.2.18
-- 1.3.6.1.4.1.37950.1.1.5.12.9.2.18
-- 1.3.6.1.4.1.37950.1.1.5.12.9.2.18
-- 1.3.6.1.4.1.37950.1.1.5.12.9.2.18
-- 1.3.6.1.4.1.37950.1.1.5.12.9.2.18
-- 1.3.6.1.4.1.37950.1.1.5.12.9.2.18
-- 1.3.6.1.4.1.37950.1.1.5.12.9.2.18
-- 1.3.6.1.4.1.37950.1.1.5.12.9.2.18
		-- 1.3.6.1.4.1.37950.1.1.5.12.9.2.18
		onuPortUpLimitPFTable OBJECT-TYPE
			SYNTAX SEQUENCE OF OnuPortUpLimitPFEntry
			MAX-ACCESS not-accessible
			STATUS current
			DESCRIPTION
				"Description."
			::= { srvProfileShow 18 }

		
--          1.3.6.1.4.1.37950.1.1.5.12.9.2.18.1
-- 1.3.6.1.4.1.37950.1.1.5.12.9.2.18.1
-- 1.3.6.1.4.1.37950.1.1.5.12.9.2.18.1
-- 1.3.6.1.4.1.37950.1.1.5.12.9.2.18.1
-- 1.3.6.1.4.1.37950.1.1.5.12.9.2.18.1
-- 1.3.6.1.4.1.37950.1.1.5.12.9.2.18.1
-- 1.3.6.1.4.1.37950.1.1.5.12.9.2.18.1
-- 1.3.6.1.4.1.37950.1.1.5.12.9.2.18.1
-- 1.3.6.1.4.1.37950.1.1.5.12.9.2.18.1
		-- 1.3.6.1.4.1.37950.1.1.5.12.9.2.18.1
		onuPortUpLimitPFEntry OBJECT-TYPE
			SYNTAX OnuPortUpLimitPFEntry
			MAX-ACCESS not-accessible
			STATUS current
			DESCRIPTION
				"Description."
			INDEX { onuPortUpLimitSrvId, upLimitPortIndexS }
			::= { onuPortUpLimitPFTable 1 }

		
		OnuPortUpLimitPFEntry ::=
			SEQUENCE { 
				onuPortUpLimitSrvId
					Integer32,
				upLimitPortIndexS
					INTEGER,
				onuPortUpLimitCirS
					Integer32,
				onuPortUpLimitCbsS
					Integer32,
				onuPortUpLimitEbsS
					Integer32
			 }

--          1.3.6.1.4.1.37950.1.1.5.12.9.2.18.1.1
-- 1.3.6.1.4.1.37950.1.1.5.12.9.2.18.1.1
-- 1.3.6.1.4.1.37950.1.1.5.12.9.2.18.1.1
-- 1.3.6.1.4.1.37950.1.1.5.12.9.2.18.1.1
-- 1.3.6.1.4.1.37950.1.1.5.12.9.2.18.1.1
-- 1.3.6.1.4.1.37950.1.1.5.12.9.2.18.1.1
-- 1.3.6.1.4.1.37950.1.1.5.12.9.2.18.1.1
-- 1.3.6.1.4.1.37950.1.1.5.12.9.2.18.1.1
-- 1.3.6.1.4.1.37950.1.1.5.12.9.2.18.1.1
		-- 1.3.6.1.4.1.37950.1.1.5.12.9.2.18.1.1
		onuPortUpLimitSrvId OBJECT-TYPE
			SYNTAX Integer32 (0..65535)
			MAX-ACCESS read-only
			STATUS current
			DESCRIPTION
				"Description."
			::= { onuPortUpLimitPFEntry 1 }

		
--          1.3.6.1.4.1.37950.1.1.5.12.9.2.18.1.2
-- 1.3.6.1.4.1.37950.1.1.5.12.9.2.18.1.2
-- 1.3.6.1.4.1.37950.1.1.5.12.9.2.18.1.2
-- 1.3.6.1.4.1.37950.1.1.5.12.9.2.18.1.2
-- 1.3.6.1.4.1.37950.1.1.5.12.9.2.18.1.2
-- 1.3.6.1.4.1.37950.1.1.5.12.9.2.18.1.2
-- 1.3.6.1.4.1.37950.1.1.5.12.9.2.18.1.2
-- 1.3.6.1.4.1.37950.1.1.5.12.9.2.18.1.2
-- 1.3.6.1.4.1.37950.1.1.5.12.9.2.18.1.2
		-- 1.3.6.1.4.1.37950.1.1.5.12.9.2.18.1.2
		upLimitPortIndexS OBJECT-TYPE
			SYNTAX INTEGER (1..255)
			MAX-ACCESS read-only
			STATUS current
			DESCRIPTION
				"Description."
			::= { onuPortUpLimitPFEntry 2 }

		
--          1.3.6.1.4.1.37950.1.1.5.12.9.2.18.1.3
-- 1.3.6.1.4.1.37950.1.1.5.12.9.2.18.1.3
-- 1.3.6.1.4.1.37950.1.1.5.12.9.2.18.1.3
-- 1.3.6.1.4.1.37950.1.1.5.12.9.2.18.1.3
-- 1.3.6.1.4.1.37950.1.1.5.12.9.2.18.1.3
-- 1.3.6.1.4.1.37950.1.1.5.12.9.2.18.1.3
-- 1.3.6.1.4.1.37950.1.1.5.12.9.2.18.1.3
-- 1.3.6.1.4.1.37950.1.1.5.12.9.2.18.1.3
-- 1.3.6.1.4.1.37950.1.1.5.12.9.2.18.1.3
		-- 1.3.6.1.4.1.37950.1.1.5.12.9.2.18.1.3
		onuPortUpLimitCirS OBJECT-TYPE
			SYNTAX Integer32
			MAX-ACCESS read-only
			STATUS current
			DESCRIPTION
				"Description."
			::= { onuPortUpLimitPFEntry 3 }

		
--          1.3.6.1.4.1.37950.1.1.5.12.9.2.18.1.4
-- 1.3.6.1.4.1.37950.1.1.5.12.9.2.18.1.4
-- 1.3.6.1.4.1.37950.1.1.5.12.9.2.18.1.4
-- 1.3.6.1.4.1.37950.1.1.5.12.9.2.18.1.4
-- 1.3.6.1.4.1.37950.1.1.5.12.9.2.18.1.4
-- 1.3.6.1.4.1.37950.1.1.5.12.9.2.18.1.4
-- 1.3.6.1.4.1.37950.1.1.5.12.9.2.18.1.4
-- 1.3.6.1.4.1.37950.1.1.5.12.9.2.18.1.4
-- 1.3.6.1.4.1.37950.1.1.5.12.9.2.18.1.4
		-- 1.3.6.1.4.1.37950.1.1.5.12.9.2.18.1.4
		onuPortUpLimitCbsS OBJECT-TYPE
			SYNTAX Integer32
			MAX-ACCESS read-only
			STATUS current
			DESCRIPTION
				"Description."
			::= { onuPortUpLimitPFEntry 4 }

		
--          1.3.6.1.4.1.37950.1.1.5.12.9.2.18.1.5
-- 1.3.6.1.4.1.37950.1.1.5.12.9.2.18.1.5
-- 1.3.6.1.4.1.37950.1.1.5.12.9.2.18.1.5
-- 1.3.6.1.4.1.37950.1.1.5.12.9.2.18.1.5
-- 1.3.6.1.4.1.37950.1.1.5.12.9.2.18.1.5
-- 1.3.6.1.4.1.37950.1.1.5.12.9.2.18.1.5
-- 1.3.6.1.4.1.37950.1.1.5.12.9.2.18.1.5
-- 1.3.6.1.4.1.37950.1.1.5.12.9.2.18.1.5
-- 1.3.6.1.4.1.37950.1.1.5.12.9.2.18.1.5
		-- 1.3.6.1.4.1.37950.1.1.5.12.9.2.18.1.5
		onuPortUpLimitEbsS OBJECT-TYPE
			SYNTAX Integer32
			MAX-ACCESS read-only
			STATUS current
			DESCRIPTION
				"Description."
			::= { onuPortUpLimitPFEntry 5 }

		
--          1.3.6.1.4.1.37950.1.1.5.12.9.2.19
-- 1.3.6.1.4.1.37950.1.1.5.12.9.2.19
-- 1.3.6.1.4.1.37950.1.1.5.12.9.2.19
-- 1.3.6.1.4.1.37950.1.1.5.12.9.2.19
-- 1.3.6.1.4.1.37950.1.1.5.12.9.2.19
-- 1.3.6.1.4.1.37950.1.1.5.12.9.2.19
-- 1.3.6.1.4.1.37950.1.1.5.12.9.2.19
-- 1.3.6.1.4.1.37950.1.1.5.12.9.2.19
-- 1.3.6.1.4.1.37950.1.1.5.12.9.2.19
		-- 1.3.6.1.4.1.37950.1.1.5.12.9.2.19
		onuPortDownLimitPFTable OBJECT-TYPE
			SYNTAX SEQUENCE OF OnuPortDownLimitPFEntry
			MAX-ACCESS not-accessible
			STATUS current
			DESCRIPTION
				"Description."
			::= { srvProfileShow 19 }

		
--          1.3.6.1.4.1.37950.1.1.5.12.9.2.19.1
-- 1.3.6.1.4.1.37950.1.1.5.12.9.2.19.1
-- 1.3.6.1.4.1.37950.1.1.5.12.9.2.19.1
-- 1.3.6.1.4.1.37950.1.1.5.12.9.2.19.1
-- 1.3.6.1.4.1.37950.1.1.5.12.9.2.19.1
-- 1.3.6.1.4.1.37950.1.1.5.12.9.2.19.1
-- 1.3.6.1.4.1.37950.1.1.5.12.9.2.19.1
-- 1.3.6.1.4.1.37950.1.1.5.12.9.2.19.1
-- 1.3.6.1.4.1.37950.1.1.5.12.9.2.19.1
		-- 1.3.6.1.4.1.37950.1.1.5.12.9.2.19.1
		onuPortDownLimitPFEntry OBJECT-TYPE
			SYNTAX OnuPortDownLimitPFEntry
			MAX-ACCESS not-accessible
			STATUS current
			DESCRIPTION
				"Description."
			INDEX { onuPortDownLimitSrvId, downLimitPortIndexS }
			::= { onuPortDownLimitPFTable 1 }

		
		OnuPortDownLimitPFEntry ::=
			SEQUENCE { 
				onuPortDownLimitSrvId
					Integer32,
				downLimitPortIndexS
					INTEGER,
				onuPortDownLimitCirS
					Integer32,
				onuPortDownLimitPirS
					Integer32
			 }

--          1.3.6.1.4.1.37950.1.1.5.12.9.2.19.1.1
-- 1.3.6.1.4.1.37950.1.1.5.12.9.2.19.1.1
-- 1.3.6.1.4.1.37950.1.1.5.12.9.2.19.1.1
-- 1.3.6.1.4.1.37950.1.1.5.12.9.2.19.1.1
-- 1.3.6.1.4.1.37950.1.1.5.12.9.2.19.1.1
-- 1.3.6.1.4.1.37950.1.1.5.12.9.2.19.1.1
-- 1.3.6.1.4.1.37950.1.1.5.12.9.2.19.1.1
-- 1.3.6.1.4.1.37950.1.1.5.12.9.2.19.1.1
-- 1.3.6.1.4.1.37950.1.1.5.12.9.2.19.1.1
		-- 1.3.6.1.4.1.37950.1.1.5.12.9.2.19.1.1
		onuPortDownLimitSrvId OBJECT-TYPE
			SYNTAX Integer32 (0..65535)
			MAX-ACCESS read-only
			STATUS current
			DESCRIPTION
				"Description."
			::= { onuPortDownLimitPFEntry 1 }

		
--          1.3.6.1.4.1.37950.1.1.5.12.9.2.19.1.2
-- 1.3.6.1.4.1.37950.1.1.5.12.9.2.19.1.2
-- 1.3.6.1.4.1.37950.1.1.5.12.9.2.19.1.2
-- 1.3.6.1.4.1.37950.1.1.5.12.9.2.19.1.2
-- 1.3.6.1.4.1.37950.1.1.5.12.9.2.19.1.2
-- 1.3.6.1.4.1.37950.1.1.5.12.9.2.19.1.2
-- 1.3.6.1.4.1.37950.1.1.5.12.9.2.19.1.2
-- 1.3.6.1.4.1.37950.1.1.5.12.9.2.19.1.2
-- 1.3.6.1.4.1.37950.1.1.5.12.9.2.19.1.2
		-- 1.3.6.1.4.1.37950.1.1.5.12.9.2.19.1.2
		downLimitPortIndexS OBJECT-TYPE
			SYNTAX INTEGER (1..255)
			MAX-ACCESS read-only
			STATUS current
			DESCRIPTION
				"Description."
			::= { onuPortDownLimitPFEntry 2 }

		
--          1.3.6.1.4.1.37950.1.1.5.12.9.2.19.1.3
-- 1.3.6.1.4.1.37950.1.1.5.12.9.2.19.1.3
-- 1.3.6.1.4.1.37950.1.1.5.12.9.2.19.1.3
-- 1.3.6.1.4.1.37950.1.1.5.12.9.2.19.1.3
-- 1.3.6.1.4.1.37950.1.1.5.12.9.2.19.1.3
-- 1.3.6.1.4.1.37950.1.1.5.12.9.2.19.1.3
-- 1.3.6.1.4.1.37950.1.1.5.12.9.2.19.1.3
-- 1.3.6.1.4.1.37950.1.1.5.12.9.2.19.1.3
-- 1.3.6.1.4.1.37950.1.1.5.12.9.2.19.1.3
		-- 1.3.6.1.4.1.37950.1.1.5.12.9.2.19.1.3
		onuPortDownLimitCirS OBJECT-TYPE
			SYNTAX Integer32
			MAX-ACCESS read-only
			STATUS current
			DESCRIPTION
				"Description."
			::= { onuPortDownLimitPFEntry 3 }

		
--          1.3.6.1.4.1.37950.1.1.5.12.9.2.19.1.4
-- 1.3.6.1.4.1.37950.1.1.5.12.9.2.19.1.4
-- 1.3.6.1.4.1.37950.1.1.5.12.9.2.19.1.4
-- 1.3.6.1.4.1.37950.1.1.5.12.9.2.19.1.4
-- 1.3.6.1.4.1.37950.1.1.5.12.9.2.19.1.4
-- 1.3.6.1.4.1.37950.1.1.5.12.9.2.19.1.4
-- 1.3.6.1.4.1.37950.1.1.5.12.9.2.19.1.4
-- 1.3.6.1.4.1.37950.1.1.5.12.9.2.19.1.4
-- 1.3.6.1.4.1.37950.1.1.5.12.9.2.19.1.4
		-- 1.3.6.1.4.1.37950.1.1.5.12.9.2.19.1.4
		onuPortDownLimitPirS OBJECT-TYPE
			SYNTAX Integer32
			MAX-ACCESS read-write
			STATUS current
			DESCRIPTION
				"Description."
			::= { onuPortDownLimitPFEntry 4 }

		
--          1.3.6.1.4.1.37950.1.1.5.12.9.2.20
-- 1.3.6.1.4.1.37950.1.1.5.12.9.2.20
-- 1.3.6.1.4.1.37950.1.1.5.12.9.2.20
-- 1.3.6.1.4.1.37950.1.1.5.12.9.2.20
-- 1.3.6.1.4.1.37950.1.1.5.12.9.2.20
-- 1.3.6.1.4.1.37950.1.1.5.12.9.2.20
-- 1.3.6.1.4.1.37950.1.1.5.12.9.2.20
-- 1.3.6.1.4.1.37950.1.1.5.12.9.2.20
-- 1.3.6.1.4.1.37950.1.1.5.12.9.2.20
		-- 1.3.6.1.4.1.37950.1.1.5.12.9.2.20
		portVlanModePFTable OBJECT-TYPE
			SYNTAX SEQUENCE OF PortVlanModePFEntry
			MAX-ACCESS not-accessible
			STATUS current
			DESCRIPTION
				"Description."
			::= { srvProfileShow 20 }

		
--          1.3.6.1.4.1.37950.1.1.5.12.9.2.20.1
-- 1.3.6.1.4.1.37950.1.1.5.12.9.2.20.1
-- 1.3.6.1.4.1.37950.1.1.5.12.9.2.20.1
-- 1.3.6.1.4.1.37950.1.1.5.12.9.2.20.1
-- 1.3.6.1.4.1.37950.1.1.5.12.9.2.20.1
-- 1.3.6.1.4.1.37950.1.1.5.12.9.2.20.1
-- 1.3.6.1.4.1.37950.1.1.5.12.9.2.20.1
-- 1.3.6.1.4.1.37950.1.1.5.12.9.2.20.1
-- 1.3.6.1.4.1.37950.1.1.5.12.9.2.20.1
		-- 1.3.6.1.4.1.37950.1.1.5.12.9.2.20.1
		portVlanModePFEntry OBJECT-TYPE
			SYNTAX PortVlanModePFEntry
			MAX-ACCESS not-accessible
			STATUS current
			DESCRIPTION
				"Description."
			INDEX { portVlanModeSrvId, vlanModePortIndexS }
			::= { portVlanModePFTable 1 }

		
		PortVlanModePFEntry ::=
			SEQUENCE { 
				portVlanModeSrvId
					Integer32,
				vlanModePortIndexS
					INTEGER,
				onuCtcPortVlanModeS
					INTEGER
			 }

--          1.3.6.1.4.1.37950.1.1.5.12.9.2.20.1.1
-- 1.3.6.1.4.1.37950.1.1.5.12.9.2.20.1.1
-- 1.3.6.1.4.1.37950.1.1.5.12.9.2.20.1.1
-- 1.3.6.1.4.1.37950.1.1.5.12.9.2.20.1.1
-- 1.3.6.1.4.1.37950.1.1.5.12.9.2.20.1.1
-- 1.3.6.1.4.1.37950.1.1.5.12.9.2.20.1.1
-- 1.3.6.1.4.1.37950.1.1.5.12.9.2.20.1.1
-- 1.3.6.1.4.1.37950.1.1.5.12.9.2.20.1.1
-- 1.3.6.1.4.1.37950.1.1.5.12.9.2.20.1.1
		-- 1.3.6.1.4.1.37950.1.1.5.12.9.2.20.1.1
		portVlanModeSrvId OBJECT-TYPE
			SYNTAX Integer32 (0..65535)
			MAX-ACCESS read-only
			STATUS current
			DESCRIPTION
				"Description."
			::= { portVlanModePFEntry 1 }

		
--          1.3.6.1.4.1.37950.1.1.5.12.9.2.20.1.2
-- 1.3.6.1.4.1.37950.1.1.5.12.9.2.20.1.2
-- 1.3.6.1.4.1.37950.1.1.5.12.9.2.20.1.2
-- 1.3.6.1.4.1.37950.1.1.5.12.9.2.20.1.2
-- 1.3.6.1.4.1.37950.1.1.5.12.9.2.20.1.2
-- 1.3.6.1.4.1.37950.1.1.5.12.9.2.20.1.2
-- 1.3.6.1.4.1.37950.1.1.5.12.9.2.20.1.2
-- 1.3.6.1.4.1.37950.1.1.5.12.9.2.20.1.2
-- 1.3.6.1.4.1.37950.1.1.5.12.9.2.20.1.2
		-- 1.3.6.1.4.1.37950.1.1.5.12.9.2.20.1.2
		vlanModePortIndexS OBJECT-TYPE
			SYNTAX INTEGER (1..255)
			MAX-ACCESS read-only
			STATUS current
			DESCRIPTION
				"Description."
			::= { portVlanModePFEntry 2 }

		
--          1.3.6.1.4.1.37950.1.1.5.12.9.2.20.1.3
-- 1.3.6.1.4.1.37950.1.1.5.12.9.2.20.1.3
-- 1.3.6.1.4.1.37950.1.1.5.12.9.2.20.1.3
-- 1.3.6.1.4.1.37950.1.1.5.12.9.2.20.1.3
-- 1.3.6.1.4.1.37950.1.1.5.12.9.2.20.1.3
-- 1.3.6.1.4.1.37950.1.1.5.12.9.2.20.1.3
-- 1.3.6.1.4.1.37950.1.1.5.12.9.2.20.1.3
-- 1.3.6.1.4.1.37950.1.1.5.12.9.2.20.1.3
-- 1.3.6.1.4.1.37950.1.1.5.12.9.2.20.1.3
		-- 1.3.6.1.4.1.37950.1.1.5.12.9.2.20.1.3
		onuCtcPortVlanModeS OBJECT-TYPE
			SYNTAX INTEGER
				{
				transparent(1),
				tag(2),
				translation(3),
				aggregation(4),
				trunk(5)
				}
			MAX-ACCESS read-only
			STATUS current
			DESCRIPTION
				"Description."
			::= { portVlanModePFEntry 3 }

		
--          1.3.6.1.4.1.37950.1.1.5.12.9.2.21
-- 1.3.6.1.4.1.37950.1.1.5.12.9.2.21
-- 1.3.6.1.4.1.37950.1.1.5.12.9.2.21
-- 1.3.6.1.4.1.37950.1.1.5.12.9.2.21
-- 1.3.6.1.4.1.37950.1.1.5.12.9.2.21
-- 1.3.6.1.4.1.37950.1.1.5.12.9.2.21
-- 1.3.6.1.4.1.37950.1.1.5.12.9.2.21
-- 1.3.6.1.4.1.37950.1.1.5.12.9.2.21
-- 1.3.6.1.4.1.37950.1.1.5.12.9.2.21
		-- 1.3.6.1.4.1.37950.1.1.5.12.9.2.21
		portVlanPvidPFTable OBJECT-TYPE
			SYNTAX SEQUENCE OF PortVlanPvidPFEntry
			MAX-ACCESS not-accessible
			STATUS current
			DESCRIPTION
				"Description."
			::= { srvProfileShow 21 }

		
--          1.3.6.1.4.1.37950.1.1.5.12.9.2.21.1
-- 1.3.6.1.4.1.37950.1.1.5.12.9.2.21.1
-- 1.3.6.1.4.1.37950.1.1.5.12.9.2.21.1
-- 1.3.6.1.4.1.37950.1.1.5.12.9.2.21.1
-- 1.3.6.1.4.1.37950.1.1.5.12.9.2.21.1
-- 1.3.6.1.4.1.37950.1.1.5.12.9.2.21.1
-- 1.3.6.1.4.1.37950.1.1.5.12.9.2.21.1
-- 1.3.6.1.4.1.37950.1.1.5.12.9.2.21.1
-- 1.3.6.1.4.1.37950.1.1.5.12.9.2.21.1
		-- 1.3.6.1.4.1.37950.1.1.5.12.9.2.21.1
		portVlanPvidPFEntry OBJECT-TYPE
			SYNTAX PortVlanPvidPFEntry
			MAX-ACCESS not-accessible
			STATUS current
			DESCRIPTION
				"Description."
			INDEX { portVlanPvidSrvId, vlanPvidPortIndexS }
			::= { portVlanPvidPFTable 1 }

		
		PortVlanPvidPFEntry ::=
			SEQUENCE { 
				portVlanPvidSrvId
					Integer32,
				vlanPvidPortIndexS
					INTEGER,
				vlanPvidS
					Integer32,
				vlanTpidS
					OCTET STRING,
				vlanPvidPriS
					INTEGER
			 }

--          1.3.6.1.4.1.37950.1.1.5.12.9.2.21.1.1
-- 1.3.6.1.4.1.37950.1.1.5.12.9.2.21.1.1
-- 1.3.6.1.4.1.37950.1.1.5.12.9.2.21.1.1
-- 1.3.6.1.4.1.37950.1.1.5.12.9.2.21.1.1
-- 1.3.6.1.4.1.37950.1.1.5.12.9.2.21.1.1
-- 1.3.6.1.4.1.37950.1.1.5.12.9.2.21.1.1
-- 1.3.6.1.4.1.37950.1.1.5.12.9.2.21.1.1
-- 1.3.6.1.4.1.37950.1.1.5.12.9.2.21.1.1
-- 1.3.6.1.4.1.37950.1.1.5.12.9.2.21.1.1
		-- 1.3.6.1.4.1.37950.1.1.5.12.9.2.21.1.1
		portVlanPvidSrvId OBJECT-TYPE
			SYNTAX Integer32 (0..65535)
			MAX-ACCESS read-only
			STATUS current
			DESCRIPTION
				"Description."
			::= { portVlanPvidPFEntry 1 }

		
--          1.3.6.1.4.1.37950.1.1.5.12.9.2.21.1.2
-- 1.3.6.1.4.1.37950.1.1.5.12.9.2.21.1.2
-- 1.3.6.1.4.1.37950.1.1.5.12.9.2.21.1.2
-- 1.3.6.1.4.1.37950.1.1.5.12.9.2.21.1.2
-- 1.3.6.1.4.1.37950.1.1.5.12.9.2.21.1.2
-- 1.3.6.1.4.1.37950.1.1.5.12.9.2.21.1.2
-- 1.3.6.1.4.1.37950.1.1.5.12.9.2.21.1.2
-- 1.3.6.1.4.1.37950.1.1.5.12.9.2.21.1.2
-- 1.3.6.1.4.1.37950.1.1.5.12.9.2.21.1.2
		-- 1.3.6.1.4.1.37950.1.1.5.12.9.2.21.1.2
		vlanPvidPortIndexS OBJECT-TYPE
			SYNTAX INTEGER (1..255)
			MAX-ACCESS read-only
			STATUS current
			DESCRIPTION
				"Description."
			::= { portVlanPvidPFEntry 2 }

		
--          1.3.6.1.4.1.37950.1.1.5.12.9.2.21.1.3
-- 1.3.6.1.4.1.37950.1.1.5.12.9.2.21.1.3
-- 1.3.6.1.4.1.37950.1.1.5.12.9.2.21.1.3
-- 1.3.6.1.4.1.37950.1.1.5.12.9.2.21.1.3
-- 1.3.6.1.4.1.37950.1.1.5.12.9.2.21.1.3
-- 1.3.6.1.4.1.37950.1.1.5.12.9.2.21.1.3
-- 1.3.6.1.4.1.37950.1.1.5.12.9.2.21.1.3
-- 1.3.6.1.4.1.37950.1.1.5.12.9.2.21.1.3
-- 1.3.6.1.4.1.37950.1.1.5.12.9.2.21.1.3
		-- 1.3.6.1.4.1.37950.1.1.5.12.9.2.21.1.3
		vlanPvidS OBJECT-TYPE
			SYNTAX Integer32
			MAX-ACCESS read-only
			STATUS current
			DESCRIPTION
				"Description."
			::= { portVlanPvidPFEntry 3 }

		
--          1.3.6.1.4.1.37950.1.1.5.12.9.2.21.1.4
-- 1.3.6.1.4.1.37950.1.1.5.12.9.2.21.1.4
-- 1.3.6.1.4.1.37950.1.1.5.12.9.2.21.1.4
-- 1.3.6.1.4.1.37950.1.1.5.12.9.2.21.1.4
-- 1.3.6.1.4.1.37950.1.1.5.12.9.2.21.1.4
-- 1.3.6.1.4.1.37950.1.1.5.12.9.2.21.1.4
-- 1.3.6.1.4.1.37950.1.1.5.12.9.2.21.1.4
-- 1.3.6.1.4.1.37950.1.1.5.12.9.2.21.1.4
-- 1.3.6.1.4.1.37950.1.1.5.12.9.2.21.1.4
		-- 1.3.6.1.4.1.37950.1.1.5.12.9.2.21.1.4
		vlanTpidS OBJECT-TYPE
			SYNTAX OCTET STRING
			MAX-ACCESS read-only
			STATUS current
			DESCRIPTION
				"Description."
			::= { portVlanPvidPFEntry 4 }

		
--           1.3.6.1.4.1.37950.1.1.5.12.9.2.21.1.4
-- 1.3.6.1.4.1.37950.1.1.5.12.9.2.21.1.5
-- 1.3.6.1.4.1.37950.1.1.5.12.9.2.21.1.5
-- 1.3.6.1.4.1.37950.1.1.5.12.9.2.21.1.5
-- 1.3.6.1.4.1.37950.1.1.5.12.9.2.21.1.5
-- 1.3.6.1.4.1.37950.1.1.5.12.9.2.21.1.5
-- 1.3.6.1.4.1.37950.1.1.5.12.9.2.21.1.5
-- 1.3.6.1.4.1.37950.1.1.5.12.9.2.21.1.5
-- 1.3.6.1.4.1.37950.1.1.5.12.9.2.21.1.5
		-- 1.3.6.1.4.1.37950.1.1.5.12.9.2.21.1.5
		vlanPvidPriS OBJECT-TYPE
			SYNTAX INTEGER (0..7)
			MAX-ACCESS read-only
			STATUS current
			DESCRIPTION
				"Description."
			::= { portVlanPvidPFEntry 5 }

		
--          1.3.6.1.4.1.37950.1.1.5.12.9.2.22
-- 1.3.6.1.4.1.37950.1.1.5.12.9.2.22
-- 1.3.6.1.4.1.37950.1.1.5.12.9.2.22
-- 1.3.6.1.4.1.37950.1.1.5.12.9.2.22
-- 1.3.6.1.4.1.37950.1.1.5.12.9.2.22
-- 1.3.6.1.4.1.37950.1.1.5.12.9.2.22
-- 1.3.6.1.4.1.37950.1.1.5.12.9.2.22
-- 1.3.6.1.4.1.37950.1.1.5.12.9.2.22
-- 1.3.6.1.4.1.37950.1.1.5.12.9.2.22
		-- 1.3.6.1.4.1.37950.1.1.5.12.9.2.22
		portVlanTranslatePFTable OBJECT-TYPE
			SYNTAX SEQUENCE OF PortVlanTranslatePFEntry
			MAX-ACCESS not-accessible
			STATUS current
			DESCRIPTION
				"Description."
			::= { srvProfileShow 22 }

		
--          1.3.6.1.4.1.37950.1.1.5.12.9.2.22.1
-- 1.3.6.1.4.1.37950.1.1.5.12.9.2.22.1
-- 1.3.6.1.4.1.37950.1.1.5.12.9.2.22.1
-- 1.3.6.1.4.1.37950.1.1.5.12.9.2.22.1
-- 1.3.6.1.4.1.37950.1.1.5.12.9.2.22.1
-- 1.3.6.1.4.1.37950.1.1.5.12.9.2.22.1
-- 1.3.6.1.4.1.37950.1.1.5.12.9.2.22.1
-- 1.3.6.1.4.1.37950.1.1.5.12.9.2.22.1
-- 1.3.6.1.4.1.37950.1.1.5.12.9.2.22.1
		-- 1.3.6.1.4.1.37950.1.1.5.12.9.2.22.1
		portVlanTranslatePFEntry OBJECT-TYPE
			SYNTAX PortVlanTranslatePFEntry
			MAX-ACCESS not-accessible
			STATUS current
			DESCRIPTION
				"Description."
			INDEX { portVlanTranslateSrvId, vlanTransPortIndexS }
			::= { portVlanTranslatePFTable 1 }

		
		PortVlanTranslatePFEntry ::=
			SEQUENCE { 
				portVlanTranslateSrvId
					Integer32,
				vlanTransPortIndexS
					INTEGER,
				portVlanTransVlanStrS
					OCTET STRING
			 }

--          1.3.6.1.4.1.37950.1.1.5.12.9.2.22.1.1
-- 1.3.6.1.4.1.37950.1.1.5.12.9.2.22.1.1
-- 1.3.6.1.4.1.37950.1.1.5.12.9.2.22.1.1
-- 1.3.6.1.4.1.37950.1.1.5.12.9.2.22.1.1
-- 1.3.6.1.4.1.37950.1.1.5.12.9.2.22.1.1
-- 1.3.6.1.4.1.37950.1.1.5.12.9.2.22.1.1
-- 1.3.6.1.4.1.37950.1.1.5.12.9.2.22.1.1
-- 1.3.6.1.4.1.37950.1.1.5.12.9.2.22.1.1
-- 1.3.6.1.4.1.37950.1.1.5.12.9.2.22.1.1
		-- 1.3.6.1.4.1.37950.1.1.5.12.9.2.22.1.1
		portVlanTranslateSrvId OBJECT-TYPE
			SYNTAX Integer32 (0..65535)
			MAX-ACCESS read-only
			STATUS current
			DESCRIPTION
				"Description."
			::= { portVlanTranslatePFEntry 1 }

		
--          1.3.6.1.4.1.37950.1.1.5.12.9.2.22.1.2
-- 1.3.6.1.4.1.37950.1.1.5.12.9.2.22.1.2
-- 1.3.6.1.4.1.37950.1.1.5.12.9.2.22.1.2
-- 1.3.6.1.4.1.37950.1.1.5.12.9.2.22.1.2
-- 1.3.6.1.4.1.37950.1.1.5.12.9.2.22.1.2
-- 1.3.6.1.4.1.37950.1.1.5.12.9.2.22.1.2
-- 1.3.6.1.4.1.37950.1.1.5.12.9.2.22.1.2
-- 1.3.6.1.4.1.37950.1.1.5.12.9.2.22.1.2
-- 1.3.6.1.4.1.37950.1.1.5.12.9.2.22.1.2
		-- 1.3.6.1.4.1.37950.1.1.5.12.9.2.22.1.2
		vlanTransPortIndexS OBJECT-TYPE
			SYNTAX INTEGER (1..255)
			MAX-ACCESS read-only
			STATUS current
			DESCRIPTION
				"Description."
			::= { portVlanTranslatePFEntry 2 }

		
--          1.3.6.1.4.1.37950.1.1.5.12.9.2.22.1.3
-- 1.3.6.1.4.1.37950.1.1.5.12.9.2.22.1.3
-- 1.3.6.1.4.1.37950.1.1.5.12.9.2.22.1.3
-- 1.3.6.1.4.1.37950.1.1.5.12.9.2.22.1.3
-- 1.3.6.1.4.1.37950.1.1.5.12.9.2.22.1.3
-- 1.3.6.1.4.1.37950.1.1.5.12.9.2.22.1.3
-- 1.3.6.1.4.1.37950.1.1.5.12.9.2.22.1.3
-- 1.3.6.1.4.1.37950.1.1.5.12.9.2.22.1.3
-- 1.3.6.1.4.1.37950.1.1.5.12.9.2.22.1.3
		-- 1.3.6.1.4.1.37950.1.1.5.12.9.2.22.1.3
		portVlanTransVlanStrS OBJECT-TYPE
			SYNTAX OCTET STRING
			MAX-ACCESS read-only
			STATUS current
			DESCRIPTION
				"Description."
			::= { portVlanTranslatePFEntry 3 }

		
--          1.3.6.1.4.1.37950.1.1.5.12.9.2.23
-- 1.3.6.1.4.1.37950.1.1.5.12.9.2.23
-- 1.3.6.1.4.1.37950.1.1.5.12.9.2.23
-- 1.3.6.1.4.1.37950.1.1.5.12.9.2.23
-- 1.3.6.1.4.1.37950.1.1.5.12.9.2.23
-- 1.3.6.1.4.1.37950.1.1.5.12.9.2.23
-- 1.3.6.1.4.1.37950.1.1.5.12.9.2.23
-- 1.3.6.1.4.1.37950.1.1.5.12.9.2.23
-- 1.3.6.1.4.1.37950.1.1.5.12.9.2.23
		-- 1.3.6.1.4.1.37950.1.1.5.12.9.2.23
		portVlanTrunkPFTable OBJECT-TYPE
			SYNTAX SEQUENCE OF PortVlanTrunkPFEntry
			MAX-ACCESS not-accessible
			STATUS current
			DESCRIPTION
				"Description."
			::= { srvProfileShow 23 }

		
--          1.3.6.1.4.1.37950.1.1.5.12.9.2.23.1
-- 1.3.6.1.4.1.37950.1.1.5.12.9.2.23.1
-- 1.3.6.1.4.1.37950.1.1.5.12.9.2.23.1
-- 1.3.6.1.4.1.37950.1.1.5.12.9.2.23.1
-- 1.3.6.1.4.1.37950.1.1.5.12.9.2.23.1
-- 1.3.6.1.4.1.37950.1.1.5.12.9.2.23.1
-- 1.3.6.1.4.1.37950.1.1.5.12.9.2.23.1
-- 1.3.6.1.4.1.37950.1.1.5.12.9.2.23.1
-- 1.3.6.1.4.1.37950.1.1.5.12.9.2.23.1
		-- 1.3.6.1.4.1.37950.1.1.5.12.9.2.23.1
		portVlanTrunkPFEntry OBJECT-TYPE
			SYNTAX PortVlanTrunkPFEntry
			MAX-ACCESS not-accessible
			STATUS current
			DESCRIPTION
				"Description."
			INDEX { portVlanTrunkSrvId, trunkPortIndexS }
			::= { portVlanTrunkPFTable 1 }

		
		PortVlanTrunkPFEntry ::=
			SEQUENCE { 
				portVlanTrunkSrvId
					Integer32,
				trunkPortIndexS
					INTEGER,
				portVlanTrunkVidStrS
					OCTET STRING
			 }

--          1.3.6.1.4.1.37950.1.1.5.12.9.2.23.1.1
-- 1.3.6.1.4.1.37950.1.1.5.12.9.2.23.1.1
-- 1.3.6.1.4.1.37950.1.1.5.12.9.2.23.1.1
-- 1.3.6.1.4.1.37950.1.1.5.12.9.2.23.1.1
-- 1.3.6.1.4.1.37950.1.1.5.12.9.2.23.1.1
-- 1.3.6.1.4.1.37950.1.1.5.12.9.2.23.1.1
-- 1.3.6.1.4.1.37950.1.1.5.12.9.2.23.1.1
-- 1.3.6.1.4.1.37950.1.1.5.12.9.2.23.1.1
-- 1.3.6.1.4.1.37950.1.1.5.12.9.2.23.1.1
		-- 1.3.6.1.4.1.37950.1.1.5.12.9.2.23.1.1
		portVlanTrunkSrvId OBJECT-TYPE
			SYNTAX Integer32 (0..65535)
			MAX-ACCESS read-only
			STATUS current
			DESCRIPTION
				"Description."
			::= { portVlanTrunkPFEntry 1 }

		
--          1.3.6.1.4.1.37950.1.1.5.12.9.2.23.1.2
-- 1.3.6.1.4.1.37950.1.1.5.12.9.2.23.1.2
-- 1.3.6.1.4.1.37950.1.1.5.12.9.2.23.1.2
-- 1.3.6.1.4.1.37950.1.1.5.12.9.2.23.1.2
-- 1.3.6.1.4.1.37950.1.1.5.12.9.2.23.1.2
-- 1.3.6.1.4.1.37950.1.1.5.12.9.2.23.1.2
-- 1.3.6.1.4.1.37950.1.1.5.12.9.2.23.1.2
-- 1.3.6.1.4.1.37950.1.1.5.12.9.2.23.1.2
-- 1.3.6.1.4.1.37950.1.1.5.12.9.2.23.1.2
		-- 1.3.6.1.4.1.37950.1.1.5.12.9.2.23.1.2
		trunkPortIndexS OBJECT-TYPE
			SYNTAX INTEGER (1..255)
			MAX-ACCESS read-only
			STATUS current
			DESCRIPTION
				"Description."
			::= { portVlanTrunkPFEntry 2 }

		
--          1.3.6.1.4.1.37950.1.1.5.12.9.2.23.1.3
-- 1.3.6.1.4.1.37950.1.1.5.12.9.2.23.1.3
-- 1.3.6.1.4.1.37950.1.1.5.12.9.2.23.1.3
-- 1.3.6.1.4.1.37950.1.1.5.12.9.2.23.1.3
-- 1.3.6.1.4.1.37950.1.1.5.12.9.2.23.1.3
-- 1.3.6.1.4.1.37950.1.1.5.12.9.2.23.1.3
-- 1.3.6.1.4.1.37950.1.1.5.12.9.2.23.1.3
-- 1.3.6.1.4.1.37950.1.1.5.12.9.2.23.1.3
-- 1.3.6.1.4.1.37950.1.1.5.12.9.2.23.1.3
		-- 1.3.6.1.4.1.37950.1.1.5.12.9.2.23.1.3
		portVlanTrunkVidStrS OBJECT-TYPE
			SYNTAX OCTET STRING
			MAX-ACCESS read-only
			STATUS current
			DESCRIPTION
				"Description."
			::= { portVlanTrunkPFEntry 3 }

		
--          1.3.6.1.4.1.37950.1.1.5.12.9.2.24
-- 1.3.6.1.4.1.37950.1.1.5.12.9.2.24
-- 1.3.6.1.4.1.37950.1.1.5.12.9.2.24
-- 1.3.6.1.4.1.37950.1.1.5.12.9.2.24
-- 1.3.6.1.4.1.37950.1.1.5.12.9.2.24
-- 1.3.6.1.4.1.37950.1.1.5.12.9.2.24
-- 1.3.6.1.4.1.37950.1.1.5.12.9.2.24
-- 1.3.6.1.4.1.37950.1.1.5.12.9.2.24
-- 1.3.6.1.4.1.37950.1.1.5.12.9.2.24
		-- 1.3.6.1.4.1.37950.1.1.5.12.9.2.24
		portVlanAggPFTable OBJECT-TYPE
			SYNTAX SEQUENCE OF PortVlanAggPFEntry
			MAX-ACCESS not-accessible
			STATUS current
			DESCRIPTION
				"Description."
			::= { srvProfileShow 24 }

		
--          1.3.6.1.4.1.37950.1.1.5.12.9.2.24.1
-- 1.3.6.1.4.1.37950.1.1.5.12.9.2.24.1
-- 1.3.6.1.4.1.37950.1.1.5.12.9.2.24.1
-- 1.3.6.1.4.1.37950.1.1.5.12.9.2.24.1
-- 1.3.6.1.4.1.37950.1.1.5.12.9.2.24.1
-- 1.3.6.1.4.1.37950.1.1.5.12.9.2.24.1
-- 1.3.6.1.4.1.37950.1.1.5.12.9.2.24.1
-- 1.3.6.1.4.1.37950.1.1.5.12.9.2.24.1
-- 1.3.6.1.4.1.37950.1.1.5.12.9.2.24.1
		-- 1.3.6.1.4.1.37950.1.1.5.12.9.2.24.1
		portVlanAggPFEntry OBJECT-TYPE
			SYNTAX PortVlanAggPFEntry
			MAX-ACCESS not-accessible
			STATUS current
			DESCRIPTION
				"Description."
			INDEX { portVlanAggSrvId, vlanAggPortIndexS }
			::= { portVlanAggPFTable 1 }

		
		PortVlanAggPFEntry ::=
			SEQUENCE { 
				portVlanAggSrvId
					Integer32,
				vlanAggPortIndexS
					INTEGER,
				portVlanAggNewVlanS
					Integer32,
				portVlanAggOldVlanStrS
					OCTET STRING
			 }

--          1.3.6.1.4.1.37950.1.1.5.12.9.2.24.1.1
-- 1.3.6.1.4.1.37950.1.1.5.12.9.2.24.1.1
-- 1.3.6.1.4.1.37950.1.1.5.12.9.2.24.1.1
-- 1.3.6.1.4.1.37950.1.1.5.12.9.2.24.1.1
-- 1.3.6.1.4.1.37950.1.1.5.12.9.2.24.1.1
-- 1.3.6.1.4.1.37950.1.1.5.12.9.2.24.1.1
-- 1.3.6.1.4.1.37950.1.1.5.12.9.2.24.1.1
-- 1.3.6.1.4.1.37950.1.1.5.12.9.2.24.1.1
-- 1.3.6.1.4.1.37950.1.1.5.12.9.2.24.1.1
		-- 1.3.6.1.4.1.37950.1.1.5.12.9.2.24.1.1
		portVlanAggSrvId OBJECT-TYPE
			SYNTAX Integer32 (0..65535)
			MAX-ACCESS read-only
			STATUS current
			DESCRIPTION
				"Description."
			::= { portVlanAggPFEntry 1 }

		
--          1.3.6.1.4.1.37950.1.1.5.12.9.2.24.1.2
-- 1.3.6.1.4.1.37950.1.1.5.12.9.2.24.1.2
-- 1.3.6.1.4.1.37950.1.1.5.12.9.2.24.1.2
-- 1.3.6.1.4.1.37950.1.1.5.12.9.2.24.1.2
-- 1.3.6.1.4.1.37950.1.1.5.12.9.2.24.1.2
-- 1.3.6.1.4.1.37950.1.1.5.12.9.2.24.1.2
-- 1.3.6.1.4.1.37950.1.1.5.12.9.2.24.1.2
-- 1.3.6.1.4.1.37950.1.1.5.12.9.2.24.1.2
-- 1.3.6.1.4.1.37950.1.1.5.12.9.2.24.1.2
		-- 1.3.6.1.4.1.37950.1.1.5.12.9.2.24.1.2
		vlanAggPortIndexS OBJECT-TYPE
			SYNTAX INTEGER (1..255)
			MAX-ACCESS read-only
			STATUS current
			DESCRIPTION
				"Description."
			::= { portVlanAggPFEntry 2 }

		
--          1.3.6.1.4.1.37950.1.1.5.12.9.2.24.1.3
-- 1.3.6.1.4.1.37950.1.1.5.12.9.2.24.1.3
-- 1.3.6.1.4.1.37950.1.1.5.12.9.2.24.1.3
-- 1.3.6.1.4.1.37950.1.1.5.12.9.2.24.1.3
-- 1.3.6.1.4.1.37950.1.1.5.12.9.2.24.1.3
-- 1.3.6.1.4.1.37950.1.1.5.12.9.2.24.1.3
-- 1.3.6.1.4.1.37950.1.1.5.12.9.2.24.1.3
-- 1.3.6.1.4.1.37950.1.1.5.12.9.2.24.1.3
-- 1.3.6.1.4.1.37950.1.1.5.12.9.2.24.1.3
		-- 1.3.6.1.4.1.37950.1.1.5.12.9.2.24.1.3
		portVlanAggNewVlanS OBJECT-TYPE
			SYNTAX Integer32
			MAX-ACCESS read-only
			STATUS current
			DESCRIPTION
				"Description."
			::= { portVlanAggPFEntry 3 }

		
--          1.3.6.1.4.1.37950.1.1.5.12.9.2.24.1.4
-- 1.3.6.1.4.1.37950.1.1.5.12.9.2.24.1.4
-- 1.3.6.1.4.1.37950.1.1.5.12.9.2.24.1.4
-- 1.3.6.1.4.1.37950.1.1.5.12.9.2.24.1.4
-- 1.3.6.1.4.1.37950.1.1.5.12.9.2.24.1.4
-- 1.3.6.1.4.1.37950.1.1.5.12.9.2.24.1.4
-- 1.3.6.1.4.1.37950.1.1.5.12.9.2.24.1.4
-- 1.3.6.1.4.1.37950.1.1.5.12.9.2.24.1.4
-- 1.3.6.1.4.1.37950.1.1.5.12.9.2.24.1.4
		-- 1.3.6.1.4.1.37950.1.1.5.12.9.2.24.1.4
		portVlanAggOldVlanStrS OBJECT-TYPE
			SYNTAX OCTET STRING
			MAX-ACCESS read-only
			STATUS current
			DESCRIPTION
				"Description."
			::= { portVlanAggPFEntry 4 }

		
--          1.3.6.1.4.1.37950.1.1.5.12.9.2.25
-- 1.3.6.1.4.1.37950.1.1.5.12.9.2.25
-- 1.3.6.1.4.1.37950.1.1.5.12.9.2.25
-- 1.3.6.1.4.1.37950.1.1.5.12.9.2.25
-- 1.3.6.1.4.1.37950.1.1.5.12.9.2.25
-- 1.3.6.1.4.1.37950.1.1.5.12.9.2.25
-- 1.3.6.1.4.1.37950.1.1.5.12.9.2.25
-- 1.3.6.1.4.1.37950.1.1.5.12.9.2.25
-- 1.3.6.1.4.1.37950.1.1.5.12.9.2.25
		-- 1.3.6.1.4.1.37950.1.1.5.12.9.2.25
		portMcVlanPFTable OBJECT-TYPE
			SYNTAX SEQUENCE OF PortMcVlanPFEntry
			MAX-ACCESS not-accessible
			STATUS current
			DESCRIPTION
				"Description."
			::= { srvProfileShow 25 }

		
--          1.3.6.1.4.1.37950.1.1.5.12.9.2.25.1
-- 1.3.6.1.4.1.37950.1.1.5.12.9.2.25.1
-- 1.3.6.1.4.1.37950.1.1.5.12.9.2.25.1
-- 1.3.6.1.4.1.37950.1.1.5.12.9.2.25.1
-- 1.3.6.1.4.1.37950.1.1.5.12.9.2.25.1
-- 1.3.6.1.4.1.37950.1.1.5.12.9.2.25.1
-- 1.3.6.1.4.1.37950.1.1.5.12.9.2.25.1
-- 1.3.6.1.4.1.37950.1.1.5.12.9.2.25.1
-- 1.3.6.1.4.1.37950.1.1.5.12.9.2.25.1
		-- 1.3.6.1.4.1.37950.1.1.5.12.9.2.25.1
		portMcVlanPFEntry OBJECT-TYPE
			SYNTAX PortMcVlanPFEntry
			MAX-ACCESS not-accessible
			STATUS current
			DESCRIPTION
				"Description."
			INDEX { portMcVlanSrvId, mcVlanPortIndexS }
			::= { portMcVlanPFTable 1 }

		
		PortMcVlanPFEntry ::=
			SEQUENCE { 
				portMcVlanSrvId
					Integer32,
				mcVlanPortIndexS
					INTEGER,
				portMcVlanStrS
					OCTET STRING
			 }

--          1.3.6.1.4.1.37950.1.1.5.12.9.2.25.1.1
-- 1.3.6.1.4.1.37950.1.1.5.12.9.2.25.1.1
-- 1.3.6.1.4.1.37950.1.1.5.12.9.2.25.1.1
-- 1.3.6.1.4.1.37950.1.1.5.12.9.2.25.1.1
-- 1.3.6.1.4.1.37950.1.1.5.12.9.2.25.1.1
-- 1.3.6.1.4.1.37950.1.1.5.12.9.2.25.1.1
-- 1.3.6.1.4.1.37950.1.1.5.12.9.2.25.1.1
-- 1.3.6.1.4.1.37950.1.1.5.12.9.2.25.1.1
-- 1.3.6.1.4.1.37950.1.1.5.12.9.2.25.1.1
		-- 1.3.6.1.4.1.37950.1.1.5.12.9.2.25.1.1
		portMcVlanSrvId OBJECT-TYPE
			SYNTAX Integer32 (0..65535)
			MAX-ACCESS read-only
			STATUS current
			DESCRIPTION
				"Description."
			::= { portMcVlanPFEntry 1 }

		
--          1.3.6.1.4.1.37950.1.1.5.12.9.2.25.1.2
-- 1.3.6.1.4.1.37950.1.1.5.12.9.2.25.1.2
-- 1.3.6.1.4.1.37950.1.1.5.12.9.2.25.1.2
-- 1.3.6.1.4.1.37950.1.1.5.12.9.2.25.1.2
-- 1.3.6.1.4.1.37950.1.1.5.12.9.2.25.1.2
-- 1.3.6.1.4.1.37950.1.1.5.12.9.2.25.1.2
-- 1.3.6.1.4.1.37950.1.1.5.12.9.2.25.1.2
-- 1.3.6.1.4.1.37950.1.1.5.12.9.2.25.1.2
-- 1.3.6.1.4.1.37950.1.1.5.12.9.2.25.1.2
		-- 1.3.6.1.4.1.37950.1.1.5.12.9.2.25.1.2
		mcVlanPortIndexS OBJECT-TYPE
			SYNTAX INTEGER (1..255)
			MAX-ACCESS read-only
			STATUS current
			DESCRIPTION
				"Description."
			::= { portMcVlanPFEntry 2 }

		
--          1.3.6.1.4.1.37950.1.1.5.12.9.2.25.1.3
-- 1.3.6.1.4.1.37950.1.1.5.12.9.2.25.1.3
-- 1.3.6.1.4.1.37950.1.1.5.12.9.2.25.1.3
-- 1.3.6.1.4.1.37950.1.1.5.12.9.2.25.1.3
-- 1.3.6.1.4.1.37950.1.1.5.12.9.2.25.1.3
-- 1.3.6.1.4.1.37950.1.1.5.12.9.2.25.1.3
-- 1.3.6.1.4.1.37950.1.1.5.12.9.2.25.1.3
-- 1.3.6.1.4.1.37950.1.1.5.12.9.2.25.1.3
-- 1.3.6.1.4.1.37950.1.1.5.12.9.2.25.1.3
		-- 1.3.6.1.4.1.37950.1.1.5.12.9.2.25.1.3
		portMcVlanStrS OBJECT-TYPE
			SYNTAX OCTET STRING
			MAX-ACCESS read-only
			STATUS current
			DESCRIPTION
				"Description."
			::= { portMcVlanPFEntry 3 }

		
--          1.3.6.1.4.1.37950.1.1.5.12.9.2.26
-- 1.3.6.1.4.1.37950.1.1.5.12.9.2.26
-- 1.3.6.1.4.1.37950.1.1.5.12.9.2.26
-- 1.3.6.1.4.1.37950.1.1.5.12.9.2.26
-- 1.3.6.1.4.1.37950.1.1.5.12.9.2.26
-- 1.3.6.1.4.1.37950.1.1.5.12.9.2.26
-- 1.3.6.1.4.1.37950.1.1.5.12.9.2.26
-- 1.3.6.1.4.1.37950.1.1.5.12.9.2.26
-- 1.3.6.1.4.1.37950.1.1.5.12.9.2.26
		-- 1.3.6.1.4.1.37950.1.1.5.12.9.2.26
		onuClassifyPFTable OBJECT-TYPE
			SYNTAX SEQUENCE OF OnuClassifyPFEntry
			MAX-ACCESS not-accessible
			STATUS current
			DESCRIPTION
				"Description."
			::= { srvProfileShow 26 }

		
--          1.3.6.1.4.1.37950.1.1.5.12.9.2.26.1
-- 1.3.6.1.4.1.37950.1.1.5.12.9.2.26.1
-- 1.3.6.1.4.1.37950.1.1.5.12.9.2.26.1
-- 1.3.6.1.4.1.37950.1.1.5.12.9.2.26.1
-- 1.3.6.1.4.1.37950.1.1.5.12.9.2.26.1
-- 1.3.6.1.4.1.37950.1.1.5.12.9.2.26.1
-- 1.3.6.1.4.1.37950.1.1.5.12.9.2.26.1
-- 1.3.6.1.4.1.37950.1.1.5.12.9.2.26.1
-- 1.3.6.1.4.1.37950.1.1.5.12.9.2.26.1
		-- 1.3.6.1.4.1.37950.1.1.5.12.9.2.26.1
		onuClassifyPFEntry OBJECT-TYPE
			SYNTAX OnuClassifyPFEntry
			MAX-ACCESS not-accessible
			STATUS current
			DESCRIPTION
				"Description."
			INDEX { onuClassifySrvId, cfyPortIndexS, ctcCfyPrecedenceS }
			::= { onuClassifyPFTable 1 }

		
		OnuClassifyPFEntry ::=
			SEQUENCE { 
				onuClassifySrvId
					Integer32,
				cfyPortIndexS
					INTEGER,
				ctcCfyPrecedenceS
					Integer32,
				ctcCfyPriS
					Integer32,
				ctcCfyDstMacEqualS
					INTEGER,
				ctcCfyDstMacValueS
					OCTET STRING,
				ctcCfySrcMacEqualS
					INTEGER,
				ctcCfySrcMacValueS
					OCTET STRING,
				ctcCfyVlanEqualS
					INTEGER,
				ctcCfyVlanValueS
					INTEGER,
				ctcCfyCosEqualS
					INTEGER,
				ctcCfyCosValueS
					INTEGER,
				ctcCfyEthTypeEqualS
					INTEGER,
				ctcCfyEthTypeValueS
					OCTET STRING,
				ctcCfySrcIpEqualS
					INTEGER,
				ctcCfySrcIpValueS
					IpAddress,
				ctcCfyDestIpEqualS
					INTEGER,
				ctcCfyDestIpValueS
					IpAddress,
				ctcCfyProEqualS
					INTEGER,
				ctcCfyProValueS
					INTEGER,
				ctcCfyTosDscpEuqalS
					INTEGER,
				ctcCfyTosDscpValueS
					INTEGER,
				ctcCfySrcPortEqualS
					INTEGER,
				ctcCfySrcPortValueS
					INTEGER,
				ctcCfyDestPortEqualS
					INTEGER,
				ctcCfyDestPortValueS
					INTEGER,
				onuCfyQueueS
					Integer32
			 }

--          1.3.6.1.4.1.37950.1.1.5.12.9.2.26.1.1
-- 1.3.6.1.4.1.37950.1.1.5.12.9.2.26.1.1
-- 1.3.6.1.4.1.37950.1.1.5.12.9.2.26.1.1
-- 1.3.6.1.4.1.37950.1.1.5.12.9.2.26.1.1
-- 1.3.6.1.4.1.37950.1.1.5.12.9.2.26.1.1
-- 1.3.6.1.4.1.37950.1.1.5.12.9.2.26.1.1
-- 1.3.6.1.4.1.37950.1.1.5.12.9.2.26.1.1
-- 1.3.6.1.4.1.37950.1.1.5.12.9.2.26.1.1
-- 1.3.6.1.4.1.37950.1.1.5.12.9.2.26.1.1
		-- 1.3.6.1.4.1.37950.1.1.5.12.9.2.26.1.1
		onuClassifySrvId OBJECT-TYPE
			SYNTAX Integer32 (0..65535)
			MAX-ACCESS read-only
			STATUS current
			DESCRIPTION
				"Description."
			::= { onuClassifyPFEntry 1 }

		
--          1.3.6.1.4.1.37950.1.1.5.12.9.2.26.1.2
-- 1.3.6.1.4.1.37950.1.1.5.12.9.2.26.1.2
-- 1.3.6.1.4.1.37950.1.1.5.12.9.2.26.1.2
-- 1.3.6.1.4.1.37950.1.1.5.12.9.2.26.1.2
-- 1.3.6.1.4.1.37950.1.1.5.12.9.2.26.1.2
-- 1.3.6.1.4.1.37950.1.1.5.12.9.2.26.1.2
-- 1.3.6.1.4.1.37950.1.1.5.12.9.2.26.1.2
-- 1.3.6.1.4.1.37950.1.1.5.12.9.2.26.1.2
-- 1.3.6.1.4.1.37950.1.1.5.12.9.2.26.1.2
		-- 1.3.6.1.4.1.37950.1.1.5.12.9.2.26.1.2
		cfyPortIndexS OBJECT-TYPE
			SYNTAX INTEGER (1..255)
			MAX-ACCESS read-only
			STATUS current
			DESCRIPTION
				"Description."
			::= { onuClassifyPFEntry 2 }

		
--          1.3.6.1.4.1.37950.1.1.5.12.9.2.26.1.3
-- 1.3.6.1.4.1.37950.1.1.5.12.9.2.26.1.3
-- 1.3.6.1.4.1.37950.1.1.5.12.9.2.26.1.3
-- 1.3.6.1.4.1.37950.1.1.5.12.9.2.26.1.3
-- 1.3.6.1.4.1.37950.1.1.5.12.9.2.26.1.3
-- 1.3.6.1.4.1.37950.1.1.5.12.9.2.26.1.3
-- 1.3.6.1.4.1.37950.1.1.5.12.9.2.26.1.3
-- 1.3.6.1.4.1.37950.1.1.5.12.9.2.26.1.3
-- 1.3.6.1.4.1.37950.1.1.5.12.9.2.26.1.3
		-- 1.3.6.1.4.1.37950.1.1.5.12.9.2.26.1.3
		ctcCfyPrecedenceS OBJECT-TYPE
			SYNTAX Integer32 (1..8)
			MAX-ACCESS read-only
			STATUS current
			DESCRIPTION
				"Description."
			::= { onuClassifyPFEntry 3 }

		
--          1.3.6.1.4.1.37950.1.1.5.12.9.2.26.1.4
-- 1.3.6.1.4.1.37950.1.1.5.12.9.2.26.1.4
-- 1.3.6.1.4.1.37950.1.1.5.12.9.2.26.1.4
-- 1.3.6.1.4.1.37950.1.1.5.12.9.2.26.1.4
-- 1.3.6.1.4.1.37950.1.1.5.12.9.2.26.1.4
-- 1.3.6.1.4.1.37950.1.1.5.12.9.2.26.1.4
-- 1.3.6.1.4.1.37950.1.1.5.12.9.2.26.1.4
-- 1.3.6.1.4.1.37950.1.1.5.12.9.2.26.1.4
-- 1.3.6.1.4.1.37950.1.1.5.12.9.2.26.1.4
		-- 1.3.6.1.4.1.37950.1.1.5.12.9.2.26.1.4
		ctcCfyPriS OBJECT-TYPE
			SYNTAX Integer32 (0..7)
			MAX-ACCESS read-only
			STATUS current
			DESCRIPTION
				"Description."
			::= { onuClassifyPFEntry 4 }

		
--          1.3.6.1.4.1.37950.1.1.5.12.9.2.26.1.5
-- 1.3.6.1.4.1.37950.1.1.5.12.9.2.26.1.5
-- 1.3.6.1.4.1.37950.1.1.5.12.9.2.26.1.5
-- 1.3.6.1.4.1.37950.1.1.5.12.9.2.26.1.5
-- 1.3.6.1.4.1.37950.1.1.5.12.9.2.26.1.5
-- 1.3.6.1.4.1.37950.1.1.5.12.9.2.26.1.5
-- 1.3.6.1.4.1.37950.1.1.5.12.9.2.26.1.5
-- 1.3.6.1.4.1.37950.1.1.5.12.9.2.26.1.5
-- 1.3.6.1.4.1.37950.1.1.5.12.9.2.26.1.5
		-- 1.3.6.1.4.1.37950.1.1.5.12.9.2.26.1.5
		ctcCfyDstMacEqualS OBJECT-TYPE
			SYNTAX INTEGER
				{
				init(0),
				equal(1),
				unequal(2)
				}
			MAX-ACCESS read-only
			STATUS current
			DESCRIPTION
				"Description."
			::= { onuClassifyPFEntry 5 }

		
--          1.3.6.1.4.1.37950.1.1.5.12.9.2.26.1.6
-- 1.3.6.1.4.1.37950.1.1.5.12.9.2.26.1.6
-- 1.3.6.1.4.1.37950.1.1.5.12.9.2.26.1.6
-- 1.3.6.1.4.1.37950.1.1.5.12.9.2.26.1.6
-- 1.3.6.1.4.1.37950.1.1.5.12.9.2.26.1.6
-- 1.3.6.1.4.1.37950.1.1.5.12.9.2.26.1.6
-- 1.3.6.1.4.1.37950.1.1.5.12.9.2.26.1.6
-- 1.3.6.1.4.1.37950.1.1.5.12.9.2.26.1.6
-- 1.3.6.1.4.1.37950.1.1.5.12.9.2.26.1.6
		-- 1.3.6.1.4.1.37950.1.1.5.12.9.2.26.1.6
		ctcCfyDstMacValueS OBJECT-TYPE
			SYNTAX OCTET STRING
			MAX-ACCESS read-only
			STATUS current
			DESCRIPTION
				"Description."
			::= { onuClassifyPFEntry 6 }

		
--          1.3.6.1.4.1.37950.1.1.5.12.9.2.26.1.7
-- 1.3.6.1.4.1.37950.1.1.5.12.9.2.26.1.7
-- 1.3.6.1.4.1.37950.1.1.5.12.9.2.26.1.7
-- 1.3.6.1.4.1.37950.1.1.5.12.9.2.26.1.7
-- 1.3.6.1.4.1.37950.1.1.5.12.9.2.26.1.7
-- 1.3.6.1.4.1.37950.1.1.5.12.9.2.26.1.7
-- 1.3.6.1.4.1.37950.1.1.5.12.9.2.26.1.7
-- 1.3.6.1.4.1.37950.1.1.5.12.9.2.26.1.7
-- 1.3.6.1.4.1.37950.1.1.5.12.9.2.26.1.7
		-- 1.3.6.1.4.1.37950.1.1.5.12.9.2.26.1.7
		ctcCfySrcMacEqualS OBJECT-TYPE
			SYNTAX INTEGER
				{
				init(0),
				equal(1),
				unequal(2)
				}
			MAX-ACCESS read-only
			STATUS current
			DESCRIPTION
				"Description."
			::= { onuClassifyPFEntry 7 }

		
--          1.3.6.1.4.1.37950.1.1.5.12.9.2.26.1.8
-- 1.3.6.1.4.1.37950.1.1.5.12.9.2.26.1.8
-- 1.3.6.1.4.1.37950.1.1.5.12.9.2.26.1.8
-- 1.3.6.1.4.1.37950.1.1.5.12.9.2.26.1.8
-- 1.3.6.1.4.1.37950.1.1.5.12.9.2.26.1.8
-- 1.3.6.1.4.1.37950.1.1.5.12.9.2.26.1.8
-- 1.3.6.1.4.1.37950.1.1.5.12.9.2.26.1.8
-- 1.3.6.1.4.1.37950.1.1.5.12.9.2.26.1.8
-- 1.3.6.1.4.1.37950.1.1.5.12.9.2.26.1.8
		-- 1.3.6.1.4.1.37950.1.1.5.12.9.2.26.1.8
		ctcCfySrcMacValueS OBJECT-TYPE
			SYNTAX OCTET STRING
			MAX-ACCESS read-only
			STATUS current
			DESCRIPTION
				"Description."
			::= { onuClassifyPFEntry 8 }

		
--          1.3.6.1.4.1.37950.1.1.5.12.9.2.26.1.9
-- 1.3.6.1.4.1.37950.1.1.5.12.9.2.26.1.9
-- 1.3.6.1.4.1.37950.1.1.5.12.9.2.26.1.9
-- 1.3.6.1.4.1.37950.1.1.5.12.9.2.26.1.9
-- 1.3.6.1.4.1.37950.1.1.5.12.9.2.26.1.9
-- 1.3.6.1.4.1.37950.1.1.5.12.9.2.26.1.9
-- 1.3.6.1.4.1.37950.1.1.5.12.9.2.26.1.9
-- 1.3.6.1.4.1.37950.1.1.5.12.9.2.26.1.9
-- 1.3.6.1.4.1.37950.1.1.5.12.9.2.26.1.9
		-- 1.3.6.1.4.1.37950.1.1.5.12.9.2.26.1.9
		ctcCfyVlanEqualS OBJECT-TYPE
			SYNTAX INTEGER
				{
				init(0),
				equal(1),
				unequal(2)
				}
			MAX-ACCESS read-only
			STATUS current
			DESCRIPTION
				"Description."
			::= { onuClassifyPFEntry 9 }

		
--          1.3.6.1.4.1.37950.1.1.5.12.9.2.26.1.10
-- 1.3.6.1.4.1.37950.1.1.5.12.9.2.26.1.10
-- 1.3.6.1.4.1.37950.1.1.5.12.9.2.26.1.10
-- 1.3.6.1.4.1.37950.1.1.5.12.9.2.26.1.10
-- 1.3.6.1.4.1.37950.1.1.5.12.9.2.26.1.10
-- 1.3.6.1.4.1.37950.1.1.5.12.9.2.26.1.10
-- 1.3.6.1.4.1.37950.1.1.5.12.9.2.26.1.10
-- 1.3.6.1.4.1.37950.1.1.5.12.9.2.26.1.10
-- 1.3.6.1.4.1.37950.1.1.5.12.9.2.26.1.10
		-- 1.3.6.1.4.1.37950.1.1.5.12.9.2.26.1.10
		ctcCfyVlanValueS OBJECT-TYPE
			SYNTAX INTEGER (0..4094)
			MAX-ACCESS read-only
			STATUS current
			DESCRIPTION
				"Description."
			::= { onuClassifyPFEntry 10 }

		
--          1.3.6.1.4.1.37950.1.1.5.12.9.2.26.1.11
-- 1.3.6.1.4.1.37950.1.1.5.12.9.2.26.1.11
-- 1.3.6.1.4.1.37950.1.1.5.12.9.2.26.1.11
-- 1.3.6.1.4.1.37950.1.1.5.12.9.2.26.1.11
-- 1.3.6.1.4.1.37950.1.1.5.12.9.2.26.1.11
-- 1.3.6.1.4.1.37950.1.1.5.12.9.2.26.1.11
-- 1.3.6.1.4.1.37950.1.1.5.12.9.2.26.1.11
-- 1.3.6.1.4.1.37950.1.1.5.12.9.2.26.1.11
-- 1.3.6.1.4.1.37950.1.1.5.12.9.2.26.1.11
		-- 1.3.6.1.4.1.37950.1.1.5.12.9.2.26.1.11
		ctcCfyCosEqualS OBJECT-TYPE
			SYNTAX INTEGER
				{
				init(0),
				equal(1),
				unequal(2)
				}
			MAX-ACCESS read-only
			STATUS current
			DESCRIPTION
				"Description."
			::= { onuClassifyPFEntry 11 }

		
--          1.3.6.1.4.1.37950.1.1.5.12.9.2.26.1.12
-- 1.3.6.1.4.1.37950.1.1.5.12.9.2.26.1.12
-- 1.3.6.1.4.1.37950.1.1.5.12.9.2.26.1.12
-- 1.3.6.1.4.1.37950.1.1.5.12.9.2.26.1.12
-- 1.3.6.1.4.1.37950.1.1.5.12.9.2.26.1.12
-- 1.3.6.1.4.1.37950.1.1.5.12.9.2.26.1.12
-- 1.3.6.1.4.1.37950.1.1.5.12.9.2.26.1.12
-- 1.3.6.1.4.1.37950.1.1.5.12.9.2.26.1.12
-- 1.3.6.1.4.1.37950.1.1.5.12.9.2.26.1.12
		-- 1.3.6.1.4.1.37950.1.1.5.12.9.2.26.1.12
		ctcCfyCosValueS OBJECT-TYPE
			SYNTAX INTEGER (-1..7)
			MAX-ACCESS read-only
			STATUS current
			DESCRIPTION
				"Description."
			::= { onuClassifyPFEntry 12 }

		
--          1.3.6.1.4.1.37950.1.1.5.12.9.2.26.1.13
-- 1.3.6.1.4.1.37950.1.1.5.12.9.2.26.1.13
-- 1.3.6.1.4.1.37950.1.1.5.12.9.2.26.1.13
-- 1.3.6.1.4.1.37950.1.1.5.12.9.2.26.1.13
-- 1.3.6.1.4.1.37950.1.1.5.12.9.2.26.1.13
-- 1.3.6.1.4.1.37950.1.1.5.12.9.2.26.1.13
-- 1.3.6.1.4.1.37950.1.1.5.12.9.2.26.1.13
-- 1.3.6.1.4.1.37950.1.1.5.12.9.2.26.1.13
-- 1.3.6.1.4.1.37950.1.1.5.12.9.2.26.1.13
		-- 1.3.6.1.4.1.37950.1.1.5.12.9.2.26.1.13
		ctcCfyEthTypeEqualS OBJECT-TYPE
			SYNTAX INTEGER
				{
				init(0),
				equal(1),
				unequal(2)
				}
			MAX-ACCESS read-only
			STATUS current
			DESCRIPTION
				"Description."
			::= { onuClassifyPFEntry 13 }

		
--          1.3.6.1.4.1.37950.1.1.5.12.9.2.26.1.14
-- 1.3.6.1.4.1.37950.1.1.5.12.9.2.26.1.14
-- 1.3.6.1.4.1.37950.1.1.5.12.9.2.26.1.14
-- 1.3.6.1.4.1.37950.1.1.5.12.9.2.26.1.14
-- 1.3.6.1.4.1.37950.1.1.5.12.9.2.26.1.14
-- 1.3.6.1.4.1.37950.1.1.5.12.9.2.26.1.14
-- 1.3.6.1.4.1.37950.1.1.5.12.9.2.26.1.14
-- 1.3.6.1.4.1.37950.1.1.5.12.9.2.26.1.14
-- 1.3.6.1.4.1.37950.1.1.5.12.9.2.26.1.14
		-- 1.3.6.1.4.1.37950.1.1.5.12.9.2.26.1.14
		ctcCfyEthTypeValueS OBJECT-TYPE
			SYNTAX OCTET STRING
			MAX-ACCESS read-only
			STATUS current
			DESCRIPTION
				"Description."
			::= { onuClassifyPFEntry 14 }

		
--          1.3.6.1.4.1.37950.1.1.5.12.9.2.26.1.15
-- 1.3.6.1.4.1.37950.1.1.5.12.9.2.26.1.15
-- 1.3.6.1.4.1.37950.1.1.5.12.9.2.26.1.15
-- 1.3.6.1.4.1.37950.1.1.5.12.9.2.26.1.15
-- 1.3.6.1.4.1.37950.1.1.5.12.9.2.26.1.15
-- 1.3.6.1.4.1.37950.1.1.5.12.9.2.26.1.15
-- 1.3.6.1.4.1.37950.1.1.5.12.9.2.26.1.15
-- 1.3.6.1.4.1.37950.1.1.5.12.9.2.26.1.15
-- 1.3.6.1.4.1.37950.1.1.5.12.9.2.26.1.15
		-- 1.3.6.1.4.1.37950.1.1.5.12.9.2.26.1.15
		ctcCfySrcIpEqualS OBJECT-TYPE
			SYNTAX INTEGER
				{
				init(0),
				equal(1),
				unequal(2)
				}
			MAX-ACCESS read-only
			STATUS current
			DESCRIPTION
				"Description."
			::= { onuClassifyPFEntry 15 }

		
--          1.3.6.1.4.1.37950.1.1.5.12.9.2.26.1.16
-- 1.3.6.1.4.1.37950.1.1.5.12.9.2.26.1.16
-- 1.3.6.1.4.1.37950.1.1.5.12.9.2.26.1.16
-- 1.3.6.1.4.1.37950.1.1.5.12.9.2.26.1.16
-- 1.3.6.1.4.1.37950.1.1.5.12.9.2.26.1.16
-- 1.3.6.1.4.1.37950.1.1.5.12.9.2.26.1.16
-- 1.3.6.1.4.1.37950.1.1.5.12.9.2.26.1.16
-- 1.3.6.1.4.1.37950.1.1.5.12.9.2.26.1.16
-- 1.3.6.1.4.1.37950.1.1.5.12.9.2.26.1.16
		-- 1.3.6.1.4.1.37950.1.1.5.12.9.2.26.1.16
		ctcCfySrcIpValueS OBJECT-TYPE
			SYNTAX IpAddress
			MAX-ACCESS read-only
			STATUS current
			DESCRIPTION
				"Description."
			::= { onuClassifyPFEntry 16 }

		
--          1.3.6.1.4.1.37950.1.1.5.12.9.2.26.1.17
-- 1.3.6.1.4.1.37950.1.1.5.12.9.2.26.1.17
-- 1.3.6.1.4.1.37950.1.1.5.12.9.2.26.1.17
-- 1.3.6.1.4.1.37950.1.1.5.12.9.2.26.1.17
-- 1.3.6.1.4.1.37950.1.1.5.12.9.2.26.1.17
-- 1.3.6.1.4.1.37950.1.1.5.12.9.2.26.1.17
-- 1.3.6.1.4.1.37950.1.1.5.12.9.2.26.1.17
-- 1.3.6.1.4.1.37950.1.1.5.12.9.2.26.1.17
-- 1.3.6.1.4.1.37950.1.1.5.12.9.2.26.1.17
		-- 1.3.6.1.4.1.37950.1.1.5.12.9.2.26.1.17
		ctcCfyDestIpEqualS OBJECT-TYPE
			SYNTAX INTEGER
				{
				init(0),
				equal(1),
				unequal(2)
				}
			MAX-ACCESS read-only
			STATUS current
			DESCRIPTION
				"Description."
			::= { onuClassifyPFEntry 17 }

		
--          1.3.6.1.4.1.37950.1.1.5.12.9.2.26.1.18
-- 1.3.6.1.4.1.37950.1.1.5.12.9.2.26.1.18
-- 1.3.6.1.4.1.37950.1.1.5.12.9.2.26.1.18
-- 1.3.6.1.4.1.37950.1.1.5.12.9.2.26.1.18
-- 1.3.6.1.4.1.37950.1.1.5.12.9.2.26.1.18
-- 1.3.6.1.4.1.37950.1.1.5.12.9.2.26.1.18
-- 1.3.6.1.4.1.37950.1.1.5.12.9.2.26.1.18
-- 1.3.6.1.4.1.37950.1.1.5.12.9.2.26.1.18
-- 1.3.6.1.4.1.37950.1.1.5.12.9.2.26.1.18
		-- 1.3.6.1.4.1.37950.1.1.5.12.9.2.26.1.18
		ctcCfyDestIpValueS OBJECT-TYPE
			SYNTAX IpAddress
			MAX-ACCESS read-only
			STATUS current
			DESCRIPTION
				"Description."
			::= { onuClassifyPFEntry 18 }

		
--          1.3.6.1.4.1.37950.1.1.5.12.9.2.26.1.19
-- 1.3.6.1.4.1.37950.1.1.5.12.9.2.26.1.19
-- 1.3.6.1.4.1.37950.1.1.5.12.9.2.26.1.19
-- 1.3.6.1.4.1.37950.1.1.5.12.9.2.26.1.19
-- 1.3.6.1.4.1.37950.1.1.5.12.9.2.26.1.19
-- 1.3.6.1.4.1.37950.1.1.5.12.9.2.26.1.19
-- 1.3.6.1.4.1.37950.1.1.5.12.9.2.26.1.19
-- 1.3.6.1.4.1.37950.1.1.5.12.9.2.26.1.19
-- 1.3.6.1.4.1.37950.1.1.5.12.9.2.26.1.19
		-- 1.3.6.1.4.1.37950.1.1.5.12.9.2.26.1.19
		ctcCfyProEqualS OBJECT-TYPE
			SYNTAX INTEGER
				{
				init(0),
				equal(1),
				unequal(2)
				}
			MAX-ACCESS read-only
			STATUS current
			DESCRIPTION
				"Description."
			::= { onuClassifyPFEntry 19 }

		
--          1.3.6.1.4.1.37950.1.1.5.12.9.2.26.1.20
-- 1.3.6.1.4.1.37950.1.1.5.12.9.2.26.1.20
-- 1.3.6.1.4.1.37950.1.1.5.12.9.2.26.1.20
-- 1.3.6.1.4.1.37950.1.1.5.12.9.2.26.1.20
-- 1.3.6.1.4.1.37950.1.1.5.12.9.2.26.1.20
-- 1.3.6.1.4.1.37950.1.1.5.12.9.2.26.1.20
-- 1.3.6.1.4.1.37950.1.1.5.12.9.2.26.1.20
-- 1.3.6.1.4.1.37950.1.1.5.12.9.2.26.1.20
-- 1.3.6.1.4.1.37950.1.1.5.12.9.2.26.1.20
		-- 1.3.6.1.4.1.37950.1.1.5.12.9.2.26.1.20
		ctcCfyProValueS OBJECT-TYPE
			SYNTAX INTEGER (-1..255)
			MAX-ACCESS read-only
			STATUS current
			DESCRIPTION
				"Description."
			::= { onuClassifyPFEntry 20 }

		
--          1.3.6.1.4.1.37950.1.1.5.12.9.2.26.1.21
-- 1.3.6.1.4.1.37950.1.1.5.12.9.2.26.1.21
-- 1.3.6.1.4.1.37950.1.1.5.12.9.2.26.1.21
-- 1.3.6.1.4.1.37950.1.1.5.12.9.2.26.1.21
-- 1.3.6.1.4.1.37950.1.1.5.12.9.2.26.1.21
-- 1.3.6.1.4.1.37950.1.1.5.12.9.2.26.1.21
-- 1.3.6.1.4.1.37950.1.1.5.12.9.2.26.1.21
-- 1.3.6.1.4.1.37950.1.1.5.12.9.2.26.1.21
-- 1.3.6.1.4.1.37950.1.1.5.12.9.2.26.1.21
		-- 1.3.6.1.4.1.37950.1.1.5.12.9.2.26.1.21
		ctcCfyTosDscpEuqalS OBJECT-TYPE
			SYNTAX INTEGER
				{
				init(0),
				equal(1),
				unequal(2)
				}
			MAX-ACCESS read-only
			STATUS current
			DESCRIPTION
				"Description."
			::= { onuClassifyPFEntry 21 }

		
--          1.3.6.1.4.1.37950.1.1.5.12.9.2.26.1.22
-- 1.3.6.1.4.1.37950.1.1.5.12.9.2.26.1.22
-- 1.3.6.1.4.1.37950.1.1.5.12.9.2.26.1.22
-- 1.3.6.1.4.1.37950.1.1.5.12.9.2.26.1.22
-- 1.3.6.1.4.1.37950.1.1.5.12.9.2.26.1.22
-- 1.3.6.1.4.1.37950.1.1.5.12.9.2.26.1.22
-- 1.3.6.1.4.1.37950.1.1.5.12.9.2.26.1.22
-- 1.3.6.1.4.1.37950.1.1.5.12.9.2.26.1.22
-- 1.3.6.1.4.1.37950.1.1.5.12.9.2.26.1.22
		-- 1.3.6.1.4.1.37950.1.1.5.12.9.2.26.1.22
		ctcCfyTosDscpValueS OBJECT-TYPE
			SYNTAX INTEGER (-1..255)
			MAX-ACCESS read-only
			STATUS current
			DESCRIPTION
				"Description."
			::= { onuClassifyPFEntry 22 }

		
--          1.3.6.1.4.1.37950.1.1.5.12.9.2.26.1.23
-- 1.3.6.1.4.1.37950.1.1.5.12.9.2.26.1.23
-- 1.3.6.1.4.1.37950.1.1.5.12.9.2.26.1.23
-- 1.3.6.1.4.1.37950.1.1.5.12.9.2.26.1.23
-- 1.3.6.1.4.1.37950.1.1.5.12.9.2.26.1.23
-- 1.3.6.1.4.1.37950.1.1.5.12.9.2.26.1.23
-- 1.3.6.1.4.1.37950.1.1.5.12.9.2.26.1.23
-- 1.3.6.1.4.1.37950.1.1.5.12.9.2.26.1.23
-- 1.3.6.1.4.1.37950.1.1.5.12.9.2.26.1.23
		-- 1.3.6.1.4.1.37950.1.1.5.12.9.2.26.1.23
		ctcCfySrcPortEqualS OBJECT-TYPE
			SYNTAX INTEGER
				{
				init(0),
				equal(1),
				unequal(2)
				}
			MAX-ACCESS read-only
			STATUS current
			DESCRIPTION
				"Description."
			::= { onuClassifyPFEntry 23 }

		
--          1.3.6.1.4.1.37950.1.1.5.12.9.2.26.1.24
-- 1.3.6.1.4.1.37950.1.1.5.12.9.2.26.1.24
-- 1.3.6.1.4.1.37950.1.1.5.12.9.2.26.1.24
-- 1.3.6.1.4.1.37950.1.1.5.12.9.2.26.1.24
-- 1.3.6.1.4.1.37950.1.1.5.12.9.2.26.1.24
-- 1.3.6.1.4.1.37950.1.1.5.12.9.2.26.1.24
-- 1.3.6.1.4.1.37950.1.1.5.12.9.2.26.1.24
-- 1.3.6.1.4.1.37950.1.1.5.12.9.2.26.1.24
-- 1.3.6.1.4.1.37950.1.1.5.12.9.2.26.1.24
		-- 1.3.6.1.4.1.37950.1.1.5.12.9.2.26.1.24
		ctcCfySrcPortValueS OBJECT-TYPE
			SYNTAX INTEGER (-1..65535)
			MAX-ACCESS read-only
			STATUS current
			DESCRIPTION
				"Description."
			::= { onuClassifyPFEntry 24 }

		
--          1.3.6.1.4.1.37950.1.1.5.12.9.2.26.1.25
-- 1.3.6.1.4.1.37950.1.1.5.12.9.2.26.1.25
-- 1.3.6.1.4.1.37950.1.1.5.12.9.2.26.1.25
-- 1.3.6.1.4.1.37950.1.1.5.12.9.2.26.1.25
-- 1.3.6.1.4.1.37950.1.1.5.12.9.2.26.1.25
-- 1.3.6.1.4.1.37950.1.1.5.12.9.2.26.1.25
-- 1.3.6.1.4.1.37950.1.1.5.12.9.2.26.1.25
-- 1.3.6.1.4.1.37950.1.1.5.12.9.2.26.1.25
-- 1.3.6.1.4.1.37950.1.1.5.12.9.2.26.1.25
		-- 1.3.6.1.4.1.37950.1.1.5.12.9.2.26.1.25
		ctcCfyDestPortEqualS OBJECT-TYPE
			SYNTAX INTEGER
				{
				init(0),
				equal(1),
				unequal(2)
				}
			MAX-ACCESS read-only
			STATUS current
			DESCRIPTION
				"Description."
			::= { onuClassifyPFEntry 25 }

		
--          1.3.6.1.4.1.37950.1.1.5.12.9.2.26.1.26
-- 1.3.6.1.4.1.37950.1.1.5.12.9.2.26.1.26
-- 1.3.6.1.4.1.37950.1.1.5.12.9.2.26.1.26
-- 1.3.6.1.4.1.37950.1.1.5.12.9.2.26.1.26
-- 1.3.6.1.4.1.37950.1.1.5.12.9.2.26.1.26
-- 1.3.6.1.4.1.37950.1.1.5.12.9.2.26.1.26
-- 1.3.6.1.4.1.37950.1.1.5.12.9.2.26.1.26
-- 1.3.6.1.4.1.37950.1.1.5.12.9.2.26.1.26
-- 1.3.6.1.4.1.37950.1.1.5.12.9.2.26.1.26
		-- 1.3.6.1.4.1.37950.1.1.5.12.9.2.26.1.26
		ctcCfyDestPortValueS OBJECT-TYPE
			SYNTAX INTEGER (-1..65535)
			MAX-ACCESS read-only
			STATUS current
			DESCRIPTION
				"Description."
			::= { onuClassifyPFEntry 26 }

		
--          1.3.6.1.4.1.37950.1.1.5.12.9.2.26.1.27
-- 1.3.6.1.4.1.37950.1.1.5.12.9.2.26.1.27
-- 1.3.6.1.4.1.37950.1.1.5.12.9.2.26.1.27
-- 1.3.6.1.4.1.37950.1.1.5.12.9.2.26.1.27
-- 1.3.6.1.4.1.37950.1.1.5.12.9.2.26.1.27
-- 1.3.6.1.4.1.37950.1.1.5.12.9.2.26.1.27
-- 1.3.6.1.4.1.37950.1.1.5.12.9.2.26.1.27
-- 1.3.6.1.4.1.37950.1.1.5.12.9.2.26.1.27
-- 1.3.6.1.4.1.37950.1.1.5.12.9.2.26.1.27
		-- 1.3.6.1.4.1.37950.1.1.5.12.9.2.26.1.27
		onuCfyQueueS OBJECT-TYPE
			SYNTAX Integer32 (0..7)
			MAX-ACCESS read-only
			STATUS current
			DESCRIPTION
				"Description."
			::= { onuClassifyPFEntry 27 }

		
--          1.3.6.1.4.1.37950.1.1.5.12.9.2.27
-- 1.3.6.1.4.1.37950.1.1.5.12.9.2.27
-- 1.3.6.1.4.1.37950.1.1.5.12.9.2.27
-- 1.3.6.1.4.1.37950.1.1.5.12.9.2.27
-- 1.3.6.1.4.1.37950.1.1.5.12.9.2.27
-- 1.3.6.1.4.1.37950.1.1.5.12.9.2.27
-- 1.3.6.1.4.1.37950.1.1.5.12.9.2.27
-- 1.3.6.1.4.1.37950.1.1.5.12.9.2.27
-- 1.3.6.1.4.1.37950.1.1.5.12.9.2.27
		-- 1.3.6.1.4.1.37950.1.1.5.12.9.2.27
		onuMacAgetimePFTable OBJECT-TYPE
			SYNTAX SEQUENCE OF OnuMacAgetimePFEntry
			MAX-ACCESS not-accessible
			STATUS current
			DESCRIPTION
				"Description."
			::= { srvProfileShow 27 }

		
--          1.3.6.1.4.1.37950.1.1.5.12.9.2.27.1
-- 1.3.6.1.4.1.37950.1.1.5.12.9.2.27.1
-- 1.3.6.1.4.1.37950.1.1.5.12.9.2.27.1
-- 1.3.6.1.4.1.37950.1.1.5.12.9.2.27.1
-- 1.3.6.1.4.1.37950.1.1.5.12.9.2.27.1
-- 1.3.6.1.4.1.37950.1.1.5.12.9.2.27.1
-- 1.3.6.1.4.1.37950.1.1.5.12.9.2.27.1
-- 1.3.6.1.4.1.37950.1.1.5.12.9.2.27.1
-- 1.3.6.1.4.1.37950.1.1.5.12.9.2.27.1
		-- 1.3.6.1.4.1.37950.1.1.5.12.9.2.27.1
		onuMacAgetimePFEntry OBJECT-TYPE
			SYNTAX OnuMacAgetimePFEntry
			MAX-ACCESS not-accessible
			STATUS current
			DESCRIPTION
				"Description."
			INDEX { onuMacAgetimeSrvId }
			::= { onuMacAgetimePFTable 1 }

		
		OnuMacAgetimePFEntry ::=
			SEQUENCE { 
				onuMacAgetimeSrvId
					Integer32,
				onuMacAgetimeS
					INTEGER
			 }

--          1.3.6.1.4.1.37950.1.1.5.12.9.2.27.1.1
-- 1.3.6.1.4.1.37950.1.1.5.12.9.2.27.1.1
-- 1.3.6.1.4.1.37950.1.1.5.12.9.2.27.1.1
-- 1.3.6.1.4.1.37950.1.1.5.12.9.2.27.1.1
-- 1.3.6.1.4.1.37950.1.1.5.12.9.2.27.1.1
-- 1.3.6.1.4.1.37950.1.1.5.12.9.2.27.1.1
-- 1.3.6.1.4.1.37950.1.1.5.12.9.2.27.1.1
-- 1.3.6.1.4.1.37950.1.1.5.12.9.2.27.1.1
-- 1.3.6.1.4.1.37950.1.1.5.12.9.2.27.1.1
		-- 1.3.6.1.4.1.37950.1.1.5.12.9.2.27.1.1
		onuMacAgetimeSrvId OBJECT-TYPE
			SYNTAX Integer32 (0..65535)
			MAX-ACCESS read-only
			STATUS current
			DESCRIPTION
				"Description."
			::= { onuMacAgetimePFEntry 1 }

		
--          1.3.6.1.4.1.37950.1.1.5.12.9.2.27.1.2
-- 1.3.6.1.4.1.37950.1.1.5.12.9.2.27.1.2
-- 1.3.6.1.4.1.37950.1.1.5.12.9.2.27.1.2
-- 1.3.6.1.4.1.37950.1.1.5.12.9.2.27.1.2
-- 1.3.6.1.4.1.37950.1.1.5.12.9.2.27.1.2
-- 1.3.6.1.4.1.37950.1.1.5.12.9.2.27.1.2
-- 1.3.6.1.4.1.37950.1.1.5.12.9.2.27.1.2
-- 1.3.6.1.4.1.37950.1.1.5.12.9.2.27.1.2
-- 1.3.6.1.4.1.37950.1.1.5.12.9.2.27.1.2
		-- 1.3.6.1.4.1.37950.1.1.5.12.9.2.27.1.2
		onuMacAgetimeS OBJECT-TYPE
			SYNTAX INTEGER (0..65535)
			MAX-ACCESS read-only
			STATUS current
			DESCRIPTION
				"Description."
			::= { onuMacAgetimePFEntry 2 }

		
--          1.3.6.1.4.1.37950.1.1.5.12.9.2.28
-- 1.3.6.1.4.1.37950.1.1.5.12.9.2.28
-- 1.3.6.1.4.1.37950.1.1.5.12.9.2.28
-- 1.3.6.1.4.1.37950.1.1.5.12.9.2.28
-- 1.3.6.1.4.1.37950.1.1.5.12.9.2.28
-- 1.3.6.1.4.1.37950.1.1.5.12.9.2.28
-- 1.3.6.1.4.1.37950.1.1.5.12.9.2.28
-- 1.3.6.1.4.1.37950.1.1.5.12.9.2.28
-- 1.3.6.1.4.1.37950.1.1.5.12.9.2.28
		-- 1.3.6.1.4.1.37950.1.1.5.12.9.2.28
		onuPonProtectPFTable OBJECT-TYPE
			SYNTAX SEQUENCE OF OnuPonProtectPFEntry
			MAX-ACCESS not-accessible
			STATUS current
			DESCRIPTION
				"Description."
			::= { srvProfileShow 28 }

		
--          1.3.6.1.4.1.37950.1.1.5.12.9.2.28.1
-- 1.3.6.1.4.1.37950.1.1.5.12.9.2.28.1
-- 1.3.6.1.4.1.37950.1.1.5.12.9.2.28.1
-- 1.3.6.1.4.1.37950.1.1.5.12.9.2.28.1
-- 1.3.6.1.4.1.37950.1.1.5.12.9.2.28.1
-- 1.3.6.1.4.1.37950.1.1.5.12.9.2.28.1
-- 1.3.6.1.4.1.37950.1.1.5.12.9.2.28.1
-- 1.3.6.1.4.1.37950.1.1.5.12.9.2.28.1
-- 1.3.6.1.4.1.37950.1.1.5.12.9.2.28.1
		-- 1.3.6.1.4.1.37950.1.1.5.12.9.2.28.1
		onuPonProtectPFEntry OBJECT-TYPE
			SYNTAX OnuPonProtectPFEntry
			MAX-ACCESS not-accessible
			STATUS current
			DESCRIPTION
				"Description."
			INDEX { onuPonProtectSrvId }
			::= { onuPonProtectPFTable 1 }

		
		OnuPonProtectPFEntry ::=
			SEQUENCE { 
				onuPonProtectSrvId
					Integer32,
				onuPonProtectLosOpS
					INTEGER,
				onuPonProtectLosMpcpS
					INTEGER
			 }

--          1.3.6.1.4.1.37950.1.1.5.12.9.2.28.1.1
-- 1.3.6.1.4.1.37950.1.1.5.12.9.2.28.1.1
-- 1.3.6.1.4.1.37950.1.1.5.12.9.2.28.1.1
-- 1.3.6.1.4.1.37950.1.1.5.12.9.2.28.1.1
-- 1.3.6.1.4.1.37950.1.1.5.12.9.2.28.1.1
-- 1.3.6.1.4.1.37950.1.1.5.12.9.2.28.1.1
-- 1.3.6.1.4.1.37950.1.1.5.12.9.2.28.1.1
-- 1.3.6.1.4.1.37950.1.1.5.12.9.2.28.1.1
-- 1.3.6.1.4.1.37950.1.1.5.12.9.2.28.1.1
		-- 1.3.6.1.4.1.37950.1.1.5.12.9.2.28.1.1
		onuPonProtectSrvId OBJECT-TYPE
			SYNTAX Integer32 (0..65535)
			MAX-ACCESS read-only
			STATUS current
			DESCRIPTION
				"Description."
			::= { onuPonProtectPFEntry 1 }

		
--          1.3.6.1.4.1.37950.1.1.5.12.9.2.28.1.2
-- 1.3.6.1.4.1.37950.1.1.5.12.9.2.28.1.2
-- 1.3.6.1.4.1.37950.1.1.5.12.9.2.28.1.2
-- 1.3.6.1.4.1.37950.1.1.5.12.9.2.28.1.2
-- 1.3.6.1.4.1.37950.1.1.5.12.9.2.28.1.2
-- 1.3.6.1.4.1.37950.1.1.5.12.9.2.28.1.2
-- 1.3.6.1.4.1.37950.1.1.5.12.9.2.28.1.2
-- 1.3.6.1.4.1.37950.1.1.5.12.9.2.28.1.2
-- 1.3.6.1.4.1.37950.1.1.5.12.9.2.28.1.2
		-- 1.3.6.1.4.1.37950.1.1.5.12.9.2.28.1.2
		onuPonProtectLosOpS OBJECT-TYPE
			SYNTAX INTEGER (0..65535)
			MAX-ACCESS read-only
			STATUS current
			DESCRIPTION
				"Description."
			::= { onuPonProtectPFEntry 2 }

		
--          1.3.6.1.4.1.37950.1.1.5.12.9.2.28.1.3
-- 1.3.6.1.4.1.37950.1.1.5.12.9.2.28.1.3
-- 1.3.6.1.4.1.37950.1.1.5.12.9.2.28.1.3
-- 1.3.6.1.4.1.37950.1.1.5.12.9.2.28.1.3
-- 1.3.6.1.4.1.37950.1.1.5.12.9.2.28.1.3
-- 1.3.6.1.4.1.37950.1.1.5.12.9.2.28.1.3
-- 1.3.6.1.4.1.37950.1.1.5.12.9.2.28.1.3
-- 1.3.6.1.4.1.37950.1.1.5.12.9.2.28.1.3
-- 1.3.6.1.4.1.37950.1.1.5.12.9.2.28.1.3
		-- 1.3.6.1.4.1.37950.1.1.5.12.9.2.28.1.3
		onuPonProtectLosMpcpS OBJECT-TYPE
			SYNTAX INTEGER (0..65535)
			MAX-ACCESS read-only
			STATUS current
			DESCRIPTION
				"Description."
			::= { onuPonProtectPFEntry 3 }

		
--          1.3.6.1.4.1.37950.1.1.5.12.9.2.29
-- 1.3.6.1.4.1.37950.1.1.5.12.9.2.29
-- 1.3.6.1.4.1.37950.1.1.5.12.9.2.29
-- 1.3.6.1.4.1.37950.1.1.5.12.9.2.29
-- 1.3.6.1.4.1.37950.1.1.5.12.9.2.29
-- 1.3.6.1.4.1.37950.1.1.5.12.9.2.29
-- 1.3.6.1.4.1.37950.1.1.5.12.9.2.29
-- 1.3.6.1.4.1.37950.1.1.5.12.9.2.29
-- 1.3.6.1.4.1.37950.1.1.5.12.9.2.29
		-- 1.3.6.1.4.1.37950.1.1.5.12.9.2.29
		onuPowerSavePFTable OBJECT-TYPE
			SYNTAX SEQUENCE OF OnuPowerSavePFEntry
			MAX-ACCESS not-accessible
			STATUS current
			DESCRIPTION
				"Description."
			::= { srvProfileShow 29 }

		
--          1.3.6.1.4.1.37950.1.1.5.12.9.2.29.1
-- 1.3.6.1.4.1.37950.1.1.5.12.9.2.29.1
-- 1.3.6.1.4.1.37950.1.1.5.12.9.2.29.1
-- 1.3.6.1.4.1.37950.1.1.5.12.9.2.29.1
-- 1.3.6.1.4.1.37950.1.1.5.12.9.2.29.1
-- 1.3.6.1.4.1.37950.1.1.5.12.9.2.29.1
-- 1.3.6.1.4.1.37950.1.1.5.12.9.2.29.1
-- 1.3.6.1.4.1.37950.1.1.5.12.9.2.29.1
-- 1.3.6.1.4.1.37950.1.1.5.12.9.2.29.1
		-- 1.3.6.1.4.1.37950.1.1.5.12.9.2.29.1
		onuPowerSavePFEntry OBJECT-TYPE
			SYNTAX OnuPowerSavePFEntry
			MAX-ACCESS not-accessible
			STATUS current
			DESCRIPTION
				"Description."
			INDEX { onuPowerSaveSrvId }
			::= { onuPowerSavePFTable 1 }

		
		OnuPowerSavePFEntry ::=
			SEQUENCE { 
				onuPowerSaveSrvId
					Integer32,
				onuPSEarlyWakeupS
					INTEGER,
				onuPSSleepDurationMaxS
					INTEGER
			 }

--          1.3.6.1.4.1.37950.1.1.5.12.9.2.29.1.1
-- 1.3.6.1.4.1.37950.1.1.5.12.9.2.29.1.1
-- 1.3.6.1.4.1.37950.1.1.5.12.9.2.29.1.1
-- 1.3.6.1.4.1.37950.1.1.5.12.9.2.29.1.1
-- 1.3.6.1.4.1.37950.1.1.5.12.9.2.29.1.1
-- 1.3.6.1.4.1.37950.1.1.5.12.9.2.29.1.1
-- 1.3.6.1.4.1.37950.1.1.5.12.9.2.29.1.1
-- 1.3.6.1.4.1.37950.1.1.5.12.9.2.29.1.1
-- 1.3.6.1.4.1.37950.1.1.5.12.9.2.29.1.1
		-- 1.3.6.1.4.1.37950.1.1.5.12.9.2.29.1.1
		onuPowerSaveSrvId OBJECT-TYPE
			SYNTAX Integer32 (0..65535)
			MAX-ACCESS read-only
			STATUS current
			DESCRIPTION
				"Description."
			::= { onuPowerSavePFEntry 1 }

		
--          1.3.6.1.4.1.37950.1.1.5.12.9.2.29.1.2
-- 1.3.6.1.4.1.37950.1.1.5.12.9.2.29.1.2
-- 1.3.6.1.4.1.37950.1.1.5.12.9.2.29.1.2
-- 1.3.6.1.4.1.37950.1.1.5.12.9.2.29.1.2
-- 1.3.6.1.4.1.37950.1.1.5.12.9.2.29.1.2
-- 1.3.6.1.4.1.37950.1.1.5.12.9.2.29.1.2
-- 1.3.6.1.4.1.37950.1.1.5.12.9.2.29.1.2
-- 1.3.6.1.4.1.37950.1.1.5.12.9.2.29.1.2
-- 1.3.6.1.4.1.37950.1.1.5.12.9.2.29.1.2
		-- 1.3.6.1.4.1.37950.1.1.5.12.9.2.29.1.2
		onuPSEarlyWakeupS OBJECT-TYPE
			SYNTAX INTEGER
				{
				disable(0),
				enable(1)
				}
			MAX-ACCESS read-only
			STATUS current
			DESCRIPTION
				"Description."
			::= { onuPowerSavePFEntry 2 }

		
--          1.3.6.1.4.1.37950.1.1.5.12.9.2.29.1.3
-- 1.3.6.1.4.1.37950.1.1.5.12.9.2.29.1.3
-- 1.3.6.1.4.1.37950.1.1.5.12.9.2.29.1.3
-- 1.3.6.1.4.1.37950.1.1.5.12.9.2.29.1.3
-- 1.3.6.1.4.1.37950.1.1.5.12.9.2.29.1.3
-- 1.3.6.1.4.1.37950.1.1.5.12.9.2.29.1.3
-- 1.3.6.1.4.1.37950.1.1.5.12.9.2.29.1.3
-- 1.3.6.1.4.1.37950.1.1.5.12.9.2.29.1.3
-- 1.3.6.1.4.1.37950.1.1.5.12.9.2.29.1.3
		-- 1.3.6.1.4.1.37950.1.1.5.12.9.2.29.1.3
		onuPSSleepDurationMaxS OBJECT-TYPE
			SYNTAX INTEGER (0..65535)
			MAX-ACCESS read-only
			STATUS current
			DESCRIPTION
				"Description."
			::= { onuPowerSavePFEntry 3 }

		
--          1.3.6.1.4.1.37950.1.1.5.12.9.2.30
-- 1.3.6.1.4.1.37950.1.1.5.12.9.2.30
-- 1.3.6.1.4.1.37950.1.1.5.12.9.2.30
-- 1.3.6.1.4.1.37950.1.1.5.12.9.2.30
-- 1.3.6.1.4.1.37950.1.1.5.12.9.2.30
-- 1.3.6.1.4.1.37950.1.1.5.12.9.2.30
-- 1.3.6.1.4.1.37950.1.1.5.12.9.2.30
-- 1.3.6.1.4.1.37950.1.1.5.12.9.2.30
-- 1.3.6.1.4.1.37950.1.1.5.12.9.2.30
		-- 1.3.6.1.4.1.37950.1.1.5.12.9.2.30
		onuSleepPFTable OBJECT-TYPE
			SYNTAX SEQUENCE OF OnuSleepPFEntry
			MAX-ACCESS not-accessible
			STATUS current
			DESCRIPTION
				"Description."
			::= { srvProfileShow 30 }

		
--          1.3.6.1.4.1.37950.1.1.5.12.9.2.30.1
-- 1.3.6.1.4.1.37950.1.1.5.12.9.2.30.1
-- 1.3.6.1.4.1.37950.1.1.5.12.9.2.30.1
-- 1.3.6.1.4.1.37950.1.1.5.12.9.2.30.1
-- 1.3.6.1.4.1.37950.1.1.5.12.9.2.30.1
-- 1.3.6.1.4.1.37950.1.1.5.12.9.2.30.1
-- 1.3.6.1.4.1.37950.1.1.5.12.9.2.30.1
-- 1.3.6.1.4.1.37950.1.1.5.12.9.2.30.1
-- 1.3.6.1.4.1.37950.1.1.5.12.9.2.30.1
		-- 1.3.6.1.4.1.37950.1.1.5.12.9.2.30.1
		onuSleepPFEntry OBJECT-TYPE
			SYNTAX OnuSleepPFEntry
			MAX-ACCESS not-accessible
			STATUS current
			DESCRIPTION
				"Description."
			INDEX { onuSleepSrvId }
			::= { onuSleepPFTable 1 }

		
		OnuSleepPFEntry ::=
			SEQUENCE { 
				onuSleepSrvId
					Integer32,
				onuSleepDurationS
					INTEGER,
				onuWakeDurationS
					INTEGER,
				onuSleepFlagS
					INTEGER,
				onuSleepModeS
					INTEGER
			 }

--          1.3.6.1.4.1.37950.1.1.5.12.9.2.30.1.1
-- 1.3.6.1.4.1.37950.1.1.5.12.9.2.30.1.1
-- 1.3.6.1.4.1.37950.1.1.5.12.9.2.30.1.1
-- 1.3.6.1.4.1.37950.1.1.5.12.9.2.30.1.1
-- 1.3.6.1.4.1.37950.1.1.5.12.9.2.30.1.1
-- 1.3.6.1.4.1.37950.1.1.5.12.9.2.30.1.1
-- 1.3.6.1.4.1.37950.1.1.5.12.9.2.30.1.1
-- 1.3.6.1.4.1.37950.1.1.5.12.9.2.30.1.1
-- 1.3.6.1.4.1.37950.1.1.5.12.9.2.30.1.1
		-- 1.3.6.1.4.1.37950.1.1.5.12.9.2.30.1.1
		onuSleepSrvId OBJECT-TYPE
			SYNTAX Integer32 (0..65535)
			MAX-ACCESS read-only
			STATUS current
			DESCRIPTION
				"Description."
			::= { onuSleepPFEntry 1 }

		
--          1.3.6.1.4.1.37950.1.1.5.12.9.2.30.1.2
-- 1.3.6.1.4.1.37950.1.1.5.12.9.2.30.1.2
-- 1.3.6.1.4.1.37950.1.1.5.12.9.2.30.1.2
-- 1.3.6.1.4.1.37950.1.1.5.12.9.2.30.1.2
-- 1.3.6.1.4.1.37950.1.1.5.12.9.2.30.1.2
-- 1.3.6.1.4.1.37950.1.1.5.12.9.2.30.1.2
-- 1.3.6.1.4.1.37950.1.1.5.12.9.2.30.1.2
-- 1.3.6.1.4.1.37950.1.1.5.12.9.2.30.1.2
-- 1.3.6.1.4.1.37950.1.1.5.12.9.2.30.1.2
		-- 1.3.6.1.4.1.37950.1.1.5.12.9.2.30.1.2
		onuSleepDurationS OBJECT-TYPE
			SYNTAX INTEGER (0..65535)
			MAX-ACCESS read-only
			STATUS current
			DESCRIPTION
				"Description."
			::= { onuSleepPFEntry 2 }

		
--          1.3.6.1.4.1.37950.1.1.5.12.9.2.30.1.3
-- 1.3.6.1.4.1.37950.1.1.5.12.9.2.30.1.3
-- 1.3.6.1.4.1.37950.1.1.5.12.9.2.30.1.3
-- 1.3.6.1.4.1.37950.1.1.5.12.9.2.30.1.3
-- 1.3.6.1.4.1.37950.1.1.5.12.9.2.30.1.3
-- 1.3.6.1.4.1.37950.1.1.5.12.9.2.30.1.3
-- 1.3.6.1.4.1.37950.1.1.5.12.9.2.30.1.3
-- 1.3.6.1.4.1.37950.1.1.5.12.9.2.30.1.3
-- 1.3.6.1.4.1.37950.1.1.5.12.9.2.30.1.3
		-- 1.3.6.1.4.1.37950.1.1.5.12.9.2.30.1.3
		onuWakeDurationS OBJECT-TYPE
			SYNTAX INTEGER (0..65535)
			MAX-ACCESS read-only
			STATUS current
			DESCRIPTION
				"Description."
			::= { onuSleepPFEntry 3 }

		
--          1.3.6.1.4.1.37950.1.1.5.12.9.2.30.1.4
-- 1.3.6.1.4.1.37950.1.1.5.12.9.2.30.1.4
-- 1.3.6.1.4.1.37950.1.1.5.12.9.2.30.1.4
-- 1.3.6.1.4.1.37950.1.1.5.12.9.2.30.1.4
-- 1.3.6.1.4.1.37950.1.1.5.12.9.2.30.1.4
-- 1.3.6.1.4.1.37950.1.1.5.12.9.2.30.1.4
-- 1.3.6.1.4.1.37950.1.1.5.12.9.2.30.1.4
-- 1.3.6.1.4.1.37950.1.1.5.12.9.2.30.1.4
-- 1.3.6.1.4.1.37950.1.1.5.12.9.2.30.1.4
		-- 1.3.6.1.4.1.37950.1.1.5.12.9.2.30.1.4
		onuSleepFlagS OBJECT-TYPE
			SYNTAX INTEGER
				{
				off(1),
				add(2),
				change(3)
				}
			MAX-ACCESS read-only
			STATUS current
			DESCRIPTION
				"Description."
			::= { onuSleepPFEntry 4 }

		
--          1.3.6.1.4.1.37950.1.1.5.12.9.2.30.1.5
-- 1.3.6.1.4.1.37950.1.1.5.12.9.2.30.1.5
-- 1.3.6.1.4.1.37950.1.1.5.12.9.2.30.1.5
-- 1.3.6.1.4.1.37950.1.1.5.12.9.2.30.1.5
-- 1.3.6.1.4.1.37950.1.1.5.12.9.2.30.1.5
-- 1.3.6.1.4.1.37950.1.1.5.12.9.2.30.1.5
-- 1.3.6.1.4.1.37950.1.1.5.12.9.2.30.1.5
-- 1.3.6.1.4.1.37950.1.1.5.12.9.2.30.1.5
-- 1.3.6.1.4.1.37950.1.1.5.12.9.2.30.1.5
		-- 1.3.6.1.4.1.37950.1.1.5.12.9.2.30.1.5
		onuSleepModeS OBJECT-TYPE
			SYNTAX INTEGER
				{
				none(1),
				tx-sleep-only(2),
				tx-and-rx-sleep(3)
				}
			MAX-ACCESS read-only
			STATUS current
			DESCRIPTION
				"Description."
			::= { onuSleepPFEntry 5 }

		
--          1.3.6.1.4.1.37950.1.1.5.12.9.2.31
-- 1.3.6.1.4.1.37950.1.1.5.12.9.2.31
-- 1.3.6.1.4.1.37950.1.1.5.12.9.2.31
-- 1.3.6.1.4.1.37950.1.1.5.12.9.2.31
-- 1.3.6.1.4.1.37950.1.1.5.12.9.2.31
-- 1.3.6.1.4.1.37950.1.1.5.12.9.2.31
-- 1.3.6.1.4.1.37950.1.1.5.12.9.2.31
-- 1.3.6.1.4.1.37950.1.1.5.12.9.2.31
-- 1.3.6.1.4.1.37950.1.1.5.12.9.2.31
		-- 1.3.6.1.4.1.37950.1.1.5.12.9.2.31
		onuDisableLoopPFTable OBJECT-TYPE
			SYNTAX SEQUENCE OF OnuDisableLoopPFEntry
			MAX-ACCESS not-accessible
			STATUS current
			DESCRIPTION
				"Description."
			::= { srvProfileShow 31 }

		
--          1.3.6.1.4.1.37950.1.1.5.12.9.2.31.1
-- 1.3.6.1.4.1.37950.1.1.5.12.9.2.31.1
-- 1.3.6.1.4.1.37950.1.1.5.12.9.2.31.1
-- 1.3.6.1.4.1.37950.1.1.5.12.9.2.31.1
-- 1.3.6.1.4.1.37950.1.1.5.12.9.2.31.1
-- 1.3.6.1.4.1.37950.1.1.5.12.9.2.31.1
-- 1.3.6.1.4.1.37950.1.1.5.12.9.2.31.1
-- 1.3.6.1.4.1.37950.1.1.5.12.9.2.31.1
-- 1.3.6.1.4.1.37950.1.1.5.12.9.2.31.1
		-- 1.3.6.1.4.1.37950.1.1.5.12.9.2.31.1
		onuDisableLoopPFEntry OBJECT-TYPE
			SYNTAX OnuDisableLoopPFEntry
			MAX-ACCESS not-accessible
			STATUS current
			DESCRIPTION
				"Description."
			INDEX { onuDisableLoopSrvId, disableLoopPortIndexS }
			::= { onuDisableLoopPFTable 1 }

		
		OnuDisableLoopPFEntry ::=
			SEQUENCE { 
				onuDisableLoopSrvId
					Integer32,
				disableLoopPortIndexS
					INTEGER,
				onuDisableLoopS
					INTEGER
			 }

--          1.3.6.1.4.1.37950.1.1.5.12.9.2.31.1.1
-- 1.3.6.1.4.1.37950.1.1.5.12.9.2.31.1.1
-- 1.3.6.1.4.1.37950.1.1.5.12.9.2.31.1.1
-- 1.3.6.1.4.1.37950.1.1.5.12.9.2.31.1.1
-- 1.3.6.1.4.1.37950.1.1.5.12.9.2.31.1.1
-- 1.3.6.1.4.1.37950.1.1.5.12.9.2.31.1.1
-- 1.3.6.1.4.1.37950.1.1.5.12.9.2.31.1.1
-- 1.3.6.1.4.1.37950.1.1.5.12.9.2.31.1.1
-- 1.3.6.1.4.1.37950.1.1.5.12.9.2.31.1.1
		-- 1.3.6.1.4.1.37950.1.1.5.12.9.2.31.1.1
		onuDisableLoopSrvId OBJECT-TYPE
			SYNTAX Integer32 (0..65535)
			MAX-ACCESS read-only
			STATUS current
			DESCRIPTION
				"Description."
			::= { onuDisableLoopPFEntry 1 }

		
--          1.3.6.1.4.1.37950.1.1.5.12.9.2.31.1.2
-- 1.3.6.1.4.1.37950.1.1.5.12.9.2.31.1.2
-- 1.3.6.1.4.1.37950.1.1.5.12.9.2.31.1.2
-- 1.3.6.1.4.1.37950.1.1.5.12.9.2.31.1.2
-- 1.3.6.1.4.1.37950.1.1.5.12.9.2.31.1.2
-- 1.3.6.1.4.1.37950.1.1.5.12.9.2.31.1.2
-- 1.3.6.1.4.1.37950.1.1.5.12.9.2.31.1.2
-- 1.3.6.1.4.1.37950.1.1.5.12.9.2.31.1.2
-- 1.3.6.1.4.1.37950.1.1.5.12.9.2.31.1.2
		-- 1.3.6.1.4.1.37950.1.1.5.12.9.2.31.1.2
		disableLoopPortIndexS OBJECT-TYPE
			SYNTAX INTEGER (1..255)
			MAX-ACCESS read-only
			STATUS current
			DESCRIPTION
				"Description."
			::= { onuDisableLoopPFEntry 2 }

		
--          1.3.6.1.4.1.37950.1.1.5.12.9.2.31.1.3
-- 1.3.6.1.4.1.37950.1.1.5.12.9.2.31.1.3
-- 1.3.6.1.4.1.37950.1.1.5.12.9.2.31.1.3
-- 1.3.6.1.4.1.37950.1.1.5.12.9.2.31.1.3
-- 1.3.6.1.4.1.37950.1.1.5.12.9.2.31.1.3
-- 1.3.6.1.4.1.37950.1.1.5.12.9.2.31.1.3
-- 1.3.6.1.4.1.37950.1.1.5.12.9.2.31.1.3
-- 1.3.6.1.4.1.37950.1.1.5.12.9.2.31.1.3
-- 1.3.6.1.4.1.37950.1.1.5.12.9.2.31.1.3
		-- 1.3.6.1.4.1.37950.1.1.5.12.9.2.31.1.3
		onuDisableLoopS OBJECT-TYPE
			SYNTAX INTEGER
				{
				disable(0),
				enable(1)
				}
			MAX-ACCESS read-only
			STATUS current
			DESCRIPTION
				"Description."
			::= { onuDisableLoopPFEntry 3 }

		
--          1.3.6.1.4.1.37950.1.1.5.12.9.2.32
-- 1.3.6.1.4.1.37950.1.1.5.12.9.2.32
-- 1.3.6.1.4.1.37950.1.1.5.12.9.2.32
-- 1.3.6.1.4.1.37950.1.1.5.12.9.2.32
-- 1.3.6.1.4.1.37950.1.1.5.12.9.2.32
-- 1.3.6.1.4.1.37950.1.1.5.12.9.2.32
-- 1.3.6.1.4.1.37950.1.1.5.12.9.2.32
-- 1.3.6.1.4.1.37950.1.1.5.12.9.2.32
-- 1.3.6.1.4.1.37950.1.1.5.12.9.2.32
		-- 1.3.6.1.4.1.37950.1.1.5.12.9.2.32
		onuPortStatPFTable OBJECT-TYPE
			SYNTAX SEQUENCE OF OnuPortStatPFEntry
			MAX-ACCESS not-accessible
			STATUS current
			DESCRIPTION
				"Description."
			::= { srvProfileShow 32 }

		
--          1.3.6.1.4.1.37950.1.1.5.12.9.2.32.1
-- 1.3.6.1.4.1.37950.1.1.5.12.9.2.32.1
-- 1.3.6.1.4.1.37950.1.1.5.12.9.2.32.1
-- 1.3.6.1.4.1.37950.1.1.5.12.9.2.32.1
-- 1.3.6.1.4.1.37950.1.1.5.12.9.2.32.1
-- 1.3.6.1.4.1.37950.1.1.5.12.9.2.32.1
-- 1.3.6.1.4.1.37950.1.1.5.12.9.2.32.1
-- 1.3.6.1.4.1.37950.1.1.5.12.9.2.32.1
-- 1.3.6.1.4.1.37950.1.1.5.12.9.2.32.1
		-- 1.3.6.1.4.1.37950.1.1.5.12.9.2.32.1
		onuPortStatPFEntry OBJECT-TYPE
			SYNTAX OnuPortStatPFEntry
			MAX-ACCESS not-accessible
			STATUS current
			DESCRIPTION
				"Description."
			INDEX { onuPortStatSrvId, onuPortStatPortIdS }
			::= { onuPortStatPFTable 1 }

		
		OnuPortStatPFEntry ::=
			SEQUENCE { 
				onuPortStatSrvId
					Integer32,
				onuPortStatPortIdS
					INTEGER,
				onuPortStatStatusS
					INTEGER,
				onuPortStatCountS
					INTEGER
			 }

--          1.3.6.1.4.1.37950.1.1.5.12.9.2.32.1.1
-- 1.3.6.1.4.1.37950.1.1.5.12.9.2.32.1.1
-- 1.3.6.1.4.1.37950.1.1.5.12.9.2.32.1.1
-- 1.3.6.1.4.1.37950.1.1.5.12.9.2.32.1.1
-- 1.3.6.1.4.1.37950.1.1.5.12.9.2.32.1.1
-- 1.3.6.1.4.1.37950.1.1.5.12.9.2.32.1.1
-- 1.3.6.1.4.1.37950.1.1.5.12.9.2.32.1.1
-- 1.3.6.1.4.1.37950.1.1.5.12.9.2.32.1.1
-- 1.3.6.1.4.1.37950.1.1.5.12.9.2.32.1.1
		-- 1.3.6.1.4.1.37950.1.1.5.12.9.2.32.1.1
		onuPortStatSrvId OBJECT-TYPE
			SYNTAX Integer32 (0..65535)
			MAX-ACCESS read-only
			STATUS current
			DESCRIPTION
				"Description."
			::= { onuPortStatPFEntry 1 }

		
--          1.3.6.1.4.1.37950.1.1.5.12.9.2.32.1.2
-- 1.3.6.1.4.1.37950.1.1.5.12.9.2.32.1.2
-- 1.3.6.1.4.1.37950.1.1.5.12.9.2.32.1.2
-- 1.3.6.1.4.1.37950.1.1.5.12.9.2.32.1.2
-- 1.3.6.1.4.1.37950.1.1.5.12.9.2.32.1.2
-- 1.3.6.1.4.1.37950.1.1.5.12.9.2.32.1.2
-- 1.3.6.1.4.1.37950.1.1.5.12.9.2.32.1.2
-- 1.3.6.1.4.1.37950.1.1.5.12.9.2.32.1.2
-- 1.3.6.1.4.1.37950.1.1.5.12.9.2.32.1.2
		-- 1.3.6.1.4.1.37950.1.1.5.12.9.2.32.1.2
		onuPortStatPortIdS OBJECT-TYPE
			SYNTAX INTEGER (0..255)
			MAX-ACCESS read-only
			STATUS current
			DESCRIPTION
				"Description."
			::= { onuPortStatPFEntry 2 }

		
--          1.3.6.1.4.1.37950.1.1.5.12.9.2.32.1.3
-- 1.3.6.1.4.1.37950.1.1.5.12.9.2.32.1.3
-- 1.3.6.1.4.1.37950.1.1.5.12.9.2.32.1.3
-- 1.3.6.1.4.1.37950.1.1.5.12.9.2.32.1.3
-- 1.3.6.1.4.1.37950.1.1.5.12.9.2.32.1.3
-- 1.3.6.1.4.1.37950.1.1.5.12.9.2.32.1.3
-- 1.3.6.1.4.1.37950.1.1.5.12.9.2.32.1.3
-- 1.3.6.1.4.1.37950.1.1.5.12.9.2.32.1.3
-- 1.3.6.1.4.1.37950.1.1.5.12.9.2.32.1.3
		-- 1.3.6.1.4.1.37950.1.1.5.12.9.2.32.1.3
		onuPortStatStatusS OBJECT-TYPE
			SYNTAX INTEGER
				{
				disable(0),
				enable(1)
				}
			MAX-ACCESS read-only
			STATUS current
			DESCRIPTION
				"Description."
			::= { onuPortStatPFEntry 3 }

		
--          1.3.6.1.4.1.37950.1.1.5.12.9.2.32.1.4
-- 1.3.6.1.4.1.37950.1.1.5.12.9.2.32.1.4
-- 1.3.6.1.4.1.37950.1.1.5.12.9.2.32.1.4
-- 1.3.6.1.4.1.37950.1.1.5.12.9.2.32.1.4
-- 1.3.6.1.4.1.37950.1.1.5.12.9.2.32.1.4
-- 1.3.6.1.4.1.37950.1.1.5.12.9.2.32.1.4
-- 1.3.6.1.4.1.37950.1.1.5.12.9.2.32.1.4
-- 1.3.6.1.4.1.37950.1.1.5.12.9.2.32.1.4
-- 1.3.6.1.4.1.37950.1.1.5.12.9.2.32.1.4
		-- 1.3.6.1.4.1.37950.1.1.5.12.9.2.32.1.4
		onuPortStatCountS OBJECT-TYPE
			SYNTAX INTEGER (0..65535)
			MAX-ACCESS read-only
			STATUS current
			DESCRIPTION
				"Description."
			::= { onuPortStatPFEntry 4 }

		
--          1.3.6.1.4.1.37950.1.1.5.12.9.2.33
-- 1.3.6.1.4.1.37950.1.1.5.12.9.2.33
-- 1.3.6.1.4.1.37950.1.1.5.12.9.2.33
-- 1.3.6.1.4.1.37950.1.1.5.12.9.2.33
-- 1.3.6.1.4.1.37950.1.1.5.12.9.2.33
-- 1.3.6.1.4.1.37950.1.1.5.12.9.2.33
-- 1.3.6.1.4.1.37950.1.1.5.12.9.2.33
-- 1.3.6.1.4.1.37950.1.1.5.12.9.2.33
-- 1.3.6.1.4.1.37950.1.1.5.12.9.2.33
		-- 1.3.6.1.4.1.37950.1.1.5.12.9.2.33
		onuPortStatClearPFTable OBJECT-TYPE
			SYNTAX SEQUENCE OF OnuPortStatClearPFEntry
			MAX-ACCESS not-accessible
			STATUS current
			DESCRIPTION
				"Description."
			::= { srvProfileShow 33 }

		
--          1.3.6.1.4.1.37950.1.1.5.12.9.2.33.1
-- 1.3.6.1.4.1.37950.1.1.5.12.9.2.33.1
-- 1.3.6.1.4.1.37950.1.1.5.12.9.2.33.1
-- 1.3.6.1.4.1.37950.1.1.5.12.9.2.33.1
-- 1.3.6.1.4.1.37950.1.1.5.12.9.2.33.1
-- 1.3.6.1.4.1.37950.1.1.5.12.9.2.33.1
-- 1.3.6.1.4.1.37950.1.1.5.12.9.2.33.1
-- 1.3.6.1.4.1.37950.1.1.5.12.9.2.33.1
-- 1.3.6.1.4.1.37950.1.1.5.12.9.2.33.1
		-- 1.3.6.1.4.1.37950.1.1.5.12.9.2.33.1
		onuPortStatClearPFEntry OBJECT-TYPE
			SYNTAX OnuPortStatClearPFEntry
			MAX-ACCESS not-accessible
			STATUS current
			DESCRIPTION
				"Description."
			INDEX { onuPortStatClearSrvId, onuPortStatClearPortIdS }
			::= { onuPortStatClearPFTable 1 }

		
		OnuPortStatClearPFEntry ::=
			SEQUENCE { 
				onuPortStatClearSrvId
					Integer32,
				onuPortStatClearPortIdS
					INTEGER
			 }

--          1.3.6.1.4.1.37950.1.1.5.12.9.2.33.1.1
-- 1.3.6.1.4.1.37950.1.1.5.12.9.2.33.1.1
-- 1.3.6.1.4.1.37950.1.1.5.12.9.2.33.1.1
-- 1.3.6.1.4.1.37950.1.1.5.12.9.2.33.1.1
-- 1.3.6.1.4.1.37950.1.1.5.12.9.2.33.1.1
-- 1.3.6.1.4.1.37950.1.1.5.12.9.2.33.1.1
-- 1.3.6.1.4.1.37950.1.1.5.12.9.2.33.1.1
-- 1.3.6.1.4.1.37950.1.1.5.12.9.2.33.1.1
-- 1.3.6.1.4.1.37950.1.1.5.12.9.2.33.1.1
		-- 1.3.6.1.4.1.37950.1.1.5.12.9.2.33.1.1
		onuPortStatClearSrvId OBJECT-TYPE
			SYNTAX Integer32 (0..65535)
			MAX-ACCESS read-write
			STATUS current
			DESCRIPTION
				"Description."
			::= { onuPortStatClearPFEntry 1 }

		
--          1.3.6.1.4.1.37950.1.1.5.12.9.2.33.1.2
-- 1.3.6.1.4.1.37950.1.1.5.12.9.2.33.1.2
-- 1.3.6.1.4.1.37950.1.1.5.12.9.2.33.1.2
-- 1.3.6.1.4.1.37950.1.1.5.12.9.2.33.1.2
-- 1.3.6.1.4.1.37950.1.1.5.12.9.2.33.1.2
-- 1.3.6.1.4.1.37950.1.1.5.12.9.2.33.1.2
-- 1.3.6.1.4.1.37950.1.1.5.12.9.2.33.1.2
-- 1.3.6.1.4.1.37950.1.1.5.12.9.2.33.1.2
-- 1.3.6.1.4.1.37950.1.1.5.12.9.2.33.1.2
		-- 1.3.6.1.4.1.37950.1.1.5.12.9.2.33.1.2
		onuPortStatClearPortIdS OBJECT-TYPE
			SYNTAX INTEGER (0..255)
			MAX-ACCESS read-write
			STATUS current
			DESCRIPTION
				"Description."
			::= { onuPortStatClearPFEntry 2 }

		
--          1.3.6.1.4.1.37950.1.1.5.12.9.2.34
-- 1.3.6.1.4.1.37950.1.1.5.12.9.2.34
-- 1.3.6.1.4.1.37950.1.1.5.12.9.2.34
-- 1.3.6.1.4.1.37950.1.1.5.12.9.2.34
-- 1.3.6.1.4.1.37950.1.1.5.12.9.2.34
-- 1.3.6.1.4.1.37950.1.1.5.12.9.2.34
-- 1.3.6.1.4.1.37950.1.1.5.12.9.2.34
-- 1.3.6.1.4.1.37950.1.1.5.12.9.2.34
-- 1.3.6.1.4.1.37950.1.1.5.12.9.2.34
		-- 1.3.6.1.4.1.37950.1.1.5.12.9.2.34
		onuIgmpAdminPFTable OBJECT-TYPE
			SYNTAX SEQUENCE OF OnuIgmpAdminPFEntry
			MAX-ACCESS not-accessible
			STATUS current
			DESCRIPTION
				"Description."
			::= { srvProfileShow 34 }

		
--          1.3.6.1.4.1.37950.1.1.5.12.9.2.34.1
-- 1.3.6.1.4.1.37950.1.1.5.12.9.2.34.1
-- 1.3.6.1.4.1.37950.1.1.5.12.9.2.34.1
-- 1.3.6.1.4.1.37950.1.1.5.12.9.2.34.1
-- 1.3.6.1.4.1.37950.1.1.5.12.9.2.34.1
-- 1.3.6.1.4.1.37950.1.1.5.12.9.2.34.1
-- 1.3.6.1.4.1.37950.1.1.5.12.9.2.34.1
-- 1.3.6.1.4.1.37950.1.1.5.12.9.2.34.1
-- 1.3.6.1.4.1.37950.1.1.5.12.9.2.34.1
		-- 1.3.6.1.4.1.37950.1.1.5.12.9.2.34.1
		onuIgmpAdminPFEntry OBJECT-TYPE
			SYNTAX OnuIgmpAdminPFEntry
			MAX-ACCESS not-accessible
			STATUS current
			DESCRIPTION
				"Description."
			INDEX { onuIgmpAdminSrvID }
			::= { onuIgmpAdminPFTable 1 }

		
		OnuIgmpAdminPFEntry ::=
			SEQUENCE { 
				onuIgmpAdminSrvID
					INTEGER,
				onuIgmpAdminEnableS
					INTEGER
			 }

--          1.3.6.1.4.1.37950.1.1.5.12.9.2.34.1.1
-- 1.3.6.1.4.1.37950.1.1.5.12.9.2.34.1.1
-- 1.3.6.1.4.1.37950.1.1.5.12.9.2.34.1.1
-- 1.3.6.1.4.1.37950.1.1.5.12.9.2.34.1.1
-- 1.3.6.1.4.1.37950.1.1.5.12.9.2.34.1.1
-- 1.3.6.1.4.1.37950.1.1.5.12.9.2.34.1.1
-- 1.3.6.1.4.1.37950.1.1.5.12.9.2.34.1.1
-- 1.3.6.1.4.1.37950.1.1.5.12.9.2.34.1.1
-- 1.3.6.1.4.1.37950.1.1.5.12.9.2.34.1.1
		-- 1.3.6.1.4.1.37950.1.1.5.12.9.2.34.1.1
		onuIgmpAdminSrvID OBJECT-TYPE
			SYNTAX INTEGER (0..65535)
			MAX-ACCESS read-write
			STATUS current
			DESCRIPTION
				"Description."
			::= { onuIgmpAdminPFEntry 1 }

		
--          1.3.6.1.4.1.37950.1.1.5.12.9.2.34.1.2
-- 1.3.6.1.4.1.37950.1.1.5.12.9.2.34.1.2
-- 1.3.6.1.4.1.37950.1.1.5.12.9.2.34.1.2
-- 1.3.6.1.4.1.37950.1.1.5.12.9.2.34.1.2
-- 1.3.6.1.4.1.37950.1.1.5.12.9.2.34.1.2
-- 1.3.6.1.4.1.37950.1.1.5.12.9.2.34.1.2
-- 1.3.6.1.4.1.37950.1.1.5.12.9.2.34.1.2
-- 1.3.6.1.4.1.37950.1.1.5.12.9.2.34.1.2
-- 1.3.6.1.4.1.37950.1.1.5.12.9.2.34.1.2
		-- 1.3.6.1.4.1.37950.1.1.5.12.9.2.34.1.2
		onuIgmpAdminEnableS OBJECT-TYPE
			SYNTAX INTEGER
				{
				disable(0),
				enable(1)
				}
			MAX-ACCESS read-write
			STATUS current
			DESCRIPTION
				"Description."
			::= { onuIgmpAdminPFEntry 2 }

		
--          1.3.6.1.4.1.37950.1.1.5.12.9.2.35
-- 1.3.6.1.4.1.37950.1.1.5.12.9.2.35
-- 1.3.6.1.4.1.37950.1.1.5.12.9.2.35
-- 1.3.6.1.4.1.37950.1.1.5.12.9.2.35
-- 1.3.6.1.4.1.37950.1.1.5.12.9.2.35
-- 1.3.6.1.4.1.37950.1.1.5.12.9.2.35
-- 1.3.6.1.4.1.37950.1.1.5.12.9.2.35
-- 1.3.6.1.4.1.37950.1.1.5.12.9.2.35
-- 1.3.6.1.4.1.37950.1.1.5.12.9.2.35
		-- 1.3.6.1.4.1.37950.1.1.5.12.9.2.35
		onuCatvStatusPFTable OBJECT-TYPE
			SYNTAX SEQUENCE OF OnuCatvStatusPFEntry
			MAX-ACCESS not-accessible
			STATUS current
			DESCRIPTION
				"Description."
			::= { srvProfileShow 35 }

		
--          1.3.6.1.4.1.37950.1.1.5.12.9.2.35.1
-- 1.3.6.1.4.1.37950.1.1.5.12.9.2.35.1
-- 1.3.6.1.4.1.37950.1.1.5.12.9.2.35.1
-- 1.3.6.1.4.1.37950.1.1.5.12.9.2.35.1
-- 1.3.6.1.4.1.37950.1.1.5.12.9.2.35.1
-- 1.3.6.1.4.1.37950.1.1.5.12.9.2.35.1
-- 1.3.6.1.4.1.37950.1.1.5.12.9.2.35.1
-- 1.3.6.1.4.1.37950.1.1.5.12.9.2.35.1
-- 1.3.6.1.4.1.37950.1.1.5.12.9.2.35.1
		-- 1.3.6.1.4.1.37950.1.1.5.12.9.2.35.1
		onuCatvStatusPFEntry OBJECT-TYPE
			SYNTAX OnuCatvStatusPFEntry
			MAX-ACCESS not-accessible
			STATUS current
			DESCRIPTION
				"Description."
			INDEX { onuCatvSatusSrvId }
			::= { onuCatvStatusPFTable 1 }

		
		OnuCatvStatusPFEntry ::=
			SEQUENCE { 
				onuCatvSatusSrvId
					INTEGER,
				onuCatvStatusS
					INTEGER
			 }

--          1.3.6.1.4.1.37950.1.1.5.12.9.2.35.1.1
-- 1.3.6.1.4.1.37950.1.1.5.12.9.2.35.1.1
-- 1.3.6.1.4.1.37950.1.1.5.12.9.2.35.1.1
-- 1.3.6.1.4.1.37950.1.1.5.12.9.2.35.1.1
-- 1.3.6.1.4.1.37950.1.1.5.12.9.2.35.1.1
-- 1.3.6.1.4.1.37950.1.1.5.12.9.2.35.1.1
-- 1.3.6.1.4.1.37950.1.1.5.12.9.2.35.1.1
-- 1.3.6.1.4.1.37950.1.1.5.12.9.2.35.1.1
-- 1.3.6.1.4.1.37950.1.1.5.12.9.2.35.1.1
		-- 1.3.6.1.4.1.37950.1.1.5.12.9.2.35.1.1
		onuCatvSatusSrvId OBJECT-TYPE
			SYNTAX INTEGER (0..65535)
			MAX-ACCESS read-write
			STATUS current
			DESCRIPTION
				"Description."
			::= { onuCatvStatusPFEntry 1 }

		
--          1.3.6.1.4.1.37950.1.1.5.12.9.2.35.1.2
-- 1.3.6.1.4.1.37950.1.1.5.12.9.2.35.1.2
-- 1.3.6.1.4.1.37950.1.1.5.12.9.2.35.1.2
-- 1.3.6.1.4.1.37950.1.1.5.12.9.2.35.1.2
-- 1.3.6.1.4.1.37950.1.1.5.12.9.2.35.1.2
-- 1.3.6.1.4.1.37950.1.1.5.12.9.2.35.1.2
-- 1.3.6.1.4.1.37950.1.1.5.12.9.2.35.1.2
-- 1.3.6.1.4.1.37950.1.1.5.12.9.2.35.1.2
-- 1.3.6.1.4.1.37950.1.1.5.12.9.2.35.1.2
		-- 1.3.6.1.4.1.37950.1.1.5.12.9.2.35.1.2
		onuCatvStatusS OBJECT-TYPE
			SYNTAX INTEGER
				{
				disable(0),
				enable(1)
				}
			MAX-ACCESS read-write
			STATUS current
			DESCRIPTION
				"Description."
			::= { onuCatvStatusPFEntry 2 }

		
--          1.3.6.1.4.1.37950.1.1.5.12.9.2.36
-- 1.3.6.1.4.1.37950.1.1.5.12.9.2.36
-- 1.3.6.1.4.1.37950.1.1.5.12.9.2.36
-- 1.3.6.1.4.1.37950.1.1.5.12.9.2.36
-- 1.3.6.1.4.1.37950.1.1.5.12.9.2.36
-- 1.3.6.1.4.1.37950.1.1.5.12.9.2.36
-- 1.3.6.1.4.1.37950.1.1.5.12.9.2.36
-- 1.3.6.1.4.1.37950.1.1.5.12.9.2.36
-- 1.3.6.1.4.1.37950.1.1.5.12.9.2.36
		-- 1.3.6.1.4.1.37950.1.1.5.12.9.2.36
		onuCtcoamSkipPFTable OBJECT-TYPE
			SYNTAX SEQUENCE OF OnuCtcoamSkipPFEntry
			MAX-ACCESS not-accessible
			STATUS current
			DESCRIPTION
				"Description."
			::= { srvProfileShow 36 }

		
--          1.3.6.1.4.1.37950.1.1.5.12.9.2.36.1
-- 1.3.6.1.4.1.37950.1.1.5.12.9.2.36.1
-- 1.3.6.1.4.1.37950.1.1.5.12.9.2.36.1
-- 1.3.6.1.4.1.37950.1.1.5.12.9.2.36.1
-- 1.3.6.1.4.1.37950.1.1.5.12.9.2.36.1
-- 1.3.6.1.4.1.37950.1.1.5.12.9.2.36.1
-- 1.3.6.1.4.1.37950.1.1.5.12.9.2.36.1
-- 1.3.6.1.4.1.37950.1.1.5.12.9.2.36.1
-- 1.3.6.1.4.1.37950.1.1.5.12.9.2.36.1
		-- 1.3.6.1.4.1.37950.1.1.5.12.9.2.36.1
		onuCtcoamSkipPFEntry OBJECT-TYPE
			SYNTAX OnuCtcoamSkipPFEntry
			MAX-ACCESS not-accessible
			STATUS current
			DESCRIPTION
				"Description."
			INDEX { onuCtcOamSkipSrvId }
			::= { onuCtcoamSkipPFTable 1 }

		
		OnuCtcoamSkipPFEntry ::=
			SEQUENCE { 
				onuCtcOamSkipSrvId
					INTEGER,
				onuCtcoamSkipS
					INTEGER
			 }

--          1.3.6.1.4.1.37950.1.1.5.12.9.2.36.1.1
-- 1.3.6.1.4.1.37950.1.1.5.12.9.2.36.1.1
-- 1.3.6.1.4.1.37950.1.1.5.12.9.2.36.1.1
-- 1.3.6.1.4.1.37950.1.1.5.12.9.2.36.1.1
-- 1.3.6.1.4.1.37950.1.1.5.12.9.2.36.1.1
-- 1.3.6.1.4.1.37950.1.1.5.12.9.2.36.1.1
-- 1.3.6.1.4.1.37950.1.1.5.12.9.2.36.1.1
-- 1.3.6.1.4.1.37950.1.1.5.12.9.2.36.1.1
-- 1.3.6.1.4.1.37950.1.1.5.12.9.2.36.1.1
		-- 1.3.6.1.4.1.37950.1.1.5.12.9.2.36.1.1
		onuCtcOamSkipSrvId OBJECT-TYPE
			SYNTAX INTEGER (0..65535)
			MAX-ACCESS read-write
			STATUS current
			DESCRIPTION
				"Description."
			::= { onuCtcoamSkipPFEntry 1 }

		
--          1.3.6.1.4.1.37950.1.1.5.12.9.2.36.1.2
-- 1.3.6.1.4.1.37950.1.1.5.12.9.2.36.1.2
-- 1.3.6.1.4.1.37950.1.1.5.12.9.2.36.1.2
-- 1.3.6.1.4.1.37950.1.1.5.12.9.2.36.1.2
-- 1.3.6.1.4.1.37950.1.1.5.12.9.2.36.1.2
-- 1.3.6.1.4.1.37950.1.1.5.12.9.2.36.1.2
-- 1.3.6.1.4.1.37950.1.1.5.12.9.2.36.1.2
-- 1.3.6.1.4.1.37950.1.1.5.12.9.2.36.1.2
-- 1.3.6.1.4.1.37950.1.1.5.12.9.2.36.1.2
		-- 1.3.6.1.4.1.37950.1.1.5.12.9.2.36.1.2
		onuCtcoamSkipS OBJECT-TYPE
			SYNTAX INTEGER
				{
				disable(0),
				enable(1)
				}
			MAX-ACCESS read-write
			STATUS current
			DESCRIPTION
				"Description."
			::= { onuCtcoamSkipPFEntry 2 }

		
--          1.3.6.1.4.1.37950.1.1.5.12.9.2.37
-- 1.3.6.1.4.1.37950.1.1.5.12.9.2.37
-- 1.3.6.1.4.1.37950.1.1.5.12.9.2.37
-- 1.3.6.1.4.1.37950.1.1.5.12.9.2.37
-- 1.3.6.1.4.1.37950.1.1.5.12.9.2.37
-- 1.3.6.1.4.1.37950.1.1.5.12.9.2.37
-- 1.3.6.1.4.1.37950.1.1.5.12.9.2.37
-- 1.3.6.1.4.1.37950.1.1.5.12.9.2.37
-- 1.3.6.1.4.1.37950.1.1.5.12.9.2.37
		-- 1.3.6.1.4.1.37950.1.1.5.12.9.2.37
		onuWifiSwichPFTable OBJECT-TYPE
			SYNTAX SEQUENCE OF OnuWifiSwichPFEntry
			MAX-ACCESS not-accessible
			STATUS current
			DESCRIPTION
				"Description."
			::= { srvProfileShow 37 }

		
--          1.3.6.1.4.1.37950.1.1.5.12.9.2.37.1
-- 1.3.6.1.4.1.37950.1.1.5.12.9.2.37.1
-- 1.3.6.1.4.1.37950.1.1.5.12.9.2.37.1
-- 1.3.6.1.4.1.37950.1.1.5.12.9.2.37.1
-- 1.3.6.1.4.1.37950.1.1.5.12.9.2.37.1
-- 1.3.6.1.4.1.37950.1.1.5.12.9.2.37.1
-- 1.3.6.1.4.1.37950.1.1.5.12.9.2.37.1
-- 1.3.6.1.4.1.37950.1.1.5.12.9.2.37.1
-- 1.3.6.1.4.1.37950.1.1.5.12.9.2.37.1
		-- 1.3.6.1.4.1.37950.1.1.5.12.9.2.37.1
		onuWifiSwichPFEntry OBJECT-TYPE
			SYNTAX OnuWifiSwichPFEntry
			MAX-ACCESS not-accessible
			STATUS current
			DESCRIPTION
				"Description."
			INDEX { onuWifiSwichSrvId }
			::= { onuWifiSwichPFTable 1 }

		
		OnuWifiSwichPFEntry ::=
			SEQUENCE { 
				onuWifiSwichSrvId
					INTEGER,
				onuWifiSwichActive
					INTEGER,
				onuWifiSwichAPModuleS
					INTEGER,
				onuWifiSwichCountry
					INTEGER,
				onuWifiSwichChannelS
					INTEGER,
				onuWifiSwichStandardS
					INTEGER,
				onuWifiSwitchPower
					INTEGER,
				onuWifiSwichChannelWidth
					INTEGER
			 }

--          1.3.6.1.4.1.37950.1.1.5.12.9.2.37.1.1
-- 1.3.6.1.4.1.37950.1.1.5.12.9.2.37.1.1
-- 1.3.6.1.4.1.37950.1.1.5.12.9.2.37.1.1
-- 1.3.6.1.4.1.37950.1.1.5.12.9.2.37.1.1
-- 1.3.6.1.4.1.37950.1.1.5.12.9.2.37.1.1
-- 1.3.6.1.4.1.37950.1.1.5.12.9.2.37.1.1
-- 1.3.6.1.4.1.37950.1.1.5.12.9.2.37.1.1
-- 1.3.6.1.4.1.37950.1.1.5.12.9.2.37.1.1
-- 1.3.6.1.4.1.37950.1.1.5.12.9.2.37.1.1
		-- 1.3.6.1.4.1.37950.1.1.5.12.9.2.37.1.1
		onuWifiSwichSrvId OBJECT-TYPE
			SYNTAX INTEGER (0..65535)
			MAX-ACCESS read-write
			STATUS current
			DESCRIPTION
				"Description."
			::= { onuWifiSwichPFEntry 1 }

		
--          1.3.6.1.4.1.37950.1.1.5.12.9.2.37.1.2
-- 1.3.6.1.4.1.37950.1.1.5.12.9.2.37.1.2
-- 1.3.6.1.4.1.37950.1.1.5.12.9.2.37.1.2
-- 1.3.6.1.4.1.37950.1.1.5.12.9.2.37.1.2
-- 1.3.6.1.4.1.37950.1.1.5.12.9.2.37.1.2
-- 1.3.6.1.4.1.37950.1.1.5.12.9.2.37.1.2
-- 1.3.6.1.4.1.37950.1.1.5.12.9.2.37.1.2
-- 1.3.6.1.4.1.37950.1.1.5.12.9.2.37.1.2
		-- 1.3.6.1.4.1.37950.1.1.5.12.9.2.37.1.2
		onuWifiSwichActive OBJECT-TYPE
			SYNTAX INTEGER
				{
				deactive(0),
				active(1)
				}
			MAX-ACCESS read-write
			STATUS current
			DESCRIPTION
				"Description."
			::= { onuWifiSwichPFEntry 2 }

		
--         1.3.6.1.4.1.37950.1.1.5.12.9.2.37.1.3
-- 1.3.6.1.4.1.37950.1.1.5.12.9.2.37.1.3
-- 1.3.6.1.4.1.37950.1.1.5.12.9.2.37.1.3
-- 1.3.6.1.4.1.37950.1.1.5.12.9.2.37.1.3
-- 1.3.6.1.4.1.37950.1.1.5.12.9.2.37.1.3
-- 1.3.6.1.4.1.37950.1.1.5.12.9.2.37.1.3
-- 1.3.6.1.4.1.37950.1.1.5.12.9.2.37.1.3
-- 1.3.6.1.4.1.37950.1.1.5.12.9.2.37.1.3
		-- 1.3.6.1.4.1.37950.1.1.5.12.9.2.37.1.3
		onuWifiSwichAPModuleS OBJECT-TYPE
			SYNTAX INTEGER
				{
				disable(0),
				enable(1)
				}
			MAX-ACCESS read-write
			STATUS current
			DESCRIPTION
				"Description."
			::= { onuWifiSwichPFEntry 3 }

		
--         1.3.6.1.4.1.37950.1.1.5.12.9.2.37.1.4
-- 1.3.6.1.4.1.37950.1.1.5.12.9.2.37.1.4
-- 1.3.6.1.4.1.37950.1.1.5.12.9.2.37.1.4
-- 1.3.6.1.4.1.37950.1.1.5.12.9.2.37.1.4
-- 1.3.6.1.4.1.37950.1.1.5.12.9.2.37.1.4
-- 1.3.6.1.4.1.37950.1.1.5.12.9.2.37.1.4
-- 1.3.6.1.4.1.37950.1.1.5.12.9.2.37.1.4
-- 1.3.6.1.4.1.37950.1.1.5.12.9.2.37.1.4
		-- 1.3.6.1.4.1.37950.1.1.5.12.9.2.37.1.4
		onuWifiSwichCountry OBJECT-TYPE
			SYNTAX INTEGER
				{
				etsi(0),
				fcc(1),
				ic(2),
				spain(3),
				france(4),
				mkk(5),
				isreal(6),
				mkk2(7),
				mkk3(8),
				russian(9),
				cn(10),
				global(11),
				world-wide(12),
				mkk1(13),
				ncc(14)
				}
			MAX-ACCESS read-write
			STATUS current
			DESCRIPTION
				"Description."
			::= { onuWifiSwichPFEntry 4 }

		
--         1.3.6.1.4.1.37950.1.1.5.12.9.2.37.1.5
-- 1.3.6.1.4.1.37950.1.1.5.12.9.2.37.1.5
-- 1.3.6.1.4.1.37950.1.1.5.12.9.2.37.1.5
-- 1.3.6.1.4.1.37950.1.1.5.12.9.2.37.1.5
-- 1.3.6.1.4.1.37950.1.1.5.12.9.2.37.1.5
-- 1.3.6.1.4.1.37950.1.1.5.12.9.2.37.1.5
-- 1.3.6.1.4.1.37950.1.1.5.12.9.2.37.1.5
-- 1.3.6.1.4.1.37950.1.1.5.12.9.2.37.1.5
		-- 1.3.6.1.4.1.37950.1.1.5.12.9.2.37.1.5
		onuWifiSwichChannelS OBJECT-TYPE
			SYNTAX INTEGER (0..13)
			MAX-ACCESS read-write
			STATUS current
			DESCRIPTION
				"Description."
			::= { onuWifiSwichPFEntry 5 }

		
--         1.3.6.1.4.1.37950.1.1.5.12.9.2.37.1.6
-- 1.3.6.1.4.1.37950.1.1.5.12.9.2.37.1.6
-- 1.3.6.1.4.1.37950.1.1.5.12.9.2.37.1.6
-- 1.3.6.1.4.1.37950.1.1.5.12.9.2.37.1.6
-- 1.3.6.1.4.1.37950.1.1.5.12.9.2.37.1.6
-- 1.3.6.1.4.1.37950.1.1.5.12.9.2.37.1.6
-- 1.3.6.1.4.1.37950.1.1.5.12.9.2.37.1.6
-- 1.3.6.1.4.1.37950.1.1.5.12.9.2.37.1.6
		-- 1.3.6.1.4.1.37950.1.1.5.12.9.2.37.1.6
		onuWifiSwichStandardS OBJECT-TYPE
			SYNTAX INTEGER
				{
				s80211b(0),
				s80211g(1),
				s80211bg(2),
				s80211n(3),
				s80211bgn(4),
				s80211ax(5),
				s80211bgnax(6)
				}
			MAX-ACCESS read-write
			STATUS current
			DESCRIPTION
				"Description."
			::= { onuWifiSwichPFEntry 6 }

		
--         1.3.6.1.4.1.37950.1.1.5.12.9.2.37.1.7
-- 1.3.6.1.4.1.37950.1.1.5.12.9.2.37.1.7
-- 1.3.6.1.4.1.37950.1.1.5.12.9.2.37.1.7
-- 1.3.6.1.4.1.37950.1.1.5.12.9.2.37.1.7
-- 1.3.6.1.4.1.37950.1.1.5.12.9.2.37.1.7
-- 1.3.6.1.4.1.37950.1.1.5.12.9.2.37.1.7
-- 1.3.6.1.4.1.37950.1.1.5.12.9.2.37.1.7
-- 1.3.6.1.4.1.37950.1.1.5.12.9.2.37.1.7
		-- 1.3.6.1.4.1.37950.1.1.5.12.9.2.37.1.7
		onuWifiSwitchPower OBJECT-TYPE
			SYNTAX INTEGER (0..20)
			MAX-ACCESS read-write
			STATUS current
			DESCRIPTION
				"Description."
			::= { onuWifiSwichPFEntry 7 }

		
--         1.3.6.1.4.1.37950.1.1.5.12.9.2.37.1.8
-- 1.3.6.1.4.1.37950.1.1.5.12.9.2.37.1.8
-- 1.3.6.1.4.1.37950.1.1.5.12.9.2.37.1.8
-- 1.3.6.1.4.1.37950.1.1.5.12.9.2.37.1.8
-- 1.3.6.1.4.1.37950.1.1.5.12.9.2.37.1.8
-- 1.3.6.1.4.1.37950.1.1.5.12.9.2.37.1.8
-- 1.3.6.1.4.1.37950.1.1.5.12.9.2.37.1.8
-- 1.3.6.1.4.1.37950.1.1.5.12.9.2.37.1.8
		-- 1.3.6.1.4.1.37950.1.1.5.12.9.2.37.1.8
		onuWifiSwichChannelWidth OBJECT-TYPE
			SYNTAX INTEGER
				{
				s20(0),
				s40(1),
				s20-40(3)
				}
			MAX-ACCESS read-write
			STATUS current
			DESCRIPTION
				"Description."
			::= { onuWifiSwichPFEntry 8 }

		
--          1.3.6.1.4.1.37950.1.1.5.12.9.2.38
-- 1.3.6.1.4.1.37950.1.1.5.12.9.2.38
-- 1.3.6.1.4.1.37950.1.1.5.12.9.2.38
-- 1.3.6.1.4.1.37950.1.1.5.12.9.2.38
-- 1.3.6.1.4.1.37950.1.1.5.12.9.2.38
-- 1.3.6.1.4.1.37950.1.1.5.12.9.2.38
-- 1.3.6.1.4.1.37950.1.1.5.12.9.2.38
-- 1.3.6.1.4.1.37950.1.1.5.12.9.2.38
-- 1.3.6.1.4.1.37950.1.1.5.12.9.2.38
		-- 1.3.6.1.4.1.37950.1.1.5.12.9.2.38
		onuWifiSsidPFTable OBJECT-TYPE
			SYNTAX SEQUENCE OF OnuWifiSsidPFEntry
			MAX-ACCESS not-accessible
			STATUS current
			DESCRIPTION
				"Description."
			::= { srvProfileShow 38 }

		
--          1.3.6.1.4.1.37950.1.1.5.12.9.2.38.1
-- 1.3.6.1.4.1.37950.1.1.5.12.9.2.38.1
-- 1.3.6.1.4.1.37950.1.1.5.12.9.2.38.1
-- 1.3.6.1.4.1.37950.1.1.5.12.9.2.38.1
-- 1.3.6.1.4.1.37950.1.1.5.12.9.2.38.1
-- 1.3.6.1.4.1.37950.1.1.5.12.9.2.38.1
-- 1.3.6.1.4.1.37950.1.1.5.12.9.2.38.1
-- 1.3.6.1.4.1.37950.1.1.5.12.9.2.38.1
-- 1.3.6.1.4.1.37950.1.1.5.12.9.2.38.1
		-- 1.3.6.1.4.1.37950.1.1.5.12.9.2.38.1
		onuWifiSsidPFEntry OBJECT-TYPE
			SYNTAX OnuWifiSsidPFEntry
			MAX-ACCESS not-accessible
			STATUS current
			DESCRIPTION
				"Description."
			INDEX { onuWifiSsidSrvId, onuWifiSsidIdS }
			::= { onuWifiSsidPFTable 1 }

		
		OnuWifiSsidPFEntry ::=
			SEQUENCE { 
				onuWifiSsidSrvId
					INTEGER,
				onuWifiSsidIdS
					Integer32,
				onuWifiSsidNameS
					OCTET STRING,
				onuWifiSsidEnableS
					INTEGER,
				onuWifiSsidHideS
					INTEGER,
				onuWifiSsidAuthMode
					INTEGER,
				onuWifiSsidEncryTpeS
					INTEGER,
				ssidPreshareKeyS
					OCTET STRING,
				ssidWpaRekeyIntervalS
					INTEGER,
				ssidRadiusServIpTypeS
					INTEGER,
				ssidRadiusServIp
					OCTET STRING,
				ssidRadiusServIpPrefixLenS
					INTEGER,
				ssidRadiusPortS
					INTEGER,
				ssidRadiusKeyS
					OCTET STRING,
				ssidWepEncryptionLevelS
					INTEGER,
				ssidWepKeyIndexS
					INTEGER,
				ssidWepKey1S
					OCTET STRING,
				ssidWepKey2S
					OCTET STRING,
				ssidWepKey3S
					OCTET STRING,
				ssidWepKey4S
					OCTET STRING
			 }

--          1.3.6.1.4.1.37950.1.1.5.12.9.2.38.1.1
-- 1.3.6.1.4.1.37950.1.1.5.12.9.2.38.1.1
-- 1.3.6.1.4.1.37950.1.1.5.12.9.2.38.1.1
-- 1.3.6.1.4.1.37950.1.1.5.12.9.2.38.1.1
-- 1.3.6.1.4.1.37950.1.1.5.12.9.2.38.1.1
-- 1.3.6.1.4.1.37950.1.1.5.12.9.2.38.1.1
-- 1.3.6.1.4.1.37950.1.1.5.12.9.2.38.1.1
-- 1.3.6.1.4.1.37950.1.1.5.12.9.2.38.1.1
-- 1.3.6.1.4.1.37950.1.1.5.12.9.2.38.1.1
		-- 1.3.6.1.4.1.37950.1.1.5.12.9.2.38.1.1
		onuWifiSsidSrvId OBJECT-TYPE
			SYNTAX INTEGER (0..65535)
			MAX-ACCESS read-write
			STATUS current
			DESCRIPTION
				"Description."
			::= { onuWifiSsidPFEntry 1 }

		
--          1.3.6.1.4.1.37950.1.1.5.12.9.2.38.1.2
-- 1.3.6.1.4.1.37950.1.1.5.12.9.2.38.1.2
-- 1.3.6.1.4.1.37950.1.1.5.12.9.2.38.1.2
-- 1.3.6.1.4.1.37950.1.1.5.12.9.2.38.1.2
-- 1.3.6.1.4.1.37950.1.1.5.12.9.2.38.1.2
-- 1.3.6.1.4.1.37950.1.1.5.12.9.2.38.1.2
-- 1.3.6.1.4.1.37950.1.1.5.12.9.2.38.1.2
-- 1.3.6.1.4.1.37950.1.1.5.12.9.2.38.1.2
-- 1.3.6.1.4.1.37950.1.1.5.12.9.2.38.1.2
		-- 1.3.6.1.4.1.37950.1.1.5.12.9.2.38.1.2
		onuWifiSsidIdS OBJECT-TYPE
			SYNTAX Integer32 (1..4)
			MAX-ACCESS read-write
			STATUS current
			DESCRIPTION
				"Description."
			::= { onuWifiSsidPFEntry 2 }

		
--          1.3.6.1.4.1.37950.1.1.5.12.9.2.38.1.3
-- 1.3.6.1.4.1.37950.1.1.5.12.9.2.38.1.3
-- 1.3.6.1.4.1.37950.1.1.5.12.9.2.38.1.3
-- 1.3.6.1.4.1.37950.1.1.5.12.9.2.38.1.3
-- 1.3.6.1.4.1.37950.1.1.5.12.9.2.38.1.3
-- 1.3.6.1.4.1.37950.1.1.5.12.9.2.38.1.3
-- 1.3.6.1.4.1.37950.1.1.5.12.9.2.38.1.3
-- 1.3.6.1.4.1.37950.1.1.5.12.9.2.38.1.3
-- 1.3.6.1.4.1.37950.1.1.5.12.9.2.38.1.3
		-- 1.3.6.1.4.1.37950.1.1.5.12.9.2.38.1.3
		onuWifiSsidNameS OBJECT-TYPE
			SYNTAX OCTET STRING
			MAX-ACCESS read-write
			STATUS current
			DESCRIPTION
				"Description."
			::= { onuWifiSsidPFEntry 3 }

		
--          1.3.6.1.4.1.37950.1.1.5.12.9.2.38.1.4
-- 1.3.6.1.4.1.37950.1.1.5.12.9.2.38.1.4
-- 1.3.6.1.4.1.37950.1.1.5.12.9.2.38.1.4
-- 1.3.6.1.4.1.37950.1.1.5.12.9.2.38.1.4
-- 1.3.6.1.4.1.37950.1.1.5.12.9.2.38.1.4
-- 1.3.6.1.4.1.37950.1.1.5.12.9.2.38.1.4
-- 1.3.6.1.4.1.37950.1.1.5.12.9.2.38.1.4
-- 1.3.6.1.4.1.37950.1.1.5.12.9.2.38.1.4
-- 1.3.6.1.4.1.37950.1.1.5.12.9.2.38.1.4
		-- 1.3.6.1.4.1.37950.1.1.5.12.9.2.38.1.4
		onuWifiSsidEnableS OBJECT-TYPE
			SYNTAX INTEGER
				{
				disable(0),
				enable(1)
				}
			MAX-ACCESS read-write
			STATUS current
			DESCRIPTION
				"Description."
			::= { onuWifiSsidPFEntry 4 }

		
--          1.3.6.1.4.1.37950.1.1.5.12.9.2.38.1.5
-- 1.3.6.1.4.1.37950.1.1.5.12.9.2.38.1.5
-- 1.3.6.1.4.1.37950.1.1.5.12.9.2.38.1.5
-- 1.3.6.1.4.1.37950.1.1.5.12.9.2.38.1.5
-- 1.3.6.1.4.1.37950.1.1.5.12.9.2.38.1.5
-- 1.3.6.1.4.1.37950.1.1.5.12.9.2.38.1.5
-- 1.3.6.1.4.1.37950.1.1.5.12.9.2.38.1.5
-- 1.3.6.1.4.1.37950.1.1.5.12.9.2.38.1.5
-- 1.3.6.1.4.1.37950.1.1.5.12.9.2.38.1.5
		-- 1.3.6.1.4.1.37950.1.1.5.12.9.2.38.1.5
		onuWifiSsidHideS OBJECT-TYPE
			SYNTAX INTEGER
				{
				disable(0),
				enable(1)
				}
			MAX-ACCESS read-write
			STATUS current
			DESCRIPTION
				"Description."
			::= { onuWifiSsidPFEntry 5 }

		
--          1.3.6.1.4.1.37950.1.1.5.12.9.2.38.1.6
-- 1.3.6.1.4.1.37950.1.1.5.12.9.2.38.1.6
-- 1.3.6.1.4.1.37950.1.1.5.12.9.2.38.1.6
-- 1.3.6.1.4.1.37950.1.1.5.12.9.2.38.1.6
-- 1.3.6.1.4.1.37950.1.1.5.12.9.2.38.1.6
-- 1.3.6.1.4.1.37950.1.1.5.12.9.2.38.1.6
-- 1.3.6.1.4.1.37950.1.1.5.12.9.2.38.1.6
-- 1.3.6.1.4.1.37950.1.1.5.12.9.2.38.1.6
-- 1.3.6.1.4.1.37950.1.1.5.12.9.2.38.1.6
		-- 1.3.6.1.4.1.37950.1.1.5.12.9.2.38.1.6
		onuWifiSsidAuthMode OBJECT-TYPE
			SYNTAX INTEGER
				{
				open(1),
				shared(2),
				wepauto(3),
				wpapsk(4),
				wpa(5),
				wpa2psk(6),
				wpa2(7),
				wpa-wpa2(8),
				wpapsk-wpa2psk(9),
				wpa3psk(10),
				wpa2psk-wpa3psk(11)
				}
			MAX-ACCESS read-write
			STATUS current
			DESCRIPTION
				"Description."
			::= { onuWifiSsidPFEntry 6 }

		
--          1.3.6.1.4.1.37950.1.1.5.12.9.2.38.1.7
-- 1.3.6.1.4.1.37950.1.1.5.12.9.2.38.1.7
-- 1.3.6.1.4.1.37950.1.1.5.12.9.2.38.1.7
-- 1.3.6.1.4.1.37950.1.1.5.12.9.2.38.1.7
-- 1.3.6.1.4.1.37950.1.1.5.12.9.2.38.1.7
-- 1.3.6.1.4.1.37950.1.1.5.12.9.2.38.1.7
-- 1.3.6.1.4.1.37950.1.1.5.12.9.2.38.1.7
-- 1.3.6.1.4.1.37950.1.1.5.12.9.2.38.1.7
-- 1.3.6.1.4.1.37950.1.1.5.12.9.2.38.1.7
		-- 1.3.6.1.4.1.37950.1.1.5.12.9.2.38.1.7
		onuWifiSsidEncryTpeS OBJECT-TYPE
			SYNTAX INTEGER
				{
				none(1),
				wep(2),
				tkip(3),
				aes(4),
				tkipaes(5)
				}
			MAX-ACCESS read-write
			STATUS current
			DESCRIPTION
				"Description."
			::= { onuWifiSsidPFEntry 7 }

		
--          1.3.6.1.4.1.37950.1.1.5.12.9.2.38.1.8
-- 1.3.6.1.4.1.37950.1.1.5.12.9.2.38.1.8
-- 1.3.6.1.4.1.37950.1.1.5.12.9.2.38.1.8
-- 1.3.6.1.4.1.37950.1.1.5.12.9.2.38.1.8
-- 1.3.6.1.4.1.37950.1.1.5.12.9.2.38.1.8
-- 1.3.6.1.4.1.37950.1.1.5.12.9.2.38.1.8
-- 1.3.6.1.4.1.37950.1.1.5.12.9.2.38.1.8
-- 1.3.6.1.4.1.37950.1.1.5.12.9.2.38.1.8
-- 1.3.6.1.4.1.37950.1.1.5.12.9.2.38.1.8
		-- 1.3.6.1.4.1.37950.1.1.5.12.9.2.38.1.8
		ssidPreshareKeyS OBJECT-TYPE
			SYNTAX OCTET STRING
			MAX-ACCESS read-write
			STATUS current
			DESCRIPTION
				"Description."
			::= { onuWifiSsidPFEntry 8 }

		
--          1.3.6.1.4.1.37950.1.1.5.12.9.2.38.1.9
-- 1.3.6.1.4.1.37950.1.1.5.12.9.2.38.1.9
-- 1.3.6.1.4.1.37950.1.1.5.12.9.2.38.1.9
-- 1.3.6.1.4.1.37950.1.1.5.12.9.2.38.1.9
-- 1.3.6.1.4.1.37950.1.1.5.12.9.2.38.1.9
-- 1.3.6.1.4.1.37950.1.1.5.12.9.2.38.1.9
-- 1.3.6.1.4.1.37950.1.1.5.12.9.2.38.1.9
-- 1.3.6.1.4.1.37950.1.1.5.12.9.2.38.1.9
-- 1.3.6.1.4.1.37950.1.1.5.12.9.2.38.1.9
		-- 1.3.6.1.4.1.37950.1.1.5.12.9.2.38.1.9
		ssidWpaRekeyIntervalS OBJECT-TYPE
			SYNTAX INTEGER (0..4194303)
			MAX-ACCESS read-write
			STATUS current
			DESCRIPTION
				"Description."
			::= { onuWifiSsidPFEntry 9 }

		
--          1.3.6.1.4.1.37950.1.1.5.12.9.2.38.1.10
-- 1.3.6.1.4.1.37950.1.1.5.12.9.2.38.1.10
-- 1.3.6.1.4.1.37950.1.1.5.12.9.2.38.1.10
-- 1.3.6.1.4.1.37950.1.1.5.12.9.2.38.1.10
-- 1.3.6.1.4.1.37950.1.1.5.12.9.2.38.1.10
-- 1.3.6.1.4.1.37950.1.1.5.12.9.2.38.1.10
-- 1.3.6.1.4.1.37950.1.1.5.12.9.2.38.1.10
-- 1.3.6.1.4.1.37950.1.1.5.12.9.2.38.1.10
-- 1.3.6.1.4.1.37950.1.1.5.12.9.2.38.1.10
		-- 1.3.6.1.4.1.37950.1.1.5.12.9.2.38.1.10
		ssidRadiusServIpTypeS OBJECT-TYPE
			SYNTAX INTEGER
				{
				unknown(0),
				ipv4(1),
				ipv6(2),
				ipv4z(3),
				ipv6z(4),
				dns(16)
				}
			MAX-ACCESS read-write
			STATUS current
			DESCRIPTION
				"Description."
			::= { onuWifiSsidPFEntry 10 }

		
--          1.3.6.1.4.1.37950.1.1.5.12.9.2.38.1.11
-- 1.3.6.1.4.1.37950.1.1.5.12.9.2.38.1.11
-- 1.3.6.1.4.1.37950.1.1.5.12.9.2.38.1.11
-- 1.3.6.1.4.1.37950.1.1.5.12.9.2.38.1.11
-- 1.3.6.1.4.1.37950.1.1.5.12.9.2.38.1.11
-- 1.3.6.1.4.1.37950.1.1.5.12.9.2.38.1.11
-- 1.3.6.1.4.1.37950.1.1.5.12.9.2.38.1.11
-- 1.3.6.1.4.1.37950.1.1.5.12.9.2.38.1.11
-- 1.3.6.1.4.1.37950.1.1.5.12.9.2.38.1.11
		-- 1.3.6.1.4.1.37950.1.1.5.12.9.2.38.1.11
		ssidRadiusServIp OBJECT-TYPE
			SYNTAX OCTET STRING
			MAX-ACCESS read-write
			STATUS current
			DESCRIPTION
				"Description."
			::= { onuWifiSsidPFEntry 11 }

		
--          1.3.6.1.4.1.37950.1.1.5.12.9.2.38.1.12
-- 1.3.6.1.4.1.37950.1.1.5.12.9.2.38.1.12
-- 1.3.6.1.4.1.37950.1.1.5.12.9.2.38.1.12
-- 1.3.6.1.4.1.37950.1.1.5.12.9.2.38.1.12
-- 1.3.6.1.4.1.37950.1.1.5.12.9.2.38.1.12
-- 1.3.6.1.4.1.37950.1.1.5.12.9.2.38.1.12
-- 1.3.6.1.4.1.37950.1.1.5.12.9.2.38.1.12
-- 1.3.6.1.4.1.37950.1.1.5.12.9.2.38.1.12
-- 1.3.6.1.4.1.37950.1.1.5.12.9.2.38.1.12
		-- 1.3.6.1.4.1.37950.1.1.5.12.9.2.38.1.12
		ssidRadiusServIpPrefixLenS OBJECT-TYPE
			SYNTAX INTEGER (0..255)
			MAX-ACCESS read-write
			STATUS current
			DESCRIPTION
				"Description."
			::= { onuWifiSsidPFEntry 12 }

		
--          1.3.6.1.4.1.37950.1.1.5.12.9.2.38.1.13
-- 1.3.6.1.4.1.37950.1.1.5.12.9.2.38.1.13
-- 1.3.6.1.4.1.37950.1.1.5.12.9.2.38.1.13
-- 1.3.6.1.4.1.37950.1.1.5.12.9.2.38.1.13
-- 1.3.6.1.4.1.37950.1.1.5.12.9.2.38.1.13
-- 1.3.6.1.4.1.37950.1.1.5.12.9.2.38.1.13
-- 1.3.6.1.4.1.37950.1.1.5.12.9.2.38.1.13
-- 1.3.6.1.4.1.37950.1.1.5.12.9.2.38.1.13
-- 1.3.6.1.4.1.37950.1.1.5.12.9.2.38.1.13
		-- 1.3.6.1.4.1.37950.1.1.5.12.9.2.38.1.13
		ssidRadiusPortS OBJECT-TYPE
			SYNTAX INTEGER (0..65535)
			MAX-ACCESS read-write
			STATUS current
			DESCRIPTION
				"Description."
			::= { onuWifiSsidPFEntry 13 }

		
--          1.3.6.1.4.1.37950.1.1.5.12.9.2.38.1.14
-- 1.3.6.1.4.1.37950.1.1.5.12.9.2.38.1.14
-- 1.3.6.1.4.1.37950.1.1.5.12.9.2.38.1.14
-- 1.3.6.1.4.1.37950.1.1.5.12.9.2.38.1.14
-- 1.3.6.1.4.1.37950.1.1.5.12.9.2.38.1.14
-- 1.3.6.1.4.1.37950.1.1.5.12.9.2.38.1.14
-- 1.3.6.1.4.1.37950.1.1.5.12.9.2.38.1.14
-- 1.3.6.1.4.1.37950.1.1.5.12.9.2.38.1.14
-- 1.3.6.1.4.1.37950.1.1.5.12.9.2.38.1.14
		-- 1.3.6.1.4.1.37950.1.1.5.12.9.2.38.1.14
		ssidRadiusKeyS OBJECT-TYPE
			SYNTAX OCTET STRING (SIZE (0..32))
			MAX-ACCESS read-write
			STATUS current
			DESCRIPTION
				"Description."
			::= { onuWifiSsidPFEntry 14 }

		
--          1.3.6.1.4.1.37950.1.1.5.12.9.2.38.1.15
-- 1.3.6.1.4.1.37950.1.1.5.12.9.2.38.1.15
-- 1.3.6.1.4.1.37950.1.1.5.12.9.2.38.1.15
-- 1.3.6.1.4.1.37950.1.1.5.12.9.2.38.1.15
-- 1.3.6.1.4.1.37950.1.1.5.12.9.2.38.1.15
-- 1.3.6.1.4.1.37950.1.1.5.12.9.2.38.1.15
-- 1.3.6.1.4.1.37950.1.1.5.12.9.2.38.1.15
-- 1.3.6.1.4.1.37950.1.1.5.12.9.2.38.1.15
-- 1.3.6.1.4.1.37950.1.1.5.12.9.2.38.1.15
		-- 1.3.6.1.4.1.37950.1.1.5.12.9.2.38.1.15
		ssidWepEncryptionLevelS OBJECT-TYPE
			SYNTAX INTEGER
				{
				s64bit(1),
				s128bit(2)
				}
			MAX-ACCESS read-write
			STATUS current
			DESCRIPTION
				"Description."
			::= { onuWifiSsidPFEntry 15 }

		
--          1.3.6.1.4.1.37950.1.1.5.12.9.2.38.1.16
-- 1.3.6.1.4.1.37950.1.1.5.12.9.2.38.1.16
-- 1.3.6.1.4.1.37950.1.1.5.12.9.2.38.1.16
-- 1.3.6.1.4.1.37950.1.1.5.12.9.2.38.1.16
-- 1.3.6.1.4.1.37950.1.1.5.12.9.2.38.1.16
-- 1.3.6.1.4.1.37950.1.1.5.12.9.2.38.1.16
-- 1.3.6.1.4.1.37950.1.1.5.12.9.2.38.1.16
-- 1.3.6.1.4.1.37950.1.1.5.12.9.2.38.1.16
-- 1.3.6.1.4.1.37950.1.1.5.12.9.2.38.1.16
		-- 1.3.6.1.4.1.37950.1.1.5.12.9.2.38.1.16
		ssidWepKeyIndexS OBJECT-TYPE
			SYNTAX INTEGER (1..4)
			MAX-ACCESS read-write
			STATUS current
			DESCRIPTION
				"Description."
			::= { onuWifiSsidPFEntry 16 }

		
--          1.3.6.1.4.1.37950.1.1.5.12.9.2.38.1.17
-- 1.3.6.1.4.1.37950.1.1.5.12.9.2.38.1.17
-- 1.3.6.1.4.1.37950.1.1.5.12.9.2.38.1.17
-- 1.3.6.1.4.1.37950.1.1.5.12.9.2.38.1.17
-- 1.3.6.1.4.1.37950.1.1.5.12.9.2.38.1.17
-- 1.3.6.1.4.1.37950.1.1.5.12.9.2.38.1.17
-- 1.3.6.1.4.1.37950.1.1.5.12.9.2.38.1.17
-- 1.3.6.1.4.1.37950.1.1.5.12.9.2.38.1.17
-- 1.3.6.1.4.1.37950.1.1.5.12.9.2.38.1.17
		-- 1.3.6.1.4.1.37950.1.1.5.12.9.2.38.1.17
		ssidWepKey1S OBJECT-TYPE
			SYNTAX OCTET STRING
			MAX-ACCESS read-write
			STATUS current
			DESCRIPTION
				"Description."
			::= { onuWifiSsidPFEntry 17 }

		
--          1.3.6.1.4.1.37950.1.1.5.12.9.2.38.1.18
-- 1.3.6.1.4.1.37950.1.1.5.12.9.2.38.1.18
-- 1.3.6.1.4.1.37950.1.1.5.12.9.2.38.1.18
-- 1.3.6.1.4.1.37950.1.1.5.12.9.2.38.1.18
-- 1.3.6.1.4.1.37950.1.1.5.12.9.2.38.1.18
-- 1.3.6.1.4.1.37950.1.1.5.12.9.2.38.1.18
-- 1.3.6.1.4.1.37950.1.1.5.12.9.2.38.1.18
-- 1.3.6.1.4.1.37950.1.1.5.12.9.2.38.1.18
-- 1.3.6.1.4.1.37950.1.1.5.12.9.2.38.1.18
		-- 1.3.6.1.4.1.37950.1.1.5.12.9.2.38.1.18
		ssidWepKey2S OBJECT-TYPE
			SYNTAX OCTET STRING
			MAX-ACCESS read-write
			STATUS current
			DESCRIPTION
				"Description."
			::= { onuWifiSsidPFEntry 18 }

		
--          1.3.6.1.4.1.37950.1.1.5.12.9.2.38.1.19
-- 1.3.6.1.4.1.37950.1.1.5.12.9.2.38.1.19
-- 1.3.6.1.4.1.37950.1.1.5.12.9.2.38.1.19
-- 1.3.6.1.4.1.37950.1.1.5.12.9.2.38.1.19
-- 1.3.6.1.4.1.37950.1.1.5.12.9.2.38.1.19
-- 1.3.6.1.4.1.37950.1.1.5.12.9.2.38.1.19
-- 1.3.6.1.4.1.37950.1.1.5.12.9.2.38.1.19
-- 1.3.6.1.4.1.37950.1.1.5.12.9.2.38.1.19
-- 1.3.6.1.4.1.37950.1.1.5.12.9.2.38.1.19
		-- 1.3.6.1.4.1.37950.1.1.5.12.9.2.38.1.19
		ssidWepKey3S OBJECT-TYPE
			SYNTAX OCTET STRING
			MAX-ACCESS read-write
			STATUS current
			DESCRIPTION
				"Description."
			::= { onuWifiSsidPFEntry 19 }

		
--          1.3.6.1.4.1.37950.1.1.5.12.9.2.38.1.20
-- 1.3.6.1.4.1.37950.1.1.5.12.9.2.38.1.20
-- 1.3.6.1.4.1.37950.1.1.5.12.9.2.38.1.20
-- 1.3.6.1.4.1.37950.1.1.5.12.9.2.38.1.20
-- 1.3.6.1.4.1.37950.1.1.5.12.9.2.38.1.20
-- 1.3.6.1.4.1.37950.1.1.5.12.9.2.38.1.20
-- 1.3.6.1.4.1.37950.1.1.5.12.9.2.38.1.20
-- 1.3.6.1.4.1.37950.1.1.5.12.9.2.38.1.20
-- 1.3.6.1.4.1.37950.1.1.5.12.9.2.38.1.20
		-- 1.3.6.1.4.1.37950.1.1.5.12.9.2.38.1.20
		ssidWepKey4S OBJECT-TYPE
			SYNTAX OCTET STRING
			MAX-ACCESS read-write
			STATUS current
			DESCRIPTION
				"Description."
			::= { onuWifiSsidPFEntry 20 }

		
--          1.3.6.1.4.1.37950.1.1.5.12.9.2.39
-- 1.3.6.1.4.1.37950.1.1.5.12.9.2.39
-- 1.3.6.1.4.1.37950.1.1.5.12.9.2.39
-- 1.3.6.1.4.1.37950.1.1.5.12.9.2.39
-- 1.3.6.1.4.1.37950.1.1.5.12.9.2.39
-- 1.3.6.1.4.1.37950.1.1.5.12.9.2.39
-- 1.3.6.1.4.1.37950.1.1.5.12.9.2.39
-- 1.3.6.1.4.1.37950.1.1.5.12.9.2.39
-- 1.3.6.1.4.1.37950.1.1.5.12.9.2.39
		-- 1.3.6.1.4.1.37950.1.1.5.12.9.2.39
		onuWanConnPFTable OBJECT-TYPE
			SYNTAX SEQUENCE OF OnuWanConnPFEntry
			MAX-ACCESS not-accessible
			STATUS current
			DESCRIPTION
				"Description."
			::= { srvProfileShow 39 }

		
--          1.3.6.1.4.1.37950.1.1.5.12.9.2.39.1
-- 1.3.6.1.4.1.37950.1.1.5.12.9.2.39.1
-- 1.3.6.1.4.1.37950.1.1.5.12.9.2.39.1
-- 1.3.6.1.4.1.37950.1.1.5.12.9.2.39.1
-- 1.3.6.1.4.1.37950.1.1.5.12.9.2.39.1
-- 1.3.6.1.4.1.37950.1.1.5.12.9.2.39.1
-- 1.3.6.1.4.1.37950.1.1.5.12.9.2.39.1
-- 1.3.6.1.4.1.37950.1.1.5.12.9.2.39.1
-- 1.3.6.1.4.1.37950.1.1.5.12.9.2.39.1
		-- 1.3.6.1.4.1.37950.1.1.5.12.9.2.39.1
		onuWanConnPFEntry OBJECT-TYPE
			SYNTAX OnuWanConnPFEntry
			MAX-ACCESS not-accessible
			STATUS current
			DESCRIPTION
				"Description."
			INDEX { wanConnSrvId, wanConnIndexS }
			::= { onuWanConnPFTable 1 }

		
		OnuWanConnPFEntry ::=
			SEQUENCE { 
				wanConnSrvId
					INTEGER,
				wanConnIndexS
					Integer32,
				wanConnBindLanS
					INTEGER,
				wanConnBindSsidS
					INTEGER,
				wanModeS
					INTEGER,
				wanConnTypeS
					INTEGER,
				wanConnVlanIdS
					INTEGER,
				wanConnVlanCosS
					INTEGER,
				wanConnNatEnableS
					INTEGER,
				wanConnModeS
					INTEGER,
				wanConnIpAddressS
					IpAddress,
				wanConnIpMaskS
					IpAddress,
				wanConnGatewayS
					IpAddress,
				wanConnMasterDns
					IpAddress,
				wanConnSlaveDns
					IpAddress,
				wanConnPppoeProxyS
					INTEGER,
				wanConnPppoeUsernameS
					OCTET STRING,
				wanConnPppoePasswordS
					OCTET STRING,
				wanConnPppoeSerName
					OCTET STRING,
				wanConnPppoeModeS
					INTEGER,
				wanConnQosEnableS
					INTEGER,
				wanConnVlanModeS
					INTEGER,
				wanConnTranslationEnableS
					INTEGER,
				wanConnTranslationVlanS
					INTEGER,
				wanConnTranslationCosS
					INTEGER,
				wanConnQinqEnableS
					INTEGER,
				wanConnQinqTpidS
					INTEGER,
				wanConnSvlanIdS
					INTEGER,
				wanConnSvlanCosS
					INTEGER,
				wanConnRouteMtuS
					INTEGER
			 }

--          1.3.6.1.4.1.37950.1.1.5.12.9.2.39.1.1
-- 1.3.6.1.4.1.37950.1.1.5.12.9.2.39.1.1
-- 1.3.6.1.4.1.37950.1.1.5.12.9.2.39.1.1
-- 1.3.6.1.4.1.37950.1.1.5.12.9.2.39.1.1
-- 1.3.6.1.4.1.37950.1.1.5.12.9.2.39.1.1
-- 1.3.6.1.4.1.37950.1.1.5.12.9.2.39.1.1
-- 1.3.6.1.4.1.37950.1.1.5.12.9.2.39.1.1
-- 1.3.6.1.4.1.37950.1.1.5.12.9.2.39.1.1
-- 1.3.6.1.4.1.37950.1.1.5.12.9.2.39.1.1
		-- 1.3.6.1.4.1.37950.1.1.5.12.9.2.39.1.1
		wanConnSrvId OBJECT-TYPE
			SYNTAX INTEGER (0..65535)
			MAX-ACCESS read-write
			STATUS current
			DESCRIPTION
				"Description."
			::= { onuWanConnPFEntry 1 }

		
--          1.3.6.1.4.1.37950.1.1.5.12.9.2.39.1.2
-- 1.3.6.1.4.1.37950.1.1.5.12.9.2.39.1.2
-- 1.3.6.1.4.1.37950.1.1.5.12.9.2.39.1.2
-- 1.3.6.1.4.1.37950.1.1.5.12.9.2.39.1.2
-- 1.3.6.1.4.1.37950.1.1.5.12.9.2.39.1.2
-- 1.3.6.1.4.1.37950.1.1.5.12.9.2.39.1.2
-- 1.3.6.1.4.1.37950.1.1.5.12.9.2.39.1.2
-- 1.3.6.1.4.1.37950.1.1.5.12.9.2.39.1.2
-- 1.3.6.1.4.1.37950.1.1.5.12.9.2.39.1.2
		-- 1.3.6.1.4.1.37950.1.1.5.12.9.2.39.1.2
		wanConnIndexS OBJECT-TYPE
			SYNTAX Integer32 (1..8)
			MAX-ACCESS read-write
			STATUS current
			DESCRIPTION
				"Description."
			::= { onuWanConnPFEntry 2 }

		
--          1.3.6.1.4.1.37950.1.1.5.12.9.2.39.1.3
-- 1.3.6.1.4.1.37950.1.1.5.12.9.2.39.1.3
-- 1.3.6.1.4.1.37950.1.1.5.12.9.2.39.1.3
-- 1.3.6.1.4.1.37950.1.1.5.12.9.2.39.1.3
-- 1.3.6.1.4.1.37950.1.1.5.12.9.2.39.1.3
-- 1.3.6.1.4.1.37950.1.1.5.12.9.2.39.1.3
-- 1.3.6.1.4.1.37950.1.1.5.12.9.2.39.1.3
-- 1.3.6.1.4.1.37950.1.1.5.12.9.2.39.1.3
-- 1.3.6.1.4.1.37950.1.1.5.12.9.2.39.1.3
		-- 1.3.6.1.4.1.37950.1.1.5.12.9.2.39.1.3
		wanConnBindLanS OBJECT-TYPE
			SYNTAX INTEGER (0..15)
			MAX-ACCESS read-write
			STATUS current
			DESCRIPTION
				"Description."
			::= { onuWanConnPFEntry 3 }

		
--          1.3.6.1.4.1.37950.1.1.5.12.9.2.39.1.4
-- 1.3.6.1.4.1.37950.1.1.5.12.9.2.39.1.4
-- 1.3.6.1.4.1.37950.1.1.5.12.9.2.39.1.4
-- 1.3.6.1.4.1.37950.1.1.5.12.9.2.39.1.4
-- 1.3.6.1.4.1.37950.1.1.5.12.9.2.39.1.4
-- 1.3.6.1.4.1.37950.1.1.5.12.9.2.39.1.4
-- 1.3.6.1.4.1.37950.1.1.5.12.9.2.39.1.4
-- 1.3.6.1.4.1.37950.1.1.5.12.9.2.39.1.4
-- 1.3.6.1.4.1.37950.1.1.5.12.9.2.39.1.4
		-- 1.3.6.1.4.1.37950.1.1.5.12.9.2.39.1.4
		wanConnBindSsidS OBJECT-TYPE
			SYNTAX INTEGER (0..15)
			MAX-ACCESS read-write
			STATUS current
			DESCRIPTION
				"Description."
			::= { onuWanConnPFEntry 4 }

		
--          1.3.6.1.4.1.37950.1.1.5.12.9.2.39.1.5
-- 1.3.6.1.4.1.37950.1.1.5.12.9.2.39.1.5
-- 1.3.6.1.4.1.37950.1.1.5.12.9.2.39.1.5
-- 1.3.6.1.4.1.37950.1.1.5.12.9.2.39.1.5
-- 1.3.6.1.4.1.37950.1.1.5.12.9.2.39.1.5
-- 1.3.6.1.4.1.37950.1.1.5.12.9.2.39.1.5
-- 1.3.6.1.4.1.37950.1.1.5.12.9.2.39.1.5
-- 1.3.6.1.4.1.37950.1.1.5.12.9.2.39.1.5
-- 1.3.6.1.4.1.37950.1.1.5.12.9.2.39.1.5
		-- 1.3.6.1.4.1.37950.1.1.5.12.9.2.39.1.5
		wanModeS OBJECT-TYPE
			SYNTAX INTEGER
				{
				internet(0),
				multicast(1),
				tr069(2),
				tr069-internet(3),
				tr069-voip(4),
				voip-internet(5),
				tr069-voip-internet(6),
				other(100)
				}
			MAX-ACCESS read-write
			STATUS current
			DESCRIPTION
				"Description."
			::= { onuWanConnPFEntry 5 }

		
--          1.3.6.1.4.1.37950.1.1.5.12.9.2.39.1.6
-- 1.3.6.1.4.1.37950.1.1.5.12.9.2.39.1.6
-- 1.3.6.1.4.1.37950.1.1.5.12.9.2.39.1.6
-- 1.3.6.1.4.1.37950.1.1.5.12.9.2.39.1.6
-- 1.3.6.1.4.1.37950.1.1.5.12.9.2.39.1.6
-- 1.3.6.1.4.1.37950.1.1.5.12.9.2.39.1.6
-- 1.3.6.1.4.1.37950.1.1.5.12.9.2.39.1.6
-- 1.3.6.1.4.1.37950.1.1.5.12.9.2.39.1.6
-- 1.3.6.1.4.1.37950.1.1.5.12.9.2.39.1.6
		-- 1.3.6.1.4.1.37950.1.1.5.12.9.2.39.1.6
		wanConnTypeS OBJECT-TYPE
			SYNTAX INTEGER
				{
				bridge(0),
				route(1)
				}
			MAX-ACCESS read-write
			STATUS current
			DESCRIPTION
				"Description."
			::= { onuWanConnPFEntry 6 }

		
--          1.3.6.1.4.1.37950.1.1.5.12.9.2.39.1.7
-- 1.3.6.1.4.1.37950.1.1.5.12.9.2.39.1.7
-- 1.3.6.1.4.1.37950.1.1.5.12.9.2.39.1.7
-- 1.3.6.1.4.1.37950.1.1.5.12.9.2.39.1.7
-- 1.3.6.1.4.1.37950.1.1.5.12.9.2.39.1.7
-- 1.3.6.1.4.1.37950.1.1.5.12.9.2.39.1.7
-- 1.3.6.1.4.1.37950.1.1.5.12.9.2.39.1.7
-- 1.3.6.1.4.1.37950.1.1.5.12.9.2.39.1.7
-- 1.3.6.1.4.1.37950.1.1.5.12.9.2.39.1.7
		-- 1.3.6.1.4.1.37950.1.1.5.12.9.2.39.1.7
		wanConnVlanIdS OBJECT-TYPE
			SYNTAX INTEGER (0..4095)
			MAX-ACCESS read-write
			STATUS current
			DESCRIPTION
				"Description."
			::= { onuWanConnPFEntry 7 }

		
--          1.3.6.1.4.1.37950.1.1.5.12.9.2.39.1.8
-- 1.3.6.1.4.1.37950.1.1.5.12.9.2.39.1.8
-- 1.3.6.1.4.1.37950.1.1.5.12.9.2.39.1.8
-- 1.3.6.1.4.1.37950.1.1.5.12.9.2.39.1.8
-- 1.3.6.1.4.1.37950.1.1.5.12.9.2.39.1.8
-- 1.3.6.1.4.1.37950.1.1.5.12.9.2.39.1.8
-- 1.3.6.1.4.1.37950.1.1.5.12.9.2.39.1.8
-- 1.3.6.1.4.1.37950.1.1.5.12.9.2.39.1.8
-- 1.3.6.1.4.1.37950.1.1.5.12.9.2.39.1.8
		-- 1.3.6.1.4.1.37950.1.1.5.12.9.2.39.1.8
		wanConnVlanCosS OBJECT-TYPE
			SYNTAX INTEGER (0..7)
			MAX-ACCESS read-write
			STATUS current
			DESCRIPTION
				"Description."
			::= { onuWanConnPFEntry 8 }

		
--          1.3.6.1.4.1.37950.1.1.5.12.9.2.39.1.9
-- 1.3.6.1.4.1.37950.1.1.5.12.9.2.39.1.9
-- 1.3.6.1.4.1.37950.1.1.5.12.9.2.39.1.9
-- 1.3.6.1.4.1.37950.1.1.5.12.9.2.39.1.9
-- 1.3.6.1.4.1.37950.1.1.5.12.9.2.39.1.9
-- 1.3.6.1.4.1.37950.1.1.5.12.9.2.39.1.9
-- 1.3.6.1.4.1.37950.1.1.5.12.9.2.39.1.9
-- 1.3.6.1.4.1.37950.1.1.5.12.9.2.39.1.9
-- 1.3.6.1.4.1.37950.1.1.5.12.9.2.39.1.9
		-- 1.3.6.1.4.1.37950.1.1.5.12.9.2.39.1.9
		wanConnNatEnableS OBJECT-TYPE
			SYNTAX INTEGER
				{
				disable(0),
				enable(1)
				}
			MAX-ACCESS read-write
			STATUS current
			DESCRIPTION
				"Description."
			::= { onuWanConnPFEntry 9 }

		
--          1.3.6.1.4.1.37950.1.1.5.12.9.2.39.1.10
-- 1.3.6.1.4.1.37950.1.1.5.12.9.2.39.1.10
-- 1.3.6.1.4.1.37950.1.1.5.12.9.2.39.1.10
-- 1.3.6.1.4.1.37950.1.1.5.12.9.2.39.1.10
-- 1.3.6.1.4.1.37950.1.1.5.12.9.2.39.1.10
-- 1.3.6.1.4.1.37950.1.1.5.12.9.2.39.1.10
-- 1.3.6.1.4.1.37950.1.1.5.12.9.2.39.1.10
-- 1.3.6.1.4.1.37950.1.1.5.12.9.2.39.1.10
-- 1.3.6.1.4.1.37950.1.1.5.12.9.2.39.1.10
		-- 1.3.6.1.4.1.37950.1.1.5.12.9.2.39.1.10
		wanConnModeS OBJECT-TYPE
			SYNTAX INTEGER
				{
				dhcp(0),
				static(1),
				pppoe(2)
				}
			MAX-ACCESS read-write
			STATUS current
			DESCRIPTION
				"Description."
			::= { onuWanConnPFEntry 10 }

		
--          1.3.6.1.4.1.37950.1.1.5.12.9.2.39.1.11
-- 1.3.6.1.4.1.37950.1.1.5.12.9.2.39.1.11
-- 1.3.6.1.4.1.37950.1.1.5.12.9.2.39.1.11
-- 1.3.6.1.4.1.37950.1.1.5.12.9.2.39.1.11
-- 1.3.6.1.4.1.37950.1.1.5.12.9.2.39.1.11
-- 1.3.6.1.4.1.37950.1.1.5.12.9.2.39.1.11
-- 1.3.6.1.4.1.37950.1.1.5.12.9.2.39.1.11
-- 1.3.6.1.4.1.37950.1.1.5.12.9.2.39.1.11
-- 1.3.6.1.4.1.37950.1.1.5.12.9.2.39.1.11
		-- 1.3.6.1.4.1.37950.1.1.5.12.9.2.39.1.11
		wanConnIpAddressS OBJECT-TYPE
			SYNTAX IpAddress
			MAX-ACCESS read-write
			STATUS current
			DESCRIPTION
				"Description."
			::= { onuWanConnPFEntry 11 }

		
--          1.3.6.1.4.1.37950.1.1.5.12.9.2.39.1.12
-- 1.3.6.1.4.1.37950.1.1.5.12.9.2.39.1.12
-- 1.3.6.1.4.1.37950.1.1.5.12.9.2.39.1.12
-- 1.3.6.1.4.1.37950.1.1.5.12.9.2.39.1.12
-- 1.3.6.1.4.1.37950.1.1.5.12.9.2.39.1.12
-- 1.3.6.1.4.1.37950.1.1.5.12.9.2.39.1.12
-- 1.3.6.1.4.1.37950.1.1.5.12.9.2.39.1.12
-- 1.3.6.1.4.1.37950.1.1.5.12.9.2.39.1.12
-- 1.3.6.1.4.1.37950.1.1.5.12.9.2.39.1.12
		-- 1.3.6.1.4.1.37950.1.1.5.12.9.2.39.1.12
		wanConnIpMaskS OBJECT-TYPE
			SYNTAX IpAddress
			MAX-ACCESS read-write
			STATUS current
			DESCRIPTION
				"Description."
			::= { onuWanConnPFEntry 12 }

		
--          1.3.6.1.4.1.37950.1.1.5.12.9.2.39.1.13
-- 1.3.6.1.4.1.37950.1.1.5.12.9.2.39.1.13
-- 1.3.6.1.4.1.37950.1.1.5.12.9.2.39.1.13
-- 1.3.6.1.4.1.37950.1.1.5.12.9.2.39.1.13
-- 1.3.6.1.4.1.37950.1.1.5.12.9.2.39.1.13
-- 1.3.6.1.4.1.37950.1.1.5.12.9.2.39.1.13
-- 1.3.6.1.4.1.37950.1.1.5.12.9.2.39.1.13
-- 1.3.6.1.4.1.37950.1.1.5.12.9.2.39.1.13
-- 1.3.6.1.4.1.37950.1.1.5.12.9.2.39.1.13
		-- 1.3.6.1.4.1.37950.1.1.5.12.9.2.39.1.13
		wanConnGatewayS OBJECT-TYPE
			SYNTAX IpAddress
			MAX-ACCESS read-write
			STATUS current
			DESCRIPTION
				"Description."
			::= { onuWanConnPFEntry 13 }

		
--          1.3.6.1.4.1.37950.1.1.5.12.9.2.39.1.14
-- 1.3.6.1.4.1.37950.1.1.5.12.9.2.39.1.14
-- 1.3.6.1.4.1.37950.1.1.5.12.9.2.39.1.14
-- 1.3.6.1.4.1.37950.1.1.5.12.9.2.39.1.14
-- 1.3.6.1.4.1.37950.1.1.5.12.9.2.39.1.14
-- 1.3.6.1.4.1.37950.1.1.5.12.9.2.39.1.14
-- 1.3.6.1.4.1.37950.1.1.5.12.9.2.39.1.14
-- 1.3.6.1.4.1.37950.1.1.5.12.9.2.39.1.14
-- 1.3.6.1.4.1.37950.1.1.5.12.9.2.39.1.14
		-- 1.3.6.1.4.1.37950.1.1.5.12.9.2.39.1.14
		wanConnMasterDns OBJECT-TYPE
			SYNTAX IpAddress
			MAX-ACCESS read-write
			STATUS current
			DESCRIPTION
				"Description."
			::= { onuWanConnPFEntry 14 }

		
--          1.3.6.1.4.1.37950.1.1.5.12.9.2.39.1.15
-- 1.3.6.1.4.1.37950.1.1.5.12.9.2.39.1.15
-- 1.3.6.1.4.1.37950.1.1.5.12.9.2.39.1.15
-- 1.3.6.1.4.1.37950.1.1.5.12.9.2.39.1.15
-- 1.3.6.1.4.1.37950.1.1.5.12.9.2.39.1.15
-- 1.3.6.1.4.1.37950.1.1.5.12.9.2.39.1.15
-- 1.3.6.1.4.1.37950.1.1.5.12.9.2.39.1.15
-- 1.3.6.1.4.1.37950.1.1.5.12.9.2.39.1.15
-- 1.3.6.1.4.1.37950.1.1.5.12.9.2.39.1.15
		-- 1.3.6.1.4.1.37950.1.1.5.12.9.2.39.1.15
		wanConnSlaveDns OBJECT-TYPE
			SYNTAX IpAddress
			MAX-ACCESS read-write
			STATUS current
			DESCRIPTION
				"Description."
			::= { onuWanConnPFEntry 15 }

		
--          1.3.6.1.4.1.37950.1.1.5.12.9.2.39.1.16
-- 1.3.6.1.4.1.37950.1.1.5.12.9.2.39.1.16
-- 1.3.6.1.4.1.37950.1.1.5.12.9.2.39.1.16
-- 1.3.6.1.4.1.37950.1.1.5.12.9.2.39.1.16
-- 1.3.6.1.4.1.37950.1.1.5.12.9.2.39.1.16
-- 1.3.6.1.4.1.37950.1.1.5.12.9.2.39.1.16
-- 1.3.6.1.4.1.37950.1.1.5.12.9.2.39.1.16
-- 1.3.6.1.4.1.37950.1.1.5.12.9.2.39.1.16
-- 1.3.6.1.4.1.37950.1.1.5.12.9.2.39.1.16
		-- 1.3.6.1.4.1.37950.1.1.5.12.9.2.39.1.16
		wanConnPppoeProxyS OBJECT-TYPE
			SYNTAX INTEGER
				{
				disable(0),
				enable(1)
				}
			MAX-ACCESS read-write
			STATUS current
			DESCRIPTION
				"Description."
			::= { onuWanConnPFEntry 16 }

		
--          1.3.6.1.4.1.37950.1.1.5.12.9.2.39.1.17
-- 1.3.6.1.4.1.37950.1.1.5.12.9.2.39.1.17
-- 1.3.6.1.4.1.37950.1.1.5.12.9.2.39.1.17
-- 1.3.6.1.4.1.37950.1.1.5.12.9.2.39.1.17
-- 1.3.6.1.4.1.37950.1.1.5.12.9.2.39.1.17
-- 1.3.6.1.4.1.37950.1.1.5.12.9.2.39.1.17
-- 1.3.6.1.4.1.37950.1.1.5.12.9.2.39.1.17
-- 1.3.6.1.4.1.37950.1.1.5.12.9.2.39.1.17
-- 1.3.6.1.4.1.37950.1.1.5.12.9.2.39.1.17
		-- 1.3.6.1.4.1.37950.1.1.5.12.9.2.39.1.17
		wanConnPppoeUsernameS OBJECT-TYPE
			SYNTAX OCTET STRING
			MAX-ACCESS read-write
			STATUS current
			DESCRIPTION
				"Description."
			::= { onuWanConnPFEntry 17 }

		
--          1.3.6.1.4.1.37950.1.1.5.12.9.2.39.1.18
-- 1.3.6.1.4.1.37950.1.1.5.12.9.2.39.1.18
-- 1.3.6.1.4.1.37950.1.1.5.12.9.2.39.1.18
-- 1.3.6.1.4.1.37950.1.1.5.12.9.2.39.1.18
-- 1.3.6.1.4.1.37950.1.1.5.12.9.2.39.1.18
-- 1.3.6.1.4.1.37950.1.1.5.12.9.2.39.1.18
-- 1.3.6.1.4.1.37950.1.1.5.12.9.2.39.1.18
-- 1.3.6.1.4.1.37950.1.1.5.12.9.2.39.1.18
-- 1.3.6.1.4.1.37950.1.1.5.12.9.2.39.1.18
		-- 1.3.6.1.4.1.37950.1.1.5.12.9.2.39.1.18
		wanConnPppoePasswordS OBJECT-TYPE
			SYNTAX OCTET STRING
			MAX-ACCESS read-write
			STATUS current
			DESCRIPTION
				"Description."
			::= { onuWanConnPFEntry 18 }

		
--          1.3.6.1.4.1.37950.1.1.5.12.9.2.39.1.19
-- 1.3.6.1.4.1.37950.1.1.5.12.9.2.39.1.19
-- 1.3.6.1.4.1.37950.1.1.5.12.9.2.39.1.19
-- 1.3.6.1.4.1.37950.1.1.5.12.9.2.39.1.19
-- 1.3.6.1.4.1.37950.1.1.5.12.9.2.39.1.19
-- 1.3.6.1.4.1.37950.1.1.5.12.9.2.39.1.19
-- 1.3.6.1.4.1.37950.1.1.5.12.9.2.39.1.19
-- 1.3.6.1.4.1.37950.1.1.5.12.9.2.39.1.19
-- 1.3.6.1.4.1.37950.1.1.5.12.9.2.39.1.19
		-- 1.3.6.1.4.1.37950.1.1.5.12.9.2.39.1.19
		wanConnPppoeSerName OBJECT-TYPE
			SYNTAX OCTET STRING
			MAX-ACCESS read-write
			STATUS current
			DESCRIPTION
				"Description."
			::= { onuWanConnPFEntry 19 }

		
--          1.3.6.1.4.1.37950.1.1.5.12.9.2.39.1.20
-- 1.3.6.1.4.1.37950.1.1.5.12.9.2.39.1.20
-- 1.3.6.1.4.1.37950.1.1.5.12.9.2.39.1.20
-- 1.3.6.1.4.1.37950.1.1.5.12.9.2.39.1.20
-- 1.3.6.1.4.1.37950.1.1.5.12.9.2.39.1.20
-- 1.3.6.1.4.1.37950.1.1.5.12.9.2.39.1.20
-- 1.3.6.1.4.1.37950.1.1.5.12.9.2.39.1.20
-- 1.3.6.1.4.1.37950.1.1.5.12.9.2.39.1.20
-- 1.3.6.1.4.1.37950.1.1.5.12.9.2.39.1.20
		-- 1.3.6.1.4.1.37950.1.1.5.12.9.2.39.1.20
		wanConnPppoeModeS OBJECT-TYPE
			SYNTAX INTEGER
				{
				autoConnect(0),
				connectWhenPayload(1)
				}
			MAX-ACCESS read-write
			STATUS current
			DESCRIPTION
				"Description."
			::= { onuWanConnPFEntry 20 }

		
--          1.3.6.1.4.1.37950.1.1.5.12.9.2.39.1.21
-- 1.3.6.1.4.1.37950.1.1.5.12.9.2.39.1.21
-- 1.3.6.1.4.1.37950.1.1.5.12.9.2.39.1.21
-- 1.3.6.1.4.1.37950.1.1.5.12.9.2.39.1.21
-- 1.3.6.1.4.1.37950.1.1.5.12.9.2.39.1.21
-- 1.3.6.1.4.1.37950.1.1.5.12.9.2.39.1.21
-- 1.3.6.1.4.1.37950.1.1.5.12.9.2.39.1.21
-- 1.3.6.1.4.1.37950.1.1.5.12.9.2.39.1.21
-- 1.3.6.1.4.1.37950.1.1.5.12.9.2.39.1.21
		-- 1.3.6.1.4.1.37950.1.1.5.12.9.2.39.1.21
		wanConnQosEnableS OBJECT-TYPE
			SYNTAX INTEGER
				{
				disable(0),
				enable(1)
				}
			MAX-ACCESS read-write
			STATUS current
			DESCRIPTION
				"Description."
			::= { onuWanConnPFEntry 21 }

		
--          1.3.6.1.4.1.37950.1.1.5.12.9.2.39.1.22
-- 1.3.6.1.4.1.37950.1.1.5.12.9.2.39.1.22
-- 1.3.6.1.4.1.37950.1.1.5.12.9.2.39.1.22
-- 1.3.6.1.4.1.37950.1.1.5.12.9.2.39.1.22
-- 1.3.6.1.4.1.37950.1.1.5.12.9.2.39.1.22
-- 1.3.6.1.4.1.37950.1.1.5.12.9.2.39.1.22
-- 1.3.6.1.4.1.37950.1.1.5.12.9.2.39.1.22
-- 1.3.6.1.4.1.37950.1.1.5.12.9.2.39.1.22
-- 1.3.6.1.4.1.37950.1.1.5.12.9.2.39.1.22
		-- 1.3.6.1.4.1.37950.1.1.5.12.9.2.39.1.22
		wanConnVlanModeS OBJECT-TYPE
			SYNTAX INTEGER
				{
				disable(0),
				tag(1),
				transparent(2)
				}
			MAX-ACCESS read-write
			STATUS current
			DESCRIPTION
				"Description."
			::= { onuWanConnPFEntry 22 }

		
--          1.3.6.1.4.1.37950.1.1.5.12.9.2.39.1.23
-- 1.3.6.1.4.1.37950.1.1.5.12.9.2.39.1.23
-- 1.3.6.1.4.1.37950.1.1.5.12.9.2.39.1.23
-- 1.3.6.1.4.1.37950.1.1.5.12.9.2.39.1.23
-- 1.3.6.1.4.1.37950.1.1.5.12.9.2.39.1.23
-- 1.3.6.1.4.1.37950.1.1.5.12.9.2.39.1.23
-- 1.3.6.1.4.1.37950.1.1.5.12.9.2.39.1.23
-- 1.3.6.1.4.1.37950.1.1.5.12.9.2.39.1.23
-- 1.3.6.1.4.1.37950.1.1.5.12.9.2.39.1.23
		-- 1.3.6.1.4.1.37950.1.1.5.12.9.2.39.1.23
		wanConnTranslationEnableS OBJECT-TYPE
			SYNTAX INTEGER
				{
				disable(0),
				enable(1)
				}
			MAX-ACCESS read-write
			STATUS current
			DESCRIPTION
				"Description."
			::= { onuWanConnPFEntry 23 }

		
--          1.3.6.1.4.1.37950.1.1.5.12.9.2.39.1.24
-- 1.3.6.1.4.1.37950.1.1.5.12.9.2.39.1.24
-- 1.3.6.1.4.1.37950.1.1.5.12.9.2.39.1.24
-- 1.3.6.1.4.1.37950.1.1.5.12.9.2.39.1.24
-- 1.3.6.1.4.1.37950.1.1.5.12.9.2.39.1.24
-- 1.3.6.1.4.1.37950.1.1.5.12.9.2.39.1.24
-- 1.3.6.1.4.1.37950.1.1.5.12.9.2.39.1.24
-- 1.3.6.1.4.1.37950.1.1.5.12.9.2.39.1.24
-- 1.3.6.1.4.1.37950.1.1.5.12.9.2.39.1.24
		-- 1.3.6.1.4.1.37950.1.1.5.12.9.2.39.1.24
		wanConnTranslationVlanS OBJECT-TYPE
			SYNTAX INTEGER (0..4095)
			MAX-ACCESS read-write
			STATUS current
			DESCRIPTION
				"Description."
			::= { onuWanConnPFEntry 24 }

		
--          1.3.6.1.4.1.37950.1.1.5.12.9.2.39.1.25
-- 1.3.6.1.4.1.37950.1.1.5.12.9.2.39.1.25
-- 1.3.6.1.4.1.37950.1.1.5.12.9.2.39.1.25
-- 1.3.6.1.4.1.37950.1.1.5.12.9.2.39.1.25
-- 1.3.6.1.4.1.37950.1.1.5.12.9.2.39.1.25
-- 1.3.6.1.4.1.37950.1.1.5.12.9.2.39.1.25
-- 1.3.6.1.4.1.37950.1.1.5.12.9.2.39.1.25
-- 1.3.6.1.4.1.37950.1.1.5.12.9.2.39.1.25
-- 1.3.6.1.4.1.37950.1.1.5.12.9.2.39.1.25
		-- 1.3.6.1.4.1.37950.1.1.5.12.9.2.39.1.25
		wanConnTranslationCosS OBJECT-TYPE
			SYNTAX INTEGER (0..7)
			MAX-ACCESS read-write
			STATUS current
			DESCRIPTION
				"Description."
			::= { onuWanConnPFEntry 25 }

		
--          1.3.6.1.4.1.37950.1.1.5.12.9.2.39.1.26
-- 1.3.6.1.4.1.37950.1.1.5.12.9.2.39.1.26
-- 1.3.6.1.4.1.37950.1.1.5.12.9.2.39.1.26
-- 1.3.6.1.4.1.37950.1.1.5.12.9.2.39.1.26
-- 1.3.6.1.4.1.37950.1.1.5.12.9.2.39.1.26
-- 1.3.6.1.4.1.37950.1.1.5.12.9.2.39.1.26
-- 1.3.6.1.4.1.37950.1.1.5.12.9.2.39.1.26
-- 1.3.6.1.4.1.37950.1.1.5.12.9.2.39.1.26
-- 1.3.6.1.4.1.37950.1.1.5.12.9.2.39.1.26
		-- 1.3.6.1.4.1.37950.1.1.5.12.9.2.39.1.26
		wanConnQinqEnableS OBJECT-TYPE
			SYNTAX INTEGER
				{
				disable(0),
				enable(1)
				}
			MAX-ACCESS read-write
			STATUS current
			DESCRIPTION
				"Description."
			::= { onuWanConnPFEntry 26 }

		
--          1.3.6.1.4.1.37950.1.1.5.12.9.2.39.1.27
-- 1.3.6.1.4.1.37950.1.1.5.12.9.2.39.1.27
-- 1.3.6.1.4.1.37950.1.1.5.12.9.2.39.1.27
-- 1.3.6.1.4.1.37950.1.1.5.12.9.2.39.1.27
-- 1.3.6.1.4.1.37950.1.1.5.12.9.2.39.1.27
-- 1.3.6.1.4.1.37950.1.1.5.12.9.2.39.1.27
-- 1.3.6.1.4.1.37950.1.1.5.12.9.2.39.1.27
-- 1.3.6.1.4.1.37950.1.1.5.12.9.2.39.1.27
-- 1.3.6.1.4.1.37950.1.1.5.12.9.2.39.1.27
		-- 1.3.6.1.4.1.37950.1.1.5.12.9.2.39.1.27
		wanConnQinqTpidS OBJECT-TYPE
			SYNTAX INTEGER (0..65534)
			MAX-ACCESS read-write
			STATUS current
			DESCRIPTION
				"Description."
			::= { onuWanConnPFEntry 27 }

		
--          1.3.6.1.4.1.37950.1.1.5.12.9.2.39.1.28
-- 1.3.6.1.4.1.37950.1.1.5.12.9.2.39.1.28
-- 1.3.6.1.4.1.37950.1.1.5.12.9.2.39.1.28
-- 1.3.6.1.4.1.37950.1.1.5.12.9.2.39.1.28
-- 1.3.6.1.4.1.37950.1.1.5.12.9.2.39.1.28
-- 1.3.6.1.4.1.37950.1.1.5.12.9.2.39.1.28
-- 1.3.6.1.4.1.37950.1.1.5.12.9.2.39.1.28
-- 1.3.6.1.4.1.37950.1.1.5.12.9.2.39.1.28
-- 1.3.6.1.4.1.37950.1.1.5.12.9.2.39.1.28
		-- 1.3.6.1.4.1.37950.1.1.5.12.9.2.39.1.28
		wanConnSvlanIdS OBJECT-TYPE
			SYNTAX INTEGER (0..4095)
			MAX-ACCESS read-write
			STATUS current
			DESCRIPTION
				"Description."
			::= { onuWanConnPFEntry 28 }

		
--          1.3.6.1.4.1.37950.1.1.5.12.9.2.39.1.29
-- 1.3.6.1.4.1.37950.1.1.5.12.9.2.39.1.29
-- 1.3.6.1.4.1.37950.1.1.5.12.9.2.39.1.29
-- 1.3.6.1.4.1.37950.1.1.5.12.9.2.39.1.29
-- 1.3.6.1.4.1.37950.1.1.5.12.9.2.39.1.29
-- 1.3.6.1.4.1.37950.1.1.5.12.9.2.39.1.29
-- 1.3.6.1.4.1.37950.1.1.5.12.9.2.39.1.29
-- 1.3.6.1.4.1.37950.1.1.5.12.9.2.39.1.29
-- 1.3.6.1.4.1.37950.1.1.5.12.9.2.39.1.29
		-- 1.3.6.1.4.1.37950.1.1.5.12.9.2.39.1.29
		wanConnSvlanCosS OBJECT-TYPE
			SYNTAX INTEGER (0..7)
			MAX-ACCESS read-write
			STATUS current
			DESCRIPTION
				"Description."
			::= { onuWanConnPFEntry 29 }

		
--           1.3.6.1.4.1.37950.1.1.5.12.9.2.39.1.29
-- 1.3.6.1.4.1.37950.1.1.5.12.9.2.39.1.30
-- 1.3.6.1.4.1.37950.1.1.5.12.9.2.39.1.30
-- 1.3.6.1.4.1.37950.1.1.5.12.9.2.39.1.30
-- 1.3.6.1.4.1.37950.1.1.5.12.9.2.39.1.30
-- 1.3.6.1.4.1.37950.1.1.5.12.9.2.39.1.30
-- 1.3.6.1.4.1.37950.1.1.5.12.9.2.39.1.30
-- 1.3.6.1.4.1.37950.1.1.5.12.9.2.39.1.30
-- 1.3.6.1.4.1.37950.1.1.5.12.9.2.39.1.30
		-- 1.3.6.1.4.1.37950.1.1.5.12.9.2.39.1.30
		wanConnRouteMtuS OBJECT-TYPE
			SYNTAX INTEGER (0 | 576..1500)
			MAX-ACCESS read-write
			STATUS current
			DESCRIPTION
				"Description."
			::= { onuWanConnPFEntry 30 }

		
--          1.3.6.1.4.1.37950.1.1.5.12.9.2.40
-- 1.3.6.1.4.1.37950.1.1.5.12.9.2.40
-- 1.3.6.1.4.1.37950.1.1.5.12.9.2.40
-- 1.3.6.1.4.1.37950.1.1.5.12.9.2.40
-- 1.3.6.1.4.1.37950.1.1.5.12.9.2.40
-- 1.3.6.1.4.1.37950.1.1.5.12.9.2.40
-- 1.3.6.1.4.1.37950.1.1.5.12.9.2.40
-- 1.3.6.1.4.1.37950.1.1.5.12.9.2.40
-- 1.3.6.1.4.1.37950.1.1.5.12.9.2.40
		-- 1.3.6.1.4.1.37950.1.1.5.12.9.2.40
		portMacLimitPFTable OBJECT-TYPE
			SYNTAX SEQUENCE OF PortMacLimitPFEntry
			MAX-ACCESS not-accessible
			STATUS current
			DESCRIPTION
				"Description."
			::= { srvProfileShow 40 }

		
--          1.3.6.1.4.1.37950.1.1.5.12.9.2.40.1
-- 1.3.6.1.4.1.37950.1.1.5.12.9.2.40.1
-- 1.3.6.1.4.1.37950.1.1.5.12.9.2.40.1
-- 1.3.6.1.4.1.37950.1.1.5.12.9.2.40.1
-- 1.3.6.1.4.1.37950.1.1.5.12.9.2.40.1
-- 1.3.6.1.4.1.37950.1.1.5.12.9.2.40.1
-- 1.3.6.1.4.1.37950.1.1.5.12.9.2.40.1
-- 1.3.6.1.4.1.37950.1.1.5.12.9.2.40.1
-- 1.3.6.1.4.1.37950.1.1.5.12.9.2.40.1
		-- 1.3.6.1.4.1.37950.1.1.5.12.9.2.40.1
		portMacLimitPFEntry OBJECT-TYPE
			SYNTAX PortMacLimitPFEntry
			MAX-ACCESS not-accessible
			STATUS current
			DESCRIPTION
				"Description."
			INDEX { portMacLimitSrvId, portMacLimitEthNoS }
			::= { portMacLimitPFTable 1 }

		
		PortMacLimitPFEntry ::=
			SEQUENCE { 
				portMacLimitSrvId
					INTEGER,
				portMacLimitEthNoS
					INTEGER,
				portMacLimitS
					INTEGER
			 }

--          1.3.6.1.4.1.37950.1.1.5.12.9.2.40.1.1
-- 1.3.6.1.4.1.37950.1.1.5.12.9.2.40.1.1
-- 1.3.6.1.4.1.37950.1.1.5.12.9.2.40.1.1
-- 1.3.6.1.4.1.37950.1.1.5.12.9.2.40.1.1
-- 1.3.6.1.4.1.37950.1.1.5.12.9.2.40.1.1
-- 1.3.6.1.4.1.37950.1.1.5.12.9.2.40.1.1
-- 1.3.6.1.4.1.37950.1.1.5.12.9.2.40.1.1
-- 1.3.6.1.4.1.37950.1.1.5.12.9.2.40.1.1
-- 1.3.6.1.4.1.37950.1.1.5.12.9.2.40.1.1
		-- 1.3.6.1.4.1.37950.1.1.5.12.9.2.40.1.1
		portMacLimitSrvId OBJECT-TYPE
			SYNTAX INTEGER (0..65535)
			MAX-ACCESS read-write
			STATUS current
			DESCRIPTION
				"Description."
			::= { portMacLimitPFEntry 1 }

		
--          1.3.6.1.4.1.37950.1.1.5.12.9.2.40.1.2
-- 1.3.6.1.4.1.37950.1.1.5.12.9.2.40.1.2
-- 1.3.6.1.4.1.37950.1.1.5.12.9.2.40.1.2
-- 1.3.6.1.4.1.37950.1.1.5.12.9.2.40.1.2
-- 1.3.6.1.4.1.37950.1.1.5.12.9.2.40.1.2
-- 1.3.6.1.4.1.37950.1.1.5.12.9.2.40.1.2
-- 1.3.6.1.4.1.37950.1.1.5.12.9.2.40.1.2
-- 1.3.6.1.4.1.37950.1.1.5.12.9.2.40.1.2
-- 1.3.6.1.4.1.37950.1.1.5.12.9.2.40.1.2
		-- 1.3.6.1.4.1.37950.1.1.5.12.9.2.40.1.2
		portMacLimitEthNoS OBJECT-TYPE
			SYNTAX INTEGER (1..255)
			MAX-ACCESS read-write
			STATUS current
			DESCRIPTION
				"Description."
			::= { portMacLimitPFEntry 2 }

		
--          1.3.6.1.4.1.37950.1.1.5.12.9.2.40.1.3
-- 1.3.6.1.4.1.37950.1.1.5.12.9.2.40.1.3
-- 1.3.6.1.4.1.37950.1.1.5.12.9.2.40.1.3
-- 1.3.6.1.4.1.37950.1.1.5.12.9.2.40.1.3
-- 1.3.6.1.4.1.37950.1.1.5.12.9.2.40.1.3
-- 1.3.6.1.4.1.37950.1.1.5.12.9.2.40.1.3
-- 1.3.6.1.4.1.37950.1.1.5.12.9.2.40.1.3
-- 1.3.6.1.4.1.37950.1.1.5.12.9.2.40.1.3
-- 1.3.6.1.4.1.37950.1.1.5.12.9.2.40.1.3
		-- 1.3.6.1.4.1.37950.1.1.5.12.9.2.40.1.3
		portMacLimitS OBJECT-TYPE
			SYNTAX INTEGER (0..65535)
			MAX-ACCESS read-write
			STATUS current
			DESCRIPTION
				"Description."
			::= { portMacLimitPFEntry 3 }

		
--          1.3.6.1.4.1.37950.1.1.5.12.9.2.41
-- 1.3.6.1.4.1.37950.1.1.5.12.9.2.41
-- 1.3.6.1.4.1.37950.1.1.5.12.9.2.41
-- 1.3.6.1.4.1.37950.1.1.5.12.9.2.41
-- 1.3.6.1.4.1.37950.1.1.5.12.9.2.41
-- 1.3.6.1.4.1.37950.1.1.5.12.9.2.41
-- 1.3.6.1.4.1.37950.1.1.5.12.9.2.41
-- 1.3.6.1.4.1.37950.1.1.5.12.9.2.41
-- 1.3.6.1.4.1.37950.1.1.5.12.9.2.41
		-- 1.3.6.1.4.1.37950.1.1.5.12.9.2.41
		portPkgSuppressPFTable OBJECT-TYPE
			SYNTAX SEQUENCE OF PortPkgSuppressPFEntry
			MAX-ACCESS not-accessible
			STATUS current
			DESCRIPTION
				"Description."
			::= { srvProfileShow 41 }

		
--          1.3.6.1.4.1.37950.1.1.5.12.9.2.41.1
-- 1.3.6.1.4.1.37950.1.1.5.12.9.2.41.1
-- 1.3.6.1.4.1.37950.1.1.5.12.9.2.41.1
-- 1.3.6.1.4.1.37950.1.1.5.12.9.2.41.1
-- 1.3.6.1.4.1.37950.1.1.5.12.9.2.41.1
-- 1.3.6.1.4.1.37950.1.1.5.12.9.2.41.1
-- 1.3.6.1.4.1.37950.1.1.5.12.9.2.41.1
-- 1.3.6.1.4.1.37950.1.1.5.12.9.2.41.1
-- 1.3.6.1.4.1.37950.1.1.5.12.9.2.41.1
		-- 1.3.6.1.4.1.37950.1.1.5.12.9.2.41.1
		portPkgSuppressPFEntry OBJECT-TYPE
			SYNTAX PortPkgSuppressPFEntry
			MAX-ACCESS not-accessible
			STATUS current
			DESCRIPTION
				"Description."
			INDEX { portPkgSuppressSrvId, portPkgSuppressEthNoS }
			::= { portPkgSuppressPFTable 1 }

		
		PortPkgSuppressPFEntry ::=
			SEQUENCE { 
				portPkgSuppressSrvId
					INTEGER,
				portPkgSuppressEthNoS
					INTEGER,
				portPkgSuppressBroadcastS
					INTEGER,
				portPkgSuppressMulticastS
					INTEGER,
				portPkgSuppressUnkownS
					INTEGER
			 }

--          1.3.6.1.4.1.37950.1.1.5.12.9.2.41.1.1
-- 1.3.6.1.4.1.37950.1.1.5.12.9.2.41.1.1
-- 1.3.6.1.4.1.37950.1.1.5.12.9.2.41.1.1
-- 1.3.6.1.4.1.37950.1.1.5.12.9.2.41.1.1
-- 1.3.6.1.4.1.37950.1.1.5.12.9.2.41.1.1
-- 1.3.6.1.4.1.37950.1.1.5.12.9.2.41.1.1
-- 1.3.6.1.4.1.37950.1.1.5.12.9.2.41.1.1
-- 1.3.6.1.4.1.37950.1.1.5.12.9.2.41.1.1
-- 1.3.6.1.4.1.37950.1.1.5.12.9.2.41.1.1
		-- 1.3.6.1.4.1.37950.1.1.5.12.9.2.41.1.1
		portPkgSuppressSrvId OBJECT-TYPE
			SYNTAX INTEGER (0..65535)
			MAX-ACCESS read-write
			STATUS current
			DESCRIPTION
				"Description."
			::= { portPkgSuppressPFEntry 1 }

		
--          1.3.6.1.4.1.37950.1.1.5.12.9.2.41.1.2
-- 1.3.6.1.4.1.37950.1.1.5.12.9.2.41.1.2
-- 1.3.6.1.4.1.37950.1.1.5.12.9.2.41.1.2
-- 1.3.6.1.4.1.37950.1.1.5.12.9.2.41.1.2
-- 1.3.6.1.4.1.37950.1.1.5.12.9.2.41.1.2
-- 1.3.6.1.4.1.37950.1.1.5.12.9.2.41.1.2
-- 1.3.6.1.4.1.37950.1.1.5.12.9.2.41.1.2
-- 1.3.6.1.4.1.37950.1.1.5.12.9.2.41.1.2
-- 1.3.6.1.4.1.37950.1.1.5.12.9.2.41.1.2
		-- 1.3.6.1.4.1.37950.1.1.5.12.9.2.41.1.2
		portPkgSuppressEthNoS OBJECT-TYPE
			SYNTAX INTEGER (1..255)
			MAX-ACCESS read-write
			STATUS current
			DESCRIPTION
				"Description."
			::= { portPkgSuppressPFEntry 2 }

		
--          1.3.6.1.4.1.37950.1.1.5.12.9.2.41.1.3
-- 1.3.6.1.4.1.37950.1.1.5.12.9.2.41.1.3
-- 1.3.6.1.4.1.37950.1.1.5.12.9.2.41.1.3
-- 1.3.6.1.4.1.37950.1.1.5.12.9.2.41.1.3
-- 1.3.6.1.4.1.37950.1.1.5.12.9.2.41.1.3
-- 1.3.6.1.4.1.37950.1.1.5.12.9.2.41.1.3
-- 1.3.6.1.4.1.37950.1.1.5.12.9.2.41.1.3
-- 1.3.6.1.4.1.37950.1.1.5.12.9.2.41.1.3
-- 1.3.6.1.4.1.37950.1.1.5.12.9.2.41.1.3
		-- 1.3.6.1.4.1.37950.1.1.5.12.9.2.41.1.3
		portPkgSuppressBroadcastS OBJECT-TYPE
			SYNTAX INTEGER (0..1024000)
			MAX-ACCESS read-write
			STATUS current
			DESCRIPTION
				"Description."
			::= { portPkgSuppressPFEntry 3 }

		
--          1.3.6.1.4.1.37950.1.1.5.12.9.2.41.1.4
-- 1.3.6.1.4.1.37950.1.1.5.12.9.2.41.1.4
-- 1.3.6.1.4.1.37950.1.1.5.12.9.2.41.1.4
-- 1.3.6.1.4.1.37950.1.1.5.12.9.2.41.1.4
-- 1.3.6.1.4.1.37950.1.1.5.12.9.2.41.1.4
-- 1.3.6.1.4.1.37950.1.1.5.12.9.2.41.1.4
-- 1.3.6.1.4.1.37950.1.1.5.12.9.2.41.1.4
-- 1.3.6.1.4.1.37950.1.1.5.12.9.2.41.1.4
-- 1.3.6.1.4.1.37950.1.1.5.12.9.2.41.1.4
		-- 1.3.6.1.4.1.37950.1.1.5.12.9.2.41.1.4
		portPkgSuppressMulticastS OBJECT-TYPE
			SYNTAX INTEGER (0..1024000)
			MAX-ACCESS read-write
			STATUS current
			DESCRIPTION
				"Description."
			::= { portPkgSuppressPFEntry 4 }

		
--          1.3.6.1.4.1.37950.1.1.5.12.9.2.41.1.5
-- 1.3.6.1.4.1.37950.1.1.5.12.9.2.41.1.5
-- 1.3.6.1.4.1.37950.1.1.5.12.9.2.41.1.5
-- 1.3.6.1.4.1.37950.1.1.5.12.9.2.41.1.5
-- 1.3.6.1.4.1.37950.1.1.5.12.9.2.41.1.5
-- 1.3.6.1.4.1.37950.1.1.5.12.9.2.41.1.5
-- 1.3.6.1.4.1.37950.1.1.5.12.9.2.41.1.5
-- 1.3.6.1.4.1.37950.1.1.5.12.9.2.41.1.5
-- 1.3.6.1.4.1.37950.1.1.5.12.9.2.41.1.5
		-- 1.3.6.1.4.1.37950.1.1.5.12.9.2.41.1.5
		portPkgSuppressUnkownS OBJECT-TYPE
			SYNTAX INTEGER (0..1024000)
			MAX-ACCESS read-write
			STATUS current
			DESCRIPTION
				"Description."
			::= { portPkgSuppressPFEntry 5 }

		
--          1.3.6.1.4.1.37950.1.1.5.12.9.2.42
-- 1.3.6.1.4.1.37950.1.1.5.12.9.2.42
-- 1.3.6.1.4.1.37950.1.1.5.12.9.2.42
-- 1.3.6.1.4.1.37950.1.1.5.12.9.2.42
-- 1.3.6.1.4.1.37950.1.1.5.12.9.2.42
-- 1.3.6.1.4.1.37950.1.1.5.12.9.2.42
-- 1.3.6.1.4.1.37950.1.1.5.12.9.2.42
-- 1.3.6.1.4.1.37950.1.1.5.12.9.2.42
-- 1.3.6.1.4.1.37950.1.1.5.12.9.2.42
		-- 1.3.6.1.4.1.37950.1.1.5.12.9.2.42
		portIsolateTable OBJECT-TYPE
			SYNTAX SEQUENCE OF PortIsolateEntry
			MAX-ACCESS not-accessible
			STATUS current
			DESCRIPTION
				"Description."
			::= { srvProfileShow 42 }

		
--          1.3.6.1.4.1.37950.1.1.5.12.9.2.42.1
-- 1.3.6.1.4.1.37950.1.1.5.12.9.2.42.1
-- 1.3.6.1.4.1.37950.1.1.5.12.9.2.42.1
-- 1.3.6.1.4.1.37950.1.1.5.12.9.2.42.1
-- 1.3.6.1.4.1.37950.1.1.5.12.9.2.42.1
-- 1.3.6.1.4.1.37950.1.1.5.12.9.2.42.1
-- 1.3.6.1.4.1.37950.1.1.5.12.9.2.42.1
-- 1.3.6.1.4.1.37950.1.1.5.12.9.2.42.1
-- 1.3.6.1.4.1.37950.1.1.5.12.9.2.42.1
		-- 1.3.6.1.4.1.37950.1.1.5.12.9.2.42.1
		portIsolateEntry OBJECT-TYPE
			SYNTAX PortIsolateEntry
			MAX-ACCESS not-accessible
			STATUS current
			DESCRIPTION
				"Description."
			INDEX { portIsolateSrvId }
			::= { portIsolateTable 1 }

		
		PortIsolateEntry ::=
			SEQUENCE { 
				portIsolateSrvId
					INTEGER,
				portIsolateS
					INTEGER
			 }

--          1.3.6.1.4.1.37950.1.1.5.12.9.2.42.1.1
-- 1.3.6.1.4.1.37950.1.1.5.12.9.2.42.1.1
-- 1.3.6.1.4.1.37950.1.1.5.12.9.2.42.1.1
-- 1.3.6.1.4.1.37950.1.1.5.12.9.2.42.1.1
-- 1.3.6.1.4.1.37950.1.1.5.12.9.2.42.1.1
-- 1.3.6.1.4.1.37950.1.1.5.12.9.2.42.1.1
-- 1.3.6.1.4.1.37950.1.1.5.12.9.2.42.1.1
-- 1.3.6.1.4.1.37950.1.1.5.12.9.2.42.1.1
-- 1.3.6.1.4.1.37950.1.1.5.12.9.2.42.1.1
		-- 1.3.6.1.4.1.37950.1.1.5.12.9.2.42.1.1
		portIsolateSrvId OBJECT-TYPE
			SYNTAX INTEGER (1..65535)
			MAX-ACCESS read-write
			STATUS current
			DESCRIPTION
				"Description."
			::= { portIsolateEntry 1 }

		
--          1.3.6.1.4.1.37950.1.1.5.12.9.2.42.1.2
-- 1.3.6.1.4.1.37950.1.1.5.12.9.2.42.1.2
-- 1.3.6.1.4.1.37950.1.1.5.12.9.2.42.1.2
-- 1.3.6.1.4.1.37950.1.1.5.12.9.2.42.1.2
-- 1.3.6.1.4.1.37950.1.1.5.12.9.2.42.1.2
-- 1.3.6.1.4.1.37950.1.1.5.12.9.2.42.1.2
-- 1.3.6.1.4.1.37950.1.1.5.12.9.2.42.1.2
-- 1.3.6.1.4.1.37950.1.1.5.12.9.2.42.1.2
-- 1.3.6.1.4.1.37950.1.1.5.12.9.2.42.1.2
		-- 1.3.6.1.4.1.37950.1.1.5.12.9.2.42.1.2
		portIsolateS OBJECT-TYPE
			SYNTAX INTEGER
				{
				disable(0),
				enable(1)
				}
			MAX-ACCESS read-write
			STATUS current
			DESCRIPTION
				"Description."
			::= { portIsolateEntry 2 }

		
--          1.3.6.1.4.1.37950.1.1.5.12.9.2.43
-- 1.3.6.1.4.1.37950.1.1.5.12.9.2.43
-- 1.3.6.1.4.1.37950.1.1.5.12.9.2.43
-- 1.3.6.1.4.1.37950.1.1.5.12.9.2.43
-- 1.3.6.1.4.1.37950.1.1.5.12.9.2.43
-- 1.3.6.1.4.1.37950.1.1.5.12.9.2.43
-- 1.3.6.1.4.1.37950.1.1.5.12.9.2.43
-- 1.3.6.1.4.1.37950.1.1.5.12.9.2.43
-- 1.3.6.1.4.1.37950.1.1.5.12.9.2.43
		-- 1.3.6.1.4.1.37950.1.1.5.12.9.2.43
		portModeControlTable OBJECT-TYPE
			SYNTAX SEQUENCE OF PortModeControlEntry
			MAX-ACCESS not-accessible
			STATUS current
			DESCRIPTION
				"Description."
			::= { srvProfileShow 43 }

		
--          1.3.6.1.4.1.37950.1.1.5.12.9.2.43.1
-- 1.3.6.1.4.1.37950.1.1.5.12.9.2.43.1
-- 1.3.6.1.4.1.37950.1.1.5.12.9.2.43.1
-- 1.3.6.1.4.1.37950.1.1.5.12.9.2.43.1
-- 1.3.6.1.4.1.37950.1.1.5.12.9.2.43.1
-- 1.3.6.1.4.1.37950.1.1.5.12.9.2.43.1
-- 1.3.6.1.4.1.37950.1.1.5.12.9.2.43.1
-- 1.3.6.1.4.1.37950.1.1.5.12.9.2.43.1
-- 1.3.6.1.4.1.37950.1.1.5.12.9.2.43.1
		-- 1.3.6.1.4.1.37950.1.1.5.12.9.2.43.1
		portModeControlEntry OBJECT-TYPE
			SYNTAX PortModeControlEntry
			MAX-ACCESS not-accessible
			STATUS current
			DESCRIPTION
				"Description."
			INDEX { portModeControlSrvId, portModeControlEthNoS }
			::= { portModeControlTable 1 }

		
		PortModeControlEntry ::=
			SEQUENCE { 
				portModeControlSrvId
					Integer32,
				portModeControlEthNoS
					Integer32,
				portModeControlS
					INTEGER
			 }

--          1.3.6.1.4.1.37950.1.1.5.12.9.2.43.1.1
-- 1.3.6.1.4.1.37950.1.1.5.12.9.2.43.1.1
-- 1.3.6.1.4.1.37950.1.1.5.12.9.2.43.1.1
-- 1.3.6.1.4.1.37950.1.1.5.12.9.2.43.1.1
-- 1.3.6.1.4.1.37950.1.1.5.12.9.2.43.1.1
-- 1.3.6.1.4.1.37950.1.1.5.12.9.2.43.1.1
-- 1.3.6.1.4.1.37950.1.1.5.12.9.2.43.1.1
-- 1.3.6.1.4.1.37950.1.1.5.12.9.2.43.1.1
-- 1.3.6.1.4.1.37950.1.1.5.12.9.2.43.1.1
		-- 1.3.6.1.4.1.37950.1.1.5.12.9.2.43.1.1
		portModeControlSrvId OBJECT-TYPE
			SYNTAX Integer32
			MAX-ACCESS read-write
			STATUS current
			DESCRIPTION
				"Description."
			::= { portModeControlEntry 1 }

		
--          1.3.6.1.4.1.37950.1.1.5.12.9.2.43.1.2
-- 1.3.6.1.4.1.37950.1.1.5.12.9.2.43.1.2
-- 1.3.6.1.4.1.37950.1.1.5.12.9.2.43.1.2
-- 1.3.6.1.4.1.37950.1.1.5.12.9.2.43.1.2
-- 1.3.6.1.4.1.37950.1.1.5.12.9.2.43.1.2
-- 1.3.6.1.4.1.37950.1.1.5.12.9.2.43.1.2
-- 1.3.6.1.4.1.37950.1.1.5.12.9.2.43.1.2
-- 1.3.6.1.4.1.37950.1.1.5.12.9.2.43.1.2
-- 1.3.6.1.4.1.37950.1.1.5.12.9.2.43.1.2
		-- 1.3.6.1.4.1.37950.1.1.5.12.9.2.43.1.2
		portModeControlEthNoS OBJECT-TYPE
			SYNTAX Integer32
			MAX-ACCESS read-write
			STATUS current
			DESCRIPTION
				"Description."
			::= { portModeControlEntry 2 }

		
--          1.3.6.1.4.1.37950.1.1.5.12.9.2.43.1.3
-- 1.3.6.1.4.1.37950.1.1.5.12.9.2.43.1.3
-- 1.3.6.1.4.1.37950.1.1.5.12.9.2.43.1.3
-- 1.3.6.1.4.1.37950.1.1.5.12.9.2.43.1.3
-- 1.3.6.1.4.1.37950.1.1.5.12.9.2.43.1.3
-- 1.3.6.1.4.1.37950.1.1.5.12.9.2.43.1.3
-- 1.3.6.1.4.1.37950.1.1.5.12.9.2.43.1.3
-- 1.3.6.1.4.1.37950.1.1.5.12.9.2.43.1.3
-- 1.3.6.1.4.1.37950.1.1.5.12.9.2.43.1.3
		-- 1.3.6.1.4.1.37950.1.1.5.12.9.2.43.1.3
		portModeControlS OBJECT-TYPE
			SYNTAX INTEGER
				{
				s10hd(1),
				s10fd(2),
				s100hd(3),
				s100fd(4),
				s1000hd(5),
				s1000fd(6),
				s10000fd(7)
				}
			MAX-ACCESS read-write
			STATUS current
			DESCRIPTION
				"Description."
			::= { portModeControlEntry 3 }

		
--          1.3.6.1.4.1.37950.1.1.5.12.9.2.44
-- 1.3.6.1.4.1.37950.1.1.5.12.9.2.44
-- 1.3.6.1.4.1.37950.1.1.5.12.9.2.44
-- 1.3.6.1.4.1.37950.1.1.5.12.9.2.44
-- 1.3.6.1.4.1.37950.1.1.5.12.9.2.44
-- 1.3.6.1.4.1.37950.1.1.5.12.9.2.44
-- 1.3.6.1.4.1.37950.1.1.5.12.9.2.44
-- 1.3.6.1.4.1.37950.1.1.5.12.9.2.44
-- 1.3.6.1.4.1.37950.1.1.5.12.9.2.44
		-- 1.3.6.1.4.1.37950.1.1.5.12.9.2.44
		onuDhcpServerTable OBJECT-TYPE
			SYNTAX SEQUENCE OF OnuDhcpServerEntry
			MAX-ACCESS not-accessible
			STATUS current
			DESCRIPTION
				"Description."
			::= { srvProfileShow 44 }

		
--          1.3.6.1.4.1.37950.1.1.5.12.9.2.44.1
-- 1.3.6.1.4.1.37950.1.1.5.12.9.2.44.1
-- 1.3.6.1.4.1.37950.1.1.5.12.9.2.44.1
-- 1.3.6.1.4.1.37950.1.1.5.12.9.2.44.1
-- 1.3.6.1.4.1.37950.1.1.5.12.9.2.44.1
-- 1.3.6.1.4.1.37950.1.1.5.12.9.2.44.1
-- 1.3.6.1.4.1.37950.1.1.5.12.9.2.44.1
-- 1.3.6.1.4.1.37950.1.1.5.12.9.2.44.1
-- 1.3.6.1.4.1.37950.1.1.5.12.9.2.44.1
		-- 1.3.6.1.4.1.37950.1.1.5.12.9.2.44.1
		onuDhcpServerEntry OBJECT-TYPE
			SYNTAX OnuDhcpServerEntry
			MAX-ACCESS not-accessible
			STATUS current
			DESCRIPTION
				"Description."
			INDEX { onuDhcpSrvId }
			::= { onuDhcpServerTable 1 }

		
		OnuDhcpServerEntry ::=
			SEQUENCE { 
				onuDhcpSrvId
					Integer32,
				onuDhcpLanIp
					IpAddress,
				onuDhcpMask
					IpAddress,
				onuDhcpServerEable
					INTEGER,
				onuDhcpLease
					Unsigned32,
				onuDhcpBeginIp
					IpAddress,
				onuDhcpEndIp
					IpAddress,
				onuDhcpPoolType
					INTEGER,
				onuDhcpMasterDns
					IpAddress,
				onuDhcpSlaveDns
					IpAddress,
				onuDhcpGateway
					IpAddress,
				onuDhcpRelayIp
					IpAddress
			 }

--          1.3.6.1.4.1.37950.1.1.5.12.9.2.44.1.1
-- 1.3.6.1.4.1.37950.1.1.5.12.9.2.44.1.1
-- 1.3.6.1.4.1.37950.1.1.5.12.9.2.44.1.1
-- 1.3.6.1.4.1.37950.1.1.5.12.9.2.44.1.1
-- 1.3.6.1.4.1.37950.1.1.5.12.9.2.44.1.1
-- 1.3.6.1.4.1.37950.1.1.5.12.9.2.44.1.1
-- 1.3.6.1.4.1.37950.1.1.5.12.9.2.44.1.1
-- 1.3.6.1.4.1.37950.1.1.5.12.9.2.44.1.1
-- 1.3.6.1.4.1.37950.1.1.5.12.9.2.44.1.1
		-- 1.3.6.1.4.1.37950.1.1.5.12.9.2.44.1.1
		onuDhcpSrvId OBJECT-TYPE
			SYNTAX Integer32
			MAX-ACCESS read-write
			STATUS current
			DESCRIPTION
				"Description."
			::= { onuDhcpServerEntry 1 }

		
--          1.3.6.1.4.1.37950.1.1.5.12.9.2.44.1.2
-- 1.3.6.1.4.1.37950.1.1.5.12.9.2.44.1.2
-- 1.3.6.1.4.1.37950.1.1.5.12.9.2.44.1.2
-- 1.3.6.1.4.1.37950.1.1.5.12.9.2.44.1.2
-- 1.3.6.1.4.1.37950.1.1.5.12.9.2.44.1.2
-- 1.3.6.1.4.1.37950.1.1.5.12.9.2.44.1.2
-- 1.3.6.1.4.1.37950.1.1.5.12.9.2.44.1.2
-- 1.3.6.1.4.1.37950.1.1.5.12.9.2.44.1.2
-- 1.3.6.1.4.1.37950.1.1.5.12.9.2.44.1.2
		-- 1.3.6.1.4.1.37950.1.1.5.12.9.2.44.1.2
		onuDhcpLanIp OBJECT-TYPE
			SYNTAX IpAddress
			MAX-ACCESS read-write
			STATUS current
			DESCRIPTION
				"Description."
			::= { onuDhcpServerEntry 2 }

		
--          1.3.6.1.4.1.37950.1.1.5.12.9.2.44.1.3
-- 1.3.6.1.4.1.37950.1.1.5.12.9.2.44.1.3
-- 1.3.6.1.4.1.37950.1.1.5.12.9.2.44.1.3
-- 1.3.6.1.4.1.37950.1.1.5.12.9.2.44.1.3
-- 1.3.6.1.4.1.37950.1.1.5.12.9.2.44.1.3
-- 1.3.6.1.4.1.37950.1.1.5.12.9.2.44.1.3
-- 1.3.6.1.4.1.37950.1.1.5.12.9.2.44.1.3
-- 1.3.6.1.4.1.37950.1.1.5.12.9.2.44.1.3
-- 1.3.6.1.4.1.37950.1.1.5.12.9.2.44.1.3
		-- 1.3.6.1.4.1.37950.1.1.5.12.9.2.44.1.3
		onuDhcpMask OBJECT-TYPE
			SYNTAX IpAddress
			MAX-ACCESS read-write
			STATUS current
			DESCRIPTION
				"Description."
			::= { onuDhcpServerEntry 3 }

		
--          1.3.6.1.4.1.37950.1.1.5.12.9.2.44.1.4
-- 1.3.6.1.4.1.37950.1.1.5.12.9.2.44.1.4
-- 1.3.6.1.4.1.37950.1.1.5.12.9.2.44.1.4
-- 1.3.6.1.4.1.37950.1.1.5.12.9.2.44.1.4
-- 1.3.6.1.4.1.37950.1.1.5.12.9.2.44.1.4
-- 1.3.6.1.4.1.37950.1.1.5.12.9.2.44.1.4
-- 1.3.6.1.4.1.37950.1.1.5.12.9.2.44.1.4
-- 1.3.6.1.4.1.37950.1.1.5.12.9.2.44.1.4
-- 1.3.6.1.4.1.37950.1.1.5.12.9.2.44.1.4
		-- 1.3.6.1.4.1.37950.1.1.5.12.9.2.44.1.4
		onuDhcpServerEable OBJECT-TYPE
			SYNTAX INTEGER
				{
				disable(0),
				enable(1),
				relay(2)
				}
			MAX-ACCESS read-write
			STATUS current
			DESCRIPTION
				"Description."
			::= { onuDhcpServerEntry 4 }

		
--          1.3.6.1.4.1.37950.1.1.5.12.9.2.44.1.5
-- 1.3.6.1.4.1.37950.1.1.5.12.9.2.44.1.5
-- 1.3.6.1.4.1.37950.1.1.5.12.9.2.44.1.5
-- 1.3.6.1.4.1.37950.1.1.5.12.9.2.44.1.5
-- 1.3.6.1.4.1.37950.1.1.5.12.9.2.44.1.5
-- 1.3.6.1.4.1.37950.1.1.5.12.9.2.44.1.5
-- 1.3.6.1.4.1.37950.1.1.5.12.9.2.44.1.5
-- 1.3.6.1.4.1.37950.1.1.5.12.9.2.44.1.5
-- 1.3.6.1.4.1.37950.1.1.5.12.9.2.44.1.5
		-- 1.3.6.1.4.1.37950.1.1.5.12.9.2.44.1.5
		onuDhcpLease OBJECT-TYPE
			SYNTAX Unsigned32
			MAX-ACCESS read-write
			STATUS current
			DESCRIPTION
				"Description."
			::= { onuDhcpServerEntry 5 }

		
--          1.3.6.1.4.1.37950.1.1.5.12.9.2.44.1.6
-- 1.3.6.1.4.1.37950.1.1.5.12.9.2.44.1.6
-- 1.3.6.1.4.1.37950.1.1.5.12.9.2.44.1.6
-- 1.3.6.1.4.1.37950.1.1.5.12.9.2.44.1.6
-- 1.3.6.1.4.1.37950.1.1.5.12.9.2.44.1.6
-- 1.3.6.1.4.1.37950.1.1.5.12.9.2.44.1.6
-- 1.3.6.1.4.1.37950.1.1.5.12.9.2.44.1.6
-- 1.3.6.1.4.1.37950.1.1.5.12.9.2.44.1.6
-- 1.3.6.1.4.1.37950.1.1.5.12.9.2.44.1.6
		-- 1.3.6.1.4.1.37950.1.1.5.12.9.2.44.1.6
		onuDhcpBeginIp OBJECT-TYPE
			SYNTAX IpAddress
			MAX-ACCESS read-write
			STATUS current
			DESCRIPTION
				"Description."
			::= { onuDhcpServerEntry 6 }

		
--          1.3.6.1.4.1.37950.1.1.5.12.9.2.44.1.7
-- 1.3.6.1.4.1.37950.1.1.5.12.9.2.44.1.7
-- 1.3.6.1.4.1.37950.1.1.5.12.9.2.44.1.7
-- 1.3.6.1.4.1.37950.1.1.5.12.9.2.44.1.7
-- 1.3.6.1.4.1.37950.1.1.5.12.9.2.44.1.7
-- 1.3.6.1.4.1.37950.1.1.5.12.9.2.44.1.7
-- 1.3.6.1.4.1.37950.1.1.5.12.9.2.44.1.7
-- 1.3.6.1.4.1.37950.1.1.5.12.9.2.44.1.7
-- 1.3.6.1.4.1.37950.1.1.5.12.9.2.44.1.7
		-- 1.3.6.1.4.1.37950.1.1.5.12.9.2.44.1.7
		onuDhcpEndIp OBJECT-TYPE
			SYNTAX IpAddress
			MAX-ACCESS read-write
			STATUS current
			DESCRIPTION
				"Description."
			::= { onuDhcpServerEntry 7 }

		
--          1.3.6.1.4.1.37950.1.1.5.12.9.2.44.1.8
-- 1.3.6.1.4.1.37950.1.1.5.12.9.2.44.1.8
-- 1.3.6.1.4.1.37950.1.1.5.12.9.2.44.1.8
-- 1.3.6.1.4.1.37950.1.1.5.12.9.2.44.1.8
-- 1.3.6.1.4.1.37950.1.1.5.12.9.2.44.1.8
-- 1.3.6.1.4.1.37950.1.1.5.12.9.2.44.1.8
-- 1.3.6.1.4.1.37950.1.1.5.12.9.2.44.1.8
-- 1.3.6.1.4.1.37950.1.1.5.12.9.2.44.1.8
-- 1.3.6.1.4.1.37950.1.1.5.12.9.2.44.1.8
		-- 1.3.6.1.4.1.37950.1.1.5.12.9.2.44.1.8
		onuDhcpPoolType OBJECT-TYPE
			SYNTAX INTEGER
				{
				pc(0),
				camera(1),
				stb(2),
				ip-phone(3)
				}
			MAX-ACCESS read-write
			STATUS current
			DESCRIPTION
				"Description."
			::= { onuDhcpServerEntry 8 }

		
--          1.3.6.1.4.1.37950.1.1.5.12.9.2.44.1.9
-- 1.3.6.1.4.1.37950.1.1.5.12.9.2.44.1.9
-- 1.3.6.1.4.1.37950.1.1.5.12.9.2.44.1.9
-- 1.3.6.1.4.1.37950.1.1.5.12.9.2.44.1.9
-- 1.3.6.1.4.1.37950.1.1.5.12.9.2.44.1.9
-- 1.3.6.1.4.1.37950.1.1.5.12.9.2.44.1.9
-- 1.3.6.1.4.1.37950.1.1.5.12.9.2.44.1.9
-- 1.3.6.1.4.1.37950.1.1.5.12.9.2.44.1.9
-- 1.3.6.1.4.1.37950.1.1.5.12.9.2.44.1.9
		-- 1.3.6.1.4.1.37950.1.1.5.12.9.2.44.1.9
		onuDhcpMasterDns OBJECT-TYPE
			SYNTAX IpAddress
			MAX-ACCESS read-write
			STATUS current
			DESCRIPTION
				"Description."
			::= { onuDhcpServerEntry 9 }

		
--          1.3.6.1.4.1.37950.1.1.5.12.9.2.44.1.10
-- 1.3.6.1.4.1.37950.1.1.5.12.9.2.44.1.10
-- 1.3.6.1.4.1.37950.1.1.5.12.9.2.44.1.10
-- 1.3.6.1.4.1.37950.1.1.5.12.9.2.44.1.10
-- 1.3.6.1.4.1.37950.1.1.5.12.9.2.44.1.10
-- 1.3.6.1.4.1.37950.1.1.5.12.9.2.44.1.10
-- 1.3.6.1.4.1.37950.1.1.5.12.9.2.44.1.10
-- 1.3.6.1.4.1.37950.1.1.5.12.9.2.44.1.10
-- 1.3.6.1.4.1.37950.1.1.5.12.9.2.44.1.10
		-- 1.3.6.1.4.1.37950.1.1.5.12.9.2.44.1.10
		onuDhcpSlaveDns OBJECT-TYPE
			SYNTAX IpAddress
			MAX-ACCESS read-write
			STATUS current
			DESCRIPTION
				"Description."
			::= { onuDhcpServerEntry 10 }

		
--          1.3.6.1.4.1.37950.1.1.5.12.9.2.44.1.11
-- 1.3.6.1.4.1.37950.1.1.5.12.9.2.44.1.11
-- 1.3.6.1.4.1.37950.1.1.5.12.9.2.44.1.11
-- 1.3.6.1.4.1.37950.1.1.5.12.9.2.44.1.11
-- 1.3.6.1.4.1.37950.1.1.5.12.9.2.44.1.11
-- 1.3.6.1.4.1.37950.1.1.5.12.9.2.44.1.11
-- 1.3.6.1.4.1.37950.1.1.5.12.9.2.44.1.11
-- 1.3.6.1.4.1.37950.1.1.5.12.9.2.44.1.11
-- 1.3.6.1.4.1.37950.1.1.5.12.9.2.44.1.11
		-- 1.3.6.1.4.1.37950.1.1.5.12.9.2.44.1.11
		onuDhcpGateway OBJECT-TYPE
			SYNTAX IpAddress
			MAX-ACCESS read-write
			STATUS current
			DESCRIPTION
				"Description."
			::= { onuDhcpServerEntry 11 }

		
--          1.3.6.1.4.1.37950.1.1.5.12.9.2.44.1.12
-- 1.3.6.1.4.1.37950.1.1.5.12.9.2.44.1.12
-- 1.3.6.1.4.1.37950.1.1.5.12.9.2.44.1.12
-- 1.3.6.1.4.1.37950.1.1.5.12.9.2.44.1.12
-- 1.3.6.1.4.1.37950.1.1.5.12.9.2.44.1.12
-- 1.3.6.1.4.1.37950.1.1.5.12.9.2.44.1.12
-- 1.3.6.1.4.1.37950.1.1.5.12.9.2.44.1.12
-- 1.3.6.1.4.1.37950.1.1.5.12.9.2.44.1.12
-- 1.3.6.1.4.1.37950.1.1.5.12.9.2.44.1.12
		-- 1.3.6.1.4.1.37950.1.1.5.12.9.2.44.1.12
		onuDhcpRelayIp OBJECT-TYPE
			SYNTAX IpAddress
			MAX-ACCESS read-write
			STATUS current
			DESCRIPTION
				"Description."
			::= { onuDhcpServerEntry 12 }

		
--          1.3.6.1.4.1.37950.1.1.5.12.9.2.45
-- 1.3.6.1.4.1.37950.1.1.5.12.9.2.45
-- 1.3.6.1.4.1.37950.1.1.5.12.9.2.45
-- 1.3.6.1.4.1.37950.1.1.5.12.9.2.45
-- 1.3.6.1.4.1.37950.1.1.5.12.9.2.45
-- 1.3.6.1.4.1.37950.1.1.5.12.9.2.45
-- 1.3.6.1.4.1.37950.1.1.5.12.9.2.45
-- 1.3.6.1.4.1.37950.1.1.5.12.9.2.45
-- 1.3.6.1.4.1.37950.1.1.5.12.9.2.45
		-- 1.3.6.1.4.1.37950.1.1.5.12.9.2.45
		onuDhcpOption82Table OBJECT-TYPE
			SYNTAX SEQUENCE OF OnuDhcpOption82Entry
			MAX-ACCESS not-accessible
			STATUS current
			DESCRIPTION
				"Description."
			::= { srvProfileShow 45 }

		
--          1.3.6.1.4.1.37950.1.1.5.12.9.2.45.1
-- 1.3.6.1.4.1.37950.1.1.5.12.9.2.45.1
-- 1.3.6.1.4.1.37950.1.1.5.12.9.2.45.1
-- 1.3.6.1.4.1.37950.1.1.5.12.9.2.45.1
-- 1.3.6.1.4.1.37950.1.1.5.12.9.2.45.1
-- 1.3.6.1.4.1.37950.1.1.5.12.9.2.45.1
-- 1.3.6.1.4.1.37950.1.1.5.12.9.2.45.1
-- 1.3.6.1.4.1.37950.1.1.5.12.9.2.45.1
-- 1.3.6.1.4.1.37950.1.1.5.12.9.2.45.1
		-- 1.3.6.1.4.1.37950.1.1.5.12.9.2.45.1
		onuDhcpOption82Entry OBJECT-TYPE
			SYNTAX OnuDhcpOption82Entry
			MAX-ACCESS not-accessible
			STATUS current
			DESCRIPTION
				"Description."
			INDEX { onuDhcpOption82SrvId }
			::= { onuDhcpOption82Table 1 }

		
		OnuDhcpOption82Entry ::=
			SEQUENCE { 
				onuDhcpOption82SrvId
					Integer32,
				onuDhcpOption82Enable
					INTEGER
			 }

--          1.3.6.1.4.1.37950.1.1.5.12.9.2.45.1.1
-- 1.3.6.1.4.1.37950.1.1.5.12.9.2.45.1.1
-- 1.3.6.1.4.1.37950.1.1.5.12.9.2.45.1.1
-- 1.3.6.1.4.1.37950.1.1.5.12.9.2.45.1.1
-- 1.3.6.1.4.1.37950.1.1.5.12.9.2.45.1.1
-- 1.3.6.1.4.1.37950.1.1.5.12.9.2.45.1.1
-- 1.3.6.1.4.1.37950.1.1.5.12.9.2.45.1.1
-- 1.3.6.1.4.1.37950.1.1.5.12.9.2.45.1.1
-- 1.3.6.1.4.1.37950.1.1.5.12.9.2.45.1.1
		-- 1.3.6.1.4.1.37950.1.1.5.12.9.2.45.1.1
		onuDhcpOption82SrvId OBJECT-TYPE
			SYNTAX Integer32 (0..65535)
			MAX-ACCESS read-write
			STATUS current
			DESCRIPTION
				"Description."
			::= { onuDhcpOption82Entry 1 }

		
--          1.3.6.1.4.1.37950.1.1.5.12.9.2.45.1.2
-- 1.3.6.1.4.1.37950.1.1.5.12.9.2.45.1.2
-- 1.3.6.1.4.1.37950.1.1.5.12.9.2.45.1.2
-- 1.3.6.1.4.1.37950.1.1.5.12.9.2.45.1.2
-- 1.3.6.1.4.1.37950.1.1.5.12.9.2.45.1.2
-- 1.3.6.1.4.1.37950.1.1.5.12.9.2.45.1.2
-- 1.3.6.1.4.1.37950.1.1.5.12.9.2.45.1.2
-- 1.3.6.1.4.1.37950.1.1.5.12.9.2.45.1.2
-- 1.3.6.1.4.1.37950.1.1.5.12.9.2.45.1.2
		-- 1.3.6.1.4.1.37950.1.1.5.12.9.2.45.1.2
		onuDhcpOption82Enable OBJECT-TYPE
			SYNTAX INTEGER
				{
				disable(0),
				enable(1)
				}
			MAX-ACCESS read-write
			STATUS current
			DESCRIPTION
				"Description."
			::= { onuDhcpOption82Entry 2 }

		
--          1.3.6.1.4.1.37950.1.1.5.12.9.2.46
-- 1.3.6.1.4.1.37950.1.1.5.12.9.2.46
-- 1.3.6.1.4.1.37950.1.1.5.12.9.2.46
-- 1.3.6.1.4.1.37950.1.1.5.12.9.2.46
-- 1.3.6.1.4.1.37950.1.1.5.12.9.2.46
-- 1.3.6.1.4.1.37950.1.1.5.12.9.2.46
-- 1.3.6.1.4.1.37950.1.1.5.12.9.2.46
-- 1.3.6.1.4.1.37950.1.1.5.12.9.2.46
-- 1.3.6.1.4.1.37950.1.1.5.12.9.2.46
		-- 1.3.6.1.4.1.37950.1.1.5.12.9.2.46
		onuPPPoETable OBJECT-TYPE
			SYNTAX SEQUENCE OF OnuPPPoEEntry
			MAX-ACCESS not-accessible
			STATUS current
			DESCRIPTION
				"Description."
			::= { srvProfileShow 46 }

		
--          1.3.6.1.4.1.37950.1.1.5.12.9.2.46.1
-- 1.3.6.1.4.1.37950.1.1.5.12.9.2.46.1
-- 1.3.6.1.4.1.37950.1.1.5.12.9.2.46.1
-- 1.3.6.1.4.1.37950.1.1.5.12.9.2.46.1
-- 1.3.6.1.4.1.37950.1.1.5.12.9.2.46.1
-- 1.3.6.1.4.1.37950.1.1.5.12.9.2.46.1
-- 1.3.6.1.4.1.37950.1.1.5.12.9.2.46.1
-- 1.3.6.1.4.1.37950.1.1.5.12.9.2.46.1
-- 1.3.6.1.4.1.37950.1.1.5.12.9.2.46.1
		-- 1.3.6.1.4.1.37950.1.1.5.12.9.2.46.1
		onuPPPoEEntry OBJECT-TYPE
			SYNTAX OnuPPPoEEntry
			MAX-ACCESS not-accessible
			STATUS current
			DESCRIPTION
				"Description."
			INDEX { onuPPPoESrvId }
			::= { onuPPPoETable 1 }

		
		OnuPPPoEEntry ::=
			SEQUENCE { 
				onuPPPoESrvId
					Integer32,
				onuPPPoEEnable
					INTEGER
			 }

--          1.3.6.1.4.1.37950.1.1.5.12.9.2.46.1.1
-- 1.3.6.1.4.1.37950.1.1.5.12.9.2.46.1.1
-- 1.3.6.1.4.1.37950.1.1.5.12.9.2.46.1.1
-- 1.3.6.1.4.1.37950.1.1.5.12.9.2.46.1.1
-- 1.3.6.1.4.1.37950.1.1.5.12.9.2.46.1.1
-- 1.3.6.1.4.1.37950.1.1.5.12.9.2.46.1.1
-- 1.3.6.1.4.1.37950.1.1.5.12.9.2.46.1.1
-- 1.3.6.1.4.1.37950.1.1.5.12.9.2.46.1.1
-- 1.3.6.1.4.1.37950.1.1.5.12.9.2.46.1.1
		-- 1.3.6.1.4.1.37950.1.1.5.12.9.2.46.1.1
		onuPPPoESrvId OBJECT-TYPE
			SYNTAX Integer32 (0..65535)
			MAX-ACCESS read-write
			STATUS current
			DESCRIPTION
				"Description."
			::= { onuPPPoEEntry 1 }

		
--          1.3.6.1.4.1.37950.1.1.5.12.9.2.46.1.2
-- 1.3.6.1.4.1.37950.1.1.5.12.9.2.46.1.2
-- 1.3.6.1.4.1.37950.1.1.5.12.9.2.46.1.2
-- 1.3.6.1.4.1.37950.1.1.5.12.9.2.46.1.2
-- 1.3.6.1.4.1.37950.1.1.5.12.9.2.46.1.2
-- 1.3.6.1.4.1.37950.1.1.5.12.9.2.46.1.2
-- 1.3.6.1.4.1.37950.1.1.5.12.9.2.46.1.2
-- 1.3.6.1.4.1.37950.1.1.5.12.9.2.46.1.2
-- 1.3.6.1.4.1.37950.1.1.5.12.9.2.46.1.2
		-- 1.3.6.1.4.1.37950.1.1.5.12.9.2.46.1.2
		onuPPPoEEnable OBJECT-TYPE
			SYNTAX INTEGER
				{
				disable(0),
				enable(1)
				}
			MAX-ACCESS read-write
			STATUS current
			DESCRIPTION
				"Description."
			::= { onuPPPoEEntry 2 }

		
--          1.3.6.1.4.1.37950.1.1.5.12.9.2.47
-- 1.3.6.1.4.1.37950.1.1.5.12.9.2.47
-- 1.3.6.1.4.1.37950.1.1.5.12.9.2.47
-- 1.3.6.1.4.1.37950.1.1.5.12.9.2.47
-- 1.3.6.1.4.1.37950.1.1.5.12.9.2.47
-- 1.3.6.1.4.1.37950.1.1.5.12.9.2.47
-- 1.3.6.1.4.1.37950.1.1.5.12.9.2.47
-- 1.3.6.1.4.1.37950.1.1.5.12.9.2.47
-- 1.3.6.1.4.1.37950.1.1.5.12.9.2.47
		-- 1.3.6.1.4.1.37950.1.1.5.12.9.2.47
		onuDhcpV6Table OBJECT-TYPE
			SYNTAX SEQUENCE OF OnuDhcpV6Entry
			MAX-ACCESS not-accessible
			STATUS current
			DESCRIPTION
				"Description."
			::= { srvProfileShow 47 }

		
--          1.3.6.1.4.1.37950.1.1.5.12.9.2.47.1
-- 1.3.6.1.4.1.37950.1.1.5.12.9.2.47.1
-- 1.3.6.1.4.1.37950.1.1.5.12.9.2.47.1
-- 1.3.6.1.4.1.37950.1.1.5.12.9.2.47.1
-- 1.3.6.1.4.1.37950.1.1.5.12.9.2.47.1
-- 1.3.6.1.4.1.37950.1.1.5.12.9.2.47.1
-- 1.3.6.1.4.1.37950.1.1.5.12.9.2.47.1
-- 1.3.6.1.4.1.37950.1.1.5.12.9.2.47.1
-- 1.3.6.1.4.1.37950.1.1.5.12.9.2.47.1
		-- 1.3.6.1.4.1.37950.1.1.5.12.9.2.47.1
		onuDhcpV6Entry OBJECT-TYPE
			SYNTAX OnuDhcpV6Entry
			MAX-ACCESS not-accessible
			STATUS current
			DESCRIPTION
				"Description."
			INDEX { onuDhcpV6SrvId }
			::= { onuDhcpV6Table 1 }

		
		OnuDhcpV6Entry ::=
			SEQUENCE { 
				onuDhcpV6SrvId
					Integer32,
				onuDhcpV6Option18Enable
					INTEGER,
				onuDhcpV6Option37Enable
					INTEGER
			 }

--          1.3.6.1.4.1.37950.1.1.5.12.9.2.47.1.1
-- 1.3.6.1.4.1.37950.1.1.5.12.9.2.47.1.1
-- 1.3.6.1.4.1.37950.1.1.5.12.9.2.47.1.1
-- 1.3.6.1.4.1.37950.1.1.5.12.9.2.47.1.1
-- 1.3.6.1.4.1.37950.1.1.5.12.9.2.47.1.1
-- 1.3.6.1.4.1.37950.1.1.5.12.9.2.47.1.1
-- 1.3.6.1.4.1.37950.1.1.5.12.9.2.47.1.1
-- 1.3.6.1.4.1.37950.1.1.5.12.9.2.47.1.1
-- 1.3.6.1.4.1.37950.1.1.5.12.9.2.47.1.1
		-- 1.3.6.1.4.1.37950.1.1.5.12.9.2.47.1.1
		onuDhcpV6SrvId OBJECT-TYPE
			SYNTAX Integer32 (0..65535)
			MAX-ACCESS read-write
			STATUS current
			DESCRIPTION
				"Description."
			::= { onuDhcpV6Entry 1 }

		
--          1.3.6.1.4.1.37950.1.1.5.12.9.2.47.1.2
-- 1.3.6.1.4.1.37950.1.1.5.12.9.2.47.1.2
-- 1.3.6.1.4.1.37950.1.1.5.12.9.2.47.1.2
-- 1.3.6.1.4.1.37950.1.1.5.12.9.2.47.1.2
-- 1.3.6.1.4.1.37950.1.1.5.12.9.2.47.1.2
-- 1.3.6.1.4.1.37950.1.1.5.12.9.2.47.1.2
-- 1.3.6.1.4.1.37950.1.1.5.12.9.2.47.1.2
-- 1.3.6.1.4.1.37950.1.1.5.12.9.2.47.1.2
-- 1.3.6.1.4.1.37950.1.1.5.12.9.2.47.1.2
		-- 1.3.6.1.4.1.37950.1.1.5.12.9.2.47.1.2
		onuDhcpV6Option18Enable OBJECT-TYPE
			SYNTAX INTEGER
				{
				disable(0),
				enable(1)
				}
			MAX-ACCESS read-write
			STATUS current
			DESCRIPTION
				"Description."
			::= { onuDhcpV6Entry 2 }

		
--          1.3.6.1.4.1.37950.1.1.5.12.9.2.47.1.3
-- 1.3.6.1.4.1.37950.1.1.5.12.9.2.47.1.3
-- 1.3.6.1.4.1.37950.1.1.5.12.9.2.47.1.3
-- 1.3.6.1.4.1.37950.1.1.5.12.9.2.47.1.3
-- 1.3.6.1.4.1.37950.1.1.5.12.9.2.47.1.3
-- 1.3.6.1.4.1.37950.1.1.5.12.9.2.47.1.3
-- 1.3.6.1.4.1.37950.1.1.5.12.9.2.47.1.3
-- 1.3.6.1.4.1.37950.1.1.5.12.9.2.47.1.3
-- 1.3.6.1.4.1.37950.1.1.5.12.9.2.47.1.3
		-- 1.3.6.1.4.1.37950.1.1.5.12.9.2.47.1.3
		onuDhcpV6Option37Enable OBJECT-TYPE
			SYNTAX INTEGER
				{
				disable(0),
				enable(1)
				}
			MAX-ACCESS read-write
			STATUS current
			DESCRIPTION
				"Description."
			::= { onuDhcpV6Entry 3 }

		
--         1.3.6.1.4.1.37950.1.1.5.12.9.2.48
-- 1.3.6.1.4.1.37950.1.1.5.12.9.2.48
-- 1.3.6.1.4.1.37950.1.1.5.12.9.2.48
-- 1.3.6.1.4.1.37950.1.1.5.12.9.2.48
-- 1.3.6.1.4.1.37950.1.1.5.12.9.2.48
-- 1.3.6.1.4.1.37950.1.1.5.12.9.2.48
-- 1.3.6.1.4.1.37950.1.1.5.12.9.2.48
-- 1.3.6.1.4.1.37950.1.1.5.12.9.2.48
		-- 1.3.6.1.4.1.37950.1.1.5.12.9.2.48
		onuUsernameTable OBJECT-TYPE
			SYNTAX SEQUENCE OF OnuUsernameEntry
			MAX-ACCESS not-accessible
			STATUS current
			DESCRIPTION
				"Description."
			::= { srvProfileShow 48 }

		
--         1.3.6.1.4.1.37950.1.1.5.12.9.2.48.1
-- 1.3.6.1.4.1.37950.1.1.5.12.9.2.48.1
-- 1.3.6.1.4.1.37950.1.1.5.12.9.2.48.1
-- 1.3.6.1.4.1.37950.1.1.5.12.9.2.48.1
-- 1.3.6.1.4.1.37950.1.1.5.12.9.2.48.1
-- 1.3.6.1.4.1.37950.1.1.5.12.9.2.48.1
-- 1.3.6.1.4.1.37950.1.1.5.12.9.2.48.1
-- 1.3.6.1.4.1.37950.1.1.5.12.9.2.48.1
		-- 1.3.6.1.4.1.37950.1.1.5.12.9.2.48.1
		onuUsernameEntry OBJECT-TYPE
			SYNTAX OnuUsernameEntry
			MAX-ACCESS not-accessible
			STATUS current
			DESCRIPTION
				"Description."
			INDEX { onuUsernamenSrvId }
			::= { onuUsernameTable 1 }

		
		OnuUsernameEntry ::=
			SEQUENCE { 
				onuUsernamenSrvId
					Integer32,
				adminCtl
					INTEGER,
				adminNameStr
					OCTET STRING,
				adminPwdStr
					OCTET STRING,
				userCtl
					INTEGER,
				userNameStr
					OCTET STRING,
				userPwdStr
					OCTET STRING
			 }

--         1.3.6.1.4.1.37950.1.1.5.12.9.2.48.1.1
-- 1.3.6.1.4.1.37950.1.1.5.12.9.2.48.1.1
-- 1.3.6.1.4.1.37950.1.1.5.12.9.2.48.1.1
-- 1.3.6.1.4.1.37950.1.1.5.12.9.2.48.1.1
-- 1.3.6.1.4.1.37950.1.1.5.12.9.2.48.1.1
-- 1.3.6.1.4.1.37950.1.1.5.12.9.2.48.1.1
-- 1.3.6.1.4.1.37950.1.1.5.12.9.2.48.1.1
-- 1.3.6.1.4.1.37950.1.1.5.12.9.2.48.1.1
		-- 1.3.6.1.4.1.37950.1.1.5.12.9.2.48.1.1
		onuUsernamenSrvId OBJECT-TYPE
			SYNTAX Integer32
			MAX-ACCESS read-only
			STATUS current
			DESCRIPTION
				"Description."
			::= { onuUsernameEntry 1 }

		
--         1.3.6.1.4.1.37950.1.1.5.12.9.2.48.1.2
-- 1.3.6.1.4.1.37950.1.1.5.12.9.2.48.1.2
-- 1.3.6.1.4.1.37950.1.1.5.12.9.2.48.1.2
-- 1.3.6.1.4.1.37950.1.1.5.12.9.2.48.1.2
-- 1.3.6.1.4.1.37950.1.1.5.12.9.2.48.1.2
-- 1.3.6.1.4.1.37950.1.1.5.12.9.2.48.1.2
-- 1.3.6.1.4.1.37950.1.1.5.12.9.2.48.1.2
-- 1.3.6.1.4.1.37950.1.1.5.12.9.2.48.1.2
		-- 1.3.6.1.4.1.37950.1.1.5.12.9.2.48.1.2
		adminCtl OBJECT-TYPE
			SYNTAX INTEGER
				{
				disable(0),
				enable(1)
				}
			MAX-ACCESS read-only
			STATUS current
			DESCRIPTION
				"Description."
			::= { onuUsernameEntry 2 }

		
--         1.3.6.1.4.1.37950.1.1.5.12.9.2.48.1.3
-- 1.3.6.1.4.1.37950.1.1.5.12.9.2.48.1.3
-- 1.3.6.1.4.1.37950.1.1.5.12.9.2.48.1.3
-- 1.3.6.1.4.1.37950.1.1.5.12.9.2.48.1.3
-- 1.3.6.1.4.1.37950.1.1.5.12.9.2.48.1.3
-- 1.3.6.1.4.1.37950.1.1.5.12.9.2.48.1.3
-- 1.3.6.1.4.1.37950.1.1.5.12.9.2.48.1.3
-- 1.3.6.1.4.1.37950.1.1.5.12.9.2.48.1.3
		-- 1.3.6.1.4.1.37950.1.1.5.12.9.2.48.1.3
		adminNameStr OBJECT-TYPE
			SYNTAX OCTET STRING
			MAX-ACCESS read-only
			STATUS current
			DESCRIPTION
				"Description."
			::= { onuUsernameEntry 3 }

		
--         1.3.6.1.4.1.37950.1.1.5.12.9.2.48.1.4
-- 1.3.6.1.4.1.37950.1.1.5.12.9.2.48.1.4
-- 1.3.6.1.4.1.37950.1.1.5.12.9.2.48.1.4
-- 1.3.6.1.4.1.37950.1.1.5.12.9.2.48.1.4
-- 1.3.6.1.4.1.37950.1.1.5.12.9.2.48.1.4
-- 1.3.6.1.4.1.37950.1.1.5.12.9.2.48.1.4
-- 1.3.6.1.4.1.37950.1.1.5.12.9.2.48.1.4
-- 1.3.6.1.4.1.37950.1.1.5.12.9.2.48.1.4
		-- 1.3.6.1.4.1.37950.1.1.5.12.9.2.48.1.4
		adminPwdStr OBJECT-TYPE
			SYNTAX OCTET STRING
			MAX-ACCESS read-only
			STATUS current
			DESCRIPTION
				"Description."
			::= { onuUsernameEntry 4 }

		
--         1.3.6.1.4.1.37950.1.1.5.12.9.2.48.1.5
-- 1.3.6.1.4.1.37950.1.1.5.12.9.2.48.1.5
-- 1.3.6.1.4.1.37950.1.1.5.12.9.2.48.1.5
-- 1.3.6.1.4.1.37950.1.1.5.12.9.2.48.1.5
-- 1.3.6.1.4.1.37950.1.1.5.12.9.2.48.1.5
-- 1.3.6.1.4.1.37950.1.1.5.12.9.2.48.1.5
-- 1.3.6.1.4.1.37950.1.1.5.12.9.2.48.1.5
-- 1.3.6.1.4.1.37950.1.1.5.12.9.2.48.1.5
		-- 1.3.6.1.4.1.37950.1.1.5.12.9.2.48.1.5
		userCtl OBJECT-TYPE
			SYNTAX INTEGER
				{
				disable(0),
				enable(1)
				}
			MAX-ACCESS read-only
			STATUS current
			DESCRIPTION
				"Description."
			::= { onuUsernameEntry 5 }

		
--         1.3.6.1.4.1.37950.1.1.5.12.9.2.48.1.6
-- 1.3.6.1.4.1.37950.1.1.5.12.9.2.48.1.6
-- 1.3.6.1.4.1.37950.1.1.5.12.9.2.48.1.6
-- 1.3.6.1.4.1.37950.1.1.5.12.9.2.48.1.6
-- 1.3.6.1.4.1.37950.1.1.5.12.9.2.48.1.6
-- 1.3.6.1.4.1.37950.1.1.5.12.9.2.48.1.6
-- 1.3.6.1.4.1.37950.1.1.5.12.9.2.48.1.6
-- 1.3.6.1.4.1.37950.1.1.5.12.9.2.48.1.6
		-- 1.3.6.1.4.1.37950.1.1.5.12.9.2.48.1.6
		userNameStr OBJECT-TYPE
			SYNTAX OCTET STRING
			MAX-ACCESS read-only
			STATUS current
			DESCRIPTION
				"Description."
			::= { onuUsernameEntry 6 }

		
--         1.3.6.1.4.1.37950.1.1.5.12.9.2.48.1.7
-- 1.3.6.1.4.1.37950.1.1.5.12.9.2.48.1.7
-- 1.3.6.1.4.1.37950.1.1.5.12.9.2.48.1.7
-- 1.3.6.1.4.1.37950.1.1.5.12.9.2.48.1.7
-- 1.3.6.1.4.1.37950.1.1.5.12.9.2.48.1.7
-- 1.3.6.1.4.1.37950.1.1.5.12.9.2.48.1.7
-- 1.3.6.1.4.1.37950.1.1.5.12.9.2.48.1.7
-- 1.3.6.1.4.1.37950.1.1.5.12.9.2.48.1.7
		-- 1.3.6.1.4.1.37950.1.1.5.12.9.2.48.1.7
		userPwdStr OBJECT-TYPE
			SYNTAX OCTET STRING
			MAX-ACCESS read-only
			STATUS current
			DESCRIPTION
				"Description."
			::= { onuUsernameEntry 7 }

		
--         1.3.6.1.4.1.37950.1.1.5.12.9.2.49
-- 1.3.6.1.4.1.37950.1.1.5.12.9.2.49
-- 1.3.6.1.4.1.37950.1.1.5.12.9.2.49
-- 1.3.6.1.4.1.37950.1.1.5.12.9.2.49
-- 1.3.6.1.4.1.37950.1.1.5.12.9.2.49
-- 1.3.6.1.4.1.37950.1.1.5.12.9.2.49
-- 1.3.6.1.4.1.37950.1.1.5.12.9.2.49
-- 1.3.6.1.4.1.37950.1.1.5.12.9.2.49
		-- 1.3.6.1.4.1.37950.1.1.5.12.9.2.49
		onuFirewallTable OBJECT-TYPE
			SYNTAX SEQUENCE OF OnuFirewallEntry
			MAX-ACCESS not-accessible
			STATUS current
			DESCRIPTION
				"Description."
			::= { srvProfileShow 49 }

		
--         1.3.6.1.4.1.37950.1.1.5.12.9.2.49.1
-- 1.3.6.1.4.1.37950.1.1.5.12.9.2.49.1
-- 1.3.6.1.4.1.37950.1.1.5.12.9.2.49.1
-- 1.3.6.1.4.1.37950.1.1.5.12.9.2.49.1
-- 1.3.6.1.4.1.37950.1.1.5.12.9.2.49.1
-- 1.3.6.1.4.1.37950.1.1.5.12.9.2.49.1
-- 1.3.6.1.4.1.37950.1.1.5.12.9.2.49.1
-- 1.3.6.1.4.1.37950.1.1.5.12.9.2.49.1
		-- 1.3.6.1.4.1.37950.1.1.5.12.9.2.49.1
		onuFirewallEntry OBJECT-TYPE
			SYNTAX OnuFirewallEntry
			MAX-ACCESS not-accessible
			STATUS current
			DESCRIPTION
				"Description."
			INDEX { onuFirewallSrvId }
			::= { onuFirewallTable 1 }

		
		OnuFirewallEntry ::=
			SEQUENCE { 
				onuFirewallSrvId
					Integer32,
				firewallLevel
					INTEGER
			 }

--         1.3.6.1.4.1.37950.1.1.5.12.9.2.49.1.1
-- 1.3.6.1.4.1.37950.1.1.5.12.9.2.49.1.1
-- 1.3.6.1.4.1.37950.1.1.5.12.9.2.49.1.1
-- 1.3.6.1.4.1.37950.1.1.5.12.9.2.49.1.1
-- 1.3.6.1.4.1.37950.1.1.5.12.9.2.49.1.1
-- 1.3.6.1.4.1.37950.1.1.5.12.9.2.49.1.1
-- 1.3.6.1.4.1.37950.1.1.5.12.9.2.49.1.1
-- 1.3.6.1.4.1.37950.1.1.5.12.9.2.49.1.1
		-- 1.3.6.1.4.1.37950.1.1.5.12.9.2.49.1.1
		onuFirewallSrvId OBJECT-TYPE
			SYNTAX Integer32
			MAX-ACCESS read-only
			STATUS current
			DESCRIPTION
				"Description."
			::= { onuFirewallEntry 1 }

		
--         1.3.6.1.4.1.37950.1.1.5.12.9.2.49.1.2
-- 1.3.6.1.4.1.37950.1.1.5.12.9.2.49.1.2
-- 1.3.6.1.4.1.37950.1.1.5.12.9.2.49.1.2
-- 1.3.6.1.4.1.37950.1.1.5.12.9.2.49.1.2
-- 1.3.6.1.4.1.37950.1.1.5.12.9.2.49.1.2
-- 1.3.6.1.4.1.37950.1.1.5.12.9.2.49.1.2
-- 1.3.6.1.4.1.37950.1.1.5.12.9.2.49.1.2
-- 1.3.6.1.4.1.37950.1.1.5.12.9.2.49.1.2
		-- 1.3.6.1.4.1.37950.1.1.5.12.9.2.49.1.2
		firewallLevel OBJECT-TYPE
			SYNTAX INTEGER
				{
				disable(0),
				low(1),
				middle(2),
				high(3)
				}
			MAX-ACCESS read-only
			STATUS current
			DESCRIPTION
				"Description."
			::= { onuFirewallEntry 2 }

		
--         1.3.6.1.4.1.37950.1.1.5.12.9.2.50
-- 1.3.6.1.4.1.37950.1.1.5.12.9.2.50
-- 1.3.6.1.4.1.37950.1.1.5.12.9.2.50
-- 1.3.6.1.4.1.37950.1.1.5.12.9.2.50
-- 1.3.6.1.4.1.37950.1.1.5.12.9.2.50
-- 1.3.6.1.4.1.37950.1.1.5.12.9.2.50
-- 1.3.6.1.4.1.37950.1.1.5.12.9.2.50
-- 1.3.6.1.4.1.37950.1.1.5.12.9.2.50
		-- 1.3.6.1.4.1.37950.1.1.5.12.9.2.50
		onuAclTable OBJECT-TYPE
			SYNTAX SEQUENCE OF OnuAclEntry
			MAX-ACCESS not-accessible
			STATUS current
			DESCRIPTION
				"Description."
			::= { srvProfileShow 50 }

		
--         1.3.6.1.4.1.37950.1.1.5.12.9.2.50.1
-- 1.3.6.1.4.1.37950.1.1.5.12.9.2.50.1
-- 1.3.6.1.4.1.37950.1.1.5.12.9.2.50.1
-- 1.3.6.1.4.1.37950.1.1.5.12.9.2.50.1
-- 1.3.6.1.4.1.37950.1.1.5.12.9.2.50.1
-- 1.3.6.1.4.1.37950.1.1.5.12.9.2.50.1
-- 1.3.6.1.4.1.37950.1.1.5.12.9.2.50.1
-- 1.3.6.1.4.1.37950.1.1.5.12.9.2.50.1
		-- 1.3.6.1.4.1.37950.1.1.5.12.9.2.50.1
		onuAclEntry OBJECT-TYPE
			SYNTAX OnuAclEntry
			MAX-ACCESS not-accessible
			STATUS current
			DESCRIPTION
				"Description."
			INDEX { onuAclSrvId, onuAclProtocolType }
			::= { onuAclTable 1 }

		
		OnuAclEntry ::=
			SEQUENCE { 
				onuAclSrvId
					Integer32,
				onuAclProtocolType
					INTEGER,
				onuAclCtl
					INTEGER,
				onuAclLanCtl
					INTEGER,
				onuAclWanCtl
					INTEGER,
				onuAclIPv4Ctl
					INTEGER,
				onuAclIPv4Addr
					IpAddress,
				onuAclIPv4Mask
					IpAddress,
				onuAclIPv6Ctl
					INTEGER,
				onuAclIPv6Addr
					OCTET STRING,
				onuAclPort
					Unsigned32
			 }

--         1.3.6.1.4.1.37950.1.1.5.12.9.2.50.1.1
-- 1.3.6.1.4.1.37950.1.1.5.12.9.2.50.1.1
-- 1.3.6.1.4.1.37950.1.1.5.12.9.2.50.1.1
-- 1.3.6.1.4.1.37950.1.1.5.12.9.2.50.1.1
-- 1.3.6.1.4.1.37950.1.1.5.12.9.2.50.1.1
-- 1.3.6.1.4.1.37950.1.1.5.12.9.2.50.1.1
-- 1.3.6.1.4.1.37950.1.1.5.12.9.2.50.1.1
-- 1.3.6.1.4.1.37950.1.1.5.12.9.2.50.1.1
		-- 1.3.6.1.4.1.37950.1.1.5.12.9.2.50.1.1
		onuAclSrvId OBJECT-TYPE
			SYNTAX Integer32
			MAX-ACCESS read-only
			STATUS current
			DESCRIPTION
				"Description."
			::= { onuAclEntry 1 }

		
--         1.3.6.1.4.1.37950.1.1.5.12.9.2.50.1.2
-- 1.3.6.1.4.1.37950.1.1.5.12.9.2.50.1.2
-- 1.3.6.1.4.1.37950.1.1.5.12.9.2.50.1.2
-- 1.3.6.1.4.1.37950.1.1.5.12.9.2.50.1.2
-- 1.3.6.1.4.1.37950.1.1.5.12.9.2.50.1.2
-- 1.3.6.1.4.1.37950.1.1.5.12.9.2.50.1.2
-- 1.3.6.1.4.1.37950.1.1.5.12.9.2.50.1.2
-- 1.3.6.1.4.1.37950.1.1.5.12.9.2.50.1.2
		-- 1.3.6.1.4.1.37950.1.1.5.12.9.2.50.1.2
		onuAclProtocolType OBJECT-TYPE
			SYNTAX INTEGER
				{
				telnet(0),
				ftp(1),
				http(2),
				https(3),
				tftp(4),
				ping(5)
				}
			MAX-ACCESS read-only
			STATUS current
			DESCRIPTION
				"Description."
			::= { onuAclEntry 2 }

		
--         1.3.6.1.4.1.37950.1.1.5.12.9.2.50.1.3
-- 1.3.6.1.4.1.37950.1.1.5.12.9.2.50.1.3
-- 1.3.6.1.4.1.37950.1.1.5.12.9.2.50.1.3
-- 1.3.6.1.4.1.37950.1.1.5.12.9.2.50.1.3
-- 1.3.6.1.4.1.37950.1.1.5.12.9.2.50.1.3
-- 1.3.6.1.4.1.37950.1.1.5.12.9.2.50.1.3
-- 1.3.6.1.4.1.37950.1.1.5.12.9.2.50.1.3
-- 1.3.6.1.4.1.37950.1.1.5.12.9.2.50.1.3
		-- 1.3.6.1.4.1.37950.1.1.5.12.9.2.50.1.3
		onuAclCtl OBJECT-TYPE
			SYNTAX INTEGER
				{
				disable(0),
				enable(1)
				}
			MAX-ACCESS read-only
			STATUS current
			DESCRIPTION
				"Description."
			::= { onuAclEntry 3 }

		
--         1.3.6.1.4.1.37950.1.1.5.12.9.2.50.1.4
-- 1.3.6.1.4.1.37950.1.1.5.12.9.2.50.1.4
-- 1.3.6.1.4.1.37950.1.1.5.12.9.2.50.1.4
-- 1.3.6.1.4.1.37950.1.1.5.12.9.2.50.1.4
-- 1.3.6.1.4.1.37950.1.1.5.12.9.2.50.1.4
-- 1.3.6.1.4.1.37950.1.1.5.12.9.2.50.1.4
-- 1.3.6.1.4.1.37950.1.1.5.12.9.2.50.1.4
-- 1.3.6.1.4.1.37950.1.1.5.12.9.2.50.1.4
		-- 1.3.6.1.4.1.37950.1.1.5.12.9.2.50.1.4
		onuAclLanCtl OBJECT-TYPE
			SYNTAX INTEGER
				{
				disable(0),
				enable(1)
				}
			MAX-ACCESS read-only
			STATUS current
			DESCRIPTION
				"Description."
			::= { onuAclEntry 4 }

		
--         1.3.6.1.4.1.37950.1.1.5.12.9.2.50.1.5
-- 1.3.6.1.4.1.37950.1.1.5.12.9.2.50.1.5
-- 1.3.6.1.4.1.37950.1.1.5.12.9.2.50.1.5
-- 1.3.6.1.4.1.37950.1.1.5.12.9.2.50.1.5
-- 1.3.6.1.4.1.37950.1.1.5.12.9.2.50.1.5
-- 1.3.6.1.4.1.37950.1.1.5.12.9.2.50.1.5
-- 1.3.6.1.4.1.37950.1.1.5.12.9.2.50.1.5
-- 1.3.6.1.4.1.37950.1.1.5.12.9.2.50.1.5
		-- 1.3.6.1.4.1.37950.1.1.5.12.9.2.50.1.5
		onuAclWanCtl OBJECT-TYPE
			SYNTAX INTEGER
				{
				disable(0),
				enable(1)
				}
			MAX-ACCESS read-only
			STATUS current
			DESCRIPTION
				"Description."
			::= { onuAclEntry 5 }

		
--         1.3.6.1.4.1.37950.1.1.5.12.9.2.50.1.6
-- 1.3.6.1.4.1.37950.1.1.5.12.9.2.50.1.6
-- 1.3.6.1.4.1.37950.1.1.5.12.9.2.50.1.6
-- 1.3.6.1.4.1.37950.1.1.5.12.9.2.50.1.6
-- 1.3.6.1.4.1.37950.1.1.5.12.9.2.50.1.6
-- 1.3.6.1.4.1.37950.1.1.5.12.9.2.50.1.6
-- 1.3.6.1.4.1.37950.1.1.5.12.9.2.50.1.6
-- 1.3.6.1.4.1.37950.1.1.5.12.9.2.50.1.6
		-- 1.3.6.1.4.1.37950.1.1.5.12.9.2.50.1.6
		onuAclIPv4Ctl OBJECT-TYPE
			SYNTAX INTEGER
				{
				disable(0),
				enable(1)
				}
			MAX-ACCESS read-only
			STATUS current
			DESCRIPTION
				"Description."
			::= { onuAclEntry 6 }

		
--         1.3.6.1.4.1.37950.1.1.5.12.9.2.50.1.7
-- 1.3.6.1.4.1.37950.1.1.5.12.9.2.50.1.7
-- 1.3.6.1.4.1.37950.1.1.5.12.9.2.50.1.7
-- 1.3.6.1.4.1.37950.1.1.5.12.9.2.50.1.7
-- 1.3.6.1.4.1.37950.1.1.5.12.9.2.50.1.7
-- 1.3.6.1.4.1.37950.1.1.5.12.9.2.50.1.7
-- 1.3.6.1.4.1.37950.1.1.5.12.9.2.50.1.7
-- 1.3.6.1.4.1.37950.1.1.5.12.9.2.50.1.7
		-- 1.3.6.1.4.1.37950.1.1.5.12.9.2.50.1.7
		onuAclIPv4Addr OBJECT-TYPE
			SYNTAX IpAddress
			MAX-ACCESS read-only
			STATUS current
			DESCRIPTION
				"Description."
			::= { onuAclEntry 7 }

		
--         1.3.6.1.4.1.37950.1.1.5.12.9.2.50.1.8
-- 1.3.6.1.4.1.37950.1.1.5.12.9.2.50.1.8
-- 1.3.6.1.4.1.37950.1.1.5.12.9.2.50.1.8
-- 1.3.6.1.4.1.37950.1.1.5.12.9.2.50.1.8
-- 1.3.6.1.4.1.37950.1.1.5.12.9.2.50.1.8
-- 1.3.6.1.4.1.37950.1.1.5.12.9.2.50.1.8
-- 1.3.6.1.4.1.37950.1.1.5.12.9.2.50.1.8
-- 1.3.6.1.4.1.37950.1.1.5.12.9.2.50.1.8
		-- 1.3.6.1.4.1.37950.1.1.5.12.9.2.50.1.8
		onuAclIPv4Mask OBJECT-TYPE
			SYNTAX IpAddress
			MAX-ACCESS read-only
			STATUS current
			DESCRIPTION
				"Description."
			::= { onuAclEntry 8 }

		
--         1.3.6.1.4.1.37950.1.1.5.12.9.2.50.1.9
-- 1.3.6.1.4.1.37950.1.1.5.12.9.2.50.1.9
-- 1.3.6.1.4.1.37950.1.1.5.12.9.2.50.1.9
-- 1.3.6.1.4.1.37950.1.1.5.12.9.2.50.1.9
-- 1.3.6.1.4.1.37950.1.1.5.12.9.2.50.1.9
-- 1.3.6.1.4.1.37950.1.1.5.12.9.2.50.1.9
-- 1.3.6.1.4.1.37950.1.1.5.12.9.2.50.1.9
-- 1.3.6.1.4.1.37950.1.1.5.12.9.2.50.1.9
		-- 1.3.6.1.4.1.37950.1.1.5.12.9.2.50.1.9
		onuAclIPv6Ctl OBJECT-TYPE
			SYNTAX INTEGER
				{
				disable(0),
				enable(1)
				}
			MAX-ACCESS read-only
			STATUS current
			DESCRIPTION
				"Description."
			::= { onuAclEntry 9 }

		
--         1.3.6.1.4.1.37950.1.1.5.12.9.2.50.1.10
-- 1.3.6.1.4.1.37950.1.1.5.12.9.2.50.1.10
-- 1.3.6.1.4.1.37950.1.1.5.12.9.2.50.1.10
-- 1.3.6.1.4.1.37950.1.1.5.12.9.2.50.1.10
-- 1.3.6.1.4.1.37950.1.1.5.12.9.2.50.1.10
-- 1.3.6.1.4.1.37950.1.1.5.12.9.2.50.1.10
-- 1.3.6.1.4.1.37950.1.1.5.12.9.2.50.1.10
-- 1.3.6.1.4.1.37950.1.1.5.12.9.2.50.1.10
		-- 1.3.6.1.4.1.37950.1.1.5.12.9.2.50.1.10
		onuAclIPv6Addr OBJECT-TYPE
			SYNTAX OCTET STRING
			MAX-ACCESS read-only
			STATUS current
			DESCRIPTION
				"Description."
			::= { onuAclEntry 10 }

		
--         1.3.6.1.4.1.37950.1.1.5.12.9.2.50.1.11
-- 1.3.6.1.4.1.37950.1.1.5.12.9.2.50.1.11
-- 1.3.6.1.4.1.37950.1.1.5.12.9.2.50.1.11
-- 1.3.6.1.4.1.37950.1.1.5.12.9.2.50.1.11
-- 1.3.6.1.4.1.37950.1.1.5.12.9.2.50.1.11
-- 1.3.6.1.4.1.37950.1.1.5.12.9.2.50.1.11
-- 1.3.6.1.4.1.37950.1.1.5.12.9.2.50.1.11
-- 1.3.6.1.4.1.37950.1.1.5.12.9.2.50.1.11
		-- 1.3.6.1.4.1.37950.1.1.5.12.9.2.50.1.11
		onuAclPort OBJECT-TYPE
			SYNTAX Unsigned32 (0..65535)
			MAX-ACCESS read-only
			STATUS current
			DESCRIPTION
				"Description."
			::= { onuAclEntry 11 }

		
--         1.3.6.1.4.1.37950.1.1.5.12.9.2.51
-- 1.3.6.1.4.1.37950.1.1.5.12.9.2.51
-- 1.3.6.1.4.1.37950.1.1.5.12.9.2.51
-- 1.3.6.1.4.1.37950.1.1.5.12.9.2.51
-- 1.3.6.1.4.1.37950.1.1.5.12.9.2.51
-- 1.3.6.1.4.1.37950.1.1.5.12.9.2.51
-- 1.3.6.1.4.1.37950.1.1.5.12.9.2.51
-- 1.3.6.1.4.1.37950.1.1.5.12.9.2.51
		-- 1.3.6.1.4.1.37950.1.1.5.12.9.2.51
		onuWifiSwitch1PFTable OBJECT-TYPE
			SYNTAX SEQUENCE OF OnuWifiSwitch1PFEntry
			MAX-ACCESS not-accessible
			STATUS current
			DESCRIPTION
				"Description."
			::= { srvProfileShow 51 }

		
--         1.3.6.1.4.1.37950.1.1.5.12.9.2.51.1
-- 1.3.6.1.4.1.37950.1.1.5.12.9.2.51.1
-- 1.3.6.1.4.1.37950.1.1.5.12.9.2.51.1
-- 1.3.6.1.4.1.37950.1.1.5.12.9.2.51.1
-- 1.3.6.1.4.1.37950.1.1.5.12.9.2.51.1
-- 1.3.6.1.4.1.37950.1.1.5.12.9.2.51.1
-- 1.3.6.1.4.1.37950.1.1.5.12.9.2.51.1
-- 1.3.6.1.4.1.37950.1.1.5.12.9.2.51.1
		-- 1.3.6.1.4.1.37950.1.1.5.12.9.2.51.1
		onuWifiSwitch1PFEntry OBJECT-TYPE
			SYNTAX OnuWifiSwitch1PFEntry
			MAX-ACCESS not-accessible
			STATUS current
			DESCRIPTION
				"Description."
			INDEX { onuWifiSwitchSrvId }
			::= { onuWifiSwitch1PFTable 1 }

		
		OnuWifiSwitch1PFEntry ::=
			SEQUENCE { 
				onuWifiSwitchSrvId
					INTEGER,
				onuWifiSwitchActive
					INTEGER,
				onuWifiSwitchAPModuleS
					INTEGER,
				onuWifiSwitchCountry
					INTEGER,
				onuWifiSwitchChannelS
					INTEGER,
				onuWifiSwitchStandardS
					INTEGER,
				onuWifiSwitchPower1
					INTEGER,
				onuWifiSwitchChannelWidth
					INTEGER,
				onuWifiSwitchEasyMeshStatus
					INTEGER
			 }

--         1.3.6.1.4.1.37950.1.1.5.12.9.2.51.1.1
-- 1.3.6.1.4.1.37950.1.1.5.12.9.2.51.1.1
-- 1.3.6.1.4.1.37950.1.1.5.12.9.2.51.1.1
-- 1.3.6.1.4.1.37950.1.1.5.12.9.2.51.1.1
-- 1.3.6.1.4.1.37950.1.1.5.12.9.2.51.1.1
-- 1.3.6.1.4.1.37950.1.1.5.12.9.2.51.1.1
-- 1.3.6.1.4.1.37950.1.1.5.12.9.2.51.1.1
-- 1.3.6.1.4.1.37950.1.1.5.12.9.2.51.1.1
		-- 1.3.6.1.4.1.37950.1.1.5.12.9.2.51.1.1
		onuWifiSwitchSrvId OBJECT-TYPE
			SYNTAX INTEGER (0..65535)
			MAX-ACCESS read-write
			STATUS current
			DESCRIPTION
				"Description."
			::= { onuWifiSwitch1PFEntry 1 }

		
--         1.3.6.1.4.1.37950.1.1.5.12.9.2.51.1.2
-- 1.3.6.1.4.1.37950.1.1.5.12.9.2.51.1.2
-- 1.3.6.1.4.1.37950.1.1.5.12.9.2.51.1.2
-- 1.3.6.1.4.1.37950.1.1.5.12.9.2.51.1.2
-- 1.3.6.1.4.1.37950.1.1.5.12.9.2.51.1.2
-- 1.3.6.1.4.1.37950.1.1.5.12.9.2.51.1.2
-- 1.3.6.1.4.1.37950.1.1.5.12.9.2.51.1.2
-- 1.3.6.1.4.1.37950.1.1.5.12.9.2.51.1.2
		-- 1.3.6.1.4.1.37950.1.1.5.12.9.2.51.1.2
		onuWifiSwitchActive OBJECT-TYPE
			SYNTAX INTEGER
				{
				deactive(0),
				active(1)
				}
			MAX-ACCESS read-write
			STATUS current
			DESCRIPTION
				"Description."
			::= { onuWifiSwitch1PFEntry 2 }

		
--         1.3.6.1.4.1.37950.1.1.5.12.9.2.51.1.3
-- 1.3.6.1.4.1.37950.1.1.5.12.9.2.51.1.3
-- 1.3.6.1.4.1.37950.1.1.5.12.9.2.51.1.3
-- 1.3.6.1.4.1.37950.1.1.5.12.9.2.51.1.3
-- 1.3.6.1.4.1.37950.1.1.5.12.9.2.51.1.3
-- 1.3.6.1.4.1.37950.1.1.5.12.9.2.51.1.3
-- 1.3.6.1.4.1.37950.1.1.5.12.9.2.51.1.3
-- 1.3.6.1.4.1.37950.1.1.5.12.9.2.51.1.3
		-- 1.3.6.1.4.1.37950.1.1.5.12.9.2.51.1.3
		onuWifiSwitchAPModuleS OBJECT-TYPE
			SYNTAX INTEGER
				{
				disable(0),
				enable(1)
				}
			MAX-ACCESS read-write
			STATUS current
			DESCRIPTION
				"Description."
			::= { onuWifiSwitch1PFEntry 3 }

		
--         1.3.6.1.4.1.37950.1.1.5.12.9.2.51.1.4
-- 1.3.6.1.4.1.37950.1.1.5.12.9.2.51.1.4
-- 1.3.6.1.4.1.37950.1.1.5.12.9.2.51.1.4
-- 1.3.6.1.4.1.37950.1.1.5.12.9.2.51.1.4
-- 1.3.6.1.4.1.37950.1.1.5.12.9.2.51.1.4
-- 1.3.6.1.4.1.37950.1.1.5.12.9.2.51.1.4
-- 1.3.6.1.4.1.37950.1.1.5.12.9.2.51.1.4
-- 1.3.6.1.4.1.37950.1.1.5.12.9.2.51.1.4
		-- 1.3.6.1.4.1.37950.1.1.5.12.9.2.51.1.4
		onuWifiSwitchCountry OBJECT-TYPE
			SYNTAX INTEGER
				{
				etsi(0),
				fcc(1),
				ic(2),
				spain(3),
				france(4),
				mkk(5),
				isreal(6),
				mkk2(7),
				mkk3(8),
				russian(9),
				cn(10),
				global(11),
				world-wide(12),
				mkk1(13),
				ncc(14)
				}
			MAX-ACCESS read-write
			STATUS current
			DESCRIPTION
				"Description."
			::= { onuWifiSwitch1PFEntry 4 }

		
--         1.3.6.1.4.1.37950.1.1.5.12.9.2.51.1.5
-- 1.3.6.1.4.1.37950.1.1.5.12.9.2.51.1.5
-- 1.3.6.1.4.1.37950.1.1.5.12.9.2.51.1.5
-- 1.3.6.1.4.1.37950.1.1.5.12.9.2.51.1.5
-- 1.3.6.1.4.1.37950.1.1.5.12.9.2.51.1.5
-- 1.3.6.1.4.1.37950.1.1.5.12.9.2.51.1.5
-- 1.3.6.1.4.1.37950.1.1.5.12.9.2.51.1.5
-- 1.3.6.1.4.1.37950.1.1.5.12.9.2.51.1.5
		-- 1.3.6.1.4.1.37950.1.1.5.12.9.2.51.1.5
		onuWifiSwitchChannelS OBJECT-TYPE
			SYNTAX INTEGER (0..13)
			MAX-ACCESS read-write
			STATUS current
			DESCRIPTION
				"Description."
			::= { onuWifiSwitch1PFEntry 5 }

		
--         1.3.6.1.4.1.37950.1.1.5.12.9.2.51.1.6
-- 1.3.6.1.4.1.37950.1.1.5.12.9.2.51.1.6
-- 1.3.6.1.4.1.37950.1.1.5.12.9.2.51.1.6
-- 1.3.6.1.4.1.37950.1.1.5.12.9.2.51.1.6
-- 1.3.6.1.4.1.37950.1.1.5.12.9.2.51.1.6
-- 1.3.6.1.4.1.37950.1.1.5.12.9.2.51.1.6
-- 1.3.6.1.4.1.37950.1.1.5.12.9.2.51.1.6
-- 1.3.6.1.4.1.37950.1.1.5.12.9.2.51.1.6
		-- 1.3.6.1.4.1.37950.1.1.5.12.9.2.51.1.6
		onuWifiSwitchStandardS OBJECT-TYPE
			SYNTAX INTEGER
				{
				s80211b(0),
				s80211g(1),
				s80211bg(2),
				s80211n(3),
				s80211bgn(4),
				s8011ac(5),
				s8011a(6),
				s8011an(7),
				s8011nac(8),
				s8011anac(9),
				s80211aan(10),
				s80211ax(11),
				s80211anacax(12)
				}
			MAX-ACCESS read-write
			STATUS current
			DESCRIPTION
				"Description."
			::= { onuWifiSwitch1PFEntry 6 }

		
--         1.3.6.1.4.1.37950.1.1.5.12.9.2.51.1.7
-- 1.3.6.1.4.1.37950.1.1.5.12.9.2.51.1.7
-- 1.3.6.1.4.1.37950.1.1.5.12.9.2.51.1.7
-- 1.3.6.1.4.1.37950.1.1.5.12.9.2.51.1.7
-- 1.3.6.1.4.1.37950.1.1.5.12.9.2.51.1.7
-- 1.3.6.1.4.1.37950.1.1.5.12.9.2.51.1.7
-- 1.3.6.1.4.1.37950.1.1.5.12.9.2.51.1.7
-- 1.3.6.1.4.1.37950.1.1.5.12.9.2.51.1.7
		-- 1.3.6.1.4.1.37950.1.1.5.12.9.2.51.1.7
		onuWifiSwitchPower1 OBJECT-TYPE
			SYNTAX INTEGER (0..20)
			MAX-ACCESS read-write
			STATUS current
			DESCRIPTION
				"Description."
			::= { onuWifiSwitch1PFEntry 7 }

		
--         1.3.6.1.4.1.37950.1.1.5.12.9.2.51.1.8
-- 1.3.6.1.4.1.37950.1.1.5.12.9.2.51.1.8
-- 1.3.6.1.4.1.37950.1.1.5.12.9.2.51.1.8
-- 1.3.6.1.4.1.37950.1.1.5.12.9.2.51.1.8
-- 1.3.6.1.4.1.37950.1.1.5.12.9.2.51.1.8
-- 1.3.6.1.4.1.37950.1.1.5.12.9.2.51.1.8
-- 1.3.6.1.4.1.37950.1.1.5.12.9.2.51.1.8
-- 1.3.6.1.4.1.37950.1.1.5.12.9.2.51.1.8
		-- 1.3.6.1.4.1.37950.1.1.5.12.9.2.51.1.8
		onuWifiSwitchChannelWidth OBJECT-TYPE
			SYNTAX INTEGER
				{
				s20(0),
				s40(1),
				s80(2),
				s20-40(3)
				}
			MAX-ACCESS read-write
			STATUS current
			DESCRIPTION
				"Description."
			::= { onuWifiSwitch1PFEntry 8 }

		
--         1.3.6.1.4.1.37950.1.1.5.12.9.2.51.1.9
-- 1.3.6.1.4.1.37950.1.1.5.12.9.2.51.1.9
-- 1.3.6.1.4.1.37950.1.1.5.12.9.2.51.1.9
-- 1.3.6.1.4.1.37950.1.1.5.12.9.2.51.1.9
-- 1.3.6.1.4.1.37950.1.1.5.12.9.2.51.1.9
-- 1.3.6.1.4.1.37950.1.1.5.12.9.2.51.1.9
-- 1.3.6.1.4.1.37950.1.1.5.12.9.2.51.1.9
-- 1.3.6.1.4.1.37950.1.1.5.12.9.2.51.1.9
		-- 1.3.6.1.4.1.37950.1.1.5.12.9.2.51.1.9
		onuWifiSwitchEasyMeshStatus OBJECT-TYPE
			SYNTAX INTEGER
				{
				disable(0),
				enable(1)
				}
			MAX-ACCESS read-write
			STATUS current
			DESCRIPTION
				"Description."
			::= { onuWifiSwitch1PFEntry 9 }

		
--         1.3.6.1.4.1.37950.1.1.5.12.9.2.52
-- 1.3.6.1.4.1.37950.1.1.5.12.9.2.52
-- 1.3.6.1.4.1.37950.1.1.5.12.9.2.52
-- 1.3.6.1.4.1.37950.1.1.5.12.9.2.52
-- 1.3.6.1.4.1.37950.1.1.5.12.9.2.52
-- 1.3.6.1.4.1.37950.1.1.5.12.9.2.52
-- 1.3.6.1.4.1.37950.1.1.5.12.9.2.52
-- 1.3.6.1.4.1.37950.1.1.5.12.9.2.52
		-- 1.3.6.1.4.1.37950.1.1.5.12.9.2.52
		onuDhcpv6ServerTable OBJECT-TYPE
			SYNTAX SEQUENCE OF OnuDhcpv6ServerEntry
			MAX-ACCESS not-accessible
			STATUS current
			DESCRIPTION
				"Description."
			::= { srvProfileShow 52 }

		
--         1.3.6.1.4.1.37950.1.1.5.12.9.2.52.1
-- 1.3.6.1.4.1.37950.1.1.5.12.9.2.52.1
-- 1.3.6.1.4.1.37950.1.1.5.12.9.2.52.1
-- 1.3.6.1.4.1.37950.1.1.5.12.9.2.52.1
-- 1.3.6.1.4.1.37950.1.1.5.12.9.2.52.1
-- 1.3.6.1.4.1.37950.1.1.5.12.9.2.52.1
-- 1.3.6.1.4.1.37950.1.1.5.12.9.2.52.1
-- 1.3.6.1.4.1.37950.1.1.5.12.9.2.52.1
		-- 1.3.6.1.4.1.37950.1.1.5.12.9.2.52.1
		onuDhcpv6ServerEntry OBJECT-TYPE
			SYNTAX OnuDhcpv6ServerEntry
			MAX-ACCESS not-accessible
			STATUS current
			DESCRIPTION
				"Description."
			INDEX { onuDhcpv6SrvId }
			::= { onuDhcpv6ServerTable 1 }

		
		OnuDhcpv6ServerEntry ::=
			SEQUENCE { 
				onuDhcpv6SrvId
					Integer32,
				onuDhcpv6LanIp
					OCTET STRING,
				onuDhcpv6Prefixlen
					INTEGER,
				onuDhcpv6PrefixMode
					INTEGER,
				onuDhcpv6PrefixModeIp
					OCTET STRING,
				onuDhcpv6ServerEable
					INTEGER,
				onuDhcpv6Preference
					Unsigned32,
				onuDhcpv6BeginIp
					OCTET STRING,
				onuDhcpv6EndIp
					OCTET STRING,
				onuDhcpv6PoolType
					INTEGER,
				onuDhcpv6MasterDns
					OCTET STRING,
				onuDhcpv6SlaveDns
					OCTET STRING,
				onuDhcpv6Gateway
					OCTET STRING,
				onuDhcpv6RelayIp
					OCTET STRING,
				onuDhcpv6RA
					INTEGER,
				onuDhcpv6RAManage
					INTEGER,
				onuDhcpv6RAOther
					INTEGER,
				onuDhcpv6RAMaxInterval
					Integer32,
				onuDhcpv6RAMinInterval
					Integer32,
				onuDhcpv6Valid
					Unsigned32,
				onuDhcpv6DnsMode
					INTEGER
			 }

--         1.3.6.1.4.1.37950.1.1.5.12.9.2.52.1.1
-- 1.3.6.1.4.1.37950.1.1.5.12.9.2.52.1.1
-- 1.3.6.1.4.1.37950.1.1.5.12.9.2.52.1.1
-- 1.3.6.1.4.1.37950.1.1.5.12.9.2.52.1.1
-- 1.3.6.1.4.1.37950.1.1.5.12.9.2.52.1.1
-- 1.3.6.1.4.1.37950.1.1.5.12.9.2.52.1.1
-- 1.3.6.1.4.1.37950.1.1.5.12.9.2.52.1.1
-- 1.3.6.1.4.1.37950.1.1.5.12.9.2.52.1.1
		-- 1.3.6.1.4.1.37950.1.1.5.12.9.2.52.1.1
		onuDhcpv6SrvId OBJECT-TYPE
			SYNTAX Integer32
			MAX-ACCESS read-write
			STATUS current
			DESCRIPTION
				"Description."
			::= { onuDhcpv6ServerEntry 1 }

		
--         1.3.6.1.4.1.37950.1.1.5.12.9.2.52.1.2
-- 1.3.6.1.4.1.37950.1.1.5.12.9.2.52.1.2
-- 1.3.6.1.4.1.37950.1.1.5.12.9.2.52.1.2
-- 1.3.6.1.4.1.37950.1.1.5.12.9.2.52.1.2
-- 1.3.6.1.4.1.37950.1.1.5.12.9.2.52.1.2
-- 1.3.6.1.4.1.37950.1.1.5.12.9.2.52.1.2
-- 1.3.6.1.4.1.37950.1.1.5.12.9.2.52.1.2
-- 1.3.6.1.4.1.37950.1.1.5.12.9.2.52.1.2
		-- 1.3.6.1.4.1.37950.1.1.5.12.9.2.52.1.2
		onuDhcpv6LanIp OBJECT-TYPE
			SYNTAX OCTET STRING
			MAX-ACCESS read-write
			STATUS current
			DESCRIPTION
				"Description."
			::= { onuDhcpv6ServerEntry 2 }

		
--         1.3.6.1.4.1.37950.1.1.5.12.9.2.52.1.3
-- 1.3.6.1.4.1.37950.1.1.5.12.9.2.52.1.3
-- 1.3.6.1.4.1.37950.1.1.5.12.9.2.52.1.3
-- 1.3.6.1.4.1.37950.1.1.5.12.9.2.52.1.3
-- 1.3.6.1.4.1.37950.1.1.5.12.9.2.52.1.3
-- 1.3.6.1.4.1.37950.1.1.5.12.9.2.52.1.3
-- 1.3.6.1.4.1.37950.1.1.5.12.9.2.52.1.3
-- 1.3.6.1.4.1.37950.1.1.5.12.9.2.52.1.3
		-- 1.3.6.1.4.1.37950.1.1.5.12.9.2.52.1.3
		onuDhcpv6Prefixlen OBJECT-TYPE
			SYNTAX INTEGER (0..128)
			MAX-ACCESS read-write
			STATUS current
			DESCRIPTION
				"Description."
			::= { onuDhcpv6ServerEntry 3 }

		
--         1.3.6.1.4.1.37950.1.1.5.12.9.2.52.1.4
-- 1.3.6.1.4.1.37950.1.1.5.12.9.2.52.1.4
-- 1.3.6.1.4.1.37950.1.1.5.12.9.2.52.1.4
-- 1.3.6.1.4.1.37950.1.1.5.12.9.2.52.1.4
-- 1.3.6.1.4.1.37950.1.1.5.12.9.2.52.1.4
-- 1.3.6.1.4.1.37950.1.1.5.12.9.2.52.1.4
-- 1.3.6.1.4.1.37950.1.1.5.12.9.2.52.1.4
-- 1.3.6.1.4.1.37950.1.1.5.12.9.2.52.1.4
		-- 1.3.6.1.4.1.37950.1.1.5.12.9.2.52.1.4
		onuDhcpv6PrefixMode OBJECT-TYPE
			SYNTAX INTEGER
				{
				disable(0),
				static(1)
				}
			MAX-ACCESS read-write
			STATUS current
			DESCRIPTION
				"Description."
			::= { onuDhcpv6ServerEntry 4 }

		
--         1.3.6.1.4.1.37950.1.1.5.12.9.2.52.1.5
-- 1.3.6.1.4.1.37950.1.1.5.12.9.2.52.1.5
-- 1.3.6.1.4.1.37950.1.1.5.12.9.2.52.1.5
-- 1.3.6.1.4.1.37950.1.1.5.12.9.2.52.1.5
-- 1.3.6.1.4.1.37950.1.1.5.12.9.2.52.1.5
-- 1.3.6.1.4.1.37950.1.1.5.12.9.2.52.1.5
-- 1.3.6.1.4.1.37950.1.1.5.12.9.2.52.1.5
-- 1.3.6.1.4.1.37950.1.1.5.12.9.2.52.1.5
		-- 1.3.6.1.4.1.37950.1.1.5.12.9.2.52.1.5
		onuDhcpv6PrefixModeIp OBJECT-TYPE
			SYNTAX OCTET STRING
			MAX-ACCESS read-write
			STATUS current
			DESCRIPTION
				"Description."
			::= { onuDhcpv6ServerEntry 5 }

		
--         1.3.6.1.4.1.37950.1.1.5.12.9.2.52.1.6
-- 1.3.6.1.4.1.37950.1.1.5.12.9.2.52.1.6
-- 1.3.6.1.4.1.37950.1.1.5.12.9.2.52.1.6
-- 1.3.6.1.4.1.37950.1.1.5.12.9.2.52.1.6
-- 1.3.6.1.4.1.37950.1.1.5.12.9.2.52.1.6
-- 1.3.6.1.4.1.37950.1.1.5.12.9.2.52.1.6
-- 1.3.6.1.4.1.37950.1.1.5.12.9.2.52.1.6
-- 1.3.6.1.4.1.37950.1.1.5.12.9.2.52.1.6
		-- 1.3.6.1.4.1.37950.1.1.5.12.9.2.52.1.6
		onuDhcpv6ServerEable OBJECT-TYPE
			SYNTAX INTEGER
				{
				disable(0),
				enable(1),
				relay(2)
				}
			MAX-ACCESS read-write
			STATUS current
			DESCRIPTION
				"Description."
			::= { onuDhcpv6ServerEntry 6 }

		
--         1.3.6.1.4.1.37950.1.1.5.12.9.2.52.1.7
-- 1.3.6.1.4.1.37950.1.1.5.12.9.2.52.1.7
-- 1.3.6.1.4.1.37950.1.1.5.12.9.2.52.1.7
-- 1.3.6.1.4.1.37950.1.1.5.12.9.2.52.1.7
-- 1.3.6.1.4.1.37950.1.1.5.12.9.2.52.1.7
-- 1.3.6.1.4.1.37950.1.1.5.12.9.2.52.1.7
-- 1.3.6.1.4.1.37950.1.1.5.12.9.2.52.1.7
-- 1.3.6.1.4.1.37950.1.1.5.12.9.2.52.1.7
		-- 1.3.6.1.4.1.37950.1.1.5.12.9.2.52.1.7
		onuDhcpv6Preference OBJECT-TYPE
			SYNTAX Unsigned32
			MAX-ACCESS read-write
			STATUS current
			DESCRIPTION
				"Description."
			::= { onuDhcpv6ServerEntry 7 }

		
--         1.3.6.1.4.1.37950.1.1.5.12.9.2.52.1.8
-- 1.3.6.1.4.1.37950.1.1.5.12.9.2.52.1.8
-- 1.3.6.1.4.1.37950.1.1.5.12.9.2.52.1.8
-- 1.3.6.1.4.1.37950.1.1.5.12.9.2.52.1.8
-- 1.3.6.1.4.1.37950.1.1.5.12.9.2.52.1.8
-- 1.3.6.1.4.1.37950.1.1.5.12.9.2.52.1.8
-- 1.3.6.1.4.1.37950.1.1.5.12.9.2.52.1.8
-- 1.3.6.1.4.1.37950.1.1.5.12.9.2.52.1.8
		-- 1.3.6.1.4.1.37950.1.1.5.12.9.2.52.1.8
		onuDhcpv6BeginIp OBJECT-TYPE
			SYNTAX OCTET STRING
			MAX-ACCESS read-write
			STATUS current
			DESCRIPTION
				"Description."
			::= { onuDhcpv6ServerEntry 8 }

		
--         1.3.6.1.4.1.37950.1.1.5.12.9.2.52.1.9
-- 1.3.6.1.4.1.37950.1.1.5.12.9.2.52.1.9
-- 1.3.6.1.4.1.37950.1.1.5.12.9.2.52.1.9
-- 1.3.6.1.4.1.37950.1.1.5.12.9.2.52.1.9
-- 1.3.6.1.4.1.37950.1.1.5.12.9.2.52.1.9
-- 1.3.6.1.4.1.37950.1.1.5.12.9.2.52.1.9
-- 1.3.6.1.4.1.37950.1.1.5.12.9.2.52.1.9
-- 1.3.6.1.4.1.37950.1.1.5.12.9.2.52.1.9
		-- 1.3.6.1.4.1.37950.1.1.5.12.9.2.52.1.9
		onuDhcpv6EndIp OBJECT-TYPE
			SYNTAX OCTET STRING
			MAX-ACCESS read-write
			STATUS current
			DESCRIPTION
				"Description."
			::= { onuDhcpv6ServerEntry 9 }

		
--         1.3.6.1.4.1.37950.1.1.5.12.9.2.52.1.10
-- 1.3.6.1.4.1.37950.1.1.5.12.9.2.52.1.10
-- 1.3.6.1.4.1.37950.1.1.5.12.9.2.52.1.10
-- 1.3.6.1.4.1.37950.1.1.5.12.9.2.52.1.10
-- 1.3.6.1.4.1.37950.1.1.5.12.9.2.52.1.10
-- 1.3.6.1.4.1.37950.1.1.5.12.9.2.52.1.10
-- 1.3.6.1.4.1.37950.1.1.5.12.9.2.52.1.10
-- 1.3.6.1.4.1.37950.1.1.5.12.9.2.52.1.10
		-- 1.3.6.1.4.1.37950.1.1.5.12.9.2.52.1.10
		onuDhcpv6PoolType OBJECT-TYPE
			SYNTAX INTEGER
				{
				pc(0),
				camera(1),
				stb(2),
				ip-phone(3)
				}
			MAX-ACCESS read-write
			STATUS current
			DESCRIPTION
				"Description."
			::= { onuDhcpv6ServerEntry 10 }

		
--         1.3.6.1.4.1.37950.1.1.5.12.9.2.52.1.11
-- 1.3.6.1.4.1.37950.1.1.5.12.9.2.52.1.11
-- 1.3.6.1.4.1.37950.1.1.5.12.9.2.52.1.11
-- 1.3.6.1.4.1.37950.1.1.5.12.9.2.52.1.11
-- 1.3.6.1.4.1.37950.1.1.5.12.9.2.52.1.11
-- 1.3.6.1.4.1.37950.1.1.5.12.9.2.52.1.11
-- 1.3.6.1.4.1.37950.1.1.5.12.9.2.52.1.11
-- 1.3.6.1.4.1.37950.1.1.5.12.9.2.52.1.11
		-- 1.3.6.1.4.1.37950.1.1.5.12.9.2.52.1.11
		onuDhcpv6MasterDns OBJECT-TYPE
			SYNTAX OCTET STRING
			MAX-ACCESS read-write
			STATUS current
			DESCRIPTION
				"Description."
			::= { onuDhcpv6ServerEntry 11 }

		
--         1.3.6.1.4.1.37950.1.1.5.12.9.2.52.1.12
-- 1.3.6.1.4.1.37950.1.1.5.12.9.2.52.1.12
-- 1.3.6.1.4.1.37950.1.1.5.12.9.2.52.1.12
-- 1.3.6.1.4.1.37950.1.1.5.12.9.2.52.1.12
-- 1.3.6.1.4.1.37950.1.1.5.12.9.2.52.1.12
-- 1.3.6.1.4.1.37950.1.1.5.12.9.2.52.1.12
-- 1.3.6.1.4.1.37950.1.1.5.12.9.2.52.1.12
-- 1.3.6.1.4.1.37950.1.1.5.12.9.2.52.1.12
		-- 1.3.6.1.4.1.37950.1.1.5.12.9.2.52.1.12
		onuDhcpv6SlaveDns OBJECT-TYPE
			SYNTAX OCTET STRING
			MAX-ACCESS read-write
			STATUS current
			DESCRIPTION
				"Description."
			::= { onuDhcpv6ServerEntry 12 }

		
--         1.3.6.1.4.1.37950.1.1.5.12.9.2.52.1.13
-- 1.3.6.1.4.1.37950.1.1.5.12.9.2.52.1.13
-- 1.3.6.1.4.1.37950.1.1.5.12.9.2.52.1.13
-- 1.3.6.1.4.1.37950.1.1.5.12.9.2.52.1.13
-- 1.3.6.1.4.1.37950.1.1.5.12.9.2.52.1.13
-- 1.3.6.1.4.1.37950.1.1.5.12.9.2.52.1.13
-- 1.3.6.1.4.1.37950.1.1.5.12.9.2.52.1.13
-- 1.3.6.1.4.1.37950.1.1.5.12.9.2.52.1.13
		-- 1.3.6.1.4.1.37950.1.1.5.12.9.2.52.1.13
		onuDhcpv6Gateway OBJECT-TYPE
			SYNTAX OCTET STRING
			MAX-ACCESS read-write
			STATUS current
			DESCRIPTION
				"Description."
			::= { onuDhcpv6ServerEntry 13 }

		
--         1.3.6.1.4.1.37950.1.1.5.12.9.2.52.1.14
-- 1.3.6.1.4.1.37950.1.1.5.12.9.2.52.1.14
-- 1.3.6.1.4.1.37950.1.1.5.12.9.2.52.1.14
-- 1.3.6.1.4.1.37950.1.1.5.12.9.2.52.1.14
-- 1.3.6.1.4.1.37950.1.1.5.12.9.2.52.1.14
-- 1.3.6.1.4.1.37950.1.1.5.12.9.2.52.1.14
-- 1.3.6.1.4.1.37950.1.1.5.12.9.2.52.1.14
-- 1.3.6.1.4.1.37950.1.1.5.12.9.2.52.1.14
		-- 1.3.6.1.4.1.37950.1.1.5.12.9.2.52.1.14
		onuDhcpv6RelayIp OBJECT-TYPE
			SYNTAX OCTET STRING
			MAX-ACCESS read-write
			STATUS current
			DESCRIPTION
				"Description."
			::= { onuDhcpv6ServerEntry 14 }

		
--         1.3.6.1.4.1.37950.1.1.5.12.9.2.52.1.15
-- 1.3.6.1.4.1.37950.1.1.5.12.9.2.52.1.15
-- 1.3.6.1.4.1.37950.1.1.5.12.9.2.52.1.15
-- 1.3.6.1.4.1.37950.1.1.5.12.9.2.52.1.15
-- 1.3.6.1.4.1.37950.1.1.5.12.9.2.52.1.15
-- 1.3.6.1.4.1.37950.1.1.5.12.9.2.52.1.15
-- 1.3.6.1.4.1.37950.1.1.5.12.9.2.52.1.15
-- 1.3.6.1.4.1.37950.1.1.5.12.9.2.52.1.15
		-- 1.3.6.1.4.1.37950.1.1.5.12.9.2.52.1.15
		onuDhcpv6RA OBJECT-TYPE
			SYNTAX INTEGER
				{
				disable(0),
				enable(1)
				}
			MAX-ACCESS read-write
			STATUS current
			DESCRIPTION
				"Description."
			::= { onuDhcpv6ServerEntry 15 }

		
--         1.3.6.1.4.1.37950.1.1.5.12.9.2.52.1.16
-- 1.3.6.1.4.1.37950.1.1.5.12.9.2.52.1.16
-- 1.3.6.1.4.1.37950.1.1.5.12.9.2.52.1.16
-- 1.3.6.1.4.1.37950.1.1.5.12.9.2.52.1.16
-- 1.3.6.1.4.1.37950.1.1.5.12.9.2.52.1.16
-- 1.3.6.1.4.1.37950.1.1.5.12.9.2.52.1.16
-- 1.3.6.1.4.1.37950.1.1.5.12.9.2.52.1.16
-- 1.3.6.1.4.1.37950.1.1.5.12.9.2.52.1.16
		-- 1.3.6.1.4.1.37950.1.1.5.12.9.2.52.1.16
		onuDhcpv6RAManage OBJECT-TYPE
			SYNTAX INTEGER
				{
				disable(0),
				enable(1)
				}
			MAX-ACCESS read-write
			STATUS current
			DESCRIPTION
				"Description."
			::= { onuDhcpv6ServerEntry 16 }

		
--         1.3.6.1.4.1.37950.1.1.5.12.9.2.52.1.17
-- 1.3.6.1.4.1.37950.1.1.5.12.9.2.52.1.17
-- 1.3.6.1.4.1.37950.1.1.5.12.9.2.52.1.17
-- 1.3.6.1.4.1.37950.1.1.5.12.9.2.52.1.17
-- 1.3.6.1.4.1.37950.1.1.5.12.9.2.52.1.17
-- 1.3.6.1.4.1.37950.1.1.5.12.9.2.52.1.17
-- 1.3.6.1.4.1.37950.1.1.5.12.9.2.52.1.17
-- 1.3.6.1.4.1.37950.1.1.5.12.9.2.52.1.17
		-- 1.3.6.1.4.1.37950.1.1.5.12.9.2.52.1.17
		onuDhcpv6RAOther OBJECT-TYPE
			SYNTAX INTEGER
				{
				disable(0),
				enable(1)
				}
			MAX-ACCESS read-write
			STATUS current
			DESCRIPTION
				"Description."
			::= { onuDhcpv6ServerEntry 17 }

		
--         1.3.6.1.4.1.37950.1.1.5.12.9.2.52.1.18
-- 1.3.6.1.4.1.37950.1.1.5.12.9.2.52.1.18
-- 1.3.6.1.4.1.37950.1.1.5.12.9.2.52.1.18
-- 1.3.6.1.4.1.37950.1.1.5.12.9.2.52.1.18
-- 1.3.6.1.4.1.37950.1.1.5.12.9.2.52.1.18
-- 1.3.6.1.4.1.37950.1.1.5.12.9.2.52.1.18
-- 1.3.6.1.4.1.37950.1.1.5.12.9.2.52.1.18
-- 1.3.6.1.4.1.37950.1.1.5.12.9.2.52.1.18
		-- 1.3.6.1.4.1.37950.1.1.5.12.9.2.52.1.18
		onuDhcpv6RAMaxInterval OBJECT-TYPE
			SYNTAX Integer32 (1..1800)
			MAX-ACCESS read-write
			STATUS current
			DESCRIPTION
				"Description."
			::= { onuDhcpv6ServerEntry 18 }

		
--         1.3.6.1.4.1.37950.1.1.5.12.9.2.52.1.19
-- 1.3.6.1.4.1.37950.1.1.5.12.9.2.52.1.19
-- 1.3.6.1.4.1.37950.1.1.5.12.9.2.52.1.19
-- 1.3.6.1.4.1.37950.1.1.5.12.9.2.52.1.19
-- 1.3.6.1.4.1.37950.1.1.5.12.9.2.52.1.19
-- 1.3.6.1.4.1.37950.1.1.5.12.9.2.52.1.19
-- 1.3.6.1.4.1.37950.1.1.5.12.9.2.52.1.19
-- 1.3.6.1.4.1.37950.1.1.5.12.9.2.52.1.19
		-- 1.3.6.1.4.1.37950.1.1.5.12.9.2.52.1.19
		onuDhcpv6RAMinInterval OBJECT-TYPE
			SYNTAX Integer32 (1..1800)
			MAX-ACCESS read-write
			STATUS current
			DESCRIPTION
				"Description."
			::= { onuDhcpv6ServerEntry 19 }

		
--         1.3.6.1.4.1.37950.1.1.5.12.9.2.52.1.20
-- 1.3.6.1.4.1.37950.1.1.5.12.9.2.52.1.20
-- 1.3.6.1.4.1.37950.1.1.5.12.9.2.52.1.20
-- 1.3.6.1.4.1.37950.1.1.5.12.9.2.52.1.20
-- 1.3.6.1.4.1.37950.1.1.5.12.9.2.52.1.20
-- 1.3.6.1.4.1.37950.1.1.5.12.9.2.52.1.20
-- 1.3.6.1.4.1.37950.1.1.5.12.9.2.52.1.20
-- 1.3.6.1.4.1.37950.1.1.5.12.9.2.52.1.20
		-- 1.3.6.1.4.1.37950.1.1.5.12.9.2.52.1.20
		onuDhcpv6Valid OBJECT-TYPE
			SYNTAX Unsigned32
			MAX-ACCESS read-write
			STATUS current
			DESCRIPTION
				"Description."
			::= { onuDhcpv6ServerEntry 20 }

		
--         1.3.6.1.4.1.37950.1.1.5.12.9.2.52.1.21
-- 1.3.6.1.4.1.37950.1.1.5.12.9.2.52.1.21
-- 1.3.6.1.4.1.37950.1.1.5.12.9.2.52.1.21
-- 1.3.6.1.4.1.37950.1.1.5.12.9.2.52.1.21
-- 1.3.6.1.4.1.37950.1.1.5.12.9.2.52.1.21
-- 1.3.6.1.4.1.37950.1.1.5.12.9.2.52.1.21
-- 1.3.6.1.4.1.37950.1.1.5.12.9.2.52.1.21
-- 1.3.6.1.4.1.37950.1.1.5.12.9.2.52.1.21
		-- 1.3.6.1.4.1.37950.1.1.5.12.9.2.52.1.21
		onuDhcpv6DnsMode OBJECT-TYPE
			SYNTAX INTEGER
				{
				wanconnection(0),
				static(1),
				hgwproxy(2)
				}
			MAX-ACCESS read-write
			STATUS current
			DESCRIPTION
				"Description."
			::= { onuDhcpv6ServerEntry 21 }

		
--           1.3.6.1.4.1.37950.1.1.5.12.3.2.6
-- 1.3.6.1.4.1.37950.1.1.5.12.9.2.53
-- 1.3.6.1.4.1.37950.1.1.5.12.9.2.53
-- 1.3.6.1.4.1.37950.1.1.5.12.9.2.53
-- 1.3.6.1.4.1.37950.1.1.5.12.9.2.53
-- 1.3.6.1.4.1.37950.1.1.5.12.9.2.53
-- 1.3.6.1.4.1.37950.1.1.5.12.9.2.53
-- 1.3.6.1.4.1.37950.1.1.5.12.9.2.53
-- 1.3.6.1.4.1.37950.1.1.5.12.9.2.53
		-- 1.3.6.1.4.1.37950.1.1.5.12.9.2.53
		onuWanConnV6Table OBJECT-TYPE
			SYNTAX SEQUENCE OF OnuWanConnV6Entry
			MAX-ACCESS not-accessible
			STATUS current
			DESCRIPTION
				"Description."
			::= { srvProfileShow 53 }

		
--           1.3.6.1.4.1.37950.1.1.5.12.3.2.6.1
-- 1.3.6.1.4.1.37950.1.1.5.12.9.2.53.1
-- 1.3.6.1.4.1.37950.1.1.5.12.9.2.53.1
-- 1.3.6.1.4.1.37950.1.1.5.12.9.2.53.1
-- 1.3.6.1.4.1.37950.1.1.5.12.9.2.53.1
-- 1.3.6.1.4.1.37950.1.1.5.12.9.2.53.1
-- 1.3.6.1.4.1.37950.1.1.5.12.9.2.53.1
-- 1.3.6.1.4.1.37950.1.1.5.12.9.2.53.1
-- 1.3.6.1.4.1.37950.1.1.5.12.9.2.53.1
		-- 1.3.6.1.4.1.37950.1.1.5.12.9.2.53.1
		onuWanConnV6Entry OBJECT-TYPE
			SYNTAX OnuWanConnV6Entry
			MAX-ACCESS not-accessible
			STATUS current
			DESCRIPTION
				"Description."
			INDEX { v6wanConnSrvId, v6wanConnIndexS, v6wanConnBindLanS }
			::= { onuWanConnV6Table 1 }

		
		OnuWanConnV6Entry ::=
			SEQUENCE { 
				v6wanConnSrvId
					INTEGER,
				v6wanConnIndexS
					Integer32,
				v6wanConnBindLanS
					INTEGER,
				v6wanConnBindSsidS
					INTEGER,
				v6WanModeS
					INTEGER,
				v6wanConnTypeS
					INTEGER,
				v6wanConnVlanIdS
					INTEGER,
				v6wanConnVlanCosS
					INTEGER,
				v6wanConnIpProtocolS
					INTEGER,
				v6WanConnModeS
					INTEGER,
				v6wanConnIpAddressIpv4S
					IpAddress,
				v6wanConnIpNetMaskIpv4S
					IpAddress,
				v6wanConnGatewayIpv4S
					IpAddress,
				v6wanConnDnsEnableIpv4S
					INTEGER,
				v6wanConnMasterDnsIpv4S
					IpAddress,
				v6wanConnSlaveDnsIpv4S
					IpAddress,
				v6wanConnNatEnableS
					INTEGER,
				v6wanConnAddressIpv6S
					OCTET STRING,
				v6wanConnPrefixLenIpv6S
					INTEGER,
				v6wanConnGatewayIpv6S
					OCTET STRING,
				v6wanConnDnsEnableIpv6S
					INTEGER,
				v6wanConnMsaterDnsIpv6S
					OCTET STRING,
				v6wanConnSlaveDnsIpv6S
					OCTET STRING,
				v6wanConnSlaacS
					INTEGER,
				v6wanConnPppoeProxyS
					INTEGER,
				v6wanConnPppoeUsernameS
					OCTET STRING,
				v6wanConnPppoePasswordS
					OCTET STRING,
				v6wanConnPppoeSerNameS
					OCTET STRING,
				v6wanConnPppoeModeS
					INTEGER,
				v6wanConnDhcpv6ClientAddressS
					INTEGER,
				v6wanConnDhcpv6ClientPrefixS
					INTEGER,
				v6wanConnDsLiteEnableS
					INTEGER,
				v6wanConnDsLiteAftrModeS
					INTEGER,
				v6wanConnDsLiteAddressTypeS
					INTEGER,
				v6wanConnDsLiteAddressS
					OCTET STRING,
				v6wanConnQosEnableS
					INTEGER,
				v6wanConnVlanModeS
					INTEGER,
				v6wanConnTranslationEnableS
					INTEGER,
				v6wanConnTranslationVlanS
					INTEGER,
				v6wanConnTranslationCosS
					INTEGER,
				v6wanConnQinqEnableS
					INTEGER,
				v6wanConnQinqTpidS
					INTEGER,
				v6wanConnSvlanIdS
					INTEGER,
				v6wanConnSvlanCosS
					INTEGER,
				v6wanConnRouteMtuS
					Integer32
			 }

--           1.3.6.1.4.1.37950.1.1.5.12.9.2.39.1.1
-- 1.3.6.1.4.1.37950.1.1.5.12.9.2.53.1.1
-- 1.3.6.1.4.1.37950.1.1.5.12.9.2.53.1.1
-- 1.3.6.1.4.1.37950.1.1.5.12.9.2.53.1.1
-- 1.3.6.1.4.1.37950.1.1.5.12.9.2.53.1.1
-- 1.3.6.1.4.1.37950.1.1.5.12.9.2.53.1.1
-- 1.3.6.1.4.1.37950.1.1.5.12.9.2.53.1.1
-- 1.3.6.1.4.1.37950.1.1.5.12.9.2.53.1.1
-- 1.3.6.1.4.1.37950.1.1.5.12.9.2.53.1.1
		-- 1.3.6.1.4.1.37950.1.1.5.12.9.2.53.1.1
		v6wanConnSrvId OBJECT-TYPE
			SYNTAX INTEGER (0..65535)
			MAX-ACCESS read-write
			STATUS current
			DESCRIPTION
				"Description."
			::= { onuWanConnV6Entry 1 }

		
--           1.3.6.1.4.1.37950.1.1.5.12.3.2.6.1.3
-- 1.3.6.1.4.1.37950.1.1.5.12.9.2.53.1.2
-- 1.3.6.1.4.1.37950.1.1.5.12.9.2.53.1.2
-- 1.3.6.1.4.1.37950.1.1.5.12.9.2.53.1.2
-- 1.3.6.1.4.1.37950.1.1.5.12.9.2.53.1.2
-- 1.3.6.1.4.1.37950.1.1.5.12.9.2.53.1.2
-- 1.3.6.1.4.1.37950.1.1.5.12.9.2.53.1.2
-- 1.3.6.1.4.1.37950.1.1.5.12.9.2.53.1.2
-- 1.3.6.1.4.1.37950.1.1.5.12.9.2.53.1.2
		-- 1.3.6.1.4.1.37950.1.1.5.12.9.2.53.1.2
		v6wanConnIndexS OBJECT-TYPE
			SYNTAX Integer32 (1..8)
			MAX-ACCESS read-write
			STATUS current
			DESCRIPTION
				"Description."
			::= { onuWanConnV6Entry 2 }

		
--           1.3.6.1.4.1.37950.1.1.5.12.3.2.6.1.4
-- 1.3.6.1.4.1.37950.1.1.5.12.9.2.53.1.3
-- 1.3.6.1.4.1.37950.1.1.5.12.9.2.53.1.3
-- 1.3.6.1.4.1.37950.1.1.5.12.9.2.53.1.3
-- 1.3.6.1.4.1.37950.1.1.5.12.9.2.53.1.3
-- 1.3.6.1.4.1.37950.1.1.5.12.9.2.53.1.3
-- 1.3.6.1.4.1.37950.1.1.5.12.9.2.53.1.3
-- 1.3.6.1.4.1.37950.1.1.5.12.9.2.53.1.3
-- 1.3.6.1.4.1.37950.1.1.5.12.9.2.53.1.3
		-- 1.3.6.1.4.1.37950.1.1.5.12.9.2.53.1.3
		v6wanConnBindLanS OBJECT-TYPE
			SYNTAX INTEGER (0..15)
			MAX-ACCESS read-write
			STATUS current
			DESCRIPTION
				"Description."
			::= { onuWanConnV6Entry 3 }

		
--           1.3.6.1.4.1.37950.1.1.5.12.3.2.6.1.5
-- 1.3.6.1.4.1.37950.1.1.5.12.9.2.53.1.4
-- 1.3.6.1.4.1.37950.1.1.5.12.9.2.53.1.4
-- 1.3.6.1.4.1.37950.1.1.5.12.9.2.53.1.4
-- 1.3.6.1.4.1.37950.1.1.5.12.9.2.53.1.4
-- 1.3.6.1.4.1.37950.1.1.5.12.9.2.53.1.4
-- 1.3.6.1.4.1.37950.1.1.5.12.9.2.53.1.4
-- 1.3.6.1.4.1.37950.1.1.5.12.9.2.53.1.4
-- 1.3.6.1.4.1.37950.1.1.5.12.9.2.53.1.4
		-- 1.3.6.1.4.1.37950.1.1.5.12.9.2.53.1.4
		v6wanConnBindSsidS OBJECT-TYPE
			SYNTAX INTEGER (0..65535)
			MAX-ACCESS read-write
			STATUS current
			DESCRIPTION
				"Description."
			::= { onuWanConnV6Entry 4 }

		
--           1.3.6.1.4.1.37950.1.1.5.12.3.2.6.1.6
-- 1.3.6.1.4.1.37950.1.1.5.12.9.2.53.1.5
-- 1.3.6.1.4.1.37950.1.1.5.12.9.2.53.1.5
-- 1.3.6.1.4.1.37950.1.1.5.12.9.2.53.1.5
-- 1.3.6.1.4.1.37950.1.1.5.12.9.2.53.1.5
-- 1.3.6.1.4.1.37950.1.1.5.12.9.2.53.1.5
-- 1.3.6.1.4.1.37950.1.1.5.12.9.2.53.1.5
-- 1.3.6.1.4.1.37950.1.1.5.12.9.2.53.1.5
-- 1.3.6.1.4.1.37950.1.1.5.12.9.2.53.1.5
		-- 1.3.6.1.4.1.37950.1.1.5.12.9.2.53.1.5
		v6WanModeS OBJECT-TYPE
			SYNTAX INTEGER
				{
				internet(0),
				multicast(1),
				tr069(2),
				tr069-internet(3),
				tr069-voip(4),
				voip-internet(5),
				tr069-voip-internet(6),
				voip(7),
				other(100)
				}
			MAX-ACCESS read-write
			STATUS current
			DESCRIPTION
				"Description."
			::= { onuWanConnV6Entry 5 }

		
--           1.3.6.1.4.1.37950.1.1.5.12.3.2.6.1.7
-- 1.3.6.1.4.1.37950.1.1.5.12.9.2.53.1.6
-- 1.3.6.1.4.1.37950.1.1.5.12.9.2.53.1.6
-- 1.3.6.1.4.1.37950.1.1.5.12.9.2.53.1.6
-- 1.3.6.1.4.1.37950.1.1.5.12.9.2.53.1.6
-- 1.3.6.1.4.1.37950.1.1.5.12.9.2.53.1.6
-- 1.3.6.1.4.1.37950.1.1.5.12.9.2.53.1.6
-- 1.3.6.1.4.1.37950.1.1.5.12.9.2.53.1.6
-- 1.3.6.1.4.1.37950.1.1.5.12.9.2.53.1.6
		-- 1.3.6.1.4.1.37950.1.1.5.12.9.2.53.1.6
		v6wanConnTypeS OBJECT-TYPE
			SYNTAX INTEGER
				{
				bridge(0),
				route(1)
				}
			MAX-ACCESS read-write
			STATUS current
			DESCRIPTION
				"Description."
			::= { onuWanConnV6Entry 6 }

		
--           1.3.6.1.4.1.37950.1.1.5.12.3.2.6.1.8
-- 1.3.6.1.4.1.37950.1.1.5.12.9.2.53.1.7
-- 1.3.6.1.4.1.37950.1.1.5.12.9.2.53.1.7
-- 1.3.6.1.4.1.37950.1.1.5.12.9.2.53.1.7
-- 1.3.6.1.4.1.37950.1.1.5.12.9.2.53.1.7
-- 1.3.6.1.4.1.37950.1.1.5.12.9.2.53.1.7
-- 1.3.6.1.4.1.37950.1.1.5.12.9.2.53.1.7
-- 1.3.6.1.4.1.37950.1.1.5.12.9.2.53.1.7
-- 1.3.6.1.4.1.37950.1.1.5.12.9.2.53.1.7
		-- 1.3.6.1.4.1.37950.1.1.5.12.9.2.53.1.7
		v6wanConnVlanIdS OBJECT-TYPE
			SYNTAX INTEGER (0..4095)
			MAX-ACCESS read-write
			STATUS current
			DESCRIPTION
				"Description."
			::= { onuWanConnV6Entry 7 }

		
--           1.3.6.1.4.1.37950.1.1.5.12.3.2.6.1.9
-- 1.3.6.1.4.1.37950.1.1.5.12.9.2.53.1.8
-- 1.3.6.1.4.1.37950.1.1.5.12.9.2.53.1.8
-- 1.3.6.1.4.1.37950.1.1.5.12.9.2.53.1.8
-- 1.3.6.1.4.1.37950.1.1.5.12.9.2.53.1.8
-- 1.3.6.1.4.1.37950.1.1.5.12.9.2.53.1.8
-- 1.3.6.1.4.1.37950.1.1.5.12.9.2.53.1.8
-- 1.3.6.1.4.1.37950.1.1.5.12.9.2.53.1.8
-- 1.3.6.1.4.1.37950.1.1.5.12.9.2.53.1.8
		-- 1.3.6.1.4.1.37950.1.1.5.12.9.2.53.1.8
		v6wanConnVlanCosS OBJECT-TYPE
			SYNTAX INTEGER (0..7)
			MAX-ACCESS read-write
			STATUS current
			DESCRIPTION
				"Description."
			::= { onuWanConnV6Entry 8 }

		
--          1.3.6.1.4.1.37950.1.1.5.12.3.2.6.1.33
-- 1.3.6.1.4.1.37950.1.1.5.12.9.2.53.1.9
-- 1.3.6.1.4.1.37950.1.1.5.12.9.2.53.1.9
-- 1.3.6.1.4.1.37950.1.1.5.12.9.2.53.1.9
-- 1.3.6.1.4.1.37950.1.1.5.12.9.2.53.1.9
-- 1.3.6.1.4.1.37950.1.1.5.12.9.2.53.1.9
-- 1.3.6.1.4.1.37950.1.1.5.12.9.2.53.1.9
-- 1.3.6.1.4.1.37950.1.1.5.12.9.2.53.1.9
-- 1.3.6.1.4.1.37950.1.1.5.12.9.2.53.1.9
		-- 1.3.6.1.4.1.37950.1.1.5.12.9.2.53.1.9
		v6wanConnIpProtocolS OBJECT-TYPE
			SYNTAX INTEGER
				{
				ipv4(0),
				ipv6(1),
				ipv4-ipv6(2)
				}
			MAX-ACCESS read-write
			STATUS current
			DESCRIPTION
				"Description."
			::= { onuWanConnV6Entry 9 }

		
--           1.3.6.1.4.1.37950.1.1.5.12.3.2.6.1.11
-- 1.3.6.1.4.1.37950.1.1.5.12.9.2.53.1.10
-- 1.3.6.1.4.1.37950.1.1.5.12.9.2.53.1.10
-- 1.3.6.1.4.1.37950.1.1.5.12.9.2.53.1.10
-- 1.3.6.1.4.1.37950.1.1.5.12.9.2.53.1.10
-- 1.3.6.1.4.1.37950.1.1.5.12.9.2.53.1.10
-- 1.3.6.1.4.1.37950.1.1.5.12.9.2.53.1.10
-- 1.3.6.1.4.1.37950.1.1.5.12.9.2.53.1.10
-- 1.3.6.1.4.1.37950.1.1.5.12.9.2.53.1.10
		-- 1.3.6.1.4.1.37950.1.1.5.12.9.2.53.1.10
		v6WanConnModeS OBJECT-TYPE
			SYNTAX INTEGER
				{
				dhcp(0),
				static(1),
				pppoe(2)
				}
			MAX-ACCESS read-write
			STATUS current
			DESCRIPTION
				"Description."
			::= { onuWanConnV6Entry 10 }

		
--           1.3.6.1.4.1.37950.1.1.5.12.3.2.6.1.12
-- 1.3.6.1.4.1.37950.1.1.5.12.9.2.53.1.11
-- 1.3.6.1.4.1.37950.1.1.5.12.9.2.53.1.11
-- 1.3.6.1.4.1.37950.1.1.5.12.9.2.53.1.11
-- 1.3.6.1.4.1.37950.1.1.5.12.9.2.53.1.11
-- 1.3.6.1.4.1.37950.1.1.5.12.9.2.53.1.11
-- 1.3.6.1.4.1.37950.1.1.5.12.9.2.53.1.11
-- 1.3.6.1.4.1.37950.1.1.5.12.9.2.53.1.11
-- 1.3.6.1.4.1.37950.1.1.5.12.9.2.53.1.11
		-- 1.3.6.1.4.1.37950.1.1.5.12.9.2.53.1.11
		v6wanConnIpAddressIpv4S OBJECT-TYPE
			SYNTAX IpAddress
			MAX-ACCESS read-write
			STATUS current
			DESCRIPTION
				"Description."
			::= { onuWanConnV6Entry 11 }

		
--           1.3.6.1.4.1.37950.1.1.5.12.3.2.6.1.13
-- 1.3.6.1.4.1.37950.1.1.5.12.9.2.53.1.12
-- 1.3.6.1.4.1.37950.1.1.5.12.9.2.53.1.12
-- 1.3.6.1.4.1.37950.1.1.5.12.9.2.53.1.12
-- 1.3.6.1.4.1.37950.1.1.5.12.9.2.53.1.12
-- 1.3.6.1.4.1.37950.1.1.5.12.9.2.53.1.12
-- 1.3.6.1.4.1.37950.1.1.5.12.9.2.53.1.12
-- 1.3.6.1.4.1.37950.1.1.5.12.9.2.53.1.12
-- 1.3.6.1.4.1.37950.1.1.5.12.9.2.53.1.12
		-- 1.3.6.1.4.1.37950.1.1.5.12.9.2.53.1.12
		v6wanConnIpNetMaskIpv4S OBJECT-TYPE
			SYNTAX IpAddress
			MAX-ACCESS read-write
			STATUS current
			DESCRIPTION
				"Description."
			::= { onuWanConnV6Entry 12 }

		
--           1.3.6.1.4.1.37950.1.1.5.12.3.2.6.1.14
-- 1.3.6.1.4.1.37950.1.1.5.12.9.2.53.1.13
-- 1.3.6.1.4.1.37950.1.1.5.12.9.2.53.1.13
-- 1.3.6.1.4.1.37950.1.1.5.12.9.2.53.1.13
-- 1.3.6.1.4.1.37950.1.1.5.12.9.2.53.1.13
-- 1.3.6.1.4.1.37950.1.1.5.12.9.2.53.1.13
-- 1.3.6.1.4.1.37950.1.1.5.12.9.2.53.1.13
-- 1.3.6.1.4.1.37950.1.1.5.12.9.2.53.1.13
-- 1.3.6.1.4.1.37950.1.1.5.12.9.2.53.1.13
		-- 1.3.6.1.4.1.37950.1.1.5.12.9.2.53.1.13
		v6wanConnGatewayIpv4S OBJECT-TYPE
			SYNTAX IpAddress
			MAX-ACCESS read-write
			STATUS current
			DESCRIPTION
				"Description."
			::= { onuWanConnV6Entry 13 }

		
--           1.3.6.1.4.1.37950.1.1.5.12.3.2.6.1.21
-- 1.3.6.1.4.1.37950.1.1.5.12.9.2.53.1.14
-- 1.3.6.1.4.1.37950.1.1.5.12.9.2.53.1.14
-- 1.3.6.1.4.1.37950.1.1.5.12.9.2.53.1.14
-- 1.3.6.1.4.1.37950.1.1.5.12.9.2.53.1.14
-- 1.3.6.1.4.1.37950.1.1.5.12.9.2.53.1.14
-- 1.3.6.1.4.1.37950.1.1.5.12.9.2.53.1.14
-- 1.3.6.1.4.1.37950.1.1.5.12.9.2.53.1.14
-- 1.3.6.1.4.1.37950.1.1.5.12.9.2.53.1.14
		-- 1.3.6.1.4.1.37950.1.1.5.12.9.2.53.1.14
		v6wanConnDnsEnableIpv4S OBJECT-TYPE
			SYNTAX INTEGER
				{
				disable(0),
				enable(1)
				}
			MAX-ACCESS read-write
			STATUS current
			DESCRIPTION
				"Description."
			::= { onuWanConnV6Entry 14 }

		
--           1.3.6.1.4.1.37950.1.1.5.12.3.2.6.1.15
-- 1.3.6.1.4.1.37950.1.1.5.12.9.2.53.1.15
-- 1.3.6.1.4.1.37950.1.1.5.12.9.2.53.1.15
-- 1.3.6.1.4.1.37950.1.1.5.12.9.2.53.1.15
-- 1.3.6.1.4.1.37950.1.1.5.12.9.2.53.1.15
-- 1.3.6.1.4.1.37950.1.1.5.12.9.2.53.1.15
-- 1.3.6.1.4.1.37950.1.1.5.12.9.2.53.1.15
-- 1.3.6.1.4.1.37950.1.1.5.12.9.2.53.1.15
-- 1.3.6.1.4.1.37950.1.1.5.12.9.2.53.1.15
		-- 1.3.6.1.4.1.37950.1.1.5.12.9.2.53.1.15
		v6wanConnMasterDnsIpv4S OBJECT-TYPE
			SYNTAX IpAddress
			MAX-ACCESS read-write
			STATUS current
			DESCRIPTION
				"Description."
			::= { onuWanConnV6Entry 15 }

		
--           1.3.6.1.4.1.37950.1.1.5.12.3.2.6.1.16
-- 1.3.6.1.4.1.37950.1.1.5.12.9.2.53.1.16
-- 1.3.6.1.4.1.37950.1.1.5.12.9.2.53.1.16
-- 1.3.6.1.4.1.37950.1.1.5.12.9.2.53.1.16
-- 1.3.6.1.4.1.37950.1.1.5.12.9.2.53.1.16
-- 1.3.6.1.4.1.37950.1.1.5.12.9.2.53.1.16
-- 1.3.6.1.4.1.37950.1.1.5.12.9.2.53.1.16
-- 1.3.6.1.4.1.37950.1.1.5.12.9.2.53.1.16
-- 1.3.6.1.4.1.37950.1.1.5.12.9.2.53.1.16
		-- 1.3.6.1.4.1.37950.1.1.5.12.9.2.53.1.16
		v6wanConnSlaveDnsIpv4S OBJECT-TYPE
			SYNTAX IpAddress
			MAX-ACCESS read-write
			STATUS current
			DESCRIPTION
				"Description."
			::= { onuWanConnV6Entry 16 }

		
--           1.3.6.1.4.1.37950.1.1.5.12.3.2.6.1.10
-- 1.3.6.1.4.1.37950.1.1.5.12.9.2.53.1.17
-- 1.3.6.1.4.1.37950.1.1.5.12.9.2.53.1.17
-- 1.3.6.1.4.1.37950.1.1.5.12.9.2.53.1.17
-- 1.3.6.1.4.1.37950.1.1.5.12.9.2.53.1.17
-- 1.3.6.1.4.1.37950.1.1.5.12.9.2.53.1.17
-- 1.3.6.1.4.1.37950.1.1.5.12.9.2.53.1.17
-- 1.3.6.1.4.1.37950.1.1.5.12.9.2.53.1.17
-- 1.3.6.1.4.1.37950.1.1.5.12.9.2.53.1.17
		-- 1.3.6.1.4.1.37950.1.1.5.12.9.2.53.1.17
		v6wanConnNatEnableS OBJECT-TYPE
			SYNTAX INTEGER
				{
				disable(0),
				enable(1)
				}
			MAX-ACCESS read-write
			STATUS current
			DESCRIPTION
				"Description."
			::= { onuWanConnV6Entry 17 }

		
--           1.3.6.1.4.1.37950.1.1.5.12.3.2.6.1.16
-- 1.3.6.1.4.1.37950.1.1.5.12.9.2.53.1.18
-- 1.3.6.1.4.1.37950.1.1.5.12.9.2.53.1.18
-- 1.3.6.1.4.1.37950.1.1.5.12.9.2.53.1.18
-- 1.3.6.1.4.1.37950.1.1.5.12.9.2.53.1.18
-- 1.3.6.1.4.1.37950.1.1.5.12.9.2.53.1.18
-- 1.3.6.1.4.1.37950.1.1.5.12.9.2.53.1.18
-- 1.3.6.1.4.1.37950.1.1.5.12.9.2.53.1.18
-- 1.3.6.1.4.1.37950.1.1.5.12.9.2.53.1.18
		-- 1.3.6.1.4.1.37950.1.1.5.12.9.2.53.1.18
		v6wanConnAddressIpv6S OBJECT-TYPE
			SYNTAX OCTET STRING
			MAX-ACCESS read-write
			STATUS current
			DESCRIPTION
				"Description."
			::= { onuWanConnV6Entry 18 }

		
--           1.3.6.1.4.1.37950.1.1.5.12.3.2.6.1.16
-- 1.3.6.1.4.1.37950.1.1.5.12.9.2.53.1.19
-- 1.3.6.1.4.1.37950.1.1.5.12.9.2.53.1.19
-- 1.3.6.1.4.1.37950.1.1.5.12.9.2.53.1.19
-- 1.3.6.1.4.1.37950.1.1.5.12.9.2.53.1.19
-- 1.3.6.1.4.1.37950.1.1.5.12.9.2.53.1.19
-- 1.3.6.1.4.1.37950.1.1.5.12.9.2.53.1.19
-- 1.3.6.1.4.1.37950.1.1.5.12.9.2.53.1.19
-- 1.3.6.1.4.1.37950.1.1.5.12.9.2.53.1.19
		-- 1.3.6.1.4.1.37950.1.1.5.12.9.2.53.1.19
		v6wanConnPrefixLenIpv6S OBJECT-TYPE
			SYNTAX INTEGER (0..128)
			MAX-ACCESS read-write
			STATUS current
			DESCRIPTION
				"Description."
			::= { onuWanConnV6Entry 19 }

		
--           1.3.6.1.4.1.37950.1.1.5.12.3.2.6.1.16
-- 1.3.6.1.4.1.37950.1.1.5.12.9.2.53.1.20
-- 1.3.6.1.4.1.37950.1.1.5.12.9.2.53.1.20
-- 1.3.6.1.4.1.37950.1.1.5.12.9.2.53.1.20
-- 1.3.6.1.4.1.37950.1.1.5.12.9.2.53.1.20
-- 1.3.6.1.4.1.37950.1.1.5.12.9.2.53.1.20
-- 1.3.6.1.4.1.37950.1.1.5.12.9.2.53.1.20
-- 1.3.6.1.4.1.37950.1.1.5.12.9.2.53.1.20
-- 1.3.6.1.4.1.37950.1.1.5.12.9.2.53.1.20
		-- 1.3.6.1.4.1.37950.1.1.5.12.9.2.53.1.20
		v6wanConnGatewayIpv6S OBJECT-TYPE
			SYNTAX OCTET STRING
			MAX-ACCESS read-write
			STATUS current
			DESCRIPTION
				"Description."
			::= { onuWanConnV6Entry 20 }

		
--           1.3.6.1.4.1.37950.1.1.5.12.3.2.6.1.21
-- 1.3.6.1.4.1.37950.1.1.5.12.9.2.53.1.21
-- 1.3.6.1.4.1.37950.1.1.5.12.9.2.53.1.21
-- 1.3.6.1.4.1.37950.1.1.5.12.9.2.53.1.21
-- 1.3.6.1.4.1.37950.1.1.5.12.9.2.53.1.21
-- 1.3.6.1.4.1.37950.1.1.5.12.9.2.53.1.21
-- 1.3.6.1.4.1.37950.1.1.5.12.9.2.53.1.21
-- 1.3.6.1.4.1.37950.1.1.5.12.9.2.53.1.21
-- 1.3.6.1.4.1.37950.1.1.5.12.9.2.53.1.21
		-- 1.3.6.1.4.1.37950.1.1.5.12.9.2.53.1.21
		v6wanConnDnsEnableIpv6S OBJECT-TYPE
			SYNTAX INTEGER
				{
				disable(0),
				enable(1)
				}
			MAX-ACCESS read-write
			STATUS current
			DESCRIPTION
				"Description."
			::= { onuWanConnV6Entry 21 }

		
--           1.3.6.1.4.1.37950.1.1.5.12.3.2.6.1.16
-- 1.3.6.1.4.1.37950.1.1.5.12.9.2.53.1.22
-- 1.3.6.1.4.1.37950.1.1.5.12.9.2.53.1.22
-- 1.3.6.1.4.1.37950.1.1.5.12.9.2.53.1.22
-- 1.3.6.1.4.1.37950.1.1.5.12.9.2.53.1.22
-- 1.3.6.1.4.1.37950.1.1.5.12.9.2.53.1.22
-- 1.3.6.1.4.1.37950.1.1.5.12.9.2.53.1.22
-- 1.3.6.1.4.1.37950.1.1.5.12.9.2.53.1.22
-- 1.3.6.1.4.1.37950.1.1.5.12.9.2.53.1.22
		-- 1.3.6.1.4.1.37950.1.1.5.12.9.2.53.1.22
		v6wanConnMsaterDnsIpv6S OBJECT-TYPE
			SYNTAX OCTET STRING
			MAX-ACCESS read-write
			STATUS current
			DESCRIPTION
				"Description."
			::= { onuWanConnV6Entry 22 }

		
--           1.3.6.1.4.1.37950.1.1.5.12.3.2.6.1.16
-- 1.3.6.1.4.1.37950.1.1.5.12.9.2.53.1.23
-- 1.3.6.1.4.1.37950.1.1.5.12.9.2.53.1.23
-- 1.3.6.1.4.1.37950.1.1.5.12.9.2.53.1.23
-- 1.3.6.1.4.1.37950.1.1.5.12.9.2.53.1.23
-- 1.3.6.1.4.1.37950.1.1.5.12.9.2.53.1.23
-- 1.3.6.1.4.1.37950.1.1.5.12.9.2.53.1.23
-- 1.3.6.1.4.1.37950.1.1.5.12.9.2.53.1.23
-- 1.3.6.1.4.1.37950.1.1.5.12.9.2.53.1.23
		-- 1.3.6.1.4.1.37950.1.1.5.12.9.2.53.1.23
		v6wanConnSlaveDnsIpv6S OBJECT-TYPE
			SYNTAX OCTET STRING
			MAX-ACCESS read-write
			STATUS current
			DESCRIPTION
				"Description."
			::= { onuWanConnV6Entry 23 }

		
--           1.3.6.1.4.1.37950.1.1.5.12.3.2.6.1.21
-- 1.3.6.1.4.1.37950.1.1.5.12.9.2.53.1.24
-- 1.3.6.1.4.1.37950.1.1.5.12.9.2.53.1.24
-- 1.3.6.1.4.1.37950.1.1.5.12.9.2.53.1.24
-- 1.3.6.1.4.1.37950.1.1.5.12.9.2.53.1.24
-- 1.3.6.1.4.1.37950.1.1.5.12.9.2.53.1.24
-- 1.3.6.1.4.1.37950.1.1.5.12.9.2.53.1.24
-- 1.3.6.1.4.1.37950.1.1.5.12.9.2.53.1.24
-- 1.3.6.1.4.1.37950.1.1.5.12.9.2.53.1.24
		-- 1.3.6.1.4.1.37950.1.1.5.12.9.2.53.1.24
		v6wanConnSlaacS OBJECT-TYPE
			SYNTAX INTEGER
				{
				disable(0),
				enable(1)
				}
			MAX-ACCESS read-write
			STATUS current
			DESCRIPTION
				"Description."
			::= { onuWanConnV6Entry 24 }

		
--           1.3.6.1.4.1.37950.1.1.5.12.3.2.6.1.17
-- 1.3.6.1.4.1.37950.1.1.5.12.9.2.53.1.25
-- 1.3.6.1.4.1.37950.1.1.5.12.9.2.53.1.25
-- 1.3.6.1.4.1.37950.1.1.5.12.9.2.53.1.25
-- 1.3.6.1.4.1.37950.1.1.5.12.9.2.53.1.25
-- 1.3.6.1.4.1.37950.1.1.5.12.9.2.53.1.25
-- 1.3.6.1.4.1.37950.1.1.5.12.9.2.53.1.25
-- 1.3.6.1.4.1.37950.1.1.5.12.9.2.53.1.25
-- 1.3.6.1.4.1.37950.1.1.5.12.9.2.53.1.25
		-- 1.3.6.1.4.1.37950.1.1.5.12.9.2.53.1.25
		v6wanConnPppoeProxyS OBJECT-TYPE
			SYNTAX INTEGER
				{
				disable(0),
				enable(1)
				}
			MAX-ACCESS read-write
			STATUS current
			DESCRIPTION
				"Description."
			::= { onuWanConnV6Entry 25 }

		
--           1.3.6.1.4.1.37950.1.1.5.12.3.2.6.1.18
-- 1.3.6.1.4.1.37950.1.1.5.12.9.2.53.1.26
-- 1.3.6.1.4.1.37950.1.1.5.12.9.2.53.1.26
-- 1.3.6.1.4.1.37950.1.1.5.12.9.2.53.1.26
-- 1.3.6.1.4.1.37950.1.1.5.12.9.2.53.1.26
-- 1.3.6.1.4.1.37950.1.1.5.12.9.2.53.1.26
-- 1.3.6.1.4.1.37950.1.1.5.12.9.2.53.1.26
-- 1.3.6.1.4.1.37950.1.1.5.12.9.2.53.1.26
-- 1.3.6.1.4.1.37950.1.1.5.12.9.2.53.1.26
		-- 1.3.6.1.4.1.37950.1.1.5.12.9.2.53.1.26
		v6wanConnPppoeUsernameS OBJECT-TYPE
			SYNTAX OCTET STRING
			MAX-ACCESS read-write
			STATUS current
			DESCRIPTION
				"Description."
			::= { onuWanConnV6Entry 26 }

		
--           1.3.6.1.4.1.37950.1.1.5.12.3.2.6.1.19
-- 1.3.6.1.4.1.37950.1.1.5.12.9.2.53.1.27
-- 1.3.6.1.4.1.37950.1.1.5.12.9.2.53.1.27
-- 1.3.6.1.4.1.37950.1.1.5.12.9.2.53.1.27
-- 1.3.6.1.4.1.37950.1.1.5.12.9.2.53.1.27
-- 1.3.6.1.4.1.37950.1.1.5.12.9.2.53.1.27
-- 1.3.6.1.4.1.37950.1.1.5.12.9.2.53.1.27
-- 1.3.6.1.4.1.37950.1.1.5.12.9.2.53.1.27
-- 1.3.6.1.4.1.37950.1.1.5.12.9.2.53.1.27
		-- 1.3.6.1.4.1.37950.1.1.5.12.9.2.53.1.27
		v6wanConnPppoePasswordS OBJECT-TYPE
			SYNTAX OCTET STRING
			MAX-ACCESS read-write
			STATUS current
			DESCRIPTION
				"Description."
			::= { onuWanConnV6Entry 27 }

		
--           1.3.6.1.4.1.37950.1.1.5.12.3.2.6.1.20
-- 1.3.6.1.4.1.37950.1.1.5.12.9.2.53.1.28
-- 1.3.6.1.4.1.37950.1.1.5.12.9.2.53.1.28
-- 1.3.6.1.4.1.37950.1.1.5.12.9.2.53.1.28
-- 1.3.6.1.4.1.37950.1.1.5.12.9.2.53.1.28
-- 1.3.6.1.4.1.37950.1.1.5.12.9.2.53.1.28
-- 1.3.6.1.4.1.37950.1.1.5.12.9.2.53.1.28
-- 1.3.6.1.4.1.37950.1.1.5.12.9.2.53.1.28
-- 1.3.6.1.4.1.37950.1.1.5.12.9.2.53.1.28
		-- 1.3.6.1.4.1.37950.1.1.5.12.9.2.53.1.28
		v6wanConnPppoeSerNameS OBJECT-TYPE
			SYNTAX OCTET STRING
			MAX-ACCESS read-write
			STATUS current
			DESCRIPTION
				"Description."
			::= { onuWanConnV6Entry 28 }

		
--           1.3.6.1.4.1.37950.1.1.5.12.3.2.6.1.21
-- 1.3.6.1.4.1.37950.1.1.5.12.9.2.53.1.29
-- 1.3.6.1.4.1.37950.1.1.5.12.9.2.53.1.29
-- 1.3.6.1.4.1.37950.1.1.5.12.9.2.53.1.29
-- 1.3.6.1.4.1.37950.1.1.5.12.9.2.53.1.29
-- 1.3.6.1.4.1.37950.1.1.5.12.9.2.53.1.29
-- 1.3.6.1.4.1.37950.1.1.5.12.9.2.53.1.29
-- 1.3.6.1.4.1.37950.1.1.5.12.9.2.53.1.29
-- 1.3.6.1.4.1.37950.1.1.5.12.9.2.53.1.29
		-- 1.3.6.1.4.1.37950.1.1.5.12.9.2.53.1.29
		v6wanConnPppoeModeS OBJECT-TYPE
			SYNTAX INTEGER
				{
				autoConnect(0),
				flowConnect(1)
				}
			MAX-ACCESS read-write
			STATUS current
			DESCRIPTION
				"Description."
			::= { onuWanConnV6Entry 29 }

		
--           1.3.6.1.4.1.37950.1.1.5.12.3.2.6.1.21
-- 1.3.6.1.4.1.37950.1.1.5.12.9.2.53.1.30
-- 1.3.6.1.4.1.37950.1.1.5.12.9.2.53.1.30
-- 1.3.6.1.4.1.37950.1.1.5.12.9.2.53.1.30
-- 1.3.6.1.4.1.37950.1.1.5.12.9.2.53.1.30
-- 1.3.6.1.4.1.37950.1.1.5.12.9.2.53.1.30
-- 1.3.6.1.4.1.37950.1.1.5.12.9.2.53.1.30
-- 1.3.6.1.4.1.37950.1.1.5.12.9.2.53.1.30
-- 1.3.6.1.4.1.37950.1.1.5.12.9.2.53.1.30
		-- 1.3.6.1.4.1.37950.1.1.5.12.9.2.53.1.30
		v6wanConnDhcpv6ClientAddressS OBJECT-TYPE
			SYNTAX INTEGER
				{
				disable(0),
				enable(1)
				}
			MAX-ACCESS read-write
			STATUS current
			DESCRIPTION
				"Description."
			::= { onuWanConnV6Entry 30 }

		
--           1.3.6.1.4.1.37950.1.1.5.12.3.2.6.1.21
-- 1.3.6.1.4.1.37950.1.1.5.12.9.2.53.1.31
-- 1.3.6.1.4.1.37950.1.1.5.12.9.2.53.1.31
-- 1.3.6.1.4.1.37950.1.1.5.12.9.2.53.1.31
-- 1.3.6.1.4.1.37950.1.1.5.12.9.2.53.1.31
-- 1.3.6.1.4.1.37950.1.1.5.12.9.2.53.1.31
-- 1.3.6.1.4.1.37950.1.1.5.12.9.2.53.1.31
-- 1.3.6.1.4.1.37950.1.1.5.12.9.2.53.1.31
-- 1.3.6.1.4.1.37950.1.1.5.12.9.2.53.1.31
		-- 1.3.6.1.4.1.37950.1.1.5.12.9.2.53.1.31
		v6wanConnDhcpv6ClientPrefixS OBJECT-TYPE
			SYNTAX INTEGER
				{
				disable(0),
				enable(1)
				}
			MAX-ACCESS read-write
			STATUS current
			DESCRIPTION
				"Description."
			::= { onuWanConnV6Entry 31 }

		
--           1.3.6.1.4.1.37950.1.1.5.12.3.2.6.1.21
-- 1.3.6.1.4.1.37950.1.1.5.12.9.2.53.1.32
-- 1.3.6.1.4.1.37950.1.1.5.12.9.2.53.1.32
-- 1.3.6.1.4.1.37950.1.1.5.12.9.2.53.1.32
-- 1.3.6.1.4.1.37950.1.1.5.12.9.2.53.1.32
-- 1.3.6.1.4.1.37950.1.1.5.12.9.2.53.1.32
-- 1.3.6.1.4.1.37950.1.1.5.12.9.2.53.1.32
-- 1.3.6.1.4.1.37950.1.1.5.12.9.2.53.1.32
-- 1.3.6.1.4.1.37950.1.1.5.12.9.2.53.1.32
		-- 1.3.6.1.4.1.37950.1.1.5.12.9.2.53.1.32
		v6wanConnDsLiteEnableS OBJECT-TYPE
			SYNTAX INTEGER
				{
				disable(0),
				enable(1)
				}
			MAX-ACCESS read-write
			STATUS current
			DESCRIPTION
				"Description."
			::= { onuWanConnV6Entry 32 }

		
--           1.3.6.1.4.1.37950.1.1.5.12.3.2.6.1.21
-- 1.3.6.1.4.1.37950.1.1.5.12.9.2.53.1.33
-- 1.3.6.1.4.1.37950.1.1.5.12.9.2.53.1.33
-- 1.3.6.1.4.1.37950.1.1.5.12.9.2.53.1.33
-- 1.3.6.1.4.1.37950.1.1.5.12.9.2.53.1.33
-- 1.3.6.1.4.1.37950.1.1.5.12.9.2.53.1.33
-- 1.3.6.1.4.1.37950.1.1.5.12.9.2.53.1.33
-- 1.3.6.1.4.1.37950.1.1.5.12.9.2.53.1.33
-- 1.3.6.1.4.1.37950.1.1.5.12.9.2.53.1.33
		-- 1.3.6.1.4.1.37950.1.1.5.12.9.2.53.1.33
		v6wanConnDsLiteAftrModeS OBJECT-TYPE
			SYNTAX INTEGER
				{
				dhcpv6(0),
				manual(1)
				}
			MAX-ACCESS read-write
			STATUS current
			DESCRIPTION
				"Description."
			::= { onuWanConnV6Entry 33 }

		
--           1.3.6.1.4.1.37950.1.1.5.12.3.2.6.1.21
-- 1.3.6.1.4.1.37950.1.1.5.12.9.2.53.1.34
-- 1.3.6.1.4.1.37950.1.1.5.12.9.2.53.1.34
-- 1.3.6.1.4.1.37950.1.1.5.12.9.2.53.1.34
-- 1.3.6.1.4.1.37950.1.1.5.12.9.2.53.1.34
-- 1.3.6.1.4.1.37950.1.1.5.12.9.2.53.1.34
-- 1.3.6.1.4.1.37950.1.1.5.12.9.2.53.1.34
-- 1.3.6.1.4.1.37950.1.1.5.12.9.2.53.1.34
-- 1.3.6.1.4.1.37950.1.1.5.12.9.2.53.1.34
		-- 1.3.6.1.4.1.37950.1.1.5.12.9.2.53.1.34
		v6wanConnDsLiteAddressTypeS OBJECT-TYPE
			SYNTAX INTEGER
				{
				ipv6(0),
				dns(1)
				}
			MAX-ACCESS read-write
			STATUS current
			DESCRIPTION
				"Description."
			::= { onuWanConnV6Entry 34 }

		
--           1.3.6.1.4.1.37950.1.1.5.12.3.2.6.1.21
-- 1.3.6.1.4.1.37950.1.1.5.12.9.2.53.1.35
-- 1.3.6.1.4.1.37950.1.1.5.12.9.2.53.1.35
-- 1.3.6.1.4.1.37950.1.1.5.12.9.2.53.1.35
-- 1.3.6.1.4.1.37950.1.1.5.12.9.2.53.1.35
-- 1.3.6.1.4.1.37950.1.1.5.12.9.2.53.1.35
-- 1.3.6.1.4.1.37950.1.1.5.12.9.2.53.1.35
-- 1.3.6.1.4.1.37950.1.1.5.12.9.2.53.1.35
-- 1.3.6.1.4.1.37950.1.1.5.12.9.2.53.1.35
		-- 1.3.6.1.4.1.37950.1.1.5.12.9.2.53.1.35
		v6wanConnDsLiteAddressS OBJECT-TYPE
			SYNTAX OCTET STRING
			MAX-ACCESS read-write
			STATUS current
			DESCRIPTION
				"Description."
			::= { onuWanConnV6Entry 35 }

		
--           1.3.6.1.4.1.37950.1.1.5.12.3.2.6.1.22
-- 1.3.6.1.4.1.37950.1.1.5.12.9.2.53.1.36
-- 1.3.6.1.4.1.37950.1.1.5.12.9.2.53.1.36
-- 1.3.6.1.4.1.37950.1.1.5.12.9.2.53.1.36
-- 1.3.6.1.4.1.37950.1.1.5.12.9.2.53.1.36
-- 1.3.6.1.4.1.37950.1.1.5.12.9.2.53.1.36
-- 1.3.6.1.4.1.37950.1.1.5.12.9.2.53.1.36
-- 1.3.6.1.4.1.37950.1.1.5.12.9.2.53.1.36
-- 1.3.6.1.4.1.37950.1.1.5.12.9.2.53.1.36
		-- 1.3.6.1.4.1.37950.1.1.5.12.9.2.53.1.36
		v6wanConnQosEnableS OBJECT-TYPE
			SYNTAX INTEGER
				{
				disable(0),
				enable(1)
				}
			MAX-ACCESS read-write
			STATUS current
			DESCRIPTION
				"Description."
			::= { onuWanConnV6Entry 36 }

		
--           1.3.6.1.4.1.37950.1.1.5.12.3.2.6.1.23
-- 1.3.6.1.4.1.37950.1.1.5.12.9.2.53.1.37
-- 1.3.6.1.4.1.37950.1.1.5.12.9.2.53.1.37
-- 1.3.6.1.4.1.37950.1.1.5.12.9.2.53.1.37
-- 1.3.6.1.4.1.37950.1.1.5.12.9.2.53.1.37
-- 1.3.6.1.4.1.37950.1.1.5.12.9.2.53.1.37
-- 1.3.6.1.4.1.37950.1.1.5.12.9.2.53.1.37
-- 1.3.6.1.4.1.37950.1.1.5.12.9.2.53.1.37
-- 1.3.6.1.4.1.37950.1.1.5.12.9.2.53.1.37
		-- 1.3.6.1.4.1.37950.1.1.5.12.9.2.53.1.37
		v6wanConnVlanModeS OBJECT-TYPE
			SYNTAX INTEGER
				{
				disable(0),
				tag(1),
				transparent(2)
				}
			MAX-ACCESS read-write
			STATUS current
			DESCRIPTION
				"Description."
			::= { onuWanConnV6Entry 37 }

		
--           1.3.6.1.4.1.37950.1.1.5.12.3.2.6.1.24
-- 1.3.6.1.4.1.37950.1.1.5.12.9.2.53.1.38
-- 1.3.6.1.4.1.37950.1.1.5.12.9.2.53.1.38
-- 1.3.6.1.4.1.37950.1.1.5.12.9.2.53.1.38
-- 1.3.6.1.4.1.37950.1.1.5.12.9.2.53.1.38
-- 1.3.6.1.4.1.37950.1.1.5.12.9.2.53.1.38
-- 1.3.6.1.4.1.37950.1.1.5.12.9.2.53.1.38
-- 1.3.6.1.4.1.37950.1.1.5.12.9.2.53.1.38
-- 1.3.6.1.4.1.37950.1.1.5.12.9.2.53.1.38
		-- 1.3.6.1.4.1.37950.1.1.5.12.9.2.53.1.38
		v6wanConnTranslationEnableS OBJECT-TYPE
			SYNTAX INTEGER
				{
				disable(0),
				enable(1)
				}
			MAX-ACCESS read-write
			STATUS current
			DESCRIPTION
				"Description."
			::= { onuWanConnV6Entry 38 }

		
--           1.3.6.1.4.1.37950.1.1.5.12.3.2.6.1.25
-- 1.3.6.1.4.1.37950.1.1.5.12.9.2.53.1.39
-- 1.3.6.1.4.1.37950.1.1.5.12.9.2.53.1.39
-- 1.3.6.1.4.1.37950.1.1.5.12.9.2.53.1.39
-- 1.3.6.1.4.1.37950.1.1.5.12.9.2.53.1.39
-- 1.3.6.1.4.1.37950.1.1.5.12.9.2.53.1.39
-- 1.3.6.1.4.1.37950.1.1.5.12.9.2.53.1.39
-- 1.3.6.1.4.1.37950.1.1.5.12.9.2.53.1.39
-- 1.3.6.1.4.1.37950.1.1.5.12.9.2.53.1.39
		-- 1.3.6.1.4.1.37950.1.1.5.12.9.2.53.1.39
		v6wanConnTranslationVlanS OBJECT-TYPE
			SYNTAX INTEGER (1..4095)
			MAX-ACCESS read-write
			STATUS current
			DESCRIPTION
				"Description."
			::= { onuWanConnV6Entry 39 }

		
--           1.3.6.1.4.1.37950.1.1.5.12.3.2.6.1.26
-- 1.3.6.1.4.1.37950.1.1.5.12.9.2.53.1.40
-- 1.3.6.1.4.1.37950.1.1.5.12.9.2.53.1.40
-- 1.3.6.1.4.1.37950.1.1.5.12.9.2.53.1.40
-- 1.3.6.1.4.1.37950.1.1.5.12.9.2.53.1.40
-- 1.3.6.1.4.1.37950.1.1.5.12.9.2.53.1.40
-- 1.3.6.1.4.1.37950.1.1.5.12.9.2.53.1.40
-- 1.3.6.1.4.1.37950.1.1.5.12.9.2.53.1.40
-- 1.3.6.1.4.1.37950.1.1.5.12.9.2.53.1.40
		-- 1.3.6.1.4.1.37950.1.1.5.12.9.2.53.1.40
		v6wanConnTranslationCosS OBJECT-TYPE
			SYNTAX INTEGER (0..7)
			MAX-ACCESS read-write
			STATUS current
			DESCRIPTION
				"Description."
			::= { onuWanConnV6Entry 40 }

		
--           1.3.6.1.4.1.37950.1.1.5.12.3.2.6.1.27
-- 1.3.6.1.4.1.37950.1.1.5.12.9.2.53.1.41
-- 1.3.6.1.4.1.37950.1.1.5.12.9.2.53.1.41
-- 1.3.6.1.4.1.37950.1.1.5.12.9.2.53.1.41
-- 1.3.6.1.4.1.37950.1.1.5.12.9.2.53.1.41
-- 1.3.6.1.4.1.37950.1.1.5.12.9.2.53.1.41
-- 1.3.6.1.4.1.37950.1.1.5.12.9.2.53.1.41
-- 1.3.6.1.4.1.37950.1.1.5.12.9.2.53.1.41
-- 1.3.6.1.4.1.37950.1.1.5.12.9.2.53.1.41
		-- 1.3.6.1.4.1.37950.1.1.5.12.9.2.53.1.41
		v6wanConnQinqEnableS OBJECT-TYPE
			SYNTAX INTEGER
				{
				disable(0),
				enable(1)
				}
			MAX-ACCESS read-write
			STATUS current
			DESCRIPTION
				"Description."
			::= { onuWanConnV6Entry 41 }

		
--           1.3.6.1.4.1.37950.1.1.5.12.3.2.6.1.28
-- 1.3.6.1.4.1.37950.1.1.5.12.9.2.53.1.42
-- 1.3.6.1.4.1.37950.1.1.5.12.9.2.53.1.42
-- 1.3.6.1.4.1.37950.1.1.5.12.9.2.53.1.42
-- 1.3.6.1.4.1.37950.1.1.5.12.9.2.53.1.42
-- 1.3.6.1.4.1.37950.1.1.5.12.9.2.53.1.42
-- 1.3.6.1.4.1.37950.1.1.5.12.9.2.53.1.42
-- 1.3.6.1.4.1.37950.1.1.5.12.9.2.53.1.42
-- 1.3.6.1.4.1.37950.1.1.5.12.9.2.53.1.42
		-- 1.3.6.1.4.1.37950.1.1.5.12.9.2.53.1.42
		v6wanConnQinqTpidS OBJECT-TYPE
			SYNTAX INTEGER (1..65534)
			MAX-ACCESS read-write
			STATUS current
			DESCRIPTION
				"Description."
			::= { onuWanConnV6Entry 42 }

		
--           1.3.6.1.4.1.37950.1.1.5.12.3.2.6.1.29
-- 1.3.6.1.4.1.37950.1.1.5.12.9.2.53.1.43
-- 1.3.6.1.4.1.37950.1.1.5.12.9.2.53.1.43
-- 1.3.6.1.4.1.37950.1.1.5.12.9.2.53.1.43
-- 1.3.6.1.4.1.37950.1.1.5.12.9.2.53.1.43
-- 1.3.6.1.4.1.37950.1.1.5.12.9.2.53.1.43
-- 1.3.6.1.4.1.37950.1.1.5.12.9.2.53.1.43
-- 1.3.6.1.4.1.37950.1.1.5.12.9.2.53.1.43
-- 1.3.6.1.4.1.37950.1.1.5.12.9.2.53.1.43
		-- 1.3.6.1.4.1.37950.1.1.5.12.9.2.53.1.43
		v6wanConnSvlanIdS OBJECT-TYPE
			SYNTAX INTEGER (1..4095)
			MAX-ACCESS read-write
			STATUS current
			DESCRIPTION
				"Description."
			::= { onuWanConnV6Entry 43 }

		
--           1.3.6.1.4.1.37950.1.1.5.12.3.2.6.1.30
-- 1.3.6.1.4.1.37950.1.1.5.12.9.2.53.1.44
-- 1.3.6.1.4.1.37950.1.1.5.12.9.2.53.1.44
-- 1.3.6.1.4.1.37950.1.1.5.12.9.2.53.1.44
-- 1.3.6.1.4.1.37950.1.1.5.12.9.2.53.1.44
-- 1.3.6.1.4.1.37950.1.1.5.12.9.2.53.1.44
-- 1.3.6.1.4.1.37950.1.1.5.12.9.2.53.1.44
-- 1.3.6.1.4.1.37950.1.1.5.12.9.2.53.1.44
-- 1.3.6.1.4.1.37950.1.1.5.12.9.2.53.1.44
		-- 1.3.6.1.4.1.37950.1.1.5.12.9.2.53.1.44
		v6wanConnSvlanCosS OBJECT-TYPE
			SYNTAX INTEGER (0..7)
			MAX-ACCESS read-write
			STATUS current
			DESCRIPTION
				"Description."
			::= { onuWanConnV6Entry 44 }

		
--           1.3.6.1.4.1.37950.1.1.5.12.3.2.6.1.30
-- 1.3.6.1.4.1.37950.1.1.5.12.9.2.53.1.45
-- 1.3.6.1.4.1.37950.1.1.5.12.9.2.53.1.45
-- 1.3.6.1.4.1.37950.1.1.5.12.9.2.53.1.45
-- 1.3.6.1.4.1.37950.1.1.5.12.9.2.53.1.45
-- 1.3.6.1.4.1.37950.1.1.5.12.9.2.53.1.45
-- 1.3.6.1.4.1.37950.1.1.5.12.9.2.53.1.45
-- 1.3.6.1.4.1.37950.1.1.5.12.9.2.53.1.45
-- 1.3.6.1.4.1.37950.1.1.5.12.9.2.53.1.45
		-- 1.3.6.1.4.1.37950.1.1.5.12.9.2.53.1.45
		v6wanConnRouteMtuS OBJECT-TYPE
			SYNTAX Integer32 (576..1500)
			MAX-ACCESS read-write
			STATUS current
			DESCRIPTION
				"Description."
			::= { onuWanConnV6Entry 45 }

		
--         1.3.6.1.4.1.37950.1.1.5.12.9.2.54
-- 1.3.6.1.4.1.37950.1.1.5.12.9.2.54
-- 1.3.6.1.4.1.37950.1.1.5.12.9.2.54
-- 1.3.6.1.4.1.37950.1.1.5.12.9.2.54
-- 1.3.6.1.4.1.37950.1.1.5.12.9.2.54
-- 1.3.6.1.4.1.37950.1.1.5.12.9.2.54
-- 1.3.6.1.4.1.37950.1.1.5.12.9.2.54
-- 1.3.6.1.4.1.37950.1.1.5.12.9.2.54
		-- 1.3.6.1.4.1.37950.1.1.5.12.9.2.54
		onuTr069ManageTable OBJECT-TYPE
			SYNTAX SEQUENCE OF OnuTr069ManageEntry
			MAX-ACCESS not-accessible
			STATUS current
			DESCRIPTION
				"Description."
			::= { srvProfileShow 54 }

		
--         1.3.6.1.4.1.37950.1.1.5.12.9.2.54.1
-- 1.3.6.1.4.1.37950.1.1.5.12.9.2.54.1
-- 1.3.6.1.4.1.37950.1.1.5.12.9.2.54.1
-- 1.3.6.1.4.1.37950.1.1.5.12.9.2.54.1
-- 1.3.6.1.4.1.37950.1.1.5.12.9.2.54.1
-- 1.3.6.1.4.1.37950.1.1.5.12.9.2.54.1
-- 1.3.6.1.4.1.37950.1.1.5.12.9.2.54.1
-- 1.3.6.1.4.1.37950.1.1.5.12.9.2.54.1
		-- 1.3.6.1.4.1.37950.1.1.5.12.9.2.54.1
		onuTr069ManageEntry OBJECT-TYPE
			SYNTAX OnuTr069ManageEntry
			MAX-ACCESS not-accessible
			STATUS current
			DESCRIPTION
				"Description."
			INDEX { onuMngSrvId }
			::= { onuTr069ManageTable 1 }

		
		OnuTr069ManageEntry ::=
			SEQUENCE { 
				onuMngSrvId
					Integer32,
				onuMngAcsAddress
					OCTET STRING,
				onuMngAcsUsername
					OCTET STRING,
				onuMngAcsPassword
					OCTET STRING,
				onuMngCertificateEn
					INTEGER,
				onuMngInformEn
					INTEGER,
				onuMngInformIntervalTime
					Unsigned32,
				onuMngRevConnUsername
					OCTET STRING,
				onuMngRevConnPassword
					OCTET STRING,
				onuMngStatus
					INTEGER
			 }

--         1.3.6.1.4.1.37950.1.1.5.12.9.2.54.1.1
-- 1.3.6.1.4.1.37950.1.1.5.12.9.2.54.1.1
-- 1.3.6.1.4.1.37950.1.1.5.12.9.2.54.1.1
-- 1.3.6.1.4.1.37950.1.1.5.12.9.2.54.1.1
-- 1.3.6.1.4.1.37950.1.1.5.12.9.2.54.1.1
-- 1.3.6.1.4.1.37950.1.1.5.12.9.2.54.1.1
-- 1.3.6.1.4.1.37950.1.1.5.12.9.2.54.1.1
-- 1.3.6.1.4.1.37950.1.1.5.12.9.2.54.1.1
		-- 1.3.6.1.4.1.37950.1.1.5.12.9.2.54.1.1
		onuMngSrvId OBJECT-TYPE
			SYNTAX Integer32
			MAX-ACCESS read-only
			STATUS current
			DESCRIPTION
				"Description."
			::= { onuTr069ManageEntry 1 }

		
--         1.3.6.1.4.1.37950.1.1.5.12.9.2.54.1.2
-- 1.3.6.1.4.1.37950.1.1.5.12.9.2.54.1.2
-- 1.3.6.1.4.1.37950.1.1.5.12.9.2.54.1.2
-- 1.3.6.1.4.1.37950.1.1.5.12.9.2.54.1.2
-- 1.3.6.1.4.1.37950.1.1.5.12.9.2.54.1.2
-- 1.3.6.1.4.1.37950.1.1.5.12.9.2.54.1.2
-- 1.3.6.1.4.1.37950.1.1.5.12.9.2.54.1.2
-- 1.3.6.1.4.1.37950.1.1.5.12.9.2.54.1.2
		-- 1.3.6.1.4.1.37950.1.1.5.12.9.2.54.1.2
		onuMngAcsAddress OBJECT-TYPE
			SYNTAX OCTET STRING
			MAX-ACCESS read-only
			STATUS current
			DESCRIPTION
				"Description."
			::= { onuTr069ManageEntry 2 }

		
--         1.3.6.1.4.1.37950.1.1.5.12.9.2.54.1.3
-- 1.3.6.1.4.1.37950.1.1.5.12.9.2.54.1.3
-- 1.3.6.1.4.1.37950.1.1.5.12.9.2.54.1.3
-- 1.3.6.1.4.1.37950.1.1.5.12.9.2.54.1.3
-- 1.3.6.1.4.1.37950.1.1.5.12.9.2.54.1.3
-- 1.3.6.1.4.1.37950.1.1.5.12.9.2.54.1.3
-- 1.3.6.1.4.1.37950.1.1.5.12.9.2.54.1.3
-- 1.3.6.1.4.1.37950.1.1.5.12.9.2.54.1.3
		-- 1.3.6.1.4.1.37950.1.1.5.12.9.2.54.1.3
		onuMngAcsUsername OBJECT-TYPE
			SYNTAX OCTET STRING
			MAX-ACCESS read-only
			STATUS current
			DESCRIPTION
				"Description."
			::= { onuTr069ManageEntry 3 }

		
--         1.3.6.1.4.1.37950.1.1.5.12.9.2.54.1.4
-- 1.3.6.1.4.1.37950.1.1.5.12.9.2.54.1.4
-- 1.3.6.1.4.1.37950.1.1.5.12.9.2.54.1.4
-- 1.3.6.1.4.1.37950.1.1.5.12.9.2.54.1.4
-- 1.3.6.1.4.1.37950.1.1.5.12.9.2.54.1.4
-- 1.3.6.1.4.1.37950.1.1.5.12.9.2.54.1.4
-- 1.3.6.1.4.1.37950.1.1.5.12.9.2.54.1.4
-- 1.3.6.1.4.1.37950.1.1.5.12.9.2.54.1.4
		-- 1.3.6.1.4.1.37950.1.1.5.12.9.2.54.1.4
		onuMngAcsPassword OBJECT-TYPE
			SYNTAX OCTET STRING
			MAX-ACCESS read-only
			STATUS current
			DESCRIPTION
				"Description."
			::= { onuTr069ManageEntry 4 }

		
--         1.3.6.1.4.1.37950.1.1.5.12.9.2.54.1.5
-- 1.3.6.1.4.1.37950.1.1.5.12.9.2.54.1.5
-- 1.3.6.1.4.1.37950.1.1.5.12.9.2.54.1.5
-- 1.3.6.1.4.1.37950.1.1.5.12.9.2.54.1.5
-- 1.3.6.1.4.1.37950.1.1.5.12.9.2.54.1.5
-- 1.3.6.1.4.1.37950.1.1.5.12.9.2.54.1.5
-- 1.3.6.1.4.1.37950.1.1.5.12.9.2.54.1.5
-- 1.3.6.1.4.1.37950.1.1.5.12.9.2.54.1.5
		-- 1.3.6.1.4.1.37950.1.1.5.12.9.2.54.1.5
		onuMngCertificateEn OBJECT-TYPE
			SYNTAX INTEGER
				{
				disable(0),
				enable(1)
				}
			MAX-ACCESS read-only
			STATUS current
			DESCRIPTION
				"Description."
			::= { onuTr069ManageEntry 5 }

		
--         1.3.6.1.4.1.37950.1.1.5.12.9.2.54.1.6
-- 1.3.6.1.4.1.37950.1.1.5.12.9.2.54.1.6
-- 1.3.6.1.4.1.37950.1.1.5.12.9.2.54.1.6
-- 1.3.6.1.4.1.37950.1.1.5.12.9.2.54.1.6
-- 1.3.6.1.4.1.37950.1.1.5.12.9.2.54.1.6
-- 1.3.6.1.4.1.37950.1.1.5.12.9.2.54.1.6
-- 1.3.6.1.4.1.37950.1.1.5.12.9.2.54.1.6
-- 1.3.6.1.4.1.37950.1.1.5.12.9.2.54.1.6
		-- 1.3.6.1.4.1.37950.1.1.5.12.9.2.54.1.6
		onuMngInformEn OBJECT-TYPE
			SYNTAX INTEGER
				{
				disable(0),
				enable(1)
				}
			MAX-ACCESS read-only
			STATUS current
			DESCRIPTION
				"Description."
			::= { onuTr069ManageEntry 6 }

		
--         1.3.6.1.4.1.37950.1.1.5.12.9.2.54.1.7
-- 1.3.6.1.4.1.37950.1.1.5.12.9.2.54.1.7
-- 1.3.6.1.4.1.37950.1.1.5.12.9.2.54.1.7
-- 1.3.6.1.4.1.37950.1.1.5.12.9.2.54.1.7
-- 1.3.6.1.4.1.37950.1.1.5.12.9.2.54.1.7
-- 1.3.6.1.4.1.37950.1.1.5.12.9.2.54.1.7
-- 1.3.6.1.4.1.37950.1.1.5.12.9.2.54.1.7
-- 1.3.6.1.4.1.37950.1.1.5.12.9.2.54.1.7
		-- 1.3.6.1.4.1.37950.1.1.5.12.9.2.54.1.7
		onuMngInformIntervalTime OBJECT-TYPE
			SYNTAX Unsigned32
			MAX-ACCESS read-only
			STATUS current
			DESCRIPTION
				"Description."
			::= { onuTr069ManageEntry 7 }

		
--         1.3.6.1.4.1.37950.1.1.5.12.9.2.54.1.8
-- 1.3.6.1.4.1.37950.1.1.5.12.9.2.54.1.8
-- 1.3.6.1.4.1.37950.1.1.5.12.9.2.54.1.8
-- 1.3.6.1.4.1.37950.1.1.5.12.9.2.54.1.8
-- 1.3.6.1.4.1.37950.1.1.5.12.9.2.54.1.8
-- 1.3.6.1.4.1.37950.1.1.5.12.9.2.54.1.8
-- 1.3.6.1.4.1.37950.1.1.5.12.9.2.54.1.8
-- 1.3.6.1.4.1.37950.1.1.5.12.9.2.54.1.8
		-- 1.3.6.1.4.1.37950.1.1.5.12.9.2.54.1.8
		onuMngRevConnUsername OBJECT-TYPE
			SYNTAX OCTET STRING
			MAX-ACCESS read-only
			STATUS current
			DESCRIPTION
				"Description."
			::= { onuTr069ManageEntry 8 }

		
--         1.3.6.1.4.1.37950.1.1.5.12.9.2.54.1.9
-- 1.3.6.1.4.1.37950.1.1.5.12.9.2.54.1.9
-- 1.3.6.1.4.1.37950.1.1.5.12.9.2.54.1.9
-- 1.3.6.1.4.1.37950.1.1.5.12.9.2.54.1.9
-- 1.3.6.1.4.1.37950.1.1.5.12.9.2.54.1.9
-- 1.3.6.1.4.1.37950.1.1.5.12.9.2.54.1.9
-- 1.3.6.1.4.1.37950.1.1.5.12.9.2.54.1.9
-- 1.3.6.1.4.1.37950.1.1.5.12.9.2.54.1.9
		-- 1.3.6.1.4.1.37950.1.1.5.12.9.2.54.1.9
		onuMngRevConnPassword OBJECT-TYPE
			SYNTAX OCTET STRING
			MAX-ACCESS read-only
			STATUS current
			DESCRIPTION
				"Description."
			::= { onuTr069ManageEntry 9 }

		
--         1.3.6.1.4.1.37950.1.1.5.12.9.2.54.1.10
-- 1.3.6.1.4.1.37950.1.1.5.12.9.2.54.1.10
-- 1.3.6.1.4.1.37950.1.1.5.12.9.2.54.1.10
-- 1.3.6.1.4.1.37950.1.1.5.12.9.2.54.1.10
-- 1.3.6.1.4.1.37950.1.1.5.12.9.2.54.1.10
-- 1.3.6.1.4.1.37950.1.1.5.12.9.2.54.1.10
-- 1.3.6.1.4.1.37950.1.1.5.12.9.2.54.1.10
-- 1.3.6.1.4.1.37950.1.1.5.12.9.2.54.1.10
		-- 1.3.6.1.4.1.37950.1.1.5.12.9.2.54.1.10
		onuMngStatus OBJECT-TYPE
			SYNTAX INTEGER
				{
				disable(0),
				enable(1)
				}
			MAX-ACCESS read-only
			STATUS current
			DESCRIPTION
				"Description."
			::= { onuTr069ManageEntry 10 }

		
--         1.3.6.1.4.1.37950.1.1.5.12.9.2.55
-- 1.3.6.1.4.1.37950.1.1.5.12.9.2.55
-- 1.3.6.1.4.1.37950.1.1.5.12.9.2.55
-- 1.3.6.1.4.1.37950.1.1.5.12.9.2.55
-- 1.3.6.1.4.1.37950.1.1.5.12.9.2.55
-- 1.3.6.1.4.1.37950.1.1.5.12.9.2.55
-- 1.3.6.1.4.1.37950.1.1.5.12.9.2.55
-- 1.3.6.1.4.1.37950.1.1.5.12.9.2.55
		-- 1.3.6.1.4.1.37950.1.1.5.12.9.2.55
		onuTr069StunTable OBJECT-TYPE
			SYNTAX SEQUENCE OF OnuTr069StunEntry
			MAX-ACCESS not-accessible
			STATUS current
			DESCRIPTION
				"Description."
			::= { srvProfileShow 55 }

		
--         1.3.6.1.4.1.37950.1.1.5.12.9.2.55.1
-- 1.3.6.1.4.1.37950.1.1.5.12.9.2.55.1
-- 1.3.6.1.4.1.37950.1.1.5.12.9.2.55.1
-- 1.3.6.1.4.1.37950.1.1.5.12.9.2.55.1
-- 1.3.6.1.4.1.37950.1.1.5.12.9.2.55.1
-- 1.3.6.1.4.1.37950.1.1.5.12.9.2.55.1
-- 1.3.6.1.4.1.37950.1.1.5.12.9.2.55.1
-- 1.3.6.1.4.1.37950.1.1.5.12.9.2.55.1
		-- 1.3.6.1.4.1.37950.1.1.5.12.9.2.55.1
		onuTr069StunEntry OBJECT-TYPE
			SYNTAX OnuTr069StunEntry
			MAX-ACCESS not-accessible
			STATUS current
			DESCRIPTION
				"Description."
			INDEX { onuStunSrvId }
			::= { onuTr069StunTable 1 }

		
		OnuTr069StunEntry ::=
			SEQUENCE { 
				onuStunSrvId
					Integer32,
				onuStunServerAddress
					OCTET STRING,
				onuStunServerPort
					Integer32,
				onuStunServerUsername
					OCTET STRING,
				onuStunServerPassword
					OCTET STRING,
				onuStunStatus
					INTEGER
			 }

--         1.3.6.1.4.1.37950.1.1.5.12.9.2.55.1.1
-- 1.3.6.1.4.1.37950.1.1.5.12.9.2.55.1.1
-- 1.3.6.1.4.1.37950.1.1.5.12.9.2.55.1.1
-- 1.3.6.1.4.1.37950.1.1.5.12.9.2.55.1.1
-- 1.3.6.1.4.1.37950.1.1.5.12.9.2.55.1.1
-- 1.3.6.1.4.1.37950.1.1.5.12.9.2.55.1.1
-- 1.3.6.1.4.1.37950.1.1.5.12.9.2.55.1.1
-- 1.3.6.1.4.1.37950.1.1.5.12.9.2.55.1.1
		-- 1.3.6.1.4.1.37950.1.1.5.12.9.2.55.1.1
		onuStunSrvId OBJECT-TYPE
			SYNTAX Integer32
			MAX-ACCESS read-only
			STATUS current
			DESCRIPTION
				"Description."
			::= { onuTr069StunEntry 1 }

		
--         1.3.6.1.4.1.37950.1.1.5.12.9.2.55.1.2
-- 1.3.6.1.4.1.37950.1.1.5.12.9.2.55.1.2
-- 1.3.6.1.4.1.37950.1.1.5.12.9.2.55.1.2
-- 1.3.6.1.4.1.37950.1.1.5.12.9.2.55.1.2
-- 1.3.6.1.4.1.37950.1.1.5.12.9.2.55.1.2
-- 1.3.6.1.4.1.37950.1.1.5.12.9.2.55.1.2
-- 1.3.6.1.4.1.37950.1.1.5.12.9.2.55.1.2
-- 1.3.6.1.4.1.37950.1.1.5.12.9.2.55.1.2
		-- 1.3.6.1.4.1.37950.1.1.5.12.9.2.55.1.2
		onuStunServerAddress OBJECT-TYPE
			SYNTAX OCTET STRING
			MAX-ACCESS read-only
			STATUS current
			DESCRIPTION
				"Description."
			::= { onuTr069StunEntry 2 }

		
--         1.3.6.1.4.1.37950.1.1.5.12.9.2.55.1.3
-- 1.3.6.1.4.1.37950.1.1.5.12.9.2.55.1.3
-- 1.3.6.1.4.1.37950.1.1.5.12.9.2.55.1.3
-- 1.3.6.1.4.1.37950.1.1.5.12.9.2.55.1.3
-- 1.3.6.1.4.1.37950.1.1.5.12.9.2.55.1.3
-- 1.3.6.1.4.1.37950.1.1.5.12.9.2.55.1.3
-- 1.3.6.1.4.1.37950.1.1.5.12.9.2.55.1.3
-- 1.3.6.1.4.1.37950.1.1.5.12.9.2.55.1.3
		-- 1.3.6.1.4.1.37950.1.1.5.12.9.2.55.1.3
		onuStunServerPort OBJECT-TYPE
			SYNTAX Integer32
			MAX-ACCESS read-only
			STATUS current
			DESCRIPTION
				"Description."
			::= { onuTr069StunEntry 3 }

		
--         1.3.6.1.4.1.37950.1.1.5.12.9.2.55.1.4
-- 1.3.6.1.4.1.37950.1.1.5.12.9.2.55.1.4
-- 1.3.6.1.4.1.37950.1.1.5.12.9.2.55.1.4
-- 1.3.6.1.4.1.37950.1.1.5.12.9.2.55.1.4
-- 1.3.6.1.4.1.37950.1.1.5.12.9.2.55.1.4
-- 1.3.6.1.4.1.37950.1.1.5.12.9.2.55.1.4
-- 1.3.6.1.4.1.37950.1.1.5.12.9.2.55.1.4
-- 1.3.6.1.4.1.37950.1.1.5.12.9.2.55.1.4
		-- 1.3.6.1.4.1.37950.1.1.5.12.9.2.55.1.4
		onuStunServerUsername OBJECT-TYPE
			SYNTAX OCTET STRING
			MAX-ACCESS read-only
			STATUS current
			DESCRIPTION
				"Description."
			::= { onuTr069StunEntry 4 }

		
--         1.3.6.1.4.1.37950.1.1.5.12.9.2.55.1.5
-- 1.3.6.1.4.1.37950.1.1.5.12.9.2.55.1.5
-- 1.3.6.1.4.1.37950.1.1.5.12.9.2.55.1.5
-- 1.3.6.1.4.1.37950.1.1.5.12.9.2.55.1.5
-- 1.3.6.1.4.1.37950.1.1.5.12.9.2.55.1.5
-- 1.3.6.1.4.1.37950.1.1.5.12.9.2.55.1.5
-- 1.3.6.1.4.1.37950.1.1.5.12.9.2.55.1.5
-- 1.3.6.1.4.1.37950.1.1.5.12.9.2.55.1.5
		-- 1.3.6.1.4.1.37950.1.1.5.12.9.2.55.1.5
		onuStunServerPassword OBJECT-TYPE
			SYNTAX OCTET STRING
			MAX-ACCESS read-only
			STATUS current
			DESCRIPTION
				"Description."
			::= { onuTr069StunEntry 5 }

		
--         1.3.6.1.4.1.37950.1.1.5.12.9.2.55.1.6
-- 1.3.6.1.4.1.37950.1.1.5.12.9.2.55.1.6
-- 1.3.6.1.4.1.37950.1.1.5.12.9.2.55.1.6
-- 1.3.6.1.4.1.37950.1.1.5.12.9.2.55.1.6
-- 1.3.6.1.4.1.37950.1.1.5.12.9.2.55.1.6
-- 1.3.6.1.4.1.37950.1.1.5.12.9.2.55.1.6
-- 1.3.6.1.4.1.37950.1.1.5.12.9.2.55.1.6
-- 1.3.6.1.4.1.37950.1.1.5.12.9.2.55.1.6
		-- 1.3.6.1.4.1.37950.1.1.5.12.9.2.55.1.6
		onuStunStatus OBJECT-TYPE
			SYNTAX INTEGER
				{
				disable(0),
				enable(1)
				}
			MAX-ACCESS read-only
			STATUS current
			DESCRIPTION
				"Description."
			::= { onuTr069StunEntry 6 }

		
--          1.3.6.1.4.1.37950.1.1.5.12.9.2.42
-- 1.3.6.1.4.1.37950.1.1.5.12.9.2.42
-- 1.3.6.1.4.1.37950.1.1.5.12.9.2.42
-- 1.3.6.1.4.1.37950.1.1.5.12.9.2.56
-- 1.3.6.1.4.1.37950.1.1.5.12.9.2.56
-- 1.3.6.1.4.1.37950.1.1.5.12.9.2.56
-- 1.3.6.1.4.1.37950.1.1.5.12.9.2.56
-- 1.3.6.1.4.1.37950.1.1.5.12.9.2.56
-- 1.3.6.1.4.1.37950.1.1.5.12.9.2.56
		-- 1.3.6.1.4.1.37950.1.1.5.12.9.2.56
		onuNatTypeTable OBJECT-TYPE
			SYNTAX SEQUENCE OF OnuNatTypeEntry
			MAX-ACCESS not-accessible
			STATUS current
			DESCRIPTION
				"Description."
			::= { srvProfileShow 56 }

		
--          1.3.6.1.4.1.37950.1.1.5.12.9.2.42.1
-- 1.3.6.1.4.1.37950.1.1.5.12.9.2.42.1
-- 1.3.6.1.4.1.37950.1.1.5.12.9.2.42.1
-- 1.3.6.1.4.1.37950.1.1.5.12.9.2.56.1
-- 1.3.6.1.4.1.37950.1.1.5.12.9.2.56.1
-- 1.3.6.1.4.1.37950.1.1.5.12.9.2.56.1
-- 1.3.6.1.4.1.37950.1.1.5.12.9.2.56.1
-- 1.3.6.1.4.1.37950.1.1.5.12.9.2.56.1
-- 1.3.6.1.4.1.37950.1.1.5.12.9.2.56.1
		-- 1.3.6.1.4.1.37950.1.1.5.12.9.2.56.1
		onuNatTypeEntry OBJECT-TYPE
			SYNTAX OnuNatTypeEntry
			MAX-ACCESS not-accessible
			STATUS current
			DESCRIPTION
				"Description."
			INDEX { natTypeSrvId }
			::= { onuNatTypeTable 1 }

		
		OnuNatTypeEntry ::=
			SEQUENCE { 
				natTypeSrvId
					INTEGER,
				natTypeS
					INTEGER
			 }

--          1.3.6.1.4.1.37950.1.1.5.12.9.2.42.1.1
-- 1.3.6.1.4.1.37950.1.1.5.12.9.2.42.1.1
-- 1.3.6.1.4.1.37950.1.1.5.12.9.2.42.1.1
-- 1.3.6.1.4.1.37950.1.1.5.12.9.2.56.1.1
-- 1.3.6.1.4.1.37950.1.1.5.12.9.2.56.1.1
-- 1.3.6.1.4.1.37950.1.1.5.12.9.2.56.1.1
-- 1.3.6.1.4.1.37950.1.1.5.12.9.2.56.1.1
-- 1.3.6.1.4.1.37950.1.1.5.12.9.2.56.1.1
-- 1.3.6.1.4.1.37950.1.1.5.12.9.2.56.1.1
		-- 1.3.6.1.4.1.37950.1.1.5.12.9.2.56.1.1
		natTypeSrvId OBJECT-TYPE
			SYNTAX INTEGER (1..65535)
			MAX-ACCESS read-write
			STATUS current
			DESCRIPTION
				"Description."
			::= { onuNatTypeEntry 1 }

		
--          1.3.6.1.4.1.37950.1.1.5.12.9.2.42.1.1
-- 1.3.6.1.4.1.37950.1.1.5.12.9.2.42.1.1
-- 1.3.6.1.4.1.37950.1.1.5.12.9.2.42.1.1
-- 1.3.6.1.4.1.37950.1.1.5.12.9.2.56.1.2
-- 1.3.6.1.4.1.37950.1.1.5.12.9.2.56.1.2
-- 1.3.6.1.4.1.37950.1.1.5.12.9.2.56.1.2
-- 1.3.6.1.4.1.37950.1.1.5.12.9.2.56.1.2
-- 1.3.6.1.4.1.37950.1.1.5.12.9.2.56.1.2
-- 1.3.6.1.4.1.37950.1.1.5.12.9.2.56.1.2
		-- 1.3.6.1.4.1.37950.1.1.5.12.9.2.56.1.2
		natTypeS OBJECT-TYPE
			SYNTAX INTEGER
				{
				nat1(1),
				nat2(2),
				nat3(3),
				nat4-napt(4)
				}
			MAX-ACCESS read-write
			STATUS current
			DESCRIPTION
				"Description."
			::= { onuNatTypeEntry 2 }

		
--          1.3.6.1.4.1.37950.1.1.5.12.9.2.42
-- 1.3.6.1.4.1.37950.1.1.5.12.9.2.42
-- 1.3.6.1.4.1.37950.1.1.5.12.9.2.42
-- 1.3.6.1.4.1.37950.1.1.5.12.9.2.57
-- 1.3.6.1.4.1.37950.1.1.5.12.9.2.57
-- 1.3.6.1.4.1.37950.1.1.5.12.9.2.57
-- 1.3.6.1.4.1.37950.1.1.5.12.9.2.57
-- 1.3.6.1.4.1.37950.1.1.5.12.9.2.57
-- 1.3.6.1.4.1.37950.1.1.5.12.9.2.57
		-- 1.3.6.1.4.1.37950.1.1.5.12.9.2.57
		onuUpnpTable OBJECT-TYPE
			SYNTAX SEQUENCE OF OnuUpnpEntry
			MAX-ACCESS not-accessible
			STATUS current
			DESCRIPTION
				"Description."
			::= { srvProfileShow 57 }

		
--          1.3.6.1.4.1.37950.1.1.5.12.9.2.42.1
-- 1.3.6.1.4.1.37950.1.1.5.12.9.2.42.1
-- 1.3.6.1.4.1.37950.1.1.5.12.9.2.42.1
-- 1.3.6.1.4.1.37950.1.1.5.12.9.2.57.1
-- 1.3.6.1.4.1.37950.1.1.5.12.9.2.57.1
-- 1.3.6.1.4.1.37950.1.1.5.12.9.2.57.1
-- 1.3.6.1.4.1.37950.1.1.5.12.9.2.57.1
-- 1.3.6.1.4.1.37950.1.1.5.12.9.2.57.1
-- 1.3.6.1.4.1.37950.1.1.5.12.9.2.57.1
		-- 1.3.6.1.4.1.37950.1.1.5.12.9.2.57.1
		onuUpnpEntry OBJECT-TYPE
			SYNTAX OnuUpnpEntry
			MAX-ACCESS not-accessible
			STATUS current
			DESCRIPTION
				"Description."
			INDEX { upnpSrvId }
			::= { onuUpnpTable 1 }

		
		OnuUpnpEntry ::=
			SEQUENCE { 
				upnpSrvId
					INTEGER,
				upnpStatusS
					INTEGER,
				upnpWanIndexS
					Integer32
			 }

--          1.3.6.1.4.1.37950.1.1.5.12.9.2.42.1.1
-- 1.3.6.1.4.1.37950.1.1.5.12.9.2.42.1.1
-- 1.3.6.1.4.1.37950.1.1.5.12.9.2.42.1.1
-- 1.3.6.1.4.1.37950.1.1.5.12.9.2.57.1.1
-- 1.3.6.1.4.1.37950.1.1.5.12.9.2.57.1.1
-- 1.3.6.1.4.1.37950.1.1.5.12.9.2.57.1.1
-- 1.3.6.1.4.1.37950.1.1.5.12.9.2.57.1.1
-- 1.3.6.1.4.1.37950.1.1.5.12.9.2.57.1.1
-- 1.3.6.1.4.1.37950.1.1.5.12.9.2.57.1.1
		-- 1.3.6.1.4.1.37950.1.1.5.12.9.2.57.1.1
		upnpSrvId OBJECT-TYPE
			SYNTAX INTEGER (1..65535)
			MAX-ACCESS read-write
			STATUS current
			DESCRIPTION
				"Description."
			::= { onuUpnpEntry 1 }

		
--          1.3.6.1.4.1.37950.1.1.5.12.9.2.42.1.2
-- 1.3.6.1.4.1.37950.1.1.5.12.9.2.42.1.2
-- 1.3.6.1.4.1.37950.1.1.5.12.9.2.42.1.2
-- 1.3.6.1.4.1.37950.1.1.5.12.9.2.57.1.2
-- 1.3.6.1.4.1.37950.1.1.5.12.9.2.57.1.2
-- 1.3.6.1.4.1.37950.1.1.5.12.9.2.57.1.2
-- 1.3.6.1.4.1.37950.1.1.5.12.9.2.57.1.2
-- 1.3.6.1.4.1.37950.1.1.5.12.9.2.57.1.2
-- 1.3.6.1.4.1.37950.1.1.5.12.9.2.57.1.2
		-- 1.3.6.1.4.1.37950.1.1.5.12.9.2.57.1.2
		upnpStatusS OBJECT-TYPE
			SYNTAX INTEGER
				{
				disable(0),
				enable(1)
				}
			MAX-ACCESS read-write
			STATUS current
			DESCRIPTION
				"Description."
			::= { onuUpnpEntry 2 }

		
--       1.3.6.1.4.1.37950.1.1.5.12.9.2.57.1.3
-- 1.3.6.1.4.1.37950.1.1.5.12.9.2.57.1.3
-- 1.3.6.1.4.1.37950.1.1.5.12.9.2.57.1.3
-- 1.3.6.1.4.1.37950.1.1.5.12.9.2.57.1.3
-- 1.3.6.1.4.1.37950.1.1.5.12.9.2.57.1.3
-- 1.3.6.1.4.1.37950.1.1.5.12.9.2.57.1.3
		-- 1.3.6.1.4.1.37950.1.1.5.12.9.2.57.1.3
		upnpWanIndexS OBJECT-TYPE
			SYNTAX Integer32 (1..8)
			MAX-ACCESS read-write
			STATUS current
			DESCRIPTION
				"Description."
			::= { onuUpnpEntry 3 }

		
--         1.3.6.1.4.1.37950.1.1.5.12.9.3
-- 1.3.6.1.4.1.37950.1.1.5.12.9.3
-- 1.3.6.1.4.1.37950.1.1.5.12.9.3
-- 1.3.6.1.4.1.37950.1.1.5.12.9.3
-- 1.3.6.1.4.1.37950.1.1.5.12.9.3
-- 1.3.6.1.4.1.37950.1.1.5.12.9.3
-- 1.3.6.1.4.1.37950.1.1.5.12.9.3
-- 1.3.6.1.4.1.37950.1.1.5.12.9.3
		-- 1.3.6.1.4.1.37950.1.1.5.12.9.3
		voipProfileShow OBJECT IDENTIFIER ::= { onuProfileShow 3 }

		
--         1.3.6.1.4.1.37950.1.1.5.12.9.3.1
-- 1.3.6.1.4.1.37950.1.1.5.12.9.3.1
-- 1.3.6.1.4.1.37950.1.1.5.12.9.3.1
-- 1.3.6.1.4.1.37950.1.1.5.12.9.3.1
-- 1.3.6.1.4.1.37950.1.1.5.12.9.3.1
-- 1.3.6.1.4.1.37950.1.1.5.12.9.3.1
-- 1.3.6.1.4.1.37950.1.1.5.12.9.3.1
-- 1.3.6.1.4.1.37950.1.1.5.12.9.3.1
		-- 1.3.6.1.4.1.37950.1.1.5.12.9.3.1
		onuPotsCountPFTable OBJECT-TYPE
			SYNTAX SEQUENCE OF OnuPotsCountPFEntry
			MAX-ACCESS not-accessible
			STATUS current
			DESCRIPTION
				"Description."
			::= { voipProfileShow 1 }

		
--         1.3.6.1.4.1.37950.1.1.5.12.9.3.1.1
-- 1.3.6.1.4.1.37950.1.1.5.12.9.3.1.1
-- 1.3.6.1.4.1.37950.1.1.5.12.9.3.1.1
-- 1.3.6.1.4.1.37950.1.1.5.12.9.3.1.1
-- 1.3.6.1.4.1.37950.1.1.5.12.9.3.1.1
-- 1.3.6.1.4.1.37950.1.1.5.12.9.3.1.1
-- 1.3.6.1.4.1.37950.1.1.5.12.9.3.1.1
-- 1.3.6.1.4.1.37950.1.1.5.12.9.3.1.1
		-- 1.3.6.1.4.1.37950.1.1.5.12.9.3.1.1
		onuPotsCountPFEntry OBJECT-TYPE
			SYNTAX OnuPotsCountPFEntry
			MAX-ACCESS not-accessible
			STATUS current
			DESCRIPTION
				"Description."
			INDEX { onuPotsCountVoipId }
			::= { onuPotsCountPFTable 1 }

		
		OnuPotsCountPFEntry ::=
			SEQUENCE { 
				onuPotsCountVoipId
					Integer32,
				onuPotsCountS
					INTEGER
			 }

--         1.3.6.1.4.1.37950.1.1.5.12.9.3.1.1.1
-- 1.3.6.1.4.1.37950.1.1.5.12.9.3.1.1.1
-- 1.3.6.1.4.1.37950.1.1.5.12.9.3.1.1.1
-- 1.3.6.1.4.1.37950.1.1.5.12.9.3.1.1.1
-- 1.3.6.1.4.1.37950.1.1.5.12.9.3.1.1.1
-- 1.3.6.1.4.1.37950.1.1.5.12.9.3.1.1.1
-- 1.3.6.1.4.1.37950.1.1.5.12.9.3.1.1.1
-- 1.3.6.1.4.1.37950.1.1.5.12.9.3.1.1.1
		-- 1.3.6.1.4.1.37950.1.1.5.12.9.3.1.1.1
		onuPotsCountVoipId OBJECT-TYPE
			SYNTAX Integer32 (0..65535)
			MAX-ACCESS read-only
			STATUS current
			DESCRIPTION
				"Description."
			::= { onuPotsCountPFEntry 1 }

		
--         1.3.6.1.4.1.37950.1.1.5.12.9.3.1.1.2
-- 1.3.6.1.4.1.37950.1.1.5.12.9.3.1.1.2
-- 1.3.6.1.4.1.37950.1.1.5.12.9.3.1.1.2
-- 1.3.6.1.4.1.37950.1.1.5.12.9.3.1.1.2
-- 1.3.6.1.4.1.37950.1.1.5.12.9.3.1.1.2
-- 1.3.6.1.4.1.37950.1.1.5.12.9.3.1.1.2
-- 1.3.6.1.4.1.37950.1.1.5.12.9.3.1.1.2
-- 1.3.6.1.4.1.37950.1.1.5.12.9.3.1.1.2
		-- 1.3.6.1.4.1.37950.1.1.5.12.9.3.1.1.2
		onuPotsCountS OBJECT-TYPE
			SYNTAX INTEGER (0..255)
			MAX-ACCESS read-only
			STATUS current
			DESCRIPTION
				"Description."
			::= { onuPotsCountPFEntry 2 }

		
--         1.3.6.1.4.1.37950.1.1.5.12.9.3.2
-- 1.3.6.1.4.1.37950.1.1.5.12.9.3.2
-- 1.3.6.1.4.1.37950.1.1.5.12.9.3.2
-- 1.3.6.1.4.1.37950.1.1.5.12.9.3.2
-- 1.3.6.1.4.1.37950.1.1.5.12.9.3.2
-- 1.3.6.1.4.1.37950.1.1.5.12.9.3.2
-- 1.3.6.1.4.1.37950.1.1.5.12.9.3.2
-- 1.3.6.1.4.1.37950.1.1.5.12.9.3.2
		-- 1.3.6.1.4.1.37950.1.1.5.12.9.3.2
		voipGlobalPFTable OBJECT-TYPE
			SYNTAX SEQUENCE OF VoipGlobalPFEntry
			MAX-ACCESS not-accessible
			STATUS current
			DESCRIPTION
				"Description."
			::= { voipProfileShow 2 }

		
--         1.3.6.1.4.1.37950.1.1.5.12.9.3.2.1
-- 1.3.6.1.4.1.37950.1.1.5.12.9.3.2.1
-- 1.3.6.1.4.1.37950.1.1.5.12.9.3.2.1
-- 1.3.6.1.4.1.37950.1.1.5.12.9.3.2.1
-- 1.3.6.1.4.1.37950.1.1.5.12.9.3.2.1
-- 1.3.6.1.4.1.37950.1.1.5.12.9.3.2.1
-- 1.3.6.1.4.1.37950.1.1.5.12.9.3.2.1
-- 1.3.6.1.4.1.37950.1.1.5.12.9.3.2.1
		-- 1.3.6.1.4.1.37950.1.1.5.12.9.3.2.1
		voipGlobalPFEntry OBJECT-TYPE
			SYNTAX VoipGlobalPFEntry
			MAX-ACCESS not-accessible
			STATUS current
			DESCRIPTION
				"Description."
			INDEX { voipGlobalVoipId }
			::= { voipGlobalPFTable 1 }

		
		VoipGlobalPFEntry ::=
			SEQUENCE { 
				voipGlobalVoipId
					Integer32,
				voipGlobalIpModeS
					INTEGER,
				voipGlobalIpAddrS
					IpAddress,
				voipGlobalIpMaskS
					IpAddress,
				voipGlobalIpGwS
					IpAddress,
				voipGlobalPppoeModeS
					INTEGER,
				voipGlobalPppoeUsrS
					OCTET STRING,
				voipGlobalPppoePwS
					OCTET STRING,
				voipGlobalModeS
					INTEGER,
				voipGlobalCvlanS
					INTEGER,
				voipGlobalSvlanS
					INTEGER,
				voipGlobalPriS
					INTEGER
			 }

--         1.3.6.1.4.1.37950.1.1.5.12.9.3.2.1.1
-- 1.3.6.1.4.1.37950.1.1.5.12.9.3.2.1.1
-- 1.3.6.1.4.1.37950.1.1.5.12.9.3.2.1.1
-- 1.3.6.1.4.1.37950.1.1.5.12.9.3.2.1.1
-- 1.3.6.1.4.1.37950.1.1.5.12.9.3.2.1.1
-- 1.3.6.1.4.1.37950.1.1.5.12.9.3.2.1.1
-- 1.3.6.1.4.1.37950.1.1.5.12.9.3.2.1.1
-- 1.3.6.1.4.1.37950.1.1.5.12.9.3.2.1.1
		-- 1.3.6.1.4.1.37950.1.1.5.12.9.3.2.1.1
		voipGlobalVoipId OBJECT-TYPE
			SYNTAX Integer32 (0..255)
			MAX-ACCESS read-only
			STATUS current
			DESCRIPTION
				"Description."
			::= { voipGlobalPFEntry 1 }

		
--         1.3.6.1.4.1.37950.1.1.5.12.9.3.2.1.2
-- 1.3.6.1.4.1.37950.1.1.5.12.9.3.2.1.2
-- 1.3.6.1.4.1.37950.1.1.5.12.9.3.2.1.2
-- 1.3.6.1.4.1.37950.1.1.5.12.9.3.2.1.2
-- 1.3.6.1.4.1.37950.1.1.5.12.9.3.2.1.2
-- 1.3.6.1.4.1.37950.1.1.5.12.9.3.2.1.2
-- 1.3.6.1.4.1.37950.1.1.5.12.9.3.2.1.2
-- 1.3.6.1.4.1.37950.1.1.5.12.9.3.2.1.2
		-- 1.3.6.1.4.1.37950.1.1.5.12.9.3.2.1.2
		voipGlobalIpModeS OBJECT-TYPE
			SYNTAX INTEGER
				{
				staticip(0),
				dhcp(1),
				pppoe(2)
				}
			MAX-ACCESS read-only
			STATUS current
			DESCRIPTION
				"Description."
			::= { voipGlobalPFEntry 2 }

		
--         1.3.6.1.4.1.37950.1.1.5.12.9.3.2.1.3
-- 1.3.6.1.4.1.37950.1.1.5.12.9.3.2.1.3
-- 1.3.6.1.4.1.37950.1.1.5.12.9.3.2.1.3
-- 1.3.6.1.4.1.37950.1.1.5.12.9.3.2.1.3
-- 1.3.6.1.4.1.37950.1.1.5.12.9.3.2.1.3
-- 1.3.6.1.4.1.37950.1.1.5.12.9.3.2.1.3
-- 1.3.6.1.4.1.37950.1.1.5.12.9.3.2.1.3
-- 1.3.6.1.4.1.37950.1.1.5.12.9.3.2.1.3
		-- 1.3.6.1.4.1.37950.1.1.5.12.9.3.2.1.3
		voipGlobalIpAddrS OBJECT-TYPE
			SYNTAX IpAddress
			MAX-ACCESS read-only
			STATUS current
			DESCRIPTION
				"Description."
			::= { voipGlobalPFEntry 3 }

		
--         1.3.6.1.4.1.37950.1.1.5.12.9.3.2.1.4
-- 1.3.6.1.4.1.37950.1.1.5.12.9.3.2.1.4
-- 1.3.6.1.4.1.37950.1.1.5.12.9.3.2.1.4
-- 1.3.6.1.4.1.37950.1.1.5.12.9.3.2.1.4
-- 1.3.6.1.4.1.37950.1.1.5.12.9.3.2.1.4
-- 1.3.6.1.4.1.37950.1.1.5.12.9.3.2.1.4
-- 1.3.6.1.4.1.37950.1.1.5.12.9.3.2.1.4
-- 1.3.6.1.4.1.37950.1.1.5.12.9.3.2.1.4
		-- 1.3.6.1.4.1.37950.1.1.5.12.9.3.2.1.4
		voipGlobalIpMaskS OBJECT-TYPE
			SYNTAX IpAddress
			MAX-ACCESS read-only
			STATUS current
			DESCRIPTION
				"Description."
			::= { voipGlobalPFEntry 4 }

		
--         1.3.6.1.4.1.37950.1.1.5.12.9.3.2.1.5
-- 1.3.6.1.4.1.37950.1.1.5.12.9.3.2.1.5
-- 1.3.6.1.4.1.37950.1.1.5.12.9.3.2.1.5
-- 1.3.6.1.4.1.37950.1.1.5.12.9.3.2.1.5
-- 1.3.6.1.4.1.37950.1.1.5.12.9.3.2.1.5
-- 1.3.6.1.4.1.37950.1.1.5.12.9.3.2.1.5
-- 1.3.6.1.4.1.37950.1.1.5.12.9.3.2.1.5
-- 1.3.6.1.4.1.37950.1.1.5.12.9.3.2.1.5
		-- 1.3.6.1.4.1.37950.1.1.5.12.9.3.2.1.5
		voipGlobalIpGwS OBJECT-TYPE
			SYNTAX IpAddress
			MAX-ACCESS read-only
			STATUS current
			DESCRIPTION
				"Description."
			::= { voipGlobalPFEntry 5 }

		
--         1.3.6.1.4.1.37950.1.1.5.12.9.3.2.1.6
-- 1.3.6.1.4.1.37950.1.1.5.12.9.3.2.1.6
-- 1.3.6.1.4.1.37950.1.1.5.12.9.3.2.1.6
-- 1.3.6.1.4.1.37950.1.1.5.12.9.3.2.1.6
-- 1.3.6.1.4.1.37950.1.1.5.12.9.3.2.1.6
-- 1.3.6.1.4.1.37950.1.1.5.12.9.3.2.1.6
-- 1.3.6.1.4.1.37950.1.1.5.12.9.3.2.1.6
-- 1.3.6.1.4.1.37950.1.1.5.12.9.3.2.1.6
		-- 1.3.6.1.4.1.37950.1.1.5.12.9.3.2.1.6
		voipGlobalPppoeModeS OBJECT-TYPE
			SYNTAX INTEGER
				{
				auto(1),
				chap(2),
				pap(3)
				}
			MAX-ACCESS read-only
			STATUS current
			DESCRIPTION
				"Description."
			::= { voipGlobalPFEntry 6 }

		
--         1.3.6.1.4.1.37950.1.1.5.12.9.3.2.1.7
-- 1.3.6.1.4.1.37950.1.1.5.12.9.3.2.1.7
-- 1.3.6.1.4.1.37950.1.1.5.12.9.3.2.1.7
-- 1.3.6.1.4.1.37950.1.1.5.12.9.3.2.1.7
-- 1.3.6.1.4.1.37950.1.1.5.12.9.3.2.1.7
-- 1.3.6.1.4.1.37950.1.1.5.12.9.3.2.1.7
-- 1.3.6.1.4.1.37950.1.1.5.12.9.3.2.1.7
-- 1.3.6.1.4.1.37950.1.1.5.12.9.3.2.1.7
		-- 1.3.6.1.4.1.37950.1.1.5.12.9.3.2.1.7
		voipGlobalPppoeUsrS OBJECT-TYPE
			SYNTAX OCTET STRING
			MAX-ACCESS read-only
			STATUS current
			DESCRIPTION
				"Description."
			::= { voipGlobalPFEntry 7 }

		
--         1.3.6.1.4.1.37950.1.1.5.12.9.3.2.1.8
-- 1.3.6.1.4.1.37950.1.1.5.12.9.3.2.1.8
-- 1.3.6.1.4.1.37950.1.1.5.12.9.3.2.1.8
-- 1.3.6.1.4.1.37950.1.1.5.12.9.3.2.1.8
-- 1.3.6.1.4.1.37950.1.1.5.12.9.3.2.1.8
-- 1.3.6.1.4.1.37950.1.1.5.12.9.3.2.1.8
-- 1.3.6.1.4.1.37950.1.1.5.12.9.3.2.1.8
-- 1.3.6.1.4.1.37950.1.1.5.12.9.3.2.1.8
		-- 1.3.6.1.4.1.37950.1.1.5.12.9.3.2.1.8
		voipGlobalPppoePwS OBJECT-TYPE
			SYNTAX OCTET STRING
			MAX-ACCESS read-only
			STATUS current
			DESCRIPTION
				"Description."
			::= { voipGlobalPFEntry 8 }

		
--         1.3.6.1.4.1.37950.1.1.5.12.9.3.2.1.9
-- 1.3.6.1.4.1.37950.1.1.5.12.9.3.2.1.9
-- 1.3.6.1.4.1.37950.1.1.5.12.9.3.2.1.9
-- 1.3.6.1.4.1.37950.1.1.5.12.9.3.2.1.9
-- 1.3.6.1.4.1.37950.1.1.5.12.9.3.2.1.9
-- 1.3.6.1.4.1.37950.1.1.5.12.9.3.2.1.9
-- 1.3.6.1.4.1.37950.1.1.5.12.9.3.2.1.9
-- 1.3.6.1.4.1.37950.1.1.5.12.9.3.2.1.9
		-- 1.3.6.1.4.1.37950.1.1.5.12.9.3.2.1.9
		voipGlobalModeS OBJECT-TYPE
			SYNTAX INTEGER
				{
				transparent(1),
				tag(2),
				vlan-stacking(3)
				}
			MAX-ACCESS read-only
			STATUS current
			DESCRIPTION
				"Description."
			::= { voipGlobalPFEntry 9 }

		
--         1.3.6.1.4.1.37950.1.1.5.12.9.3.2.1.10
-- 1.3.6.1.4.1.37950.1.1.5.12.9.3.2.1.10
-- 1.3.6.1.4.1.37950.1.1.5.12.9.3.2.1.10
-- 1.3.6.1.4.1.37950.1.1.5.12.9.3.2.1.10
-- 1.3.6.1.4.1.37950.1.1.5.12.9.3.2.1.10
-- 1.3.6.1.4.1.37950.1.1.5.12.9.3.2.1.10
-- 1.3.6.1.4.1.37950.1.1.5.12.9.3.2.1.10
-- 1.3.6.1.4.1.37950.1.1.5.12.9.3.2.1.10
		-- 1.3.6.1.4.1.37950.1.1.5.12.9.3.2.1.10
		voipGlobalCvlanS OBJECT-TYPE
			SYNTAX INTEGER (0..4095)
			MAX-ACCESS read-only
			STATUS current
			DESCRIPTION
				"Description."
			::= { voipGlobalPFEntry 10 }

		
--         1.3.6.1.4.1.37950.1.1.5.12.9.3.2.1.11
-- 1.3.6.1.4.1.37950.1.1.5.12.9.3.2.1.11
-- 1.3.6.1.4.1.37950.1.1.5.12.9.3.2.1.11
-- 1.3.6.1.4.1.37950.1.1.5.12.9.3.2.1.11
-- 1.3.6.1.4.1.37950.1.1.5.12.9.3.2.1.11
-- 1.3.6.1.4.1.37950.1.1.5.12.9.3.2.1.11
-- 1.3.6.1.4.1.37950.1.1.5.12.9.3.2.1.11
-- 1.3.6.1.4.1.37950.1.1.5.12.9.3.2.1.11
		-- 1.3.6.1.4.1.37950.1.1.5.12.9.3.2.1.11
		voipGlobalSvlanS OBJECT-TYPE
			SYNTAX INTEGER (0..4095)
			MAX-ACCESS read-only
			STATUS current
			DESCRIPTION
				"Description."
			::= { voipGlobalPFEntry 11 }

		
--         1.3.6.1.4.1.37950.1.1.5.12.9.3.2.1.12
-- 1.3.6.1.4.1.37950.1.1.5.12.9.3.2.1.12
-- 1.3.6.1.4.1.37950.1.1.5.12.9.3.2.1.12
-- 1.3.6.1.4.1.37950.1.1.5.12.9.3.2.1.12
-- 1.3.6.1.4.1.37950.1.1.5.12.9.3.2.1.12
-- 1.3.6.1.4.1.37950.1.1.5.12.9.3.2.1.12
-- 1.3.6.1.4.1.37950.1.1.5.12.9.3.2.1.12
-- 1.3.6.1.4.1.37950.1.1.5.12.9.3.2.1.12
		-- 1.3.6.1.4.1.37950.1.1.5.12.9.3.2.1.12
		voipGlobalPriS OBJECT-TYPE
			SYNTAX INTEGER (0..7)
			MAX-ACCESS read-only
			STATUS current
			DESCRIPTION
				"Description."
			::= { voipGlobalPFEntry 12 }

		
--         1.3.6.1.4.1.37950.1.1.5.12.9.3.3
-- 1.3.6.1.4.1.37950.1.1.5.12.9.3.3
-- 1.3.6.1.4.1.37950.1.1.5.12.9.3.3
-- 1.3.6.1.4.1.37950.1.1.5.12.9.3.3
-- 1.3.6.1.4.1.37950.1.1.5.12.9.3.3
-- 1.3.6.1.4.1.37950.1.1.5.12.9.3.3
-- 1.3.6.1.4.1.37950.1.1.5.12.9.3.3
-- 1.3.6.1.4.1.37950.1.1.5.12.9.3.3
		-- 1.3.6.1.4.1.37950.1.1.5.12.9.3.3
		h248ProPFTable OBJECT-TYPE
			SYNTAX SEQUENCE OF H248ProPFEntry
			MAX-ACCESS not-accessible
			STATUS current
			DESCRIPTION
				"Description."
			::= { voipProfileShow 3 }

		
--         1.3.6.1.4.1.37950.1.1.5.12.9.3.3.1
-- 1.3.6.1.4.1.37950.1.1.5.12.9.3.3.1
-- 1.3.6.1.4.1.37950.1.1.5.12.9.3.3.1
-- 1.3.6.1.4.1.37950.1.1.5.12.9.3.3.1
-- 1.3.6.1.4.1.37950.1.1.5.12.9.3.3.1
-- 1.3.6.1.4.1.37950.1.1.5.12.9.3.3.1
-- 1.3.6.1.4.1.37950.1.1.5.12.9.3.3.1
-- 1.3.6.1.4.1.37950.1.1.5.12.9.3.3.1
		-- 1.3.6.1.4.1.37950.1.1.5.12.9.3.3.1
		h248ProPFEntry OBJECT-TYPE
			SYNTAX H248ProPFEntry
			MAX-ACCESS not-accessible
			STATUS current
			DESCRIPTION
				"Description."
			INDEX { h248ProVoipId }
			::= { h248ProPFTable 1 }

		
		H248ProPFEntry ::=
			SEQUENCE { 
				h248ProVoipId
					Integer32,
				h248ProMgPortS
					INTEGER,
				h248ProMgcIpS
					IpAddress,
				h248ProMgComPortS
					INTEGER,
				h248ProBakMgcIpS
					IpAddress,
				h248ProBakMgcPortS
					INTEGER,
				h248ProRegModeS
					INTEGER,
				h248ProMIDS
					OCTET STRING,
				h248ProHBModeS
					INTEGER,
				h248ProHBCycleS
					INTEGER,
				h248ProHBCountS
					INTEGER
			 }

--         1.3.6.1.4.1.37950.1.1.5.12.9.3.3.1.1
-- 1.3.6.1.4.1.37950.1.1.5.12.9.3.3.1.1
-- 1.3.6.1.4.1.37950.1.1.5.12.9.3.3.1.1
-- 1.3.6.1.4.1.37950.1.1.5.12.9.3.3.1.1
-- 1.3.6.1.4.1.37950.1.1.5.12.9.3.3.1.1
-- 1.3.6.1.4.1.37950.1.1.5.12.9.3.3.1.1
-- 1.3.6.1.4.1.37950.1.1.5.12.9.3.3.1.1
-- 1.3.6.1.4.1.37950.1.1.5.12.9.3.3.1.1
		-- 1.3.6.1.4.1.37950.1.1.5.12.9.3.3.1.1
		h248ProVoipId OBJECT-TYPE
			SYNTAX Integer32 (0..65535)
			MAX-ACCESS read-only
			STATUS current
			DESCRIPTION
				"Description."
			::= { h248ProPFEntry 1 }

		
--         1.3.6.1.4.1.37950.1.1.5.12.9.3.3.1.2
-- 1.3.6.1.4.1.37950.1.1.5.12.9.3.3.1.2
-- 1.3.6.1.4.1.37950.1.1.5.12.9.3.3.1.2
-- 1.3.6.1.4.1.37950.1.1.5.12.9.3.3.1.2
-- 1.3.6.1.4.1.37950.1.1.5.12.9.3.3.1.2
-- 1.3.6.1.4.1.37950.1.1.5.12.9.3.3.1.2
-- 1.3.6.1.4.1.37950.1.1.5.12.9.3.3.1.2
-- 1.3.6.1.4.1.37950.1.1.5.12.9.3.3.1.2
		-- 1.3.6.1.4.1.37950.1.1.5.12.9.3.3.1.2
		h248ProMgPortS OBJECT-TYPE
			SYNTAX INTEGER (1..65535)
			MAX-ACCESS read-only
			STATUS current
			DESCRIPTION
				"Description."
			::= { h248ProPFEntry 2 }

		
--         1.3.6.1.4.1.37950.1.1.5.12.9.3.3.1.3
-- 1.3.6.1.4.1.37950.1.1.5.12.9.3.3.1.3
-- 1.3.6.1.4.1.37950.1.1.5.12.9.3.3.1.3
-- 1.3.6.1.4.1.37950.1.1.5.12.9.3.3.1.3
-- 1.3.6.1.4.1.37950.1.1.5.12.9.3.3.1.3
-- 1.3.6.1.4.1.37950.1.1.5.12.9.3.3.1.3
-- 1.3.6.1.4.1.37950.1.1.5.12.9.3.3.1.3
-- 1.3.6.1.4.1.37950.1.1.5.12.9.3.3.1.3
		-- 1.3.6.1.4.1.37950.1.1.5.12.9.3.3.1.3
		h248ProMgcIpS OBJECT-TYPE
			SYNTAX IpAddress
			MAX-ACCESS read-only
			STATUS current
			DESCRIPTION
				"Description."
			::= { h248ProPFEntry 3 }

		
--         1.3.6.1.4.1.37950.1.1.5.12.9.3.3.1.4
-- 1.3.6.1.4.1.37950.1.1.5.12.9.3.3.1.4
-- 1.3.6.1.4.1.37950.1.1.5.12.9.3.3.1.4
-- 1.3.6.1.4.1.37950.1.1.5.12.9.3.3.1.4
-- 1.3.6.1.4.1.37950.1.1.5.12.9.3.3.1.4
-- 1.3.6.1.4.1.37950.1.1.5.12.9.3.3.1.4
-- 1.3.6.1.4.1.37950.1.1.5.12.9.3.3.1.4
-- 1.3.6.1.4.1.37950.1.1.5.12.9.3.3.1.4
		-- 1.3.6.1.4.1.37950.1.1.5.12.9.3.3.1.4
		h248ProMgComPortS OBJECT-TYPE
			SYNTAX INTEGER (1..65535)
			MAX-ACCESS read-only
			STATUS current
			DESCRIPTION
				"Description."
			::= { h248ProPFEntry 4 }

		
--         1.3.6.1.4.1.37950.1.1.5.12.9.3.3.1.5
-- 1.3.6.1.4.1.37950.1.1.5.12.9.3.3.1.5
-- 1.3.6.1.4.1.37950.1.1.5.12.9.3.3.1.5
-- 1.3.6.1.4.1.37950.1.1.5.12.9.3.3.1.5
-- 1.3.6.1.4.1.37950.1.1.5.12.9.3.3.1.5
-- 1.3.6.1.4.1.37950.1.1.5.12.9.3.3.1.5
-- 1.3.6.1.4.1.37950.1.1.5.12.9.3.3.1.5
-- 1.3.6.1.4.1.37950.1.1.5.12.9.3.3.1.5
		-- 1.3.6.1.4.1.37950.1.1.5.12.9.3.3.1.5
		h248ProBakMgcIpS OBJECT-TYPE
			SYNTAX IpAddress
			MAX-ACCESS read-only
			STATUS current
			DESCRIPTION
				"Description."
			::= { h248ProPFEntry 5 }

		
--         1.3.6.1.4.1.37950.1.1.5.12.9.3.3.1.6
-- 1.3.6.1.4.1.37950.1.1.5.12.9.3.3.1.6
-- 1.3.6.1.4.1.37950.1.1.5.12.9.3.3.1.6
-- 1.3.6.1.4.1.37950.1.1.5.12.9.3.3.1.6
-- 1.3.6.1.4.1.37950.1.1.5.12.9.3.3.1.6
-- 1.3.6.1.4.1.37950.1.1.5.12.9.3.3.1.6
-- 1.3.6.1.4.1.37950.1.1.5.12.9.3.3.1.6
-- 1.3.6.1.4.1.37950.1.1.5.12.9.3.3.1.6
		-- 1.3.6.1.4.1.37950.1.1.5.12.9.3.3.1.6
		h248ProBakMgcPortS OBJECT-TYPE
			SYNTAX INTEGER (1..65535)
			MAX-ACCESS read-only
			STATUS current
			DESCRIPTION
				"Description."
			::= { h248ProPFEntry 6 }

		
--         1.3.6.1.4.1.37950.1.1.5.12.9.3.3.1.7
-- 1.3.6.1.4.1.37950.1.1.5.12.9.3.3.1.7
-- 1.3.6.1.4.1.37950.1.1.5.12.9.3.3.1.7
-- 1.3.6.1.4.1.37950.1.1.5.12.9.3.3.1.7
-- 1.3.6.1.4.1.37950.1.1.5.12.9.3.3.1.7
-- 1.3.6.1.4.1.37950.1.1.5.12.9.3.3.1.7
-- 1.3.6.1.4.1.37950.1.1.5.12.9.3.3.1.7
-- 1.3.6.1.4.1.37950.1.1.5.12.9.3.3.1.7
		-- 1.3.6.1.4.1.37950.1.1.5.12.9.3.3.1.7
		h248ProRegModeS OBJECT-TYPE
			SYNTAX INTEGER
				{
				ip-addr(0),
				realm-name(1),
				device-name(2)
				}
			MAX-ACCESS read-only
			STATUS current
			DESCRIPTION
				"Description."
			::= { h248ProPFEntry 7 }

		
--         1.3.6.1.4.1.37950.1.1.5.12.9.3.3.1.8
-- 1.3.6.1.4.1.37950.1.1.5.12.9.3.3.1.8
-- 1.3.6.1.4.1.37950.1.1.5.12.9.3.3.1.8
-- 1.3.6.1.4.1.37950.1.1.5.12.9.3.3.1.8
-- 1.3.6.1.4.1.37950.1.1.5.12.9.3.3.1.8
-- 1.3.6.1.4.1.37950.1.1.5.12.9.3.3.1.8
-- 1.3.6.1.4.1.37950.1.1.5.12.9.3.3.1.8
-- 1.3.6.1.4.1.37950.1.1.5.12.9.3.3.1.8
		-- 1.3.6.1.4.1.37950.1.1.5.12.9.3.3.1.8
		h248ProMIDS OBJECT-TYPE
			SYNTAX OCTET STRING
			MAX-ACCESS read-only
			STATUS current
			DESCRIPTION
				"Description."
			::= { h248ProPFEntry 8 }

		
--         1.3.6.1.4.1.37950.1.1.5.12.9.3.3.1.9
-- 1.3.6.1.4.1.37950.1.1.5.12.9.3.3.1.9
-- 1.3.6.1.4.1.37950.1.1.5.12.9.3.3.1.9
-- 1.3.6.1.4.1.37950.1.1.5.12.9.3.3.1.9
-- 1.3.6.1.4.1.37950.1.1.5.12.9.3.3.1.9
-- 1.3.6.1.4.1.37950.1.1.5.12.9.3.3.1.9
-- 1.3.6.1.4.1.37950.1.1.5.12.9.3.3.1.9
-- 1.3.6.1.4.1.37950.1.1.5.12.9.3.3.1.9
		-- 1.3.6.1.4.1.37950.1.1.5.12.9.3.3.1.9
		h248ProHBModeS OBJECT-TYPE
			SYNTAX INTEGER
				{
				disable(0),
				h248(1)
				}
			MAX-ACCESS read-only
			STATUS current
			DESCRIPTION
				"Description."
			::= { h248ProPFEntry 9 }

		
--         1.3.6.1.4.1.37950.1.1.5.12.9.3.3.1.10
-- 1.3.6.1.4.1.37950.1.1.5.12.9.3.3.1.10
-- 1.3.6.1.4.1.37950.1.1.5.12.9.3.3.1.10
-- 1.3.6.1.4.1.37950.1.1.5.12.9.3.3.1.10
-- 1.3.6.1.4.1.37950.1.1.5.12.9.3.3.1.10
-- 1.3.6.1.4.1.37950.1.1.5.12.9.3.3.1.10
-- 1.3.6.1.4.1.37950.1.1.5.12.9.3.3.1.10
-- 1.3.6.1.4.1.37950.1.1.5.12.9.3.3.1.10
		-- 1.3.6.1.4.1.37950.1.1.5.12.9.3.3.1.10
		h248ProHBCycleS OBJECT-TYPE
			SYNTAX INTEGER (1..65535)
			MAX-ACCESS read-only
			STATUS current
			DESCRIPTION
				"Description."
			::= { h248ProPFEntry 10 }

		
--         1.3.6.1.4.1.37950.1.1.5.12.9.3.3.1.11
-- 1.3.6.1.4.1.37950.1.1.5.12.9.3.3.1.11
-- 1.3.6.1.4.1.37950.1.1.5.12.9.3.3.1.11
-- 1.3.6.1.4.1.37950.1.1.5.12.9.3.3.1.11
-- 1.3.6.1.4.1.37950.1.1.5.12.9.3.3.1.11
-- 1.3.6.1.4.1.37950.1.1.5.12.9.3.3.1.11
-- 1.3.6.1.4.1.37950.1.1.5.12.9.3.3.1.11
-- 1.3.6.1.4.1.37950.1.1.5.12.9.3.3.1.11
		-- 1.3.6.1.4.1.37950.1.1.5.12.9.3.3.1.11
		h248ProHBCountS OBJECT-TYPE
			SYNTAX INTEGER (1..65535)
			MAX-ACCESS read-only
			STATUS current
			DESCRIPTION
				"Description."
			::= { h248ProPFEntry 11 }

		
--         1.3.6.1.4.1.37950.1.1.5.12.9.3.4
-- 1.3.6.1.4.1.37950.1.1.5.12.9.3.4
-- 1.3.6.1.4.1.37950.1.1.5.12.9.3.4
-- 1.3.6.1.4.1.37950.1.1.5.12.9.3.4
-- 1.3.6.1.4.1.37950.1.1.5.12.9.3.4
-- 1.3.6.1.4.1.37950.1.1.5.12.9.3.4
-- 1.3.6.1.4.1.37950.1.1.5.12.9.3.4
-- 1.3.6.1.4.1.37950.1.1.5.12.9.3.4
		-- 1.3.6.1.4.1.37950.1.1.5.12.9.3.4
		h248RtpTidPFTable OBJECT-TYPE
			SYNTAX SEQUENCE OF H248RtpTidPFEntry
			MAX-ACCESS not-accessible
			STATUS current
			DESCRIPTION
				"Description."
			::= { voipProfileShow 4 }

		
--         1.3.6.1.4.1.37950.1.1.5.12.9.3.4.1
-- 1.3.6.1.4.1.37950.1.1.5.12.9.3.4.1
-- 1.3.6.1.4.1.37950.1.1.5.12.9.3.4.1
-- 1.3.6.1.4.1.37950.1.1.5.12.9.3.4.1
-- 1.3.6.1.4.1.37950.1.1.5.12.9.3.4.1
-- 1.3.6.1.4.1.37950.1.1.5.12.9.3.4.1
-- 1.3.6.1.4.1.37950.1.1.5.12.9.3.4.1
-- 1.3.6.1.4.1.37950.1.1.5.12.9.3.4.1
		-- 1.3.6.1.4.1.37950.1.1.5.12.9.3.4.1
		h248RtpTidPFEntry OBJECT-TYPE
			SYNTAX H248RtpTidPFEntry
			MAX-ACCESS not-accessible
			STATUS current
			DESCRIPTION
				"Description."
			INDEX { h248RtpTidVoipId }
			::= { h248RtpTidPFTable 1 }

		
		H248RtpTidPFEntry ::=
			SEQUENCE { 
				h248RtpTidVoipId
					Integer32,
				h248RtpTidNumberS
					INTEGER,
				h248RtpTidPrefixS
					OCTET STRING,
				h248RtpTidBegin0S
					Unsigned32,
				h248RtpTidBegin1S
					Unsigned32,
				h248RtpTidModeS
					INTEGER,
				h248RtpTidDGLengthS
					INTEGER
			 }

--          1.3.6.1.4.1.37950.1.1.5.12.9.3.4.1.1
-- 1.3.6.1.4.1.37950.1.1.5.12.9.3.4.1.1
-- 1.3.6.1.4.1.37950.1.1.5.12.9.3.4.1.1
-- 1.3.6.1.4.1.37950.1.1.5.12.9.3.4.1.1
-- 1.3.6.1.4.1.37950.1.1.5.12.9.3.4.1.1
-- 1.3.6.1.4.1.37950.1.1.5.12.9.3.4.1.1
-- 1.3.6.1.4.1.37950.1.1.5.12.9.3.4.1.1
-- 1.3.6.1.4.1.37950.1.1.5.12.9.3.4.1.1
-- 1.3.6.1.4.1.37950.1.1.5.12.9.3.4.1.1
		-- 1.3.6.1.4.1.37950.1.1.5.12.9.3.4.1.1
		h248RtpTidVoipId OBJECT-TYPE
			SYNTAX Integer32 (0..65535)
			MAX-ACCESS read-only
			STATUS current
			DESCRIPTION
				"Description."
			::= { h248RtpTidPFEntry 1 }

		
--          1.3.6.1.4.1.37950.1.1.5.12.9.3.4.1.2
-- 1.3.6.1.4.1.37950.1.1.5.12.9.3.4.1.2
-- 1.3.6.1.4.1.37950.1.1.5.12.9.3.4.1.2
-- 1.3.6.1.4.1.37950.1.1.5.12.9.3.4.1.2
-- 1.3.6.1.4.1.37950.1.1.5.12.9.3.4.1.2
-- 1.3.6.1.4.1.37950.1.1.5.12.9.3.4.1.2
-- 1.3.6.1.4.1.37950.1.1.5.12.9.3.4.1.2
-- 1.3.6.1.4.1.37950.1.1.5.12.9.3.4.1.2
-- 1.3.6.1.4.1.37950.1.1.5.12.9.3.4.1.2
		-- 1.3.6.1.4.1.37950.1.1.5.12.9.3.4.1.2
		h248RtpTidNumberS OBJECT-TYPE
			SYNTAX INTEGER (0..255)
			MAX-ACCESS read-only
			STATUS current
			DESCRIPTION
				"Description."
			::= { h248RtpTidPFEntry 2 }

		
--          1.3.6.1.4.1.37950.1.1.5.12.9.3.4.1.3
-- 1.3.6.1.4.1.37950.1.1.5.12.9.3.4.1.3
-- 1.3.6.1.4.1.37950.1.1.5.12.9.3.4.1.3
-- 1.3.6.1.4.1.37950.1.1.5.12.9.3.4.1.3
-- 1.3.6.1.4.1.37950.1.1.5.12.9.3.4.1.3
-- 1.3.6.1.4.1.37950.1.1.5.12.9.3.4.1.3
-- 1.3.6.1.4.1.37950.1.1.5.12.9.3.4.1.3
-- 1.3.6.1.4.1.37950.1.1.5.12.9.3.4.1.3
-- 1.3.6.1.4.1.37950.1.1.5.12.9.3.4.1.3
		-- 1.3.6.1.4.1.37950.1.1.5.12.9.3.4.1.3
		h248RtpTidPrefixS OBJECT-TYPE
			SYNTAX OCTET STRING
			MAX-ACCESS read-only
			STATUS current
			DESCRIPTION
				"Description."
			::= { h248RtpTidPFEntry 3 }

		
--          1.3.6.1.4.1.37950.1.1.5.12.9.3.4.1.4
-- 1.3.6.1.4.1.37950.1.1.5.12.9.3.4.1.4
-- 1.3.6.1.4.1.37950.1.1.5.12.9.3.4.1.4
-- 1.3.6.1.4.1.37950.1.1.5.12.9.3.4.1.4
-- 1.3.6.1.4.1.37950.1.1.5.12.9.3.4.1.4
-- 1.3.6.1.4.1.37950.1.1.5.12.9.3.4.1.4
-- 1.3.6.1.4.1.37950.1.1.5.12.9.3.4.1.4
-- 1.3.6.1.4.1.37950.1.1.5.12.9.3.4.1.4
-- 1.3.6.1.4.1.37950.1.1.5.12.9.3.4.1.4
		-- 1.3.6.1.4.1.37950.1.1.5.12.9.3.4.1.4
		h248RtpTidBegin0S OBJECT-TYPE
			SYNTAX Unsigned32 (0..4294967295)
			MAX-ACCESS read-only
			STATUS current
			DESCRIPTION
				"Description."
			::= { h248RtpTidPFEntry 4 }

		
--          1.3.6.1.4.1.37950.1.1.5.12.9.3.4.1.5
-- 1.3.6.1.4.1.37950.1.1.5.12.9.3.4.1.5
-- 1.3.6.1.4.1.37950.1.1.5.12.9.3.4.1.5
-- 1.3.6.1.4.1.37950.1.1.5.12.9.3.4.1.5
-- 1.3.6.1.4.1.37950.1.1.5.12.9.3.4.1.5
-- 1.3.6.1.4.1.37950.1.1.5.12.9.3.4.1.5
-- 1.3.6.1.4.1.37950.1.1.5.12.9.3.4.1.5
-- 1.3.6.1.4.1.37950.1.1.5.12.9.3.4.1.5
-- 1.3.6.1.4.1.37950.1.1.5.12.9.3.4.1.5
		-- 1.3.6.1.4.1.37950.1.1.5.12.9.3.4.1.5
		h248RtpTidBegin1S OBJECT-TYPE
			SYNTAX Unsigned32 (0..4294967295)
			MAX-ACCESS read-only
			STATUS current
			DESCRIPTION
				"Description."
			::= { h248RtpTidPFEntry 5 }

		
--          1.3.6.1.4.1.37950.1.1.5.12.9.3.4.1.6
-- 1.3.6.1.4.1.37950.1.1.5.12.9.3.4.1.6
-- 1.3.6.1.4.1.37950.1.1.5.12.9.3.4.1.6
-- 1.3.6.1.4.1.37950.1.1.5.12.9.3.4.1.6
-- 1.3.6.1.4.1.37950.1.1.5.12.9.3.4.1.6
-- 1.3.6.1.4.1.37950.1.1.5.12.9.3.4.1.6
-- 1.3.6.1.4.1.37950.1.1.5.12.9.3.4.1.6
-- 1.3.6.1.4.1.37950.1.1.5.12.9.3.4.1.6
-- 1.3.6.1.4.1.37950.1.1.5.12.9.3.4.1.6
		-- 1.3.6.1.4.1.37950.1.1.5.12.9.3.4.1.6
		h248RtpTidModeS OBJECT-TYPE
			SYNTAX INTEGER
				{
				align(1),
				unalign(2)
				}
			MAX-ACCESS read-only
			STATUS current
			DESCRIPTION
				"Description."
			::= { h248RtpTidPFEntry 6 }

		
--          1.3.6.1.4.1.37950.1.1.5.12.9.3.4.1.7
-- 1.3.6.1.4.1.37950.1.1.5.12.9.3.4.1.7
-- 1.3.6.1.4.1.37950.1.1.5.12.9.3.4.1.7
-- 1.3.6.1.4.1.37950.1.1.5.12.9.3.4.1.7
-- 1.3.6.1.4.1.37950.1.1.5.12.9.3.4.1.7
-- 1.3.6.1.4.1.37950.1.1.5.12.9.3.4.1.7
-- 1.3.6.1.4.1.37950.1.1.5.12.9.3.4.1.7
-- 1.3.6.1.4.1.37950.1.1.5.12.9.3.4.1.7
-- 1.3.6.1.4.1.37950.1.1.5.12.9.3.4.1.7
		-- 1.3.6.1.4.1.37950.1.1.5.12.9.3.4.1.7
		h248RtpTidDGLengthS OBJECT-TYPE
			SYNTAX INTEGER (0..255)
			MAX-ACCESS read-only
			STATUS current
			DESCRIPTION
				"Description."
			::= { h248RtpTidPFEntry 7 }

		
--          1.3.6.1.4.1.37950.1.1.5.12.9.3.5
-- 1.3.6.1.4.1.37950.1.1.5.12.9.3.5
-- 1.3.6.1.4.1.37950.1.1.5.12.9.3.5
-- 1.3.6.1.4.1.37950.1.1.5.12.9.3.5
-- 1.3.6.1.4.1.37950.1.1.5.12.9.3.5
-- 1.3.6.1.4.1.37950.1.1.5.12.9.3.5
-- 1.3.6.1.4.1.37950.1.1.5.12.9.3.5
-- 1.3.6.1.4.1.37950.1.1.5.12.9.3.5
-- 1.3.6.1.4.1.37950.1.1.5.12.9.3.5
		-- 1.3.6.1.4.1.37950.1.1.5.12.9.3.5
		h248UserTidPFTable OBJECT-TYPE
			SYNTAX SEQUENCE OF H248UserTidPFEntry
			MAX-ACCESS not-accessible
			STATUS current
			DESCRIPTION
				"Description."
			::= { voipProfileShow 5 }

		
--          1.3.6.1.4.1.37950.1.1.5.12.9.3.5.1
-- 1.3.6.1.4.1.37950.1.1.5.12.9.3.5.1
-- 1.3.6.1.4.1.37950.1.1.5.12.9.3.5.1
-- 1.3.6.1.4.1.37950.1.1.5.12.9.3.5.1
-- 1.3.6.1.4.1.37950.1.1.5.12.9.3.5.1
-- 1.3.6.1.4.1.37950.1.1.5.12.9.3.5.1
-- 1.3.6.1.4.1.37950.1.1.5.12.9.3.5.1
-- 1.3.6.1.4.1.37950.1.1.5.12.9.3.5.1
-- 1.3.6.1.4.1.37950.1.1.5.12.9.3.5.1
		-- 1.3.6.1.4.1.37950.1.1.5.12.9.3.5.1
		h248UserTidPFEntry OBJECT-TYPE
			SYNTAX H248UserTidPFEntry
			MAX-ACCESS not-accessible
			STATUS current
			DESCRIPTION
				"Description."
			INDEX { h248UserTidVoipId, h248UserTidPotsNoS }
			::= { h248UserTidPFTable 1 }

		
		H248UserTidPFEntry ::=
			SEQUENCE { 
				h248UserTidVoipId
					Integer32,
				h248UserTidPotsNoS
					INTEGER,
				h248UserTidS
					OCTET STRING
			 }

--          1.3.6.1.4.1.37950.1.1.5.12.9.3.5.1.1
-- 1.3.6.1.4.1.37950.1.1.5.12.9.3.5.1.1
-- 1.3.6.1.4.1.37950.1.1.5.12.9.3.5.1.1
-- 1.3.6.1.4.1.37950.1.1.5.12.9.3.5.1.1
-- 1.3.6.1.4.1.37950.1.1.5.12.9.3.5.1.1
-- 1.3.6.1.4.1.37950.1.1.5.12.9.3.5.1.1
-- 1.3.6.1.4.1.37950.1.1.5.12.9.3.5.1.1
-- 1.3.6.1.4.1.37950.1.1.5.12.9.3.5.1.1
-- 1.3.6.1.4.1.37950.1.1.5.12.9.3.5.1.1
		-- 1.3.6.1.4.1.37950.1.1.5.12.9.3.5.1.1
		h248UserTidVoipId OBJECT-TYPE
			SYNTAX Integer32 (0..65535)
			MAX-ACCESS read-only
			STATUS current
			DESCRIPTION
				"Description."
			::= { h248UserTidPFEntry 1 }

		
--          1.3.6.1.4.1.37950.1.1.5.12.9.3.5.1.2
-- 1.3.6.1.4.1.37950.1.1.5.12.9.3.5.1.2
-- 1.3.6.1.4.1.37950.1.1.5.12.9.3.5.1.2
-- 1.3.6.1.4.1.37950.1.1.5.12.9.3.5.1.2
-- 1.3.6.1.4.1.37950.1.1.5.12.9.3.5.1.2
-- 1.3.6.1.4.1.37950.1.1.5.12.9.3.5.1.2
-- 1.3.6.1.4.1.37950.1.1.5.12.9.3.5.1.2
-- 1.3.6.1.4.1.37950.1.1.5.12.9.3.5.1.2
-- 1.3.6.1.4.1.37950.1.1.5.12.9.3.5.1.2
		-- 1.3.6.1.4.1.37950.1.1.5.12.9.3.5.1.2
		h248UserTidPotsNoS OBJECT-TYPE
			SYNTAX INTEGER (1..255)
			MAX-ACCESS read-only
			STATUS current
			DESCRIPTION
				"Description."
			::= { h248UserTidPFEntry 2 }

		
--          1.3.6.1.4.1.37950.1.1.5.12.9.3.5.1.3
-- 1.3.6.1.4.1.37950.1.1.5.12.9.3.5.1.3
-- 1.3.6.1.4.1.37950.1.1.5.12.9.3.5.1.3
-- 1.3.6.1.4.1.37950.1.1.5.12.9.3.5.1.3
-- 1.3.6.1.4.1.37950.1.1.5.12.9.3.5.1.3
-- 1.3.6.1.4.1.37950.1.1.5.12.9.3.5.1.3
-- 1.3.6.1.4.1.37950.1.1.5.12.9.3.5.1.3
-- 1.3.6.1.4.1.37950.1.1.5.12.9.3.5.1.3
-- 1.3.6.1.4.1.37950.1.1.5.12.9.3.5.1.3
		-- 1.3.6.1.4.1.37950.1.1.5.12.9.3.5.1.3
		h248UserTidS OBJECT-TYPE
			SYNTAX OCTET STRING
			MAX-ACCESS read-only
			STATUS current
			DESCRIPTION
				"Description."
			::= { h248UserTidPFEntry 3 }

		
--          1.3.6.1.4.1.37950.1.1.5.12.9.3.6
-- 1.3.6.1.4.1.37950.1.1.5.12.9.3.6
-- 1.3.6.1.4.1.37950.1.1.5.12.9.3.6
-- 1.3.6.1.4.1.37950.1.1.5.12.9.3.6
-- 1.3.6.1.4.1.37950.1.1.5.12.9.3.6
-- 1.3.6.1.4.1.37950.1.1.5.12.9.3.6
-- 1.3.6.1.4.1.37950.1.1.5.12.9.3.6
-- 1.3.6.1.4.1.37950.1.1.5.12.9.3.6
-- 1.3.6.1.4.1.37950.1.1.5.12.9.3.6
		-- 1.3.6.1.4.1.37950.1.1.5.12.9.3.6
		sipProPFTable OBJECT-TYPE
			SYNTAX SEQUENCE OF SipProPFEntry
			MAX-ACCESS not-accessible
			STATUS current
			DESCRIPTION
				"Description."
			::= { voipProfileShow 6 }

		
--          1.3.6.1.4.1.37950.1.1.5.12.9.3.6.1
-- 1.3.6.1.4.1.37950.1.1.5.12.9.3.6.1
-- 1.3.6.1.4.1.37950.1.1.5.12.9.3.6.1
-- 1.3.6.1.4.1.37950.1.1.5.12.9.3.6.1
-- 1.3.6.1.4.1.37950.1.1.5.12.9.3.6.1
-- 1.3.6.1.4.1.37950.1.1.5.12.9.3.6.1
-- 1.3.6.1.4.1.37950.1.1.5.12.9.3.6.1
-- 1.3.6.1.4.1.37950.1.1.5.12.9.3.6.1
-- 1.3.6.1.4.1.37950.1.1.5.12.9.3.6.1
		-- 1.3.6.1.4.1.37950.1.1.5.12.9.3.6.1
		sipProPFEntry OBJECT-TYPE
			SYNTAX SipProPFEntry
			MAX-ACCESS not-accessible
			STATUS current
			DESCRIPTION
				"Description."
			INDEX { sipProVoipId }
			::= { sipProPFTable 1 }

		
		SipProPFEntry ::=
			SEQUENCE { 
				sipProVoipId
					Integer32,
				sipProMgPortS
					INTEGER,
				sipProProxySrvIpS
					IpAddress,
				sipProProxySrvPortS
					INTEGER,
				sipProBKProxySrvIpS
					IpAddress,
				sipProBKProxySrvPortS
					INTEGER,
				sipProRegSrvIpS
					OCTET STRING,
				sipProRegSrvPortS
					INTEGER,
				sipProBKRegSrvIpS
					IpAddress,
				sipProBKRegSrvPortS
					INTEGER,
				sipProOutBoundServIpS
					IpAddress,
				sipProOutBoundServPortS
					INTEGER,
				sipProRegInterS
					INTEGER,
				sipProHBEnableS
					INTEGER,
				sipProHBCycleS
					INTEGER,
				sipProHBCountS
					INTEGER
			 }

--          1.3.6.1.4.1.37950.1.1.5.12.9.3.6.1.1
-- 1.3.6.1.4.1.37950.1.1.5.12.9.3.6.1.1
-- 1.3.6.1.4.1.37950.1.1.5.12.9.3.6.1.1
-- 1.3.6.1.4.1.37950.1.1.5.12.9.3.6.1.1
-- 1.3.6.1.4.1.37950.1.1.5.12.9.3.6.1.1
-- 1.3.6.1.4.1.37950.1.1.5.12.9.3.6.1.1
-- 1.3.6.1.4.1.37950.1.1.5.12.9.3.6.1.1
-- 1.3.6.1.4.1.37950.1.1.5.12.9.3.6.1.1
-- 1.3.6.1.4.1.37950.1.1.5.12.9.3.6.1.1
		-- 1.3.6.1.4.1.37950.1.1.5.12.9.3.6.1.1
		sipProVoipId OBJECT-TYPE
			SYNTAX Integer32 (0..65535)
			MAX-ACCESS read-only
			STATUS current
			DESCRIPTION
				"Description."
			::= { sipProPFEntry 1 }

		
--          1.3.6.1.4.1.37950.1.1.5.12.9.3.6.1.2
-- 1.3.6.1.4.1.37950.1.1.5.12.9.3.6.1.2
-- 1.3.6.1.4.1.37950.1.1.5.12.9.3.6.1.2
-- 1.3.6.1.4.1.37950.1.1.5.12.9.3.6.1.2
-- 1.3.6.1.4.1.37950.1.1.5.12.9.3.6.1.2
-- 1.3.6.1.4.1.37950.1.1.5.12.9.3.6.1.2
-- 1.3.6.1.4.1.37950.1.1.5.12.9.3.6.1.2
-- 1.3.6.1.4.1.37950.1.1.5.12.9.3.6.1.2
-- 1.3.6.1.4.1.37950.1.1.5.12.9.3.6.1.2
		-- 1.3.6.1.4.1.37950.1.1.5.12.9.3.6.1.2
		sipProMgPortS OBJECT-TYPE
			SYNTAX INTEGER (1..65535)
			MAX-ACCESS read-only
			STATUS current
			DESCRIPTION
				"Description."
			::= { sipProPFEntry 2 }

		
--          1.3.6.1.4.1.37950.1.1.5.12.9.3.6.1.3
-- 1.3.6.1.4.1.37950.1.1.5.12.9.3.6.1.3
-- 1.3.6.1.4.1.37950.1.1.5.12.9.3.6.1.3
-- 1.3.6.1.4.1.37950.1.1.5.12.9.3.6.1.3
-- 1.3.6.1.4.1.37950.1.1.5.12.9.3.6.1.3
-- 1.3.6.1.4.1.37950.1.1.5.12.9.3.6.1.3
-- 1.3.6.1.4.1.37950.1.1.5.12.9.3.6.1.3
-- 1.3.6.1.4.1.37950.1.1.5.12.9.3.6.1.3
-- 1.3.6.1.4.1.37950.1.1.5.12.9.3.6.1.3
		-- 1.3.6.1.4.1.37950.1.1.5.12.9.3.6.1.3
		sipProProxySrvIpS OBJECT-TYPE
			SYNTAX IpAddress
			MAX-ACCESS read-only
			STATUS current
			DESCRIPTION
				"Description."
			::= { sipProPFEntry 3 }

		
--          1.3.6.1.4.1.37950.1.1.5.12.9.3.6.1.4
-- 1.3.6.1.4.1.37950.1.1.5.12.9.3.6.1.4
-- 1.3.6.1.4.1.37950.1.1.5.12.9.3.6.1.4
-- 1.3.6.1.4.1.37950.1.1.5.12.9.3.6.1.4
-- 1.3.6.1.4.1.37950.1.1.5.12.9.3.6.1.4
-- 1.3.6.1.4.1.37950.1.1.5.12.9.3.6.1.4
-- 1.3.6.1.4.1.37950.1.1.5.12.9.3.6.1.4
-- 1.3.6.1.4.1.37950.1.1.5.12.9.3.6.1.4
-- 1.3.6.1.4.1.37950.1.1.5.12.9.3.6.1.4
		-- 1.3.6.1.4.1.37950.1.1.5.12.9.3.6.1.4
		sipProProxySrvPortS OBJECT-TYPE
			SYNTAX INTEGER (1..65535)
			MAX-ACCESS read-only
			STATUS current
			DESCRIPTION
				"Description."
			::= { sipProPFEntry 4 }

		
--          1.3.6.1.4.1.37950.1.1.5.12.9.3.6.1.5
-- 1.3.6.1.4.1.37950.1.1.5.12.9.3.6.1.5
-- 1.3.6.1.4.1.37950.1.1.5.12.9.3.6.1.5
-- 1.3.6.1.4.1.37950.1.1.5.12.9.3.6.1.5
-- 1.3.6.1.4.1.37950.1.1.5.12.9.3.6.1.5
-- 1.3.6.1.4.1.37950.1.1.5.12.9.3.6.1.5
-- 1.3.6.1.4.1.37950.1.1.5.12.9.3.6.1.5
-- 1.3.6.1.4.1.37950.1.1.5.12.9.3.6.1.5
-- 1.3.6.1.4.1.37950.1.1.5.12.9.3.6.1.5
		-- 1.3.6.1.4.1.37950.1.1.5.12.9.3.6.1.5
		sipProBKProxySrvIpS OBJECT-TYPE
			SYNTAX IpAddress
			MAX-ACCESS read-only
			STATUS current
			DESCRIPTION
				"Description."
			::= { sipProPFEntry 5 }

		
--          1.3.6.1.4.1.37950.1.1.5.12.9.3.6.1.6
-- 1.3.6.1.4.1.37950.1.1.5.12.9.3.6.1.6
-- 1.3.6.1.4.1.37950.1.1.5.12.9.3.6.1.6
-- 1.3.6.1.4.1.37950.1.1.5.12.9.3.6.1.6
-- 1.3.6.1.4.1.37950.1.1.5.12.9.3.6.1.6
-- 1.3.6.1.4.1.37950.1.1.5.12.9.3.6.1.6
-- 1.3.6.1.4.1.37950.1.1.5.12.9.3.6.1.6
-- 1.3.6.1.4.1.37950.1.1.5.12.9.3.6.1.6
-- 1.3.6.1.4.1.37950.1.1.5.12.9.3.6.1.6
		-- 1.3.6.1.4.1.37950.1.1.5.12.9.3.6.1.6
		sipProBKProxySrvPortS OBJECT-TYPE
			SYNTAX INTEGER (0..65535)
			MAX-ACCESS read-only
			STATUS current
			DESCRIPTION
				"Description."
			::= { sipProPFEntry 6 }

		
--          1.3.6.1.4.1.37950.1.1.5.12.9.3.6.1.7
-- 1.3.6.1.4.1.37950.1.1.5.12.9.3.6.1.7
-- 1.3.6.1.4.1.37950.1.1.5.12.9.3.6.1.7
-- 1.3.6.1.4.1.37950.1.1.5.12.9.3.6.1.7
-- 1.3.6.1.4.1.37950.1.1.5.12.9.3.6.1.7
-- 1.3.6.1.4.1.37950.1.1.5.12.9.3.6.1.7
-- 1.3.6.1.4.1.37950.1.1.5.12.9.3.6.1.7
-- 1.3.6.1.4.1.37950.1.1.5.12.9.3.6.1.7
-- 1.3.6.1.4.1.37950.1.1.5.12.9.3.6.1.7
		-- 1.3.6.1.4.1.37950.1.1.5.12.9.3.6.1.7
		sipProRegSrvIpS OBJECT-TYPE
			SYNTAX OCTET STRING
			MAX-ACCESS read-only
			STATUS current
			DESCRIPTION
				"Description."
			::= { sipProPFEntry 7 }

		
--          1.3.6.1.4.1.37950.1.1.5.12.9.3.6.1.8
-- 1.3.6.1.4.1.37950.1.1.5.12.9.3.6.1.8
-- 1.3.6.1.4.1.37950.1.1.5.12.9.3.6.1.8
-- 1.3.6.1.4.1.37950.1.1.5.12.9.3.6.1.8
-- 1.3.6.1.4.1.37950.1.1.5.12.9.3.6.1.8
-- 1.3.6.1.4.1.37950.1.1.5.12.9.3.6.1.8
-- 1.3.6.1.4.1.37950.1.1.5.12.9.3.6.1.8
-- 1.3.6.1.4.1.37950.1.1.5.12.9.3.6.1.8
-- 1.3.6.1.4.1.37950.1.1.5.12.9.3.6.1.8
		-- 1.3.6.1.4.1.37950.1.1.5.12.9.3.6.1.8
		sipProRegSrvPortS OBJECT-TYPE
			SYNTAX INTEGER (1..65535)
			MAX-ACCESS read-only
			STATUS current
			DESCRIPTION
				"Description."
			::= { sipProPFEntry 8 }

		
--          1.3.6.1.4.1.37950.1.1.5.12.9.3.6.1.9
-- 1.3.6.1.4.1.37950.1.1.5.12.9.3.6.1.9
-- 1.3.6.1.4.1.37950.1.1.5.12.9.3.6.1.9
-- 1.3.6.1.4.1.37950.1.1.5.12.9.3.6.1.9
-- 1.3.6.1.4.1.37950.1.1.5.12.9.3.6.1.9
-- 1.3.6.1.4.1.37950.1.1.5.12.9.3.6.1.9
-- 1.3.6.1.4.1.37950.1.1.5.12.9.3.6.1.9
-- 1.3.6.1.4.1.37950.1.1.5.12.9.3.6.1.9
-- 1.3.6.1.4.1.37950.1.1.5.12.9.3.6.1.9
		-- 1.3.6.1.4.1.37950.1.1.5.12.9.3.6.1.9
		sipProBKRegSrvIpS OBJECT-TYPE
			SYNTAX IpAddress
			MAX-ACCESS read-only
			STATUS current
			DESCRIPTION
				"Description."
			::= { sipProPFEntry 9 }

		
--          1.3.6.1.4.1.37950.1.1.5.12.9.3.6.1.10
-- 1.3.6.1.4.1.37950.1.1.5.12.9.3.6.1.10
-- 1.3.6.1.4.1.37950.1.1.5.12.9.3.6.1.10
-- 1.3.6.1.4.1.37950.1.1.5.12.9.3.6.1.10
-- 1.3.6.1.4.1.37950.1.1.5.12.9.3.6.1.10
-- 1.3.6.1.4.1.37950.1.1.5.12.9.3.6.1.10
-- 1.3.6.1.4.1.37950.1.1.5.12.9.3.6.1.10
-- 1.3.6.1.4.1.37950.1.1.5.12.9.3.6.1.10
-- 1.3.6.1.4.1.37950.1.1.5.12.9.3.6.1.10
		-- 1.3.6.1.4.1.37950.1.1.5.12.9.3.6.1.10
		sipProBKRegSrvPortS OBJECT-TYPE
			SYNTAX INTEGER (0..65535)
			MAX-ACCESS read-only
			STATUS current
			DESCRIPTION
				"Description."
			::= { sipProPFEntry 10 }

		
--          1.3.6.1.4.1.37950.1.1.5.12.9.3.6.1.11
-- 1.3.6.1.4.1.37950.1.1.5.12.9.3.6.1.11
-- 1.3.6.1.4.1.37950.1.1.5.12.9.3.6.1.11
-- 1.3.6.1.4.1.37950.1.1.5.12.9.3.6.1.11
-- 1.3.6.1.4.1.37950.1.1.5.12.9.3.6.1.11
-- 1.3.6.1.4.1.37950.1.1.5.12.9.3.6.1.11
-- 1.3.6.1.4.1.37950.1.1.5.12.9.3.6.1.11
-- 1.3.6.1.4.1.37950.1.1.5.12.9.3.6.1.11
-- 1.3.6.1.4.1.37950.1.1.5.12.9.3.6.1.11
		-- 1.3.6.1.4.1.37950.1.1.5.12.9.3.6.1.11
		sipProOutBoundServIpS OBJECT-TYPE
			SYNTAX IpAddress
			MAX-ACCESS read-only
			STATUS current
			DESCRIPTION
				"Description."
			::= { sipProPFEntry 11 }

		
--          1.3.6.1.4.1.37950.1.1.5.12.9.3.6.1.12
-- 1.3.6.1.4.1.37950.1.1.5.12.9.3.6.1.12
-- 1.3.6.1.4.1.37950.1.1.5.12.9.3.6.1.12
-- 1.3.6.1.4.1.37950.1.1.5.12.9.3.6.1.12
-- 1.3.6.1.4.1.37950.1.1.5.12.9.3.6.1.12
-- 1.3.6.1.4.1.37950.1.1.5.12.9.3.6.1.12
-- 1.3.6.1.4.1.37950.1.1.5.12.9.3.6.1.12
-- 1.3.6.1.4.1.37950.1.1.5.12.9.3.6.1.12
-- 1.3.6.1.4.1.37950.1.1.5.12.9.3.6.1.12
		-- 1.3.6.1.4.1.37950.1.1.5.12.9.3.6.1.12
		sipProOutBoundServPortS OBJECT-TYPE
			SYNTAX INTEGER (1..65535)
			MAX-ACCESS read-only
			STATUS current
			DESCRIPTION
				"Description."
			::= { sipProPFEntry 12 }

		
--          1.3.6.1.4.1.37950.1.1.5.12.9.3.6.1.13
-- 1.3.6.1.4.1.37950.1.1.5.12.9.3.6.1.13
-- 1.3.6.1.4.1.37950.1.1.5.12.9.3.6.1.13
-- 1.3.6.1.4.1.37950.1.1.5.12.9.3.6.1.13
-- 1.3.6.1.4.1.37950.1.1.5.12.9.3.6.1.13
-- 1.3.6.1.4.1.37950.1.1.5.12.9.3.6.1.13
-- 1.3.6.1.4.1.37950.1.1.5.12.9.3.6.1.13
-- 1.3.6.1.4.1.37950.1.1.5.12.9.3.6.1.13
-- 1.3.6.1.4.1.37950.1.1.5.12.9.3.6.1.13
		-- 1.3.6.1.4.1.37950.1.1.5.12.9.3.6.1.13
		sipProRegInterS OBJECT-TYPE
			SYNTAX INTEGER (0..65535)
			MAX-ACCESS read-only
			STATUS current
			DESCRIPTION
				"Description."
			::= { sipProPFEntry 13 }

		
--          1.3.6.1.4.1.37950.1.1.5.12.9.3.6.1.14
-- 1.3.6.1.4.1.37950.1.1.5.12.9.3.6.1.14
-- 1.3.6.1.4.1.37950.1.1.5.12.9.3.6.1.14
-- 1.3.6.1.4.1.37950.1.1.5.12.9.3.6.1.14
-- 1.3.6.1.4.1.37950.1.1.5.12.9.3.6.1.14
-- 1.3.6.1.4.1.37950.1.1.5.12.9.3.6.1.14
-- 1.3.6.1.4.1.37950.1.1.5.12.9.3.6.1.14
-- 1.3.6.1.4.1.37950.1.1.5.12.9.3.6.1.14
-- 1.3.6.1.4.1.37950.1.1.5.12.9.3.6.1.14
		-- 1.3.6.1.4.1.37950.1.1.5.12.9.3.6.1.14
		sipProHBEnableS OBJECT-TYPE
			SYNTAX INTEGER
				{
				disable(0),
				enable(1)
				}
			MAX-ACCESS read-only
			STATUS current
			DESCRIPTION
				"Description."
			::= { sipProPFEntry 14 }

		
--          1.3.6.1.4.1.37950.1.1.5.12.9.3.6.1.15
-- 1.3.6.1.4.1.37950.1.1.5.12.9.3.6.1.15
-- 1.3.6.1.4.1.37950.1.1.5.12.9.3.6.1.15
-- 1.3.6.1.4.1.37950.1.1.5.12.9.3.6.1.15
-- 1.3.6.1.4.1.37950.1.1.5.12.9.3.6.1.15
-- 1.3.6.1.4.1.37950.1.1.5.12.9.3.6.1.15
-- 1.3.6.1.4.1.37950.1.1.5.12.9.3.6.1.15
-- 1.3.6.1.4.1.37950.1.1.5.12.9.3.6.1.15
-- 1.3.6.1.4.1.37950.1.1.5.12.9.3.6.1.15
		-- 1.3.6.1.4.1.37950.1.1.5.12.9.3.6.1.15
		sipProHBCycleS OBJECT-TYPE
			SYNTAX INTEGER (1..65535)
			MAX-ACCESS read-only
			STATUS current
			DESCRIPTION
				"Description."
			::= { sipProPFEntry 15 }

		
--          1.3.6.1.4.1.37950.1.1.5.12.9.3.6.1.16
-- 1.3.6.1.4.1.37950.1.1.5.12.9.3.6.1.16
-- 1.3.6.1.4.1.37950.1.1.5.12.9.3.6.1.16
-- 1.3.6.1.4.1.37950.1.1.5.12.9.3.6.1.16
-- 1.3.6.1.4.1.37950.1.1.5.12.9.3.6.1.16
-- 1.3.6.1.4.1.37950.1.1.5.12.9.3.6.1.16
-- 1.3.6.1.4.1.37950.1.1.5.12.9.3.6.1.16
-- 1.3.6.1.4.1.37950.1.1.5.12.9.3.6.1.16
-- 1.3.6.1.4.1.37950.1.1.5.12.9.3.6.1.16
		-- 1.3.6.1.4.1.37950.1.1.5.12.9.3.6.1.16
		sipProHBCountS OBJECT-TYPE
			SYNTAX INTEGER (1..65535)
			MAX-ACCESS read-only
			STATUS current
			DESCRIPTION
				"Description."
			::= { sipProPFEntry 16 }

		
--          1.3.6.1.4.1.37950.1.1.5.12.9.3.7
-- 1.3.6.1.4.1.37950.1.1.5.12.9.3.7
-- 1.3.6.1.4.1.37950.1.1.5.12.9.3.7
-- 1.3.6.1.4.1.37950.1.1.5.12.9.3.7
-- 1.3.6.1.4.1.37950.1.1.5.12.9.3.7
-- 1.3.6.1.4.1.37950.1.1.5.12.9.3.7
-- 1.3.6.1.4.1.37950.1.1.5.12.9.3.7
-- 1.3.6.1.4.1.37950.1.1.5.12.9.3.7
-- 1.3.6.1.4.1.37950.1.1.5.12.9.3.7
		-- 1.3.6.1.4.1.37950.1.1.5.12.9.3.7
		sipUserPFTable OBJECT-TYPE
			SYNTAX SEQUENCE OF SipUserPFEntry
			MAX-ACCESS not-accessible
			STATUS current
			DESCRIPTION
				"Description."
			::= { voipProfileShow 7 }

		
--          1.3.6.1.4.1.37950.1.1.5.12.9.3.7.1
-- 1.3.6.1.4.1.37950.1.1.5.12.9.3.7.1
-- 1.3.6.1.4.1.37950.1.1.5.12.9.3.7.1
-- 1.3.6.1.4.1.37950.1.1.5.12.9.3.7.1
-- 1.3.6.1.4.1.37950.1.1.5.12.9.3.7.1
-- 1.3.6.1.4.1.37950.1.1.5.12.9.3.7.1
-- 1.3.6.1.4.1.37950.1.1.5.12.9.3.7.1
-- 1.3.6.1.4.1.37950.1.1.5.12.9.3.7.1
-- 1.3.6.1.4.1.37950.1.1.5.12.9.3.7.1
		-- 1.3.6.1.4.1.37950.1.1.5.12.9.3.7.1
		sipUserPFEntry OBJECT-TYPE
			SYNTAX SipUserPFEntry
			MAX-ACCESS not-accessible
			STATUS current
			DESCRIPTION
				"Description."
			INDEX { sipUserVoipId, sipUserPotsNoS }
			::= { sipUserPFTable 1 }

		
		SipUserPFEntry ::=
			SEQUENCE { 
				sipUserVoipId
					Integer32,
				sipUserPotsNoS
					INTEGER,
				sipUserAccountS
					OCTET STRING,
				sipUserNameS
					OCTET STRING,
				sipUserPwS
					OCTET STRING
			 }

--          1.3.6.1.4.1.37950.1.1.5.12.9.3.7.1.1
-- 1.3.6.1.4.1.37950.1.1.5.12.9.3.7.1.1
-- 1.3.6.1.4.1.37950.1.1.5.12.9.3.7.1.1
-- 1.3.6.1.4.1.37950.1.1.5.12.9.3.7.1.1
-- 1.3.6.1.4.1.37950.1.1.5.12.9.3.7.1.1
-- 1.3.6.1.4.1.37950.1.1.5.12.9.3.7.1.1
-- 1.3.6.1.4.1.37950.1.1.5.12.9.3.7.1.1
-- 1.3.6.1.4.1.37950.1.1.5.12.9.3.7.1.1
-- 1.3.6.1.4.1.37950.1.1.5.12.9.3.7.1.1
		-- 1.3.6.1.4.1.37950.1.1.5.12.9.3.7.1.1
		sipUserVoipId OBJECT-TYPE
			SYNTAX Integer32 (0..65535)
			MAX-ACCESS read-only
			STATUS current
			DESCRIPTION
				"Description."
			::= { sipUserPFEntry 1 }

		
--          1.3.6.1.4.1.37950.1.1.5.12.9.3.7.1.2
-- 1.3.6.1.4.1.37950.1.1.5.12.9.3.7.1.2
-- 1.3.6.1.4.1.37950.1.1.5.12.9.3.7.1.2
-- 1.3.6.1.4.1.37950.1.1.5.12.9.3.7.1.2
-- 1.3.6.1.4.1.37950.1.1.5.12.9.3.7.1.2
-- 1.3.6.1.4.1.37950.1.1.5.12.9.3.7.1.2
-- 1.3.6.1.4.1.37950.1.1.5.12.9.3.7.1.2
-- 1.3.6.1.4.1.37950.1.1.5.12.9.3.7.1.2
-- 1.3.6.1.4.1.37950.1.1.5.12.9.3.7.1.2
		-- 1.3.6.1.4.1.37950.1.1.5.12.9.3.7.1.2
		sipUserPotsNoS OBJECT-TYPE
			SYNTAX INTEGER (1..255)
			MAX-ACCESS read-only
			STATUS current
			DESCRIPTION
				"Description."
			::= { sipUserPFEntry 2 }

		
--          1.3.6.1.4.1.37950.1.1.5.12.9.3.7.1.3
-- 1.3.6.1.4.1.37950.1.1.5.12.9.3.7.1.3
-- 1.3.6.1.4.1.37950.1.1.5.12.9.3.7.1.3
-- 1.3.6.1.4.1.37950.1.1.5.12.9.3.7.1.3
-- 1.3.6.1.4.1.37950.1.1.5.12.9.3.7.1.3
-- 1.3.6.1.4.1.37950.1.1.5.12.9.3.7.1.3
-- 1.3.6.1.4.1.37950.1.1.5.12.9.3.7.1.3
-- 1.3.6.1.4.1.37950.1.1.5.12.9.3.7.1.3
-- 1.3.6.1.4.1.37950.1.1.5.12.9.3.7.1.3
		-- 1.3.6.1.4.1.37950.1.1.5.12.9.3.7.1.3
		sipUserAccountS OBJECT-TYPE
			SYNTAX OCTET STRING
			MAX-ACCESS read-only
			STATUS current
			DESCRIPTION
				"Description."
			::= { sipUserPFEntry 3 }

		
--          1.3.6.1.4.1.37950.1.1.5.12.9.3.7.1.4
-- 1.3.6.1.4.1.37950.1.1.5.12.9.3.7.1.4
-- 1.3.6.1.4.1.37950.1.1.5.12.9.3.7.1.4
-- 1.3.6.1.4.1.37950.1.1.5.12.9.3.7.1.4
-- 1.3.6.1.4.1.37950.1.1.5.12.9.3.7.1.4
-- 1.3.6.1.4.1.37950.1.1.5.12.9.3.7.1.4
-- 1.3.6.1.4.1.37950.1.1.5.12.9.3.7.1.4
-- 1.3.6.1.4.1.37950.1.1.5.12.9.3.7.1.4
-- 1.3.6.1.4.1.37950.1.1.5.12.9.3.7.1.4
		-- 1.3.6.1.4.1.37950.1.1.5.12.9.3.7.1.4
		sipUserNameS OBJECT-TYPE
			SYNTAX OCTET STRING
			MAX-ACCESS read-only
			STATUS current
			DESCRIPTION
				"Description."
			::= { sipUserPFEntry 4 }

		
--          1.3.6.1.4.1.37950.1.1.5.12.9.3.7.1.5
-- 1.3.6.1.4.1.37950.1.1.5.12.9.3.7.1.5
-- 1.3.6.1.4.1.37950.1.1.5.12.9.3.7.1.5
-- 1.3.6.1.4.1.37950.1.1.5.12.9.3.7.1.5
-- 1.3.6.1.4.1.37950.1.1.5.12.9.3.7.1.5
-- 1.3.6.1.4.1.37950.1.1.5.12.9.3.7.1.5
-- 1.3.6.1.4.1.37950.1.1.5.12.9.3.7.1.5
-- 1.3.6.1.4.1.37950.1.1.5.12.9.3.7.1.5
-- 1.3.6.1.4.1.37950.1.1.5.12.9.3.7.1.5
		-- 1.3.6.1.4.1.37950.1.1.5.12.9.3.7.1.5
		sipUserPwS OBJECT-TYPE
			SYNTAX OCTET STRING
			MAX-ACCESS read-only
			STATUS current
			DESCRIPTION
				"Description."
			::= { sipUserPFEntry 5 }

		
--          1.3.6.1.4.1.37950.1.1.5.12.9.3.8
-- 1.3.6.1.4.1.37950.1.1.5.12.9.3.8
-- 1.3.6.1.4.1.37950.1.1.5.12.9.3.8
-- 1.3.6.1.4.1.37950.1.1.5.12.9.3.8
-- 1.3.6.1.4.1.37950.1.1.5.12.9.3.8
-- 1.3.6.1.4.1.37950.1.1.5.12.9.3.8
-- 1.3.6.1.4.1.37950.1.1.5.12.9.3.8
-- 1.3.6.1.4.1.37950.1.1.5.12.9.3.8
-- 1.3.6.1.4.1.37950.1.1.5.12.9.3.8
		-- 1.3.6.1.4.1.37950.1.1.5.12.9.3.8
		sipDigitPFTable OBJECT-TYPE
			SYNTAX SEQUENCE OF SipDigitPFEntry
			MAX-ACCESS not-accessible
			STATUS current
			DESCRIPTION
				"Description."
			::= { voipProfileShow 8 }

		
--          1.3.6.1.4.1.37950.1.1.5.12.9.3.8.1
-- 1.3.6.1.4.1.37950.1.1.5.12.9.3.8.1
-- 1.3.6.1.4.1.37950.1.1.5.12.9.3.8.1
-- 1.3.6.1.4.1.37950.1.1.5.12.9.3.8.1
-- 1.3.6.1.4.1.37950.1.1.5.12.9.3.8.1
-- 1.3.6.1.4.1.37950.1.1.5.12.9.3.8.1
-- 1.3.6.1.4.1.37950.1.1.5.12.9.3.8.1
-- 1.3.6.1.4.1.37950.1.1.5.12.9.3.8.1
-- 1.3.6.1.4.1.37950.1.1.5.12.9.3.8.1
		-- 1.3.6.1.4.1.37950.1.1.5.12.9.3.8.1
		sipDigitPFEntry OBJECT-TYPE
			SYNTAX SipDigitPFEntry
			MAX-ACCESS not-accessible
			STATUS current
			DESCRIPTION
				"Description."
			INDEX { sipDigitVoipID }
			::= { sipDigitPFTable 1 }

		
		SipDigitPFEntry ::=
			SEQUENCE { 
				sipDigitVoipID
					Integer32,
				sipDigitNumS
					INTEGER,
				sipDigitNumBlockS
					INTEGER,
				sipDigitMapS
					OCTET STRING
			 }

--          1.3.6.1.4.1.37950.1.1.5.12.9.3.8.1.1
-- 1.3.6.1.4.1.37950.1.1.5.12.9.3.8.1.1
-- 1.3.6.1.4.1.37950.1.1.5.12.9.3.8.1.1
-- 1.3.6.1.4.1.37950.1.1.5.12.9.3.8.1.1
-- 1.3.6.1.4.1.37950.1.1.5.12.9.3.8.1.1
-- 1.3.6.1.4.1.37950.1.1.5.12.9.3.8.1.1
-- 1.3.6.1.4.1.37950.1.1.5.12.9.3.8.1.1
-- 1.3.6.1.4.1.37950.1.1.5.12.9.3.8.1.1
-- 1.3.6.1.4.1.37950.1.1.5.12.9.3.8.1.1
		-- 1.3.6.1.4.1.37950.1.1.5.12.9.3.8.1.1
		sipDigitVoipID OBJECT-TYPE
			SYNTAX Integer32 (0..65535)
			MAX-ACCESS read-only
			STATUS current
			DESCRIPTION
				"Description."
			::= { sipDigitPFEntry 1 }

		
--          1.3.6.1.4.1.37950.1.1.5.12.9.3.8.1.2
-- 1.3.6.1.4.1.37950.1.1.5.12.9.3.8.1.2
-- 1.3.6.1.4.1.37950.1.1.5.12.9.3.8.1.2
-- 1.3.6.1.4.1.37950.1.1.5.12.9.3.8.1.2
-- 1.3.6.1.4.1.37950.1.1.5.12.9.3.8.1.2
-- 1.3.6.1.4.1.37950.1.1.5.12.9.3.8.1.2
-- 1.3.6.1.4.1.37950.1.1.5.12.9.3.8.1.2
-- 1.3.6.1.4.1.37950.1.1.5.12.9.3.8.1.2
-- 1.3.6.1.4.1.37950.1.1.5.12.9.3.8.1.2
		-- 1.3.6.1.4.1.37950.1.1.5.12.9.3.8.1.2
		sipDigitNumS OBJECT-TYPE
			SYNTAX INTEGER (0..255)
			MAX-ACCESS read-only
			STATUS current
			DESCRIPTION
				"Description."
			::= { sipDigitPFEntry 2 }

		
--          1.3.6.1.4.1.37950.1.1.5.12.9.3.8.1.3
-- 1.3.6.1.4.1.37950.1.1.5.12.9.3.8.1.3
-- 1.3.6.1.4.1.37950.1.1.5.12.9.3.8.1.3
-- 1.3.6.1.4.1.37950.1.1.5.12.9.3.8.1.3
-- 1.3.6.1.4.1.37950.1.1.5.12.9.3.8.1.3
-- 1.3.6.1.4.1.37950.1.1.5.12.9.3.8.1.3
-- 1.3.6.1.4.1.37950.1.1.5.12.9.3.8.1.3
-- 1.3.6.1.4.1.37950.1.1.5.12.9.3.8.1.3
-- 1.3.6.1.4.1.37950.1.1.5.12.9.3.8.1.3
		-- 1.3.6.1.4.1.37950.1.1.5.12.9.3.8.1.3
		sipDigitNumBlockS OBJECT-TYPE
			SYNTAX INTEGER (0..255)
			MAX-ACCESS read-only
			STATUS current
			DESCRIPTION
				"Description."
			::= { sipDigitPFEntry 3 }

		
--          1.3.6.1.4.1.37950.1.1.5.12.9.3.8.1.4
-- 1.3.6.1.4.1.37950.1.1.5.12.9.3.8.1.4
-- 1.3.6.1.4.1.37950.1.1.5.12.9.3.8.1.4
-- 1.3.6.1.4.1.37950.1.1.5.12.9.3.8.1.4
-- 1.3.6.1.4.1.37950.1.1.5.12.9.3.8.1.4
-- 1.3.6.1.4.1.37950.1.1.5.12.9.3.8.1.4
-- 1.3.6.1.4.1.37950.1.1.5.12.9.3.8.1.4
-- 1.3.6.1.4.1.37950.1.1.5.12.9.3.8.1.4
-- 1.3.6.1.4.1.37950.1.1.5.12.9.3.8.1.4
		-- 1.3.6.1.4.1.37950.1.1.5.12.9.3.8.1.4
		sipDigitMapS OBJECT-TYPE
			SYNTAX OCTET STRING
			MAX-ACCESS read-only
			STATUS current
			DESCRIPTION
				"Description."
			::= { sipDigitPFEntry 4 }

		
--          1.3.6.1.4.1.37950.1.1.5.12.9.3.9
-- 1.3.6.1.4.1.37950.1.1.5.12.9.3.9
-- 1.3.6.1.4.1.37950.1.1.5.12.9.3.9
-- 1.3.6.1.4.1.37950.1.1.5.12.9.3.9
-- 1.3.6.1.4.1.37950.1.1.5.12.9.3.9
-- 1.3.6.1.4.1.37950.1.1.5.12.9.3.9
-- 1.3.6.1.4.1.37950.1.1.5.12.9.3.9
-- 1.3.6.1.4.1.37950.1.1.5.12.9.3.9
-- 1.3.6.1.4.1.37950.1.1.5.12.9.3.9
		-- 1.3.6.1.4.1.37950.1.1.5.12.9.3.9
		voipFaxModemPFTable OBJECT-TYPE
			SYNTAX SEQUENCE OF VoipFaxModemPFEntry
			MAX-ACCESS not-accessible
			STATUS current
			DESCRIPTION
				"Description."
			::= { voipProfileShow 9 }

		
--          1.3.6.1.4.1.37950.1.1.5.12.9.3.9.1
-- 1.3.6.1.4.1.37950.1.1.5.12.9.3.9.1
-- 1.3.6.1.4.1.37950.1.1.5.12.9.3.9.1
-- 1.3.6.1.4.1.37950.1.1.5.12.9.3.9.1
-- 1.3.6.1.4.1.37950.1.1.5.12.9.3.9.1
-- 1.3.6.1.4.1.37950.1.1.5.12.9.3.9.1
-- 1.3.6.1.4.1.37950.1.1.5.12.9.3.9.1
-- 1.3.6.1.4.1.37950.1.1.5.12.9.3.9.1
-- 1.3.6.1.4.1.37950.1.1.5.12.9.3.9.1
		-- 1.3.6.1.4.1.37950.1.1.5.12.9.3.9.1
		voipFaxModemPFEntry OBJECT-TYPE
			SYNTAX VoipFaxModemPFEntry
			MAX-ACCESS not-accessible
			STATUS current
			DESCRIPTION
				"Description."
			INDEX { voipFaxModemVoipId }
			::= { voipFaxModemPFTable 1 }

		
		VoipFaxModemPFEntry ::=
			SEQUENCE { 
				voipFaxModemVoipId
					Integer32,
				voipFaxModemT38EnS
					INTEGER,
				voipFaxModemControlS
					INTEGER
			 }

--          1.3.6.1.4.1.37950.1.1.5.12.9.3.9.1.1
-- 1.3.6.1.4.1.37950.1.1.5.12.9.3.9.1.1
-- 1.3.6.1.4.1.37950.1.1.5.12.9.3.9.1.1
-- 1.3.6.1.4.1.37950.1.1.5.12.9.3.9.1.1
-- 1.3.6.1.4.1.37950.1.1.5.12.9.3.9.1.1
-- 1.3.6.1.4.1.37950.1.1.5.12.9.3.9.1.1
-- 1.3.6.1.4.1.37950.1.1.5.12.9.3.9.1.1
-- 1.3.6.1.4.1.37950.1.1.5.12.9.3.9.1.1
-- 1.3.6.1.4.1.37950.1.1.5.12.9.3.9.1.1
		-- 1.3.6.1.4.1.37950.1.1.5.12.9.3.9.1.1
		voipFaxModemVoipId OBJECT-TYPE
			SYNTAX Integer32 (0..65535)
			MAX-ACCESS read-only
			STATUS current
			DESCRIPTION
				"Description."
			::= { voipFaxModemPFEntry 1 }

		
--          1.3.6.1.4.1.37950.1.1.5.12.9.3.9.1.2
-- 1.3.6.1.4.1.37950.1.1.5.12.9.3.9.1.2
-- 1.3.6.1.4.1.37950.1.1.5.12.9.3.9.1.2
-- 1.3.6.1.4.1.37950.1.1.5.12.9.3.9.1.2
-- 1.3.6.1.4.1.37950.1.1.5.12.9.3.9.1.2
-- 1.3.6.1.4.1.37950.1.1.5.12.9.3.9.1.2
-- 1.3.6.1.4.1.37950.1.1.5.12.9.3.9.1.2
-- 1.3.6.1.4.1.37950.1.1.5.12.9.3.9.1.2
-- 1.3.6.1.4.1.37950.1.1.5.12.9.3.9.1.2
		-- 1.3.6.1.4.1.37950.1.1.5.12.9.3.9.1.2
		voipFaxModemT38EnS OBJECT-TYPE
			SYNTAX INTEGER
				{
				disable(0),
				enable(1)
				}
			MAX-ACCESS read-only
			STATUS current
			DESCRIPTION
				"Description."
			::= { voipFaxModemPFEntry 2 }

		
--          1.3.6.1.4.1.37950.1.1.5.12.9.3.9.1.3
-- 1.3.6.1.4.1.37950.1.1.5.12.9.3.9.1.3
-- 1.3.6.1.4.1.37950.1.1.5.12.9.3.9.1.3
-- 1.3.6.1.4.1.37950.1.1.5.12.9.3.9.1.3
-- 1.3.6.1.4.1.37950.1.1.5.12.9.3.9.1.3
-- 1.3.6.1.4.1.37950.1.1.5.12.9.3.9.1.3
-- 1.3.6.1.4.1.37950.1.1.5.12.9.3.9.1.3
-- 1.3.6.1.4.1.37950.1.1.5.12.9.3.9.1.3
-- 1.3.6.1.4.1.37950.1.1.5.12.9.3.9.1.3
		-- 1.3.6.1.4.1.37950.1.1.5.12.9.3.9.1.3
		voipFaxModemControlS OBJECT-TYPE
			SYNTAX INTEGER
				{
				negotiation(1),
				auto-vbd(2)
				}
			MAX-ACCESS read-only
			STATUS current
			DESCRIPTION
				"Description."
			::= { voipFaxModemPFEntry 3 }

		
--          1.3.6.1.4.1.37950.1.1.5.12.9.3.10
-- 1.3.6.1.4.1.37950.1.1.5.12.9.3.10
-- 1.3.6.1.4.1.37950.1.1.5.12.9.3.10
-- 1.3.6.1.4.1.37950.1.1.5.12.9.3.10
-- 1.3.6.1.4.1.37950.1.1.5.12.9.3.10
-- 1.3.6.1.4.1.37950.1.1.5.12.9.3.10
-- 1.3.6.1.4.1.37950.1.1.5.12.9.3.10
-- 1.3.6.1.4.1.37950.1.1.5.12.9.3.10
-- 1.3.6.1.4.1.37950.1.1.5.12.9.3.10
		-- 1.3.6.1.4.1.37950.1.1.5.12.9.3.10
		voipPotsManagePFTable OBJECT-TYPE
			SYNTAX SEQUENCE OF VoipPotsManagePFEntry
			MAX-ACCESS not-accessible
			STATUS current
			DESCRIPTION
				"Description."
			::= { voipProfileShow 10 }

		
--          1.3.6.1.4.1.37950.1.1.5.12.9.3.10.1
-- 1.3.6.1.4.1.37950.1.1.5.12.9.3.10.1
-- 1.3.6.1.4.1.37950.1.1.5.12.9.3.10.1
-- 1.3.6.1.4.1.37950.1.1.5.12.9.3.10.1
-- 1.3.6.1.4.1.37950.1.1.5.12.9.3.10.1
-- 1.3.6.1.4.1.37950.1.1.5.12.9.3.10.1
-- 1.3.6.1.4.1.37950.1.1.5.12.9.3.10.1
-- 1.3.6.1.4.1.37950.1.1.5.12.9.3.10.1
-- 1.3.6.1.4.1.37950.1.1.5.12.9.3.10.1
		-- 1.3.6.1.4.1.37950.1.1.5.12.9.3.10.1
		voipPotsManagePFEntry OBJECT-TYPE
			SYNTAX VoipPotsManagePFEntry
			MAX-ACCESS not-accessible
			STATUS current
			DESCRIPTION
				"Description."
			INDEX { voipPotsManageVoipId, voipPotsManagNoS }
			::= { voipPotsManagePFTable 1 }

		
		VoipPotsManagePFEntry ::=
			SEQUENCE { 
				voipPotsManageVoipId
					Integer32,
				voipPotsManagNoS
					INTEGER,
				voipPotsManageEnableS
					INTEGER
			 }

--          1.3.6.1.4.1.37950.1.1.5.12.9.3.10.1.1
-- 1.3.6.1.4.1.37950.1.1.5.12.9.3.10.1.1
-- 1.3.6.1.4.1.37950.1.1.5.12.9.3.10.1.1
-- 1.3.6.1.4.1.37950.1.1.5.12.9.3.10.1.1
-- 1.3.6.1.4.1.37950.1.1.5.12.9.3.10.1.1
-- 1.3.6.1.4.1.37950.1.1.5.12.9.3.10.1.1
-- 1.3.6.1.4.1.37950.1.1.5.12.9.3.10.1.1
-- 1.3.6.1.4.1.37950.1.1.5.12.9.3.10.1.1
-- 1.3.6.1.4.1.37950.1.1.5.12.9.3.10.1.1
		-- 1.3.6.1.4.1.37950.1.1.5.12.9.3.10.1.1
		voipPotsManageVoipId OBJECT-TYPE
			SYNTAX Integer32 (0..65535)
			MAX-ACCESS read-only
			STATUS current
			DESCRIPTION
				"Description."
			::= { voipPotsManagePFEntry 1 }

		
--          1.3.6.1.4.1.37950.1.1.5.12.9.3.10.1.2
-- 1.3.6.1.4.1.37950.1.1.5.12.9.3.10.1.2
-- 1.3.6.1.4.1.37950.1.1.5.12.9.3.10.1.2
-- 1.3.6.1.4.1.37950.1.1.5.12.9.3.10.1.2
-- 1.3.6.1.4.1.37950.1.1.5.12.9.3.10.1.2
-- 1.3.6.1.4.1.37950.1.1.5.12.9.3.10.1.2
-- 1.3.6.1.4.1.37950.1.1.5.12.9.3.10.1.2
-- 1.3.6.1.4.1.37950.1.1.5.12.9.3.10.1.2
-- 1.3.6.1.4.1.37950.1.1.5.12.9.3.10.1.2
		-- 1.3.6.1.4.1.37950.1.1.5.12.9.3.10.1.2
		voipPotsManagNoS OBJECT-TYPE
			SYNTAX INTEGER (1..255)
			MAX-ACCESS read-only
			STATUS current
			DESCRIPTION
				"Description."
			::= { voipPotsManagePFEntry 2 }

		
--          1.3.6.1.4.1.37950.1.1.5.12.9.3.10.1.3
-- 1.3.6.1.4.1.37950.1.1.5.12.9.3.10.1.3
-- 1.3.6.1.4.1.37950.1.1.5.12.9.3.10.1.3
-- 1.3.6.1.4.1.37950.1.1.5.12.9.3.10.1.3
-- 1.3.6.1.4.1.37950.1.1.5.12.9.3.10.1.3
-- 1.3.6.1.4.1.37950.1.1.5.12.9.3.10.1.3
-- 1.3.6.1.4.1.37950.1.1.5.12.9.3.10.1.3
-- 1.3.6.1.4.1.37950.1.1.5.12.9.3.10.1.3
-- 1.3.6.1.4.1.37950.1.1.5.12.9.3.10.1.3
		-- 1.3.6.1.4.1.37950.1.1.5.12.9.3.10.1.3
		voipPotsManageEnableS OBJECT-TYPE
			SYNTAX INTEGER
				{
				disable(0),
				enable(1)
				}
			MAX-ACCESS read-only
			STATUS current
			DESCRIPTION
				"Description."
			::= { voipPotsManagePFEntry 3 }

		
--          1.3.6.1.4.1.37950.1.1.5.12.9.3.11
-- 1.3.6.1.4.1.37950.1.1.5.12.9.3.11
-- 1.3.6.1.4.1.37950.1.1.5.12.9.3.11
-- 1.3.6.1.4.1.37950.1.1.5.12.9.3.11
-- 1.3.6.1.4.1.37950.1.1.5.12.9.3.11
-- 1.3.6.1.4.1.37950.1.1.5.12.9.3.11
-- 1.3.6.1.4.1.37950.1.1.5.12.9.3.11
-- 1.3.6.1.4.1.37950.1.1.5.12.9.3.11
-- 1.3.6.1.4.1.37950.1.1.5.12.9.3.11
		-- 1.3.6.1.4.1.37950.1.1.5.12.9.3.11
		voipTimerTable OBJECT-TYPE
			SYNTAX SEQUENCE OF VoipTimerEntry
			MAX-ACCESS not-accessible
			STATUS current
			DESCRIPTION
				"Description."
			::= { voipProfileShow 11 }

		
--          1.3.6.1.4.1.37950.1.1.5.12.9.3.11.1
-- 1.3.6.1.4.1.37950.1.1.5.12.9.3.11.1
-- 1.3.6.1.4.1.37950.1.1.5.12.9.3.11.1
-- 1.3.6.1.4.1.37950.1.1.5.12.9.3.11.1
-- 1.3.6.1.4.1.37950.1.1.5.12.9.3.11.1
-- 1.3.6.1.4.1.37950.1.1.5.12.9.3.11.1
-- 1.3.6.1.4.1.37950.1.1.5.12.9.3.11.1
-- 1.3.6.1.4.1.37950.1.1.5.12.9.3.11.1
-- 1.3.6.1.4.1.37950.1.1.5.12.9.3.11.1
		-- 1.3.6.1.4.1.37950.1.1.5.12.9.3.11.1
		voipTimerEntry OBJECT-TYPE
			SYNTAX VoipTimerEntry
			MAX-ACCESS not-accessible
			STATUS current
			DESCRIPTION
				"Description."
			INDEX { voipTimerPfId }
			::= { voipTimerTable 1 }

		
		VoipTimerEntry ::=
			SEQUENCE { 
				voipTimerPfId
					Integer32,
				voipMaxWaitTime
					Integer32,
				voipStartTimer
					Integer32,
				voipLongTimer
					Integer32,
				voipShortTimer
					Integer32,
				voipDigitMapNotify
					INTEGER
			 }

--          1.3.6.1.4.1.37950.1.1.5.12.9.3.11.1.1
-- 1.3.6.1.4.1.37950.1.1.5.12.9.3.11.1.1
-- 1.3.6.1.4.1.37950.1.1.5.12.9.3.11.1.1
-- 1.3.6.1.4.1.37950.1.1.5.12.9.3.11.1.1
-- 1.3.6.1.4.1.37950.1.1.5.12.9.3.11.1.1
-- 1.3.6.1.4.1.37950.1.1.5.12.9.3.11.1.1
-- 1.3.6.1.4.1.37950.1.1.5.12.9.3.11.1.1
-- 1.3.6.1.4.1.37950.1.1.5.12.9.3.11.1.1
-- 1.3.6.1.4.1.37950.1.1.5.12.9.3.11.1.1
		-- 1.3.6.1.4.1.37950.1.1.5.12.9.3.11.1.1
		voipTimerPfId OBJECT-TYPE
			SYNTAX Integer32 (0..65535)
			MAX-ACCESS read-write
			STATUS current
			DESCRIPTION
				"Description."
			::= { voipTimerEntry 1 }

		
--          1.3.6.1.4.1.37950.1.1.5.12.9.3.11.1.2
-- 1.3.6.1.4.1.37950.1.1.5.12.9.3.11.1.2
-- 1.3.6.1.4.1.37950.1.1.5.12.9.3.11.1.2
-- 1.3.6.1.4.1.37950.1.1.5.12.9.3.11.1.2
-- 1.3.6.1.4.1.37950.1.1.5.12.9.3.11.1.2
-- 1.3.6.1.4.1.37950.1.1.5.12.9.3.11.1.2
-- 1.3.6.1.4.1.37950.1.1.5.12.9.3.11.1.2
-- 1.3.6.1.4.1.37950.1.1.5.12.9.3.11.1.2
-- 1.3.6.1.4.1.37950.1.1.5.12.9.3.11.1.2
		-- 1.3.6.1.4.1.37950.1.1.5.12.9.3.11.1.2
		voipMaxWaitTime OBJECT-TYPE
			SYNTAX Integer32 (0..254)
			MAX-ACCESS read-write
			STATUS current
			DESCRIPTION
				"Description."
			::= { voipTimerEntry 2 }

		
--          1.3.6.1.4.1.37950.1.1.5.12.9.3.11.1.3
-- 1.3.6.1.4.1.37950.1.1.5.12.9.3.11.1.3
-- 1.3.6.1.4.1.37950.1.1.5.12.9.3.11.1.3
-- 1.3.6.1.4.1.37950.1.1.5.12.9.3.11.1.3
-- 1.3.6.1.4.1.37950.1.1.5.12.9.3.11.1.3
-- 1.3.6.1.4.1.37950.1.1.5.12.9.3.11.1.3
-- 1.3.6.1.4.1.37950.1.1.5.12.9.3.11.1.3
-- 1.3.6.1.4.1.37950.1.1.5.12.9.3.11.1.3
-- 1.3.6.1.4.1.37950.1.1.5.12.9.3.11.1.3
		-- 1.3.6.1.4.1.37950.1.1.5.12.9.3.11.1.3
		voipStartTimer OBJECT-TYPE
			SYNTAX Integer32 (1..65535)
			MAX-ACCESS read-write
			STATUS current
			DESCRIPTION
				"Description."
			::= { voipTimerEntry 3 }

		
--          1.3.6.1.4.1.37950.1.1.5.12.9.3.11.1.4
-- 1.3.6.1.4.1.37950.1.1.5.12.9.3.11.1.4
-- 1.3.6.1.4.1.37950.1.1.5.12.9.3.11.1.4
-- 1.3.6.1.4.1.37950.1.1.5.12.9.3.11.1.4
-- 1.3.6.1.4.1.37950.1.1.5.12.9.3.11.1.4
-- 1.3.6.1.4.1.37950.1.1.5.12.9.3.11.1.4
-- 1.3.6.1.4.1.37950.1.1.5.12.9.3.11.1.4
-- 1.3.6.1.4.1.37950.1.1.5.12.9.3.11.1.4
-- 1.3.6.1.4.1.37950.1.1.5.12.9.3.11.1.4
		-- 1.3.6.1.4.1.37950.1.1.5.12.9.3.11.1.4
		voipLongTimer OBJECT-TYPE
			SYNTAX Integer32 (1..65535)
			MAX-ACCESS read-write
			STATUS current
			DESCRIPTION
				"Description."
			::= { voipTimerEntry 4 }

		
--          1.3.6.1.4.1.37950.1.1.5.12.9.3.11.1.5
-- 1.3.6.1.4.1.37950.1.1.5.12.9.3.11.1.5
-- 1.3.6.1.4.1.37950.1.1.5.12.9.3.11.1.5
-- 1.3.6.1.4.1.37950.1.1.5.12.9.3.11.1.5
-- 1.3.6.1.4.1.37950.1.1.5.12.9.3.11.1.5
-- 1.3.6.1.4.1.37950.1.1.5.12.9.3.11.1.5
-- 1.3.6.1.4.1.37950.1.1.5.12.9.3.11.1.5
-- 1.3.6.1.4.1.37950.1.1.5.12.9.3.11.1.5
-- 1.3.6.1.4.1.37950.1.1.5.12.9.3.11.1.5
		-- 1.3.6.1.4.1.37950.1.1.5.12.9.3.11.1.5
		voipShortTimer OBJECT-TYPE
			SYNTAX Integer32 (1..65535)
			MAX-ACCESS read-write
			STATUS current
			DESCRIPTION
				"Description."
			::= { voipTimerEntry 5 }

		
--          1.3.6.1.4.1.37950.1.1.5.12.9.3.11.1.6
-- 1.3.6.1.4.1.37950.1.1.5.12.9.3.11.1.6
-- 1.3.6.1.4.1.37950.1.1.5.12.9.3.11.1.6
-- 1.3.6.1.4.1.37950.1.1.5.12.9.3.11.1.6
-- 1.3.6.1.4.1.37950.1.1.5.12.9.3.11.1.6
-- 1.3.6.1.4.1.37950.1.1.5.12.9.3.11.1.6
-- 1.3.6.1.4.1.37950.1.1.5.12.9.3.11.1.6
-- 1.3.6.1.4.1.37950.1.1.5.12.9.3.11.1.6
-- 1.3.6.1.4.1.37950.1.1.5.12.9.3.11.1.6
		-- 1.3.6.1.4.1.37950.1.1.5.12.9.3.11.1.6
		voipDigitMapNotify OBJECT-TYPE
			SYNTAX INTEGER
				{
				disable(0),
				enable(1)
				}
			MAX-ACCESS read-write
			STATUS current
			DESCRIPTION
				"Description."
			::= { voipTimerEntry 6 }

		
--          1.3.6.1.4.1.37950.1.1.5.12.9.3.12
-- 1.3.6.1.4.1.37950.1.1.5.12.9.3.12
-- 1.3.6.1.4.1.37950.1.1.5.12.9.3.12
-- 1.3.6.1.4.1.37950.1.1.5.12.9.3.12
-- 1.3.6.1.4.1.37950.1.1.5.12.9.3.12
-- 1.3.6.1.4.1.37950.1.1.5.12.9.3.12
-- 1.3.6.1.4.1.37950.1.1.5.12.9.3.12
-- 1.3.6.1.4.1.37950.1.1.5.12.9.3.12
-- 1.3.6.1.4.1.37950.1.1.5.12.9.3.12
		-- 1.3.6.1.4.1.37950.1.1.5.12.9.3.12
		potsParamterTable OBJECT-TYPE
			SYNTAX SEQUENCE OF PotsParamterEntry
			MAX-ACCESS not-accessible
			STATUS current
			DESCRIPTION
				"Description."
			::= { voipProfileShow 12 }

		
--          1.3.6.1.4.1.37950.1.1.5.12.9.3.12.1
-- 1.3.6.1.4.1.37950.1.1.5.12.9.3.12.1
-- 1.3.6.1.4.1.37950.1.1.5.12.9.3.12.1
-- 1.3.6.1.4.1.37950.1.1.5.12.9.3.12.1
-- 1.3.6.1.4.1.37950.1.1.5.12.9.3.12.1
-- 1.3.6.1.4.1.37950.1.1.5.12.9.3.12.1
-- 1.3.6.1.4.1.37950.1.1.5.12.9.3.12.1
-- 1.3.6.1.4.1.37950.1.1.5.12.9.3.12.1
-- 1.3.6.1.4.1.37950.1.1.5.12.9.3.12.1
		-- 1.3.6.1.4.1.37950.1.1.5.12.9.3.12.1
		potsParamterEntry OBJECT-TYPE
			SYNTAX PotsParamterEntry
			MAX-ACCESS not-accessible
			STATUS current
			DESCRIPTION
				"Description."
			INDEX { potsPtPfId, potsPtPotsNo }
			::= { potsParamterTable 1 }

		
		PotsParamterEntry ::=
			SEQUENCE { 
				potsPtPfId
					Integer32,
				potsPtPotsNo
					Integer32,
				potsPtVad
					INTEGER,
				potsPtEchoCancel
					INTEGER,
				potsPtInputGain
					Integer32,
				potsPtOutputGain
					Integer32,
				potsPtDtmfMode
					INTEGER
			 }

--          1.3.6.1.4.1.37950.1.1.5.12.9.3.12.1.1
-- 1.3.6.1.4.1.37950.1.1.5.12.9.3.12.1.1
-- 1.3.6.1.4.1.37950.1.1.5.12.9.3.12.1.1
-- 1.3.6.1.4.1.37950.1.1.5.12.9.3.12.1.1
-- 1.3.6.1.4.1.37950.1.1.5.12.9.3.12.1.1
-- 1.3.6.1.4.1.37950.1.1.5.12.9.3.12.1.1
-- 1.3.6.1.4.1.37950.1.1.5.12.9.3.12.1.1
-- 1.3.6.1.4.1.37950.1.1.5.12.9.3.12.1.1
-- 1.3.6.1.4.1.37950.1.1.5.12.9.3.12.1.1
		-- 1.3.6.1.4.1.37950.1.1.5.12.9.3.12.1.1
		potsPtPfId OBJECT-TYPE
			SYNTAX Integer32 (0..65535)
			MAX-ACCESS read-write
			STATUS current
			DESCRIPTION
				"Description."
			::= { potsParamterEntry 1 }

		
--          1.3.6.1.4.1.37950.1.1.5.12.9.3.12.1.2
-- 1.3.6.1.4.1.37950.1.1.5.12.9.3.12.1.2
-- 1.3.6.1.4.1.37950.1.1.5.12.9.3.12.1.2
-- 1.3.6.1.4.1.37950.1.1.5.12.9.3.12.1.2
-- 1.3.6.1.4.1.37950.1.1.5.12.9.3.12.1.2
-- 1.3.6.1.4.1.37950.1.1.5.12.9.3.12.1.2
-- 1.3.6.1.4.1.37950.1.1.5.12.9.3.12.1.2
-- 1.3.6.1.4.1.37950.1.1.5.12.9.3.12.1.2
-- 1.3.6.1.4.1.37950.1.1.5.12.9.3.12.1.2
		-- 1.3.6.1.4.1.37950.1.1.5.12.9.3.12.1.2
		potsPtPotsNo OBJECT-TYPE
			SYNTAX Integer32 (1..255)
			MAX-ACCESS read-write
			STATUS current
			DESCRIPTION
				"Description."
			::= { potsParamterEntry 2 }

		
--          1.3.6.1.4.1.37950.1.1.5.12.9.3.12.1.3
-- 1.3.6.1.4.1.37950.1.1.5.12.9.3.12.1.3
-- 1.3.6.1.4.1.37950.1.1.5.12.9.3.12.1.3
-- 1.3.6.1.4.1.37950.1.1.5.12.9.3.12.1.3
-- 1.3.6.1.4.1.37950.1.1.5.12.9.3.12.1.3
-- 1.3.6.1.4.1.37950.1.1.5.12.9.3.12.1.3
-- 1.3.6.1.4.1.37950.1.1.5.12.9.3.12.1.3
-- 1.3.6.1.4.1.37950.1.1.5.12.9.3.12.1.3
-- 1.3.6.1.4.1.37950.1.1.5.12.9.3.12.1.3
		-- 1.3.6.1.4.1.37950.1.1.5.12.9.3.12.1.3
		potsPtVad OBJECT-TYPE
			SYNTAX INTEGER
				{
				disable(0),
				enable(1)
				}
			MAX-ACCESS read-write
			STATUS current
			DESCRIPTION
				"Description."
			::= { potsParamterEntry 3 }

		
--          1.3.6.1.4.1.37950.1.1.5.12.9.3.12.1.4
-- 1.3.6.1.4.1.37950.1.1.5.12.9.3.12.1.4
-- 1.3.6.1.4.1.37950.1.1.5.12.9.3.12.1.4
-- 1.3.6.1.4.1.37950.1.1.5.12.9.3.12.1.4
-- 1.3.6.1.4.1.37950.1.1.5.12.9.3.12.1.4
-- 1.3.6.1.4.1.37950.1.1.5.12.9.3.12.1.4
-- 1.3.6.1.4.1.37950.1.1.5.12.9.3.12.1.4
-- 1.3.6.1.4.1.37950.1.1.5.12.9.3.12.1.4
-- 1.3.6.1.4.1.37950.1.1.5.12.9.3.12.1.4
		-- 1.3.6.1.4.1.37950.1.1.5.12.9.3.12.1.4
		potsPtEchoCancel OBJECT-TYPE
			SYNTAX INTEGER
				{
				disable(0),
				enable(1)
				}
			MAX-ACCESS read-write
			STATUS current
			DESCRIPTION
				"Description."
			::= { potsParamterEntry 4 }

		
--          1.3.6.1.4.1.37950.1.1.5.12.9.3.12.1.5
-- 1.3.6.1.4.1.37950.1.1.5.12.9.3.12.1.5
-- 1.3.6.1.4.1.37950.1.1.5.12.9.3.12.1.5
-- 1.3.6.1.4.1.37950.1.1.5.12.9.3.12.1.5
-- 1.3.6.1.4.1.37950.1.1.5.12.9.3.12.1.5
-- 1.3.6.1.4.1.37950.1.1.5.12.9.3.12.1.5
-- 1.3.6.1.4.1.37950.1.1.5.12.9.3.12.1.5
-- 1.3.6.1.4.1.37950.1.1.5.12.9.3.12.1.5
-- 1.3.6.1.4.1.37950.1.1.5.12.9.3.12.1.5
		-- 1.3.6.1.4.1.37950.1.1.5.12.9.3.12.1.5
		potsPtInputGain OBJECT-TYPE
			SYNTAX Integer32 (-32..32)
			MAX-ACCESS read-write
			STATUS current
			DESCRIPTION
				"Description."
			::= { potsParamterEntry 5 }

		
--          1.3.6.1.4.1.37950.1.1.5.12.9.3.12.1.6
-- 1.3.6.1.4.1.37950.1.1.5.12.9.3.12.1.6
-- 1.3.6.1.4.1.37950.1.1.5.12.9.3.12.1.6
-- 1.3.6.1.4.1.37950.1.1.5.12.9.3.12.1.6
-- 1.3.6.1.4.1.37950.1.1.5.12.9.3.12.1.6
-- 1.3.6.1.4.1.37950.1.1.5.12.9.3.12.1.6
-- 1.3.6.1.4.1.37950.1.1.5.12.9.3.12.1.6
-- 1.3.6.1.4.1.37950.1.1.5.12.9.3.12.1.6
-- 1.3.6.1.4.1.37950.1.1.5.12.9.3.12.1.6
		-- 1.3.6.1.4.1.37950.1.1.5.12.9.3.12.1.6
		potsPtOutputGain OBJECT-TYPE
			SYNTAX Integer32 (-32..32)
			MAX-ACCESS read-write
			STATUS current
			DESCRIPTION
				"Description."
			::= { potsParamterEntry 6 }

		
--          1.3.6.1.4.1.37950.1.1.5.12.9.3.12.1.7
-- 1.3.6.1.4.1.37950.1.1.5.12.9.3.12.1.7
-- 1.3.6.1.4.1.37950.1.1.5.12.9.3.12.1.7
-- 1.3.6.1.4.1.37950.1.1.5.12.9.3.12.1.7
-- 1.3.6.1.4.1.37950.1.1.5.12.9.3.12.1.7
-- 1.3.6.1.4.1.37950.1.1.5.12.9.3.12.1.7
-- 1.3.6.1.4.1.37950.1.1.5.12.9.3.12.1.7
-- 1.3.6.1.4.1.37950.1.1.5.12.9.3.12.1.7
-- 1.3.6.1.4.1.37950.1.1.5.12.9.3.12.1.7
		-- 1.3.6.1.4.1.37950.1.1.5.12.9.3.12.1.7
		potsPtDtmfMode OBJECT-TYPE
			SYNTAX INTEGER
				{
				transparent(0),
				rfc2833(1),
				rfc2833-redundancy(2),
				outband(3)
				}
			MAX-ACCESS read-write
			STATUS current
			DESCRIPTION
				"Description."
			::= { potsParamterEntry 7 }

		
--          1.3.6.1.4.1.37950.1.1.5.12.9.3.13
-- 1.3.6.1.4.1.37950.1.1.5.12.9.3.13
-- 1.3.6.1.4.1.37950.1.1.5.12.9.3.13
-- 1.3.6.1.4.1.37950.1.1.5.12.9.3.13
-- 1.3.6.1.4.1.37950.1.1.5.12.9.3.13
-- 1.3.6.1.4.1.37950.1.1.5.12.9.3.13
-- 1.3.6.1.4.1.37950.1.1.5.12.9.3.13
-- 1.3.6.1.4.1.37950.1.1.5.12.9.3.13
-- 1.3.6.1.4.1.37950.1.1.5.12.9.3.13
		-- 1.3.6.1.4.1.37950.1.1.5.12.9.3.13
		voipParamTable OBJECT-TYPE
			SYNTAX SEQUENCE OF VoipParamEntry
			MAX-ACCESS not-accessible
			STATUS current
			DESCRIPTION
				"Description."
			::= { voipProfileShow 13 }

		
--          1.3.6.1.4.1.37950.1.1.5.12.9.3.13.1
-- 1.3.6.1.4.1.37950.1.1.5.12.9.3.13.1
-- 1.3.6.1.4.1.37950.1.1.5.12.9.3.13.1
-- 1.3.6.1.4.1.37950.1.1.5.12.9.3.13.1
-- 1.3.6.1.4.1.37950.1.1.5.12.9.3.13.1
-- 1.3.6.1.4.1.37950.1.1.5.12.9.3.13.1
-- 1.3.6.1.4.1.37950.1.1.5.12.9.3.13.1
-- 1.3.6.1.4.1.37950.1.1.5.12.9.3.13.1
-- 1.3.6.1.4.1.37950.1.1.5.12.9.3.13.1
		-- 1.3.6.1.4.1.37950.1.1.5.12.9.3.13.1
		voipParamEntry OBJECT-TYPE
			SYNTAX VoipParamEntry
			MAX-ACCESS not-accessible
			STATUS current
			DESCRIPTION
				"Description."
			INDEX { voipParamVoipId }
			::= { voipParamTable 1 }

		
		VoipParamEntry ::=
			SEQUENCE { 
				voipParamVoipId
					Integer32,
				voipParamIpMode
					INTEGER,
				voipParamIp
					IpAddress,
				voipParamMask
					IpAddress,
				voipParamGw
					IpAddress,
				voipRtpIp
					IpAddress,
				voipRtpMask
					IpAddress,
				voipRtpGw
					IpAddress,
				voipDnsMaster
					IpAddress,
				voipDnsSlave
					IpAddress,
				voipDhcpOption60En
					INTEGER,
				voipDhcpOption60Base
					OCTET STRING,
				voipDhcpOption60Val
					OCTET STRING,
				voipParamPPPoEMode
					INTEGER,
				voipPPPoEUsername
					OCTET STRING,
				voipPPPoEPassword
					OCTET STRING,
				voipSVlanTpid
					Integer32,
				voipSVlanId
					Integer32,
				voipSVlanCos
					Integer32,
				voipCVlanTpid
					Integer32,
				voipCVlanId
					Integer32,
				voipCVlanCos
					Integer32,
				voipRtpSVlanTpid
					Integer32,
				voipRtpSVlanId
					Integer32,
				voipRtpSVlanCos
					Integer32,
				voipRtpCVlanTpid
					Integer32,
				voipRtpCVlanId
					Integer32,
				voipRtpCVlanCos
					Integer32
			 }

--          1.3.6.1.4.1.37950.1.1.5.12.9.3.13.1.1
-- 1.3.6.1.4.1.37950.1.1.5.12.9.3.13.1.1
-- 1.3.6.1.4.1.37950.1.1.5.12.9.3.13.1.1
-- 1.3.6.1.4.1.37950.1.1.5.12.9.3.13.1.1
-- 1.3.6.1.4.1.37950.1.1.5.12.9.3.13.1.1
-- 1.3.6.1.4.1.37950.1.1.5.12.9.3.13.1.1
-- 1.3.6.1.4.1.37950.1.1.5.12.9.3.13.1.1
-- 1.3.6.1.4.1.37950.1.1.5.12.9.3.13.1.1
-- 1.3.6.1.4.1.37950.1.1.5.12.9.3.13.1.1
		-- 1.3.6.1.4.1.37950.1.1.5.12.9.3.13.1.1
		voipParamVoipId OBJECT-TYPE
			SYNTAX Integer32 (0..65535)
			MAX-ACCESS read-write
			STATUS current
			DESCRIPTION
				"Description."
			::= { voipParamEntry 1 }

		
--          1.3.6.1.4.1.37950.1.1.5.12.9.3.13.1.2
-- 1.3.6.1.4.1.37950.1.1.5.12.9.3.13.1.2
-- 1.3.6.1.4.1.37950.1.1.5.12.9.3.13.1.2
-- 1.3.6.1.4.1.37950.1.1.5.12.9.3.13.1.2
-- 1.3.6.1.4.1.37950.1.1.5.12.9.3.13.1.2
-- 1.3.6.1.4.1.37950.1.1.5.12.9.3.13.1.2
-- 1.3.6.1.4.1.37950.1.1.5.12.9.3.13.1.2
-- 1.3.6.1.4.1.37950.1.1.5.12.9.3.13.1.2
-- 1.3.6.1.4.1.37950.1.1.5.12.9.3.13.1.2
		-- 1.3.6.1.4.1.37950.1.1.5.12.9.3.13.1.2
		voipParamIpMode OBJECT-TYPE
			SYNTAX INTEGER
				{
				static(1),
				dhcp(2),
				pppoe(3)
				}
			MAX-ACCESS read-write
			STATUS current
			DESCRIPTION
				"Description."
			::= { voipParamEntry 2 }

		
--          1.3.6.1.4.1.37950.1.1.5.12.9.3.13.1.3
-- 1.3.6.1.4.1.37950.1.1.5.12.9.3.13.1.3
-- 1.3.6.1.4.1.37950.1.1.5.12.9.3.13.1.3
-- 1.3.6.1.4.1.37950.1.1.5.12.9.3.13.1.3
-- 1.3.6.1.4.1.37950.1.1.5.12.9.3.13.1.3
-- 1.3.6.1.4.1.37950.1.1.5.12.9.3.13.1.3
-- 1.3.6.1.4.1.37950.1.1.5.12.9.3.13.1.3
-- 1.3.6.1.4.1.37950.1.1.5.12.9.3.13.1.3
-- 1.3.6.1.4.1.37950.1.1.5.12.9.3.13.1.3
		-- 1.3.6.1.4.1.37950.1.1.5.12.9.3.13.1.3
		voipParamIp OBJECT-TYPE
			SYNTAX IpAddress
			MAX-ACCESS read-write
			STATUS current
			DESCRIPTION
				"Description."
			::= { voipParamEntry 3 }

		
--          1.3.6.1.4.1.37950.1.1.5.12.9.3.13.1.4
-- 1.3.6.1.4.1.37950.1.1.5.12.9.3.13.1.4
-- 1.3.6.1.4.1.37950.1.1.5.12.9.3.13.1.4
-- 1.3.6.1.4.1.37950.1.1.5.12.9.3.13.1.4
-- 1.3.6.1.4.1.37950.1.1.5.12.9.3.13.1.4
-- 1.3.6.1.4.1.37950.1.1.5.12.9.3.13.1.4
-- 1.3.6.1.4.1.37950.1.1.5.12.9.3.13.1.4
-- 1.3.6.1.4.1.37950.1.1.5.12.9.3.13.1.4
-- 1.3.6.1.4.1.37950.1.1.5.12.9.3.13.1.4
		-- 1.3.6.1.4.1.37950.1.1.5.12.9.3.13.1.4
		voipParamMask OBJECT-TYPE
			SYNTAX IpAddress
			MAX-ACCESS read-write
			STATUS current
			DESCRIPTION
				"Description."
			::= { voipParamEntry 4 }

		
--          1.3.6.1.4.1.37950.1.1.5.12.9.3.13.1.5
-- 1.3.6.1.4.1.37950.1.1.5.12.9.3.13.1.5
-- 1.3.6.1.4.1.37950.1.1.5.12.9.3.13.1.5
-- 1.3.6.1.4.1.37950.1.1.5.12.9.3.13.1.5
-- 1.3.6.1.4.1.37950.1.1.5.12.9.3.13.1.5
-- 1.3.6.1.4.1.37950.1.1.5.12.9.3.13.1.5
-- 1.3.6.1.4.1.37950.1.1.5.12.9.3.13.1.5
-- 1.3.6.1.4.1.37950.1.1.5.12.9.3.13.1.5
-- 1.3.6.1.4.1.37950.1.1.5.12.9.3.13.1.5
		-- 1.3.6.1.4.1.37950.1.1.5.12.9.3.13.1.5
		voipParamGw OBJECT-TYPE
			SYNTAX IpAddress
			MAX-ACCESS read-write
			STATUS current
			DESCRIPTION
				"Description."
			::= { voipParamEntry 5 }

		
--          1.3.6.1.4.1.37950.1.1.5.12.9.3.13.1.6
-- 1.3.6.1.4.1.37950.1.1.5.12.9.3.13.1.6
-- 1.3.6.1.4.1.37950.1.1.5.12.9.3.13.1.6
-- 1.3.6.1.4.1.37950.1.1.5.12.9.3.13.1.6
-- 1.3.6.1.4.1.37950.1.1.5.12.9.3.13.1.6
-- 1.3.6.1.4.1.37950.1.1.5.12.9.3.13.1.6
-- 1.3.6.1.4.1.37950.1.1.5.12.9.3.13.1.6
-- 1.3.6.1.4.1.37950.1.1.5.12.9.3.13.1.6
-- 1.3.6.1.4.1.37950.1.1.5.12.9.3.13.1.6
		-- 1.3.6.1.4.1.37950.1.1.5.12.9.3.13.1.6
		voipRtpIp OBJECT-TYPE
			SYNTAX IpAddress
			MAX-ACCESS read-write
			STATUS current
			DESCRIPTION
				"Description."
			::= { voipParamEntry 6 }

		
--          1.3.6.1.4.1.37950.1.1.5.12.9.3.13.1.7
-- 1.3.6.1.4.1.37950.1.1.5.12.9.3.13.1.7
-- 1.3.6.1.4.1.37950.1.1.5.12.9.3.13.1.7
-- 1.3.6.1.4.1.37950.1.1.5.12.9.3.13.1.7
-- 1.3.6.1.4.1.37950.1.1.5.12.9.3.13.1.7
-- 1.3.6.1.4.1.37950.1.1.5.12.9.3.13.1.7
-- 1.3.6.1.4.1.37950.1.1.5.12.9.3.13.1.7
-- 1.3.6.1.4.1.37950.1.1.5.12.9.3.13.1.7
-- 1.3.6.1.4.1.37950.1.1.5.12.9.3.13.1.7
		-- 1.3.6.1.4.1.37950.1.1.5.12.9.3.13.1.7
		voipRtpMask OBJECT-TYPE
			SYNTAX IpAddress
			MAX-ACCESS read-write
			STATUS current
			DESCRIPTION
				"Description."
			::= { voipParamEntry 7 }

		
--          1.3.6.1.4.1.37950.1.1.5.12.9.3.13.1.8
-- 1.3.6.1.4.1.37950.1.1.5.12.9.3.13.1.8
-- 1.3.6.1.4.1.37950.1.1.5.12.9.3.13.1.8
-- 1.3.6.1.4.1.37950.1.1.5.12.9.3.13.1.8
-- 1.3.6.1.4.1.37950.1.1.5.12.9.3.13.1.8
-- 1.3.6.1.4.1.37950.1.1.5.12.9.3.13.1.8
-- 1.3.6.1.4.1.37950.1.1.5.12.9.3.13.1.8
-- 1.3.6.1.4.1.37950.1.1.5.12.9.3.13.1.8
-- 1.3.6.1.4.1.37950.1.1.5.12.9.3.13.1.8
		-- 1.3.6.1.4.1.37950.1.1.5.12.9.3.13.1.8
		voipRtpGw OBJECT-TYPE
			SYNTAX IpAddress
			MAX-ACCESS read-write
			STATUS current
			DESCRIPTION
				"Description."
			::= { voipParamEntry 8 }

		
--          1.3.6.1.4.1.37950.1.1.5.12.9.3.13.1.9
-- 1.3.6.1.4.1.37950.1.1.5.12.9.3.13.1.9
-- 1.3.6.1.4.1.37950.1.1.5.12.9.3.13.1.9
-- 1.3.6.1.4.1.37950.1.1.5.12.9.3.13.1.9
-- 1.3.6.1.4.1.37950.1.1.5.12.9.3.13.1.9
-- 1.3.6.1.4.1.37950.1.1.5.12.9.3.13.1.9
-- 1.3.6.1.4.1.37950.1.1.5.12.9.3.13.1.9
-- 1.3.6.1.4.1.37950.1.1.5.12.9.3.13.1.9
-- 1.3.6.1.4.1.37950.1.1.5.12.9.3.13.1.9
		-- 1.3.6.1.4.1.37950.1.1.5.12.9.3.13.1.9
		voipDnsMaster OBJECT-TYPE
			SYNTAX IpAddress
			MAX-ACCESS read-write
			STATUS current
			DESCRIPTION
				"Description."
			::= { voipParamEntry 9 }

		
--          1.3.6.1.4.1.37950.1.1.5.12.9.3.13.1.10
-- 1.3.6.1.4.1.37950.1.1.5.12.9.3.13.1.10
-- 1.3.6.1.4.1.37950.1.1.5.12.9.3.13.1.10
-- 1.3.6.1.4.1.37950.1.1.5.12.9.3.13.1.10
-- 1.3.6.1.4.1.37950.1.1.5.12.9.3.13.1.10
-- 1.3.6.1.4.1.37950.1.1.5.12.9.3.13.1.10
-- 1.3.6.1.4.1.37950.1.1.5.12.9.3.13.1.10
-- 1.3.6.1.4.1.37950.1.1.5.12.9.3.13.1.10
-- 1.3.6.1.4.1.37950.1.1.5.12.9.3.13.1.10
		-- 1.3.6.1.4.1.37950.1.1.5.12.9.3.13.1.10
		voipDnsSlave OBJECT-TYPE
			SYNTAX IpAddress
			MAX-ACCESS read-write
			STATUS current
			DESCRIPTION
				"Description."
			::= { voipParamEntry 10 }

		
--          1.3.6.1.4.1.37950.1.1.5.12.9.3.13.1.11
-- 1.3.6.1.4.1.37950.1.1.5.12.9.3.13.1.11
-- 1.3.6.1.4.1.37950.1.1.5.12.9.3.13.1.11
-- 1.3.6.1.4.1.37950.1.1.5.12.9.3.13.1.11
-- 1.3.6.1.4.1.37950.1.1.5.12.9.3.13.1.11
-- 1.3.6.1.4.1.37950.1.1.5.12.9.3.13.1.11
-- 1.3.6.1.4.1.37950.1.1.5.12.9.3.13.1.11
-- 1.3.6.1.4.1.37950.1.1.5.12.9.3.13.1.11
-- 1.3.6.1.4.1.37950.1.1.5.12.9.3.13.1.11
		-- 1.3.6.1.4.1.37950.1.1.5.12.9.3.13.1.11
		voipDhcpOption60En OBJECT-TYPE
			SYNTAX INTEGER
				{
				disable(0),
				enable(1)
				}
			MAX-ACCESS read-write
			STATUS current
			DESCRIPTION
				"Description."
			::= { voipParamEntry 11 }

		
--          1.3.6.1.4.1.37950.1.1.5.12.9.3.13.1.12
-- 1.3.6.1.4.1.37950.1.1.5.12.9.3.13.1.12
-- 1.3.6.1.4.1.37950.1.1.5.12.9.3.13.1.12
-- 1.3.6.1.4.1.37950.1.1.5.12.9.3.13.1.12
-- 1.3.6.1.4.1.37950.1.1.5.12.9.3.13.1.12
-- 1.3.6.1.4.1.37950.1.1.5.12.9.3.13.1.12
-- 1.3.6.1.4.1.37950.1.1.5.12.9.3.13.1.12
-- 1.3.6.1.4.1.37950.1.1.5.12.9.3.13.1.12
-- 1.3.6.1.4.1.37950.1.1.5.12.9.3.13.1.12
		-- 1.3.6.1.4.1.37950.1.1.5.12.9.3.13.1.12
		voipDhcpOption60Base OBJECT-TYPE
			SYNTAX OCTET STRING
			MAX-ACCESS read-write
			STATUS current
			DESCRIPTION
				"Description."
			::= { voipParamEntry 12 }

		
--          1.3.6.1.4.1.37950.1.1.5.12.9.3.13.1.13
-- 1.3.6.1.4.1.37950.1.1.5.12.9.3.13.1.13
-- 1.3.6.1.4.1.37950.1.1.5.12.9.3.13.1.13
-- 1.3.6.1.4.1.37950.1.1.5.12.9.3.13.1.13
-- 1.3.6.1.4.1.37950.1.1.5.12.9.3.13.1.13
-- 1.3.6.1.4.1.37950.1.1.5.12.9.3.13.1.13
-- 1.3.6.1.4.1.37950.1.1.5.12.9.3.13.1.13
-- 1.3.6.1.4.1.37950.1.1.5.12.9.3.13.1.13
-- 1.3.6.1.4.1.37950.1.1.5.12.9.3.13.1.13
		-- 1.3.6.1.4.1.37950.1.1.5.12.9.3.13.1.13
		voipDhcpOption60Val OBJECT-TYPE
			SYNTAX OCTET STRING
			MAX-ACCESS read-write
			STATUS current
			DESCRIPTION
				"Description."
			::= { voipParamEntry 13 }

		
--          1.3.6.1.4.1.37950.1.1.5.12.9.3.13.1.14
-- 1.3.6.1.4.1.37950.1.1.5.12.9.3.13.1.14
-- 1.3.6.1.4.1.37950.1.1.5.12.9.3.13.1.14
-- 1.3.6.1.4.1.37950.1.1.5.12.9.3.13.1.14
-- 1.3.6.1.4.1.37950.1.1.5.12.9.3.13.1.14
-- 1.3.6.1.4.1.37950.1.1.5.12.9.3.13.1.14
-- 1.3.6.1.4.1.37950.1.1.5.12.9.3.13.1.14
-- 1.3.6.1.4.1.37950.1.1.5.12.9.3.13.1.14
-- 1.3.6.1.4.1.37950.1.1.5.12.9.3.13.1.14
		-- 1.3.6.1.4.1.37950.1.1.5.12.9.3.13.1.14
		voipParamPPPoEMode OBJECT-TYPE
			SYNTAX INTEGER
				{
				auto(1),
				chap(2),
				pap(3)
				}
			MAX-ACCESS read-write
			STATUS current
			DESCRIPTION
				"Description."
			::= { voipParamEntry 14 }

		
--          1.3.6.1.4.1.37950.1.1.5.12.9.3.13.1.15
-- 1.3.6.1.4.1.37950.1.1.5.12.9.3.13.1.15
-- 1.3.6.1.4.1.37950.1.1.5.12.9.3.13.1.15
-- 1.3.6.1.4.1.37950.1.1.5.12.9.3.13.1.15
-- 1.3.6.1.4.1.37950.1.1.5.12.9.3.13.1.15
-- 1.3.6.1.4.1.37950.1.1.5.12.9.3.13.1.15
-- 1.3.6.1.4.1.37950.1.1.5.12.9.3.13.1.15
-- 1.3.6.1.4.1.37950.1.1.5.12.9.3.13.1.15
-- 1.3.6.1.4.1.37950.1.1.5.12.9.3.13.1.15
		-- 1.3.6.1.4.1.37950.1.1.5.12.9.3.13.1.15
		voipPPPoEUsername OBJECT-TYPE
			SYNTAX OCTET STRING
			MAX-ACCESS read-write
			STATUS current
			DESCRIPTION
				"Description."
			::= { voipParamEntry 15 }

		
--          1.3.6.1.4.1.37950.1.1.5.12.9.3.13.1.16
-- 1.3.6.1.4.1.37950.1.1.5.12.9.3.13.1.16
-- 1.3.6.1.4.1.37950.1.1.5.12.9.3.13.1.16
-- 1.3.6.1.4.1.37950.1.1.5.12.9.3.13.1.16
-- 1.3.6.1.4.1.37950.1.1.5.12.9.3.13.1.16
-- 1.3.6.1.4.1.37950.1.1.5.12.9.3.13.1.16
-- 1.3.6.1.4.1.37950.1.1.5.12.9.3.13.1.16
-- 1.3.6.1.4.1.37950.1.1.5.12.9.3.13.1.16
-- 1.3.6.1.4.1.37950.1.1.5.12.9.3.13.1.16
		-- 1.3.6.1.4.1.37950.1.1.5.12.9.3.13.1.16
		voipPPPoEPassword OBJECT-TYPE
			SYNTAX OCTET STRING
			MAX-ACCESS read-write
			STATUS current
			DESCRIPTION
				"Description."
			::= { voipParamEntry 16 }

		
--          1.3.6.1.4.1.37950.1.1.5.12.9.3.13.1.17
-- 1.3.6.1.4.1.37950.1.1.5.12.9.3.13.1.17
-- 1.3.6.1.4.1.37950.1.1.5.12.9.3.13.1.17
-- 1.3.6.1.4.1.37950.1.1.5.12.9.3.13.1.17
-- 1.3.6.1.4.1.37950.1.1.5.12.9.3.13.1.17
-- 1.3.6.1.4.1.37950.1.1.5.12.9.3.13.1.17
-- 1.3.6.1.4.1.37950.1.1.5.12.9.3.13.1.17
-- 1.3.6.1.4.1.37950.1.1.5.12.9.3.13.1.17
-- 1.3.6.1.4.1.37950.1.1.5.12.9.3.13.1.17
		-- 1.3.6.1.4.1.37950.1.1.5.12.9.3.13.1.17
		voipSVlanTpid OBJECT-TYPE
			SYNTAX Integer32
			MAX-ACCESS read-write
			STATUS current
			DESCRIPTION
				"Description."
			::= { voipParamEntry 17 }

		
--          1.3.6.1.4.1.37950.1.1.5.12.9.3.13.1.18
-- 1.3.6.1.4.1.37950.1.1.5.12.9.3.13.1.18
-- 1.3.6.1.4.1.37950.1.1.5.12.9.3.13.1.18
-- 1.3.6.1.4.1.37950.1.1.5.12.9.3.13.1.18
-- 1.3.6.1.4.1.37950.1.1.5.12.9.3.13.1.18
-- 1.3.6.1.4.1.37950.1.1.5.12.9.3.13.1.18
-- 1.3.6.1.4.1.37950.1.1.5.12.9.3.13.1.18
-- 1.3.6.1.4.1.37950.1.1.5.12.9.3.13.1.18
-- 1.3.6.1.4.1.37950.1.1.5.12.9.3.13.1.18
		-- 1.3.6.1.4.1.37950.1.1.5.12.9.3.13.1.18
		voipSVlanId OBJECT-TYPE
			SYNTAX Integer32 (0..4095)
			MAX-ACCESS read-write
			STATUS current
			DESCRIPTION
				"Description."
			::= { voipParamEntry 18 }

		
--          1.3.6.1.4.1.37950.1.1.5.12.9.3.13.1.19
-- 1.3.6.1.4.1.37950.1.1.5.12.9.3.13.1.19
-- 1.3.6.1.4.1.37950.1.1.5.12.9.3.13.1.19
-- 1.3.6.1.4.1.37950.1.1.5.12.9.3.13.1.19
-- 1.3.6.1.4.1.37950.1.1.5.12.9.3.13.1.19
-- 1.3.6.1.4.1.37950.1.1.5.12.9.3.13.1.19
-- 1.3.6.1.4.1.37950.1.1.5.12.9.3.13.1.19
-- 1.3.6.1.4.1.37950.1.1.5.12.9.3.13.1.19
-- 1.3.6.1.4.1.37950.1.1.5.12.9.3.13.1.19
		-- 1.3.6.1.4.1.37950.1.1.5.12.9.3.13.1.19
		voipSVlanCos OBJECT-TYPE
			SYNTAX Integer32 (0..7)
			MAX-ACCESS read-write
			STATUS current
			DESCRIPTION
				"Description."
			::= { voipParamEntry 19 }

		
--          1.3.6.1.4.1.37950.1.1.5.12.9.3.13.1.20
-- 1.3.6.1.4.1.37950.1.1.5.12.9.3.13.1.20
-- 1.3.6.1.4.1.37950.1.1.5.12.9.3.13.1.20
-- 1.3.6.1.4.1.37950.1.1.5.12.9.3.13.1.20
-- 1.3.6.1.4.1.37950.1.1.5.12.9.3.13.1.20
-- 1.3.6.1.4.1.37950.1.1.5.12.9.3.13.1.20
-- 1.3.6.1.4.1.37950.1.1.5.12.9.3.13.1.20
-- 1.3.6.1.4.1.37950.1.1.5.12.9.3.13.1.20
-- 1.3.6.1.4.1.37950.1.1.5.12.9.3.13.1.20
		-- 1.3.6.1.4.1.37950.1.1.5.12.9.3.13.1.20
		voipCVlanTpid OBJECT-TYPE
			SYNTAX Integer32
			MAX-ACCESS read-write
			STATUS current
			DESCRIPTION
				"Description."
			::= { voipParamEntry 20 }

		
--          1.3.6.1.4.1.37950.1.1.5.12.9.3.13.1.21
-- 1.3.6.1.4.1.37950.1.1.5.12.9.3.13.1.21
-- 1.3.6.1.4.1.37950.1.1.5.12.9.3.13.1.21
-- 1.3.6.1.4.1.37950.1.1.5.12.9.3.13.1.21
-- 1.3.6.1.4.1.37950.1.1.5.12.9.3.13.1.21
-- 1.3.6.1.4.1.37950.1.1.5.12.9.3.13.1.21
-- 1.3.6.1.4.1.37950.1.1.5.12.9.3.13.1.21
-- 1.3.6.1.4.1.37950.1.1.5.12.9.3.13.1.21
-- 1.3.6.1.4.1.37950.1.1.5.12.9.3.13.1.21
		-- 1.3.6.1.4.1.37950.1.1.5.12.9.3.13.1.21
		voipCVlanId OBJECT-TYPE
			SYNTAX Integer32 (0..4095)
			MAX-ACCESS read-write
			STATUS current
			DESCRIPTION
				"Description."
			::= { voipParamEntry 21 }

		
--          1.3.6.1.4.1.37950.1.1.5.12.9.3.13.1.22
-- 1.3.6.1.4.1.37950.1.1.5.12.9.3.13.1.22
-- 1.3.6.1.4.1.37950.1.1.5.12.9.3.13.1.22
-- 1.3.6.1.4.1.37950.1.1.5.12.9.3.13.1.22
-- 1.3.6.1.4.1.37950.1.1.5.12.9.3.13.1.22
-- 1.3.6.1.4.1.37950.1.1.5.12.9.3.13.1.22
-- 1.3.6.1.4.1.37950.1.1.5.12.9.3.13.1.22
-- 1.3.6.1.4.1.37950.1.1.5.12.9.3.13.1.22
-- 1.3.6.1.4.1.37950.1.1.5.12.9.3.13.1.22
		-- 1.3.6.1.4.1.37950.1.1.5.12.9.3.13.1.22
		voipCVlanCos OBJECT-TYPE
			SYNTAX Integer32 (0..7)
			MAX-ACCESS read-write
			STATUS current
			DESCRIPTION
				"Description."
			::= { voipParamEntry 22 }

		
--          1.3.6.1.4.1.37950.1.1.5.12.9.3.13.1.23
-- 1.3.6.1.4.1.37950.1.1.5.12.9.3.13.1.23
-- 1.3.6.1.4.1.37950.1.1.5.12.9.3.13.1.23
-- 1.3.6.1.4.1.37950.1.1.5.12.9.3.13.1.23
-- 1.3.6.1.4.1.37950.1.1.5.12.9.3.13.1.23
-- 1.3.6.1.4.1.37950.1.1.5.12.9.3.13.1.23
-- 1.3.6.1.4.1.37950.1.1.5.12.9.3.13.1.23
-- 1.3.6.1.4.1.37950.1.1.5.12.9.3.13.1.23
-- 1.3.6.1.4.1.37950.1.1.5.12.9.3.13.1.23
		-- 1.3.6.1.4.1.37950.1.1.5.12.9.3.13.1.23
		voipRtpSVlanTpid OBJECT-TYPE
			SYNTAX Integer32
			MAX-ACCESS read-write
			STATUS current
			DESCRIPTION
				"Description."
			::= { voipParamEntry 23 }

		
--          1.3.6.1.4.1.37950.1.1.5.12.9.3.13.1.24
-- 1.3.6.1.4.1.37950.1.1.5.12.9.3.13.1.24
-- 1.3.6.1.4.1.37950.1.1.5.12.9.3.13.1.24
-- 1.3.6.1.4.1.37950.1.1.5.12.9.3.13.1.24
-- 1.3.6.1.4.1.37950.1.1.5.12.9.3.13.1.24
-- 1.3.6.1.4.1.37950.1.1.5.12.9.3.13.1.24
-- 1.3.6.1.4.1.37950.1.1.5.12.9.3.13.1.24
-- 1.3.6.1.4.1.37950.1.1.5.12.9.3.13.1.24
-- 1.3.6.1.4.1.37950.1.1.5.12.9.3.13.1.24
		-- 1.3.6.1.4.1.37950.1.1.5.12.9.3.13.1.24
		voipRtpSVlanId OBJECT-TYPE
			SYNTAX Integer32 (0..4095)
			MAX-ACCESS read-write
			STATUS current
			DESCRIPTION
				"Description."
			::= { voipParamEntry 24 }

		
--          1.3.6.1.4.1.37950.1.1.5.12.9.3.13.1.25
-- 1.3.6.1.4.1.37950.1.1.5.12.9.3.13.1.25
-- 1.3.6.1.4.1.37950.1.1.5.12.9.3.13.1.25
-- 1.3.6.1.4.1.37950.1.1.5.12.9.3.13.1.25
-- 1.3.6.1.4.1.37950.1.1.5.12.9.3.13.1.25
-- 1.3.6.1.4.1.37950.1.1.5.12.9.3.13.1.25
-- 1.3.6.1.4.1.37950.1.1.5.12.9.3.13.1.25
-- 1.3.6.1.4.1.37950.1.1.5.12.9.3.13.1.25
-- 1.3.6.1.4.1.37950.1.1.5.12.9.3.13.1.25
		-- 1.3.6.1.4.1.37950.1.1.5.12.9.3.13.1.25
		voipRtpSVlanCos OBJECT-TYPE
			SYNTAX Integer32 (0..7)
			MAX-ACCESS read-write
			STATUS current
			DESCRIPTION
				"Description."
			::= { voipParamEntry 25 }

		
--          1.3.6.1.4.1.37950.1.1.5.12.9.3.13.1.26
-- 1.3.6.1.4.1.37950.1.1.5.12.9.3.13.1.26
-- 1.3.6.1.4.1.37950.1.1.5.12.9.3.13.1.26
-- 1.3.6.1.4.1.37950.1.1.5.12.9.3.13.1.26
-- 1.3.6.1.4.1.37950.1.1.5.12.9.3.13.1.26
-- 1.3.6.1.4.1.37950.1.1.5.12.9.3.13.1.26
-- 1.3.6.1.4.1.37950.1.1.5.12.9.3.13.1.26
-- 1.3.6.1.4.1.37950.1.1.5.12.9.3.13.1.26
-- 1.3.6.1.4.1.37950.1.1.5.12.9.3.13.1.26
		-- 1.3.6.1.4.1.37950.1.1.5.12.9.3.13.1.26
		voipRtpCVlanTpid OBJECT-TYPE
			SYNTAX Integer32
			MAX-ACCESS read-write
			STATUS current
			DESCRIPTION
				"Description."
			::= { voipParamEntry 26 }

		
--          1.3.6.1.4.1.37950.1.1.5.12.9.3.13.1.27
-- 1.3.6.1.4.1.37950.1.1.5.12.9.3.13.1.27
-- 1.3.6.1.4.1.37950.1.1.5.12.9.3.13.1.27
-- 1.3.6.1.4.1.37950.1.1.5.12.9.3.13.1.27
-- 1.3.6.1.4.1.37950.1.1.5.12.9.3.13.1.27
-- 1.3.6.1.4.1.37950.1.1.5.12.9.3.13.1.27
-- 1.3.6.1.4.1.37950.1.1.5.12.9.3.13.1.27
-- 1.3.6.1.4.1.37950.1.1.5.12.9.3.13.1.27
-- 1.3.6.1.4.1.37950.1.1.5.12.9.3.13.1.27
		-- 1.3.6.1.4.1.37950.1.1.5.12.9.3.13.1.27
		voipRtpCVlanId OBJECT-TYPE
			SYNTAX Integer32 (0..4095)
			MAX-ACCESS read-write
			STATUS current
			DESCRIPTION
				"Description."
			::= { voipParamEntry 27 }

		
--          1.3.6.1.4.1.37950.1.1.5.12.9.3.13.1.28
-- 1.3.6.1.4.1.37950.1.1.5.12.9.3.13.1.28
-- 1.3.6.1.4.1.37950.1.1.5.12.9.3.13.1.28
-- 1.3.6.1.4.1.37950.1.1.5.12.9.3.13.1.28
-- 1.3.6.1.4.1.37950.1.1.5.12.9.3.13.1.28
-- 1.3.6.1.4.1.37950.1.1.5.12.9.3.13.1.28
-- 1.3.6.1.4.1.37950.1.1.5.12.9.3.13.1.28
-- 1.3.6.1.4.1.37950.1.1.5.12.9.3.13.1.28
-- 1.3.6.1.4.1.37950.1.1.5.12.9.3.13.1.28
		-- 1.3.6.1.4.1.37950.1.1.5.12.9.3.13.1.28
		voipRtpCVlanCos OBJECT-TYPE
			SYNTAX Integer32 (0..7)
			MAX-ACCESS read-write
			STATUS current
			DESCRIPTION
				"Description."
			::= { voipParamEntry 28 }

		
--          1.3.6.1.4.1.37950.1.1.5.12.9.3.14
-- 1.3.6.1.4.1.37950.1.1.5.12.9.3.14
-- 1.3.6.1.4.1.37950.1.1.5.12.9.3.14
-- 1.3.6.1.4.1.37950.1.1.5.12.9.3.14
-- 1.3.6.1.4.1.37950.1.1.5.12.9.3.14
-- 1.3.6.1.4.1.37950.1.1.5.12.9.3.14
-- 1.3.6.1.4.1.37950.1.1.5.12.9.3.14
-- 1.3.6.1.4.1.37950.1.1.5.12.9.3.14
-- 1.3.6.1.4.1.37950.1.1.5.12.9.3.14
		-- 1.3.6.1.4.1.37950.1.1.5.12.9.3.14
		voipSipParamTable OBJECT-TYPE
			SYNTAX SEQUENCE OF VoipSipParamEntry
			MAX-ACCESS not-accessible
			STATUS current
			DESCRIPTION
				"Description."
			::= { voipProfileShow 14 }

		
--          1.3.6.1.4.1.37950.1.1.5.12.9.3.14.1
-- 1.3.6.1.4.1.37950.1.1.5.12.9.3.14.1
-- 1.3.6.1.4.1.37950.1.1.5.12.9.3.14.1
-- 1.3.6.1.4.1.37950.1.1.5.12.9.3.14.1
-- 1.3.6.1.4.1.37950.1.1.5.12.9.3.14.1
-- 1.3.6.1.4.1.37950.1.1.5.12.9.3.14.1
-- 1.3.6.1.4.1.37950.1.1.5.12.9.3.14.1
-- 1.3.6.1.4.1.37950.1.1.5.12.9.3.14.1
-- 1.3.6.1.4.1.37950.1.1.5.12.9.3.14.1
		-- 1.3.6.1.4.1.37950.1.1.5.12.9.3.14.1
		voipSipParamEntry OBJECT-TYPE
			SYNTAX VoipSipParamEntry
			MAX-ACCESS not-accessible
			STATUS current
			DESCRIPTION
				"Description."
			INDEX { sipVoipId }
			::= { voipSipParamTable 1 }

		
		VoipSipParamEntry ::=
			SEQUENCE { 
				sipVoipId
					Integer32,
				sipProxyServName
					OCTET STRING,
				sipProxyServPort
					Integer32,
				sipBakProxyServName
					OCTET STRING,
				sipBakProxyServPort
					Integer32,
				sipRegServName
					OCTET STRING,
				sipRegServPort
					Integer32,
				sipBakRegServName
					OCTET STRING,
				sipBakRegServPort
					Integer32,
				sipOutBndServName
					OCTET STRING,
				sipOutBndServPort
					Integer32,
				sipMgPort
					Integer32,
				sipRegInterValue
					Integer32,
				sipHBeatCfg
					INTEGER,
				sipHBeatCycle
					Integer32,
				sipHBeatCount
					Integer32
			 }

--          1.3.6.1.4.1.37950.1.1.5.12.9.3.14.1.1
-- 1.3.6.1.4.1.37950.1.1.5.12.9.3.14.1.1
-- 1.3.6.1.4.1.37950.1.1.5.12.9.3.14.1.1
-- 1.3.6.1.4.1.37950.1.1.5.12.9.3.14.1.1
-- 1.3.6.1.4.1.37950.1.1.5.12.9.3.14.1.1
-- 1.3.6.1.4.1.37950.1.1.5.12.9.3.14.1.1
-- 1.3.6.1.4.1.37950.1.1.5.12.9.3.14.1.1
-- 1.3.6.1.4.1.37950.1.1.5.12.9.3.14.1.1
-- 1.3.6.1.4.1.37950.1.1.5.12.9.3.14.1.1
		-- 1.3.6.1.4.1.37950.1.1.5.12.9.3.14.1.1
		sipVoipId OBJECT-TYPE
			SYNTAX Integer32 (0..65535)
			MAX-ACCESS read-write
			STATUS current
			DESCRIPTION
				"Description."
			::= { voipSipParamEntry 1 }

		
--          1.3.6.1.4.1.37950.1.1.5.12.9.3.14.1.2
-- 1.3.6.1.4.1.37950.1.1.5.12.9.3.14.1.2
-- 1.3.6.1.4.1.37950.1.1.5.12.9.3.14.1.2
-- 1.3.6.1.4.1.37950.1.1.5.12.9.3.14.1.2
-- 1.3.6.1.4.1.37950.1.1.5.12.9.3.14.1.2
-- 1.3.6.1.4.1.37950.1.1.5.12.9.3.14.1.2
-- 1.3.6.1.4.1.37950.1.1.5.12.9.3.14.1.2
-- 1.3.6.1.4.1.37950.1.1.5.12.9.3.14.1.2
-- 1.3.6.1.4.1.37950.1.1.5.12.9.3.14.1.2
		-- 1.3.6.1.4.1.37950.1.1.5.12.9.3.14.1.2
		sipProxyServName OBJECT-TYPE
			SYNTAX OCTET STRING
			MAX-ACCESS read-write
			STATUS current
			DESCRIPTION
				"Description."
			::= { voipSipParamEntry 2 }

		
--          1.3.6.1.4.1.37950.1.1.5.12.9.3.14.1.3
-- 1.3.6.1.4.1.37950.1.1.5.12.9.3.14.1.3
-- 1.3.6.1.4.1.37950.1.1.5.12.9.3.14.1.3
-- 1.3.6.1.4.1.37950.1.1.5.12.9.3.14.1.3
-- 1.3.6.1.4.1.37950.1.1.5.12.9.3.14.1.3
-- 1.3.6.1.4.1.37950.1.1.5.12.9.3.14.1.3
-- 1.3.6.1.4.1.37950.1.1.5.12.9.3.14.1.3
-- 1.3.6.1.4.1.37950.1.1.5.12.9.3.14.1.3
-- 1.3.6.1.4.1.37950.1.1.5.12.9.3.14.1.3
		-- 1.3.6.1.4.1.37950.1.1.5.12.9.3.14.1.3
		sipProxyServPort OBJECT-TYPE
			SYNTAX Integer32 (0..65535)
			MAX-ACCESS read-write
			STATUS current
			DESCRIPTION
				"Description."
			::= { voipSipParamEntry 3 }

		
--          1.3.6.1.4.1.37950.1.1.5.12.9.3.14.1.4
-- 1.3.6.1.4.1.37950.1.1.5.12.9.3.14.1.4
-- 1.3.6.1.4.1.37950.1.1.5.12.9.3.14.1.4
-- 1.3.6.1.4.1.37950.1.1.5.12.9.3.14.1.4
-- 1.3.6.1.4.1.37950.1.1.5.12.9.3.14.1.4
-- 1.3.6.1.4.1.37950.1.1.5.12.9.3.14.1.4
-- 1.3.6.1.4.1.37950.1.1.5.12.9.3.14.1.4
-- 1.3.6.1.4.1.37950.1.1.5.12.9.3.14.1.4
-- 1.3.6.1.4.1.37950.1.1.5.12.9.3.14.1.4
		-- 1.3.6.1.4.1.37950.1.1.5.12.9.3.14.1.4
		sipBakProxyServName OBJECT-TYPE
			SYNTAX OCTET STRING
			MAX-ACCESS read-write
			STATUS current
			DESCRIPTION
				"Description."
			::= { voipSipParamEntry 4 }

		
--          1.3.6.1.4.1.37950.1.1.5.12.9.3.14.1.5
-- 1.3.6.1.4.1.37950.1.1.5.12.9.3.14.1.5
-- 1.3.6.1.4.1.37950.1.1.5.12.9.3.14.1.5
-- 1.3.6.1.4.1.37950.1.1.5.12.9.3.14.1.5
-- 1.3.6.1.4.1.37950.1.1.5.12.9.3.14.1.5
-- 1.3.6.1.4.1.37950.1.1.5.12.9.3.14.1.5
-- 1.3.6.1.4.1.37950.1.1.5.12.9.3.14.1.5
-- 1.3.6.1.4.1.37950.1.1.5.12.9.3.14.1.5
-- 1.3.6.1.4.1.37950.1.1.5.12.9.3.14.1.5
		-- 1.3.6.1.4.1.37950.1.1.5.12.9.3.14.1.5
		sipBakProxyServPort OBJECT-TYPE
			SYNTAX Integer32 (0..65535)
			MAX-ACCESS read-write
			STATUS current
			DESCRIPTION
				"Description."
			::= { voipSipParamEntry 5 }

		
--          1.3.6.1.4.1.37950.1.1.5.12.9.3.14.1.6
-- 1.3.6.1.4.1.37950.1.1.5.12.9.3.14.1.6
-- 1.3.6.1.4.1.37950.1.1.5.12.9.3.14.1.6
-- 1.3.6.1.4.1.37950.1.1.5.12.9.3.14.1.6
-- 1.3.6.1.4.1.37950.1.1.5.12.9.3.14.1.6
-- 1.3.6.1.4.1.37950.1.1.5.12.9.3.14.1.6
-- 1.3.6.1.4.1.37950.1.1.5.12.9.3.14.1.6
-- 1.3.6.1.4.1.37950.1.1.5.12.9.3.14.1.6
-- 1.3.6.1.4.1.37950.1.1.5.12.9.3.14.1.6
		-- 1.3.6.1.4.1.37950.1.1.5.12.9.3.14.1.6
		sipRegServName OBJECT-TYPE
			SYNTAX OCTET STRING
			MAX-ACCESS read-write
			STATUS current
			DESCRIPTION
				"Description."
			::= { voipSipParamEntry 6 }

		
--          1.3.6.1.4.1.37950.1.1.5.12.9.3.14.1.7
-- 1.3.6.1.4.1.37950.1.1.5.12.9.3.14.1.7
-- 1.3.6.1.4.1.37950.1.1.5.12.9.3.14.1.7
-- 1.3.6.1.4.1.37950.1.1.5.12.9.3.14.1.7
-- 1.3.6.1.4.1.37950.1.1.5.12.9.3.14.1.7
-- 1.3.6.1.4.1.37950.1.1.5.12.9.3.14.1.7
-- 1.3.6.1.4.1.37950.1.1.5.12.9.3.14.1.7
-- 1.3.6.1.4.1.37950.1.1.5.12.9.3.14.1.7
-- 1.3.6.1.4.1.37950.1.1.5.12.9.3.14.1.7
		-- 1.3.6.1.4.1.37950.1.1.5.12.9.3.14.1.7
		sipRegServPort OBJECT-TYPE
			SYNTAX Integer32 (0..65535)
			MAX-ACCESS read-write
			STATUS current
			DESCRIPTION
				"Description."
			::= { voipSipParamEntry 7 }

		
--          1.3.6.1.4.1.37950.1.1.5.12.9.3.14.1.8
-- 1.3.6.1.4.1.37950.1.1.5.12.9.3.14.1.8
-- 1.3.6.1.4.1.37950.1.1.5.12.9.3.14.1.8
-- 1.3.6.1.4.1.37950.1.1.5.12.9.3.14.1.8
-- 1.3.6.1.4.1.37950.1.1.5.12.9.3.14.1.8
-- 1.3.6.1.4.1.37950.1.1.5.12.9.3.14.1.8
-- 1.3.6.1.4.1.37950.1.1.5.12.9.3.14.1.8
-- 1.3.6.1.4.1.37950.1.1.5.12.9.3.14.1.8
-- 1.3.6.1.4.1.37950.1.1.5.12.9.3.14.1.8
		-- 1.3.6.1.4.1.37950.1.1.5.12.9.3.14.1.8
		sipBakRegServName OBJECT-TYPE
			SYNTAX OCTET STRING
			MAX-ACCESS read-write
			STATUS current
			DESCRIPTION
				"Description."
			::= { voipSipParamEntry 8 }

		
--          1.3.6.1.4.1.37950.1.1.5.12.9.3.14.1.9
-- 1.3.6.1.4.1.37950.1.1.5.12.9.3.14.1.9
-- 1.3.6.1.4.1.37950.1.1.5.12.9.3.14.1.9
-- 1.3.6.1.4.1.37950.1.1.5.12.9.3.14.1.9
-- 1.3.6.1.4.1.37950.1.1.5.12.9.3.14.1.9
-- 1.3.6.1.4.1.37950.1.1.5.12.9.3.14.1.9
-- 1.3.6.1.4.1.37950.1.1.5.12.9.3.14.1.9
-- 1.3.6.1.4.1.37950.1.1.5.12.9.3.14.1.9
-- 1.3.6.1.4.1.37950.1.1.5.12.9.3.14.1.9
		-- 1.3.6.1.4.1.37950.1.1.5.12.9.3.14.1.9
		sipBakRegServPort OBJECT-TYPE
			SYNTAX Integer32 (0..65535)
			MAX-ACCESS read-write
			STATUS current
			DESCRIPTION
				"Description."
			::= { voipSipParamEntry 9 }

		
--          1.3.6.1.4.1.37950.1.1.5.12.9.3.14.1.10
-- 1.3.6.1.4.1.37950.1.1.5.12.9.3.14.1.10
-- 1.3.6.1.4.1.37950.1.1.5.12.9.3.14.1.10
-- 1.3.6.1.4.1.37950.1.1.5.12.9.3.14.1.10
-- 1.3.6.1.4.1.37950.1.1.5.12.9.3.14.1.10
-- 1.3.6.1.4.1.37950.1.1.5.12.9.3.14.1.10
-- 1.3.6.1.4.1.37950.1.1.5.12.9.3.14.1.10
-- 1.3.6.1.4.1.37950.1.1.5.12.9.3.14.1.10
-- 1.3.6.1.4.1.37950.1.1.5.12.9.3.14.1.10
		-- 1.3.6.1.4.1.37950.1.1.5.12.9.3.14.1.10
		sipOutBndServName OBJECT-TYPE
			SYNTAX OCTET STRING
			MAX-ACCESS read-write
			STATUS current
			DESCRIPTION
				"Description."
			::= { voipSipParamEntry 10 }

		
--          1.3.6.1.4.1.37950.1.1.5.12.9.3.14.1.11
-- 1.3.6.1.4.1.37950.1.1.5.12.9.3.14.1.11
-- 1.3.6.1.4.1.37950.1.1.5.12.9.3.14.1.11
-- 1.3.6.1.4.1.37950.1.1.5.12.9.3.14.1.11
-- 1.3.6.1.4.1.37950.1.1.5.12.9.3.14.1.11
-- 1.3.6.1.4.1.37950.1.1.5.12.9.3.14.1.11
-- 1.3.6.1.4.1.37950.1.1.5.12.9.3.14.1.11
-- 1.3.6.1.4.1.37950.1.1.5.12.9.3.14.1.11
-- 1.3.6.1.4.1.37950.1.1.5.12.9.3.14.1.11
		-- 1.3.6.1.4.1.37950.1.1.5.12.9.3.14.1.11
		sipOutBndServPort OBJECT-TYPE
			SYNTAX Integer32 (0..65535)
			MAX-ACCESS read-write
			STATUS current
			DESCRIPTION
				"Description."
			::= { voipSipParamEntry 11 }

		
--          1.3.6.1.4.1.37950.1.1.5.12.9.3.14.1.12
-- 1.3.6.1.4.1.37950.1.1.5.12.9.3.14.1.12
-- 1.3.6.1.4.1.37950.1.1.5.12.9.3.14.1.12
-- 1.3.6.1.4.1.37950.1.1.5.12.9.3.14.1.12
-- 1.3.6.1.4.1.37950.1.1.5.12.9.3.14.1.12
-- 1.3.6.1.4.1.37950.1.1.5.12.9.3.14.1.12
-- 1.3.6.1.4.1.37950.1.1.5.12.9.3.14.1.12
-- 1.3.6.1.4.1.37950.1.1.5.12.9.3.14.1.12
-- 1.3.6.1.4.1.37950.1.1.5.12.9.3.14.1.12
		-- 1.3.6.1.4.1.37950.1.1.5.12.9.3.14.1.12
		sipMgPort OBJECT-TYPE
			SYNTAX Integer32 (0..65535)
			MAX-ACCESS read-write
			STATUS current
			DESCRIPTION
				"Description."
			::= { voipSipParamEntry 12 }

		
--          1.3.6.1.4.1.37950.1.1.5.12.9.3.14.1.13
-- 1.3.6.1.4.1.37950.1.1.5.12.9.3.14.1.13
-- 1.3.6.1.4.1.37950.1.1.5.12.9.3.14.1.13
-- 1.3.6.1.4.1.37950.1.1.5.12.9.3.14.1.13
-- 1.3.6.1.4.1.37950.1.1.5.12.9.3.14.1.13
-- 1.3.6.1.4.1.37950.1.1.5.12.9.3.14.1.13
-- 1.3.6.1.4.1.37950.1.1.5.12.9.3.14.1.13
-- 1.3.6.1.4.1.37950.1.1.5.12.9.3.14.1.13
-- 1.3.6.1.4.1.37950.1.1.5.12.9.3.14.1.13
		-- 1.3.6.1.4.1.37950.1.1.5.12.9.3.14.1.13
		sipRegInterValue OBJECT-TYPE
			SYNTAX Integer32 (0..10000000)
			MAX-ACCESS read-write
			STATUS current
			DESCRIPTION
				"Description."
			::= { voipSipParamEntry 13 }

		
--          1.3.6.1.4.1.37950.1.1.5.12.9.3.14.1.14
-- 1.3.6.1.4.1.37950.1.1.5.12.9.3.14.1.14
-- 1.3.6.1.4.1.37950.1.1.5.12.9.3.14.1.14
-- 1.3.6.1.4.1.37950.1.1.5.12.9.3.14.1.14
-- 1.3.6.1.4.1.37950.1.1.5.12.9.3.14.1.14
-- 1.3.6.1.4.1.37950.1.1.5.12.9.3.14.1.14
-- 1.3.6.1.4.1.37950.1.1.5.12.9.3.14.1.14
-- 1.3.6.1.4.1.37950.1.1.5.12.9.3.14.1.14
-- 1.3.6.1.4.1.37950.1.1.5.12.9.3.14.1.14
		-- 1.3.6.1.4.1.37950.1.1.5.12.9.3.14.1.14
		sipHBeatCfg OBJECT-TYPE
			SYNTAX INTEGER
				{
				disable(0),
				active(1),
				passive(2)
				}
			MAX-ACCESS read-write
			STATUS current
			DESCRIPTION
				"Description."
			::= { voipSipParamEntry 14 }

		
--          1.3.6.1.4.1.37950.1.1.5.12.9.3.14.1.15
-- 1.3.6.1.4.1.37950.1.1.5.12.9.3.14.1.15
-- 1.3.6.1.4.1.37950.1.1.5.12.9.3.14.1.15
-- 1.3.6.1.4.1.37950.1.1.5.12.9.3.14.1.15
-- 1.3.6.1.4.1.37950.1.1.5.12.9.3.14.1.15
-- 1.3.6.1.4.1.37950.1.1.5.12.9.3.14.1.15
-- 1.3.6.1.4.1.37950.1.1.5.12.9.3.14.1.15
-- 1.3.6.1.4.1.37950.1.1.5.12.9.3.14.1.15
-- 1.3.6.1.4.1.37950.1.1.5.12.9.3.14.1.15
		-- 1.3.6.1.4.1.37950.1.1.5.12.9.3.14.1.15
		sipHBeatCycle OBJECT-TYPE
			SYNTAX Integer32 (1..65525)
			MAX-ACCESS read-write
			STATUS current
			DESCRIPTION
				"Description."
			::= { voipSipParamEntry 15 }

		
--          1.3.6.1.4.1.37950.1.1.5.12.9.3.14.1.16
-- 1.3.6.1.4.1.37950.1.1.5.12.9.3.14.1.16
-- 1.3.6.1.4.1.37950.1.1.5.12.9.3.14.1.16
-- 1.3.6.1.4.1.37950.1.1.5.12.9.3.14.1.16
-- 1.3.6.1.4.1.37950.1.1.5.12.9.3.14.1.16
-- 1.3.6.1.4.1.37950.1.1.5.12.9.3.14.1.16
-- 1.3.6.1.4.1.37950.1.1.5.12.9.3.14.1.16
-- 1.3.6.1.4.1.37950.1.1.5.12.9.3.14.1.16
-- 1.3.6.1.4.1.37950.1.1.5.12.9.3.14.1.16
		-- 1.3.6.1.4.1.37950.1.1.5.12.9.3.14.1.16
		sipHBeatCount OBJECT-TYPE
			SYNTAX Integer32 (1..65535)
			MAX-ACCESS read-write
			STATUS current
			DESCRIPTION
				"Description."
			::= { voipSipParamEntry 16 }

		
--          1.3.6.1.4.1.37950.1.1.5.12.9.4
-- 1.3.6.1.4.1.37950.1.1.5.12.9.4
-- 1.3.6.1.4.1.37950.1.1.5.12.9.4
-- 1.3.6.1.4.1.37950.1.1.5.12.9.4
-- 1.3.6.1.4.1.37950.1.1.5.12.9.4
-- 1.3.6.1.4.1.37950.1.1.5.12.9.4
-- 1.3.6.1.4.1.37950.1.1.5.12.9.4
-- 1.3.6.1.4.1.37950.1.1.5.12.9.4
-- 1.3.6.1.4.1.37950.1.1.5.12.9.4
		-- 1.3.6.1.4.1.37950.1.1.5.12.9.4
		alarmProfileShow OBJECT IDENTIFIER ::= { onuProfileShow 4 }

		
--          1.3.6.1.4.1.37950.1.1.5.12.9.4.1
-- 1.3.6.1.4.1.37950.1.1.5.12.9.4.1
-- 1.3.6.1.4.1.37950.1.1.5.12.9.4.1
-- 1.3.6.1.4.1.37950.1.1.5.12.9.4.1
-- 1.3.6.1.4.1.37950.1.1.5.12.9.4.1
-- 1.3.6.1.4.1.37950.1.1.5.12.9.4.1
-- 1.3.6.1.4.1.37950.1.1.5.12.9.4.1
-- 1.3.6.1.4.1.37950.1.1.5.12.9.4.1
-- 1.3.6.1.4.1.37950.1.1.5.12.9.4.1
		-- 1.3.6.1.4.1.37950.1.1.5.12.9.4.1
		alarmOnuPFTable OBJECT-TYPE
			SYNTAX SEQUENCE OF AlarmOnuPFEntry
			MAX-ACCESS not-accessible
			STATUS current
			DESCRIPTION
				"Description."
			::= { alarmProfileShow 1 }

		
--          1.3.6.1.4.1.37950.1.1.5.12.9.4.1.1
-- 1.3.6.1.4.1.37950.1.1.5.12.9.4.1.1
-- 1.3.6.1.4.1.37950.1.1.5.12.9.4.1.1
-- 1.3.6.1.4.1.37950.1.1.5.12.9.4.1.1
-- 1.3.6.1.4.1.37950.1.1.5.12.9.4.1.1
-- 1.3.6.1.4.1.37950.1.1.5.12.9.4.1.1
-- 1.3.6.1.4.1.37950.1.1.5.12.9.4.1.1
-- 1.3.6.1.4.1.37950.1.1.5.12.9.4.1.1
-- 1.3.6.1.4.1.37950.1.1.5.12.9.4.1.1
		-- 1.3.6.1.4.1.37950.1.1.5.12.9.4.1.1
		alarmOnuPFEntry OBJECT-TYPE
			SYNTAX AlarmOnuPFEntry
			MAX-ACCESS not-accessible
			STATUS current
			DESCRIPTION
				"Description."
			INDEX { alarmOnuAlarmId, alarmOnunTypeS }
			::= { alarmOnuPFTable 1 }

		
		AlarmOnuPFEntry ::=
			SEQUENCE { 
				alarmOnuAlarmId
					Integer32,
				alarmOnunTypeS
					INTEGER,
				alarmOnuEnableS
					INTEGER
			 }

--          1.3.6.1.4.1.37950.1.1.5.12.9.4.1.1.1
-- 1.3.6.1.4.1.37950.1.1.5.12.9.4.1.1.1
-- 1.3.6.1.4.1.37950.1.1.5.12.9.4.1.1.1
-- 1.3.6.1.4.1.37950.1.1.5.12.9.4.1.1.1
-- 1.3.6.1.4.1.37950.1.1.5.12.9.4.1.1.1
-- 1.3.6.1.4.1.37950.1.1.5.12.9.4.1.1.1
-- 1.3.6.1.4.1.37950.1.1.5.12.9.4.1.1.1
-- 1.3.6.1.4.1.37950.1.1.5.12.9.4.1.1.1
-- 1.3.6.1.4.1.37950.1.1.5.12.9.4.1.1.1
		-- 1.3.6.1.4.1.37950.1.1.5.12.9.4.1.1.1
		alarmOnuAlarmId OBJECT-TYPE
			SYNTAX Integer32 (0..65535)
			MAX-ACCESS read-only
			STATUS current
			DESCRIPTION
				"Description."
			::= { alarmOnuPFEntry 1 }

		
--          1.3.6.1.4.1.37950.1.1.5.12.9.4.1.1.2
-- 1.3.6.1.4.1.37950.1.1.5.12.9.4.1.1.2
-- 1.3.6.1.4.1.37950.1.1.5.12.9.4.1.1.2
-- 1.3.6.1.4.1.37950.1.1.5.12.9.4.1.1.2
-- 1.3.6.1.4.1.37950.1.1.5.12.9.4.1.1.2
-- 1.3.6.1.4.1.37950.1.1.5.12.9.4.1.1.2
-- 1.3.6.1.4.1.37950.1.1.5.12.9.4.1.1.2
-- 1.3.6.1.4.1.37950.1.1.5.12.9.4.1.1.2
-- 1.3.6.1.4.1.37950.1.1.5.12.9.4.1.1.2
		-- 1.3.6.1.4.1.37950.1.1.5.12.9.4.1.1.2
		alarmOnunTypeS OBJECT-TYPE
			SYNTAX INTEGER
				{
				equipmentAlarm(1),
				powerAlarm(2),
				batteryMissing(3),
				batteryFailure(4),
				physicalIntrusion(5),
				onuSelfTestFailure(6),
				iadConnectionFailure(7),
				ponIfSwitch(8),
				sleepStatusUpdate(9)
				}
			MAX-ACCESS read-only
			STATUS current
			DESCRIPTION
				"Description."
			::= { alarmOnuPFEntry 2 }

		
--          1.3.6.1.4.1.37950.1.1.5.12.9.4.1.1.3
-- 1.3.6.1.4.1.37950.1.1.5.12.9.4.1.1.3
-- 1.3.6.1.4.1.37950.1.1.5.12.9.4.1.1.3
-- 1.3.6.1.4.1.37950.1.1.5.12.9.4.1.1.3
-- 1.3.6.1.4.1.37950.1.1.5.12.9.4.1.1.3
-- 1.3.6.1.4.1.37950.1.1.5.12.9.4.1.1.3
-- 1.3.6.1.4.1.37950.1.1.5.12.9.4.1.1.3
-- 1.3.6.1.4.1.37950.1.1.5.12.9.4.1.1.3
-- 1.3.6.1.4.1.37950.1.1.5.12.9.4.1.1.3
		-- 1.3.6.1.4.1.37950.1.1.5.12.9.4.1.1.3
		alarmOnuEnableS OBJECT-TYPE
			SYNTAX INTEGER
				{
				disable(0),
				enable(1)
				}
			MAX-ACCESS read-only
			STATUS current
			DESCRIPTION
				"Description."
			::= { alarmOnuPFEntry 3 }

		
--          1.3.6.1.4.1.37950.1.1.5.12.9.4.2
-- 1.3.6.1.4.1.37950.1.1.5.12.9.4.2
-- 1.3.6.1.4.1.37950.1.1.5.12.9.4.2
-- 1.3.6.1.4.1.37950.1.1.5.12.9.4.2
-- 1.3.6.1.4.1.37950.1.1.5.12.9.4.2
-- 1.3.6.1.4.1.37950.1.1.5.12.9.4.2
-- 1.3.6.1.4.1.37950.1.1.5.12.9.4.2
-- 1.3.6.1.4.1.37950.1.1.5.12.9.4.2
-- 1.3.6.1.4.1.37950.1.1.5.12.9.4.2
		-- 1.3.6.1.4.1.37950.1.1.5.12.9.4.2
		alarmOnuThrPFTable OBJECT-TYPE
			SYNTAX SEQUENCE OF AlarmOnuThrPFEntry
			MAX-ACCESS not-accessible
			STATUS current
			DESCRIPTION
				"Description."
			::= { alarmProfileShow 2 }

		
--          1.3.6.1.4.1.37950.1.1.5.12.9.4.2.1
-- 1.3.6.1.4.1.37950.1.1.5.12.9.4.2.1
-- 1.3.6.1.4.1.37950.1.1.5.12.9.4.2.1
-- 1.3.6.1.4.1.37950.1.1.5.12.9.4.2.1
-- 1.3.6.1.4.1.37950.1.1.5.12.9.4.2.1
-- 1.3.6.1.4.1.37950.1.1.5.12.9.4.2.1
-- 1.3.6.1.4.1.37950.1.1.5.12.9.4.2.1
-- 1.3.6.1.4.1.37950.1.1.5.12.9.4.2.1
-- 1.3.6.1.4.1.37950.1.1.5.12.9.4.2.1
		-- 1.3.6.1.4.1.37950.1.1.5.12.9.4.2.1
		alarmOnuThrPFEntry OBJECT-TYPE
			SYNTAX AlarmOnuThrPFEntry
			MAX-ACCESS not-accessible
			STATUS current
			DESCRIPTION
				"Description."
			INDEX { alarmOnuThrAlarmId, alarmOnuThrTypeS }
			::= { alarmOnuThrPFTable 1 }

		
		AlarmOnuThrPFEntry ::=
			SEQUENCE { 
				alarmOnuThrAlarmId
					Integer32,
				alarmOnuThrTypeS
					INTEGER,
				alarmOnuThrEnS
					INTEGER,
				alarmOnuThrAlarmS
					INTEGER,
				alarmOnuThrClearS
					INTEGER
			 }

--          1.3.6.1.4.1.37950.1.1.5.12.9.4.2.1.1
-- 1.3.6.1.4.1.37950.1.1.5.12.9.4.2.1.1
-- 1.3.6.1.4.1.37950.1.1.5.12.9.4.2.1.1
-- 1.3.6.1.4.1.37950.1.1.5.12.9.4.2.1.1
-- 1.3.6.1.4.1.37950.1.1.5.12.9.4.2.1.1
-- 1.3.6.1.4.1.37950.1.1.5.12.9.4.2.1.1
-- 1.3.6.1.4.1.37950.1.1.5.12.9.4.2.1.1
-- 1.3.6.1.4.1.37950.1.1.5.12.9.4.2.1.1
-- 1.3.6.1.4.1.37950.1.1.5.12.9.4.2.1.1
		-- 1.3.6.1.4.1.37950.1.1.5.12.9.4.2.1.1
		alarmOnuThrAlarmId OBJECT-TYPE
			SYNTAX Integer32 (0..65535)
			MAX-ACCESS read-only
			STATUS current
			DESCRIPTION
				"Description."
			::= { alarmOnuThrPFEntry 1 }

		
--          1.3.6.1.4.1.37950.1.1.5.12.9.4.2.1.2
-- 1.3.6.1.4.1.37950.1.1.5.12.9.4.2.1.2
-- 1.3.6.1.4.1.37950.1.1.5.12.9.4.2.1.2
-- 1.3.6.1.4.1.37950.1.1.5.12.9.4.2.1.2
-- 1.3.6.1.4.1.37950.1.1.5.12.9.4.2.1.2
-- 1.3.6.1.4.1.37950.1.1.5.12.9.4.2.1.2
-- 1.3.6.1.4.1.37950.1.1.5.12.9.4.2.1.2
-- 1.3.6.1.4.1.37950.1.1.5.12.9.4.2.1.2
-- 1.3.6.1.4.1.37950.1.1.5.12.9.4.2.1.2
		-- 1.3.6.1.4.1.37950.1.1.5.12.9.4.2.1.2
		alarmOnuThrTypeS OBJECT-TYPE
			SYNTAX INTEGER
				{
				onuTempHighAlarm(1),
				onuTempLowAlarm(2),
				batteryVoltLow(3)
				}
			MAX-ACCESS read-only
			STATUS current
			DESCRIPTION
				"Description."
			::= { alarmOnuThrPFEntry 2 }

		
--          1.3.6.1.4.1.37950.1.1.5.12.9.4.2.1.3
-- 1.3.6.1.4.1.37950.1.1.5.12.9.4.2.1.3
-- 1.3.6.1.4.1.37950.1.1.5.12.9.4.2.1.3
-- 1.3.6.1.4.1.37950.1.1.5.12.9.4.2.1.3
-- 1.3.6.1.4.1.37950.1.1.5.12.9.4.2.1.3
-- 1.3.6.1.4.1.37950.1.1.5.12.9.4.2.1.3
-- 1.3.6.1.4.1.37950.1.1.5.12.9.4.2.1.3
-- 1.3.6.1.4.1.37950.1.1.5.12.9.4.2.1.3
-- 1.3.6.1.4.1.37950.1.1.5.12.9.4.2.1.3
		-- 1.3.6.1.4.1.37950.1.1.5.12.9.4.2.1.3
		alarmOnuThrEnS OBJECT-TYPE
			SYNTAX INTEGER
				{
				disable(0),
				enable(1)
				}
			MAX-ACCESS read-only
			STATUS current
			DESCRIPTION
				"Description."
			::= { alarmOnuThrPFEntry 3 }

		
--          1.3.6.1.4.1.37950.1.1.5.12.9.4.2.1.4
-- 1.3.6.1.4.1.37950.1.1.5.12.9.4.2.1.4
-- 1.3.6.1.4.1.37950.1.1.5.12.9.4.2.1.4
-- 1.3.6.1.4.1.37950.1.1.5.12.9.4.2.1.4
-- 1.3.6.1.4.1.37950.1.1.5.12.9.4.2.1.4
-- 1.3.6.1.4.1.37950.1.1.5.12.9.4.2.1.4
-- 1.3.6.1.4.1.37950.1.1.5.12.9.4.2.1.4
-- 1.3.6.1.4.1.37950.1.1.5.12.9.4.2.1.4
-- 1.3.6.1.4.1.37950.1.1.5.12.9.4.2.1.4
		-- 1.3.6.1.4.1.37950.1.1.5.12.9.4.2.1.4
		alarmOnuThrAlarmS OBJECT-TYPE
			SYNTAX INTEGER
			MAX-ACCESS read-only
			STATUS current
			DESCRIPTION
				"Description."
			::= { alarmOnuThrPFEntry 4 }

		
--          1.3.6.1.4.1.37950.1.1.5.12.9.4.2.1.5
-- 1.3.6.1.4.1.37950.1.1.5.12.9.4.2.1.5
-- 1.3.6.1.4.1.37950.1.1.5.12.9.4.2.1.5
-- 1.3.6.1.4.1.37950.1.1.5.12.9.4.2.1.5
-- 1.3.6.1.4.1.37950.1.1.5.12.9.4.2.1.5
-- 1.3.6.1.4.1.37950.1.1.5.12.9.4.2.1.5
-- 1.3.6.1.4.1.37950.1.1.5.12.9.4.2.1.5
-- 1.3.6.1.4.1.37950.1.1.5.12.9.4.2.1.5
-- 1.3.6.1.4.1.37950.1.1.5.12.9.4.2.1.5
		-- 1.3.6.1.4.1.37950.1.1.5.12.9.4.2.1.5
		alarmOnuThrClearS OBJECT-TYPE
			SYNTAX INTEGER
			MAX-ACCESS read-only
			STATUS current
			DESCRIPTION
				"Description."
			::= { alarmOnuThrPFEntry 5 }

		
--          1.3.6.1.4.1.37950.1.1.5.12.9.4.3
-- 1.3.6.1.4.1.37950.1.1.5.12.9.4.3
-- 1.3.6.1.4.1.37950.1.1.5.12.9.4.3
-- 1.3.6.1.4.1.37950.1.1.5.12.9.4.3
-- 1.3.6.1.4.1.37950.1.1.5.12.9.4.3
-- 1.3.6.1.4.1.37950.1.1.5.12.9.4.3
-- 1.3.6.1.4.1.37950.1.1.5.12.9.4.3
-- 1.3.6.1.4.1.37950.1.1.5.12.9.4.3
-- 1.3.6.1.4.1.37950.1.1.5.12.9.4.3
		-- 1.3.6.1.4.1.37950.1.1.5.12.9.4.3
		alarmPonPFTable OBJECT-TYPE
			SYNTAX SEQUENCE OF AlarmPonPFEntry
			MAX-ACCESS not-accessible
			STATUS current
			DESCRIPTION
				"Description."
			::= { alarmProfileShow 3 }

		
--          1.3.6.1.4.1.37950.1.1.5.12.9.4.3.1
-- 1.3.6.1.4.1.37950.1.1.5.12.9.4.3.1
-- 1.3.6.1.4.1.37950.1.1.5.12.9.4.3.1
-- 1.3.6.1.4.1.37950.1.1.5.12.9.4.3.1
-- 1.3.6.1.4.1.37950.1.1.5.12.9.4.3.1
-- 1.3.6.1.4.1.37950.1.1.5.12.9.4.3.1
-- 1.3.6.1.4.1.37950.1.1.5.12.9.4.3.1
-- 1.3.6.1.4.1.37950.1.1.5.12.9.4.3.1
-- 1.3.6.1.4.1.37950.1.1.5.12.9.4.3.1
		-- 1.3.6.1.4.1.37950.1.1.5.12.9.4.3.1
		alarmPonPFEntry OBJECT-TYPE
			SYNTAX AlarmPonPFEntry
			MAX-ACCESS not-accessible
			STATUS current
			DESCRIPTION
				"Description."
			INDEX { alarmPonAlarmId, alarmPonTypeS }
			::= { alarmPonPFTable 1 }

		
		AlarmPonPFEntry ::=
			SEQUENCE { 
				alarmPonAlarmId
					Integer32,
				alarmPonTypeS
					INTEGER,
				alarmPonEnableS
					INTEGER,
				alarmPonAlarmS
					INTEGER,
				alarmPonClearS
					INTEGER
			 }

--          1.3.6.1.4.1.37950.1.1.5.12.9.4.3.1.1
-- 1.3.6.1.4.1.37950.1.1.5.12.9.4.3.1.1
-- 1.3.6.1.4.1.37950.1.1.5.12.9.4.3.1.1
-- 1.3.6.1.4.1.37950.1.1.5.12.9.4.3.1.1
-- 1.3.6.1.4.1.37950.1.1.5.12.9.4.3.1.1
-- 1.3.6.1.4.1.37950.1.1.5.12.9.4.3.1.1
-- 1.3.6.1.4.1.37950.1.1.5.12.9.4.3.1.1
-- 1.3.6.1.4.1.37950.1.1.5.12.9.4.3.1.1
-- 1.3.6.1.4.1.37950.1.1.5.12.9.4.3.1.1
		-- 1.3.6.1.4.1.37950.1.1.5.12.9.4.3.1.1
		alarmPonAlarmId OBJECT-TYPE
			SYNTAX Integer32 (0..65535)
			MAX-ACCESS read-only
			STATUS current
			DESCRIPTION
				"Description."
			::= { alarmPonPFEntry 1 }

		
--          1.3.6.1.4.1.37950.1.1.5.12.9.4.3.1.2
-- 1.3.6.1.4.1.37950.1.1.5.12.9.4.3.1.2
-- 1.3.6.1.4.1.37950.1.1.5.12.9.4.3.1.2
-- 1.3.6.1.4.1.37950.1.1.5.12.9.4.3.1.2
-- 1.3.6.1.4.1.37950.1.1.5.12.9.4.3.1.2
-- 1.3.6.1.4.1.37950.1.1.5.12.9.4.3.1.2
-- 1.3.6.1.4.1.37950.1.1.5.12.9.4.3.1.2
-- 1.3.6.1.4.1.37950.1.1.5.12.9.4.3.1.2
-- 1.3.6.1.4.1.37950.1.1.5.12.9.4.3.1.2
		-- 1.3.6.1.4.1.37950.1.1.5.12.9.4.3.1.2
		alarmPonTypeS OBJECT-TYPE
			SYNTAX INTEGER
				{
				rxPowerHighAlarm(1),
				rxPowerLowAlarm(2),
				txPowerHighAlarm(3),
				txPowerLowAlarm(4),
				txBiasHighAlarm(5),
				txBiasLowAlarm(6),
				vccHighAlarm(7),
				vccLowAlarm(8),
				tempHighAlarm(9),
				tempLowAlarm(10),
				rxPowerHighWarn(11),
				rxPowerLowWarn(12),
				txPowerHighWarn(13),
				txPowerLowWarn(14),
				txBiasHighWarn(15),
				txBiasLowWarn(16),
				vccHighWarn(17),
				vccLowWarn(18),
				tempHighWarn(19),
				tempLowWarn(20)
				}
			MAX-ACCESS read-only
			STATUS current
			DESCRIPTION
				"Description."
			::= { alarmPonPFEntry 2 }

		
--          1.3.6.1.4.1.37950.1.1.5.12.9.4.3.1.3
-- 1.3.6.1.4.1.37950.1.1.5.12.9.4.3.1.3
-- 1.3.6.1.4.1.37950.1.1.5.12.9.4.3.1.3
-- 1.3.6.1.4.1.37950.1.1.5.12.9.4.3.1.3
-- 1.3.6.1.4.1.37950.1.1.5.12.9.4.3.1.3
-- 1.3.6.1.4.1.37950.1.1.5.12.9.4.3.1.3
-- 1.3.6.1.4.1.37950.1.1.5.12.9.4.3.1.3
-- 1.3.6.1.4.1.37950.1.1.5.12.9.4.3.1.3
-- 1.3.6.1.4.1.37950.1.1.5.12.9.4.3.1.3
		-- 1.3.6.1.4.1.37950.1.1.5.12.9.4.3.1.3
		alarmPonEnableS OBJECT-TYPE
			SYNTAX INTEGER
				{
				disable(0),
				enable(1)
				}
			MAX-ACCESS read-only
			STATUS current
			DESCRIPTION
				"Description."
			::= { alarmPonPFEntry 3 }

		
--          1.3.6.1.4.1.37950.1.1.5.12.9.4.3.1.4
-- 1.3.6.1.4.1.37950.1.1.5.12.9.4.3.1.4
-- 1.3.6.1.4.1.37950.1.1.5.12.9.4.3.1.4
-- 1.3.6.1.4.1.37950.1.1.5.12.9.4.3.1.4
-- 1.3.6.1.4.1.37950.1.1.5.12.9.4.3.1.4
-- 1.3.6.1.4.1.37950.1.1.5.12.9.4.3.1.4
-- 1.3.6.1.4.1.37950.1.1.5.12.9.4.3.1.4
-- 1.3.6.1.4.1.37950.1.1.5.12.9.4.3.1.4
-- 1.3.6.1.4.1.37950.1.1.5.12.9.4.3.1.4
		-- 1.3.6.1.4.1.37950.1.1.5.12.9.4.3.1.4
		alarmPonAlarmS OBJECT-TYPE
			SYNTAX INTEGER
			MAX-ACCESS read-only
			STATUS current
			DESCRIPTION
				"Description."
			::= { alarmPonPFEntry 4 }

		
--          1.3.6.1.4.1.37950.1.1.5.12.9.4.3.1.5
-- 1.3.6.1.4.1.37950.1.1.5.12.9.4.3.1.5
-- 1.3.6.1.4.1.37950.1.1.5.12.9.4.3.1.5
-- 1.3.6.1.4.1.37950.1.1.5.12.9.4.3.1.5
-- 1.3.6.1.4.1.37950.1.1.5.12.9.4.3.1.5
-- 1.3.6.1.4.1.37950.1.1.5.12.9.4.3.1.5
-- 1.3.6.1.4.1.37950.1.1.5.12.9.4.3.1.5
-- 1.3.6.1.4.1.37950.1.1.5.12.9.4.3.1.5
-- 1.3.6.1.4.1.37950.1.1.5.12.9.4.3.1.5
		-- 1.3.6.1.4.1.37950.1.1.5.12.9.4.3.1.5
		alarmPonClearS OBJECT-TYPE
			SYNTAX INTEGER
			MAX-ACCESS read-only
			STATUS current
			DESCRIPTION
				"Description."
			::= { alarmPonPFEntry 5 }

		
--          1.3.6.1.4.1.37950.1.1.5.12.9.4.4
-- 1.3.6.1.4.1.37950.1.1.5.12.9.4.4
-- 1.3.6.1.4.1.37950.1.1.5.12.9.4.4
-- 1.3.6.1.4.1.37950.1.1.5.12.9.4.4
-- 1.3.6.1.4.1.37950.1.1.5.12.9.4.4
-- 1.3.6.1.4.1.37950.1.1.5.12.9.4.4
-- 1.3.6.1.4.1.37950.1.1.5.12.9.4.4
-- 1.3.6.1.4.1.37950.1.1.5.12.9.4.4
-- 1.3.6.1.4.1.37950.1.1.5.12.9.4.4
		-- 1.3.6.1.4.1.37950.1.1.5.12.9.4.4
		alarmPonStatPFTable OBJECT-TYPE
			SYNTAX SEQUENCE OF AlarmPonStatPFEntry
			MAX-ACCESS not-accessible
			STATUS current
			DESCRIPTION
				"Description."
			::= { alarmProfileShow 4 }

		
--          1.3.6.1.4.1.37950.1.1.5.12.9.4.4.1
-- 1.3.6.1.4.1.37950.1.1.5.12.9.4.4.1
-- 1.3.6.1.4.1.37950.1.1.5.12.9.4.4.1
-- 1.3.6.1.4.1.37950.1.1.5.12.9.4.4.1
-- 1.3.6.1.4.1.37950.1.1.5.12.9.4.4.1
-- 1.3.6.1.4.1.37950.1.1.5.12.9.4.4.1
-- 1.3.6.1.4.1.37950.1.1.5.12.9.4.4.1
-- 1.3.6.1.4.1.37950.1.1.5.12.9.4.4.1
-- 1.3.6.1.4.1.37950.1.1.5.12.9.4.4.1
		-- 1.3.6.1.4.1.37950.1.1.5.12.9.4.4.1
		alarmPonStatPFEntry OBJECT-TYPE
			SYNTAX AlarmPonStatPFEntry
			MAX-ACCESS not-accessible
			STATUS current
			DESCRIPTION
				"Description."
			INDEX { alarmPonStatAlarmId, alarmPonStatTypeS }
			::= { alarmPonStatPFTable 1 }

		
		AlarmPonStatPFEntry ::=
			SEQUENCE { 
				alarmPonStatAlarmId
					Integer32,
				alarmPonStatTypeS
					INTEGER,
				alarmPonStatEnableS
					INTEGER,
				alarmPonStatThldS
					INTEGER
			 }

--          1.3.6.1.4.1.37950.1.1.5.12.9.4.4.1.1
-- 1.3.6.1.4.1.37950.1.1.5.12.9.4.4.1.1
-- 1.3.6.1.4.1.37950.1.1.5.12.9.4.4.1.1
-- 1.3.6.1.4.1.37950.1.1.5.12.9.4.4.1.1
-- 1.3.6.1.4.1.37950.1.1.5.12.9.4.4.1.1
-- 1.3.6.1.4.1.37950.1.1.5.12.9.4.4.1.1
-- 1.3.6.1.4.1.37950.1.1.5.12.9.4.4.1.1
-- 1.3.6.1.4.1.37950.1.1.5.12.9.4.4.1.1
-- 1.3.6.1.4.1.37950.1.1.5.12.9.4.4.1.1
		-- 1.3.6.1.4.1.37950.1.1.5.12.9.4.4.1.1
		alarmPonStatAlarmId OBJECT-TYPE
			SYNTAX Integer32 (0..65535)
			MAX-ACCESS read-only
			STATUS current
			DESCRIPTION
				"Description."
			::= { alarmPonStatPFEntry 1 }

		
--          1.3.6.1.4.1.37950.1.1.5.12.9.4.4.1.2
-- 1.3.6.1.4.1.37950.1.1.5.12.9.4.4.1.2
-- 1.3.6.1.4.1.37950.1.1.5.12.9.4.4.1.2
-- 1.3.6.1.4.1.37950.1.1.5.12.9.4.4.1.2
-- 1.3.6.1.4.1.37950.1.1.5.12.9.4.4.1.2
-- 1.3.6.1.4.1.37950.1.1.5.12.9.4.4.1.2
-- 1.3.6.1.4.1.37950.1.1.5.12.9.4.4.1.2
-- 1.3.6.1.4.1.37950.1.1.5.12.9.4.4.1.2
-- 1.3.6.1.4.1.37950.1.1.5.12.9.4.4.1.2
		-- 1.3.6.1.4.1.37950.1.1.5.12.9.4.4.1.2
		alarmPonStatTypeS OBJECT-TYPE
			SYNTAX INTEGER
				{
				downstreamDropEventsAlarm(1),
				upstreamDropEventsAlarm(2),
				downstreamCRCErrorFramesAlarm(3),
				upstreamCRCErrorFramesAlarm(4),
				downstreamUndersizeFramesAlarm(5),
				upstreamUndersizeFramesAlarm(6),
				downstreamOversizeFramesAlarm(7),
				upstreamOversizeFramesAlarm(8),
				downstreamFragmentsAlarm(9),
				upstreamFragmentsAlarm(10),
				downstreamJabbersAlarm(11),
				upstreamJabbersAlarm(12),
				downstreamDiscardsAlarm(13),
				upstreamDiscardsAlarm(14),
				downstreamErrorsAlarm(15),
				upstreamErrorsAlarm(16),
				downstreamDropEventsWarning(17),
				upstreamDropEventsWarning(18),
				downstreamCRCErrorFramesWarning(19),
				upstreamCRCErrorFramesWarning(20),
				downstreamUndersizeFramesWarning(21),
				upstreamUndersizeFramesWarning(22),
				downstreamOversizeFramesWarning(23),
				upstreamOversizeFramesWarning(24),
				downstreamFragmentsWarning(25),
				upstreamFragmentsWarning(26),
				downstreamJabbersWarning(27),
				upstreamJabbersWarning(28),
				downstreamDiscardsWarning(29),
				upstreamDiscardsWarning(30),
				downstreamErrorsWarning(31),
				upstreamErrorsWarning(32)
				}
			MAX-ACCESS read-only
			STATUS current
			DESCRIPTION
				"Description."
			::= { alarmPonStatPFEntry 2 }

		
--          1.3.6.1.4.1.37950.1.1.5.12.9.4.4.1.3
-- 1.3.6.1.4.1.37950.1.1.5.12.9.4.4.1.3
-- 1.3.6.1.4.1.37950.1.1.5.12.9.4.4.1.3
-- 1.3.6.1.4.1.37950.1.1.5.12.9.4.4.1.3
-- 1.3.6.1.4.1.37950.1.1.5.12.9.4.4.1.3
-- 1.3.6.1.4.1.37950.1.1.5.12.9.4.4.1.3
-- 1.3.6.1.4.1.37950.1.1.5.12.9.4.4.1.3
-- 1.3.6.1.4.1.37950.1.1.5.12.9.4.4.1.3
-- 1.3.6.1.4.1.37950.1.1.5.12.9.4.4.1.3
		-- 1.3.6.1.4.1.37950.1.1.5.12.9.4.4.1.3
		alarmPonStatEnableS OBJECT-TYPE
			SYNTAX INTEGER
				{
				disable(0),
				enable(1)
				}
			MAX-ACCESS read-only
			STATUS current
			DESCRIPTION
				"Description."
			::= { alarmPonStatPFEntry 3 }

		
--          1.3.6.1.4.1.37950.1.1.5.12.9.4.4.1.4
-- 1.3.6.1.4.1.37950.1.1.5.12.9.4.4.1.4
-- 1.3.6.1.4.1.37950.1.1.5.12.9.4.4.1.4
-- 1.3.6.1.4.1.37950.1.1.5.12.9.4.4.1.4
-- 1.3.6.1.4.1.37950.1.1.5.12.9.4.4.1.4
-- 1.3.6.1.4.1.37950.1.1.5.12.9.4.4.1.4
-- 1.3.6.1.4.1.37950.1.1.5.12.9.4.4.1.4
-- 1.3.6.1.4.1.37950.1.1.5.12.9.4.4.1.4
-- 1.3.6.1.4.1.37950.1.1.5.12.9.4.4.1.4
		-- 1.3.6.1.4.1.37950.1.1.5.12.9.4.4.1.4
		alarmPonStatThldS OBJECT-TYPE
			SYNTAX INTEGER (0..65535)
			MAX-ACCESS read-only
			STATUS current
			DESCRIPTION
				"Description."
			::= { alarmPonStatPFEntry 4 }

		
--          1.3.6.1.4.1.37950.1.1.5.12.9.4.5
-- 1.3.6.1.4.1.37950.1.1.5.12.9.4.5
-- 1.3.6.1.4.1.37950.1.1.5.12.9.4.5
-- 1.3.6.1.4.1.37950.1.1.5.12.9.4.5
-- 1.3.6.1.4.1.37950.1.1.5.12.9.4.5
-- 1.3.6.1.4.1.37950.1.1.5.12.9.4.5
-- 1.3.6.1.4.1.37950.1.1.5.12.9.4.5
-- 1.3.6.1.4.1.37950.1.1.5.12.9.4.5
-- 1.3.6.1.4.1.37950.1.1.5.12.9.4.5
		-- 1.3.6.1.4.1.37950.1.1.5.12.9.4.5
		alarmPortPFTable OBJECT-TYPE
			SYNTAX SEQUENCE OF AlarmPortPFEntry
			MAX-ACCESS not-accessible
			STATUS current
			DESCRIPTION
				"Description."
			::= { alarmProfileShow 5 }

		
--          1.3.6.1.4.1.37950.1.1.5.12.9.4.5.1
-- 1.3.6.1.4.1.37950.1.1.5.12.9.4.5.1
-- 1.3.6.1.4.1.37950.1.1.5.12.9.4.5.1
-- 1.3.6.1.4.1.37950.1.1.5.12.9.4.5.1
-- 1.3.6.1.4.1.37950.1.1.5.12.9.4.5.1
-- 1.3.6.1.4.1.37950.1.1.5.12.9.4.5.1
-- 1.3.6.1.4.1.37950.1.1.5.12.9.4.5.1
-- 1.3.6.1.4.1.37950.1.1.5.12.9.4.5.1
-- 1.3.6.1.4.1.37950.1.1.5.12.9.4.5.1
		-- 1.3.6.1.4.1.37950.1.1.5.12.9.4.5.1
		alarmPortPFEntry OBJECT-TYPE
			SYNTAX AlarmPortPFEntry
			MAX-ACCESS not-accessible
			STATUS current
			DESCRIPTION
				"Description."
			INDEX { alarmPortAlarmId, alarmPortNoS, alarmPortTpyeS }
			::= { alarmPortPFTable 1 }

		
		AlarmPortPFEntry ::=
			SEQUENCE { 
				alarmPortAlarmId
					Integer32,
				alarmPortNoS
					INTEGER,
				alarmPortTpyeS
					INTEGER,
				alarmPortEnableS
					INTEGER
			 }

--          1.3.6.1.4.1.37950.1.1.5.12.9.4.5.1.1
-- 1.3.6.1.4.1.37950.1.1.5.12.9.4.5.1.1
-- 1.3.6.1.4.1.37950.1.1.5.12.9.4.5.1.1
-- 1.3.6.1.4.1.37950.1.1.5.12.9.4.5.1.1
-- 1.3.6.1.4.1.37950.1.1.5.12.9.4.5.1.1
-- 1.3.6.1.4.1.37950.1.1.5.12.9.4.5.1.1
-- 1.3.6.1.4.1.37950.1.1.5.12.9.4.5.1.1
-- 1.3.6.1.4.1.37950.1.1.5.12.9.4.5.1.1
-- 1.3.6.1.4.1.37950.1.1.5.12.9.4.5.1.1
		-- 1.3.6.1.4.1.37950.1.1.5.12.9.4.5.1.1
		alarmPortAlarmId OBJECT-TYPE
			SYNTAX Integer32 (0..65535)
			MAX-ACCESS read-only
			STATUS current
			DESCRIPTION
				"Description."
			::= { alarmPortPFEntry 1 }

		
--          1.3.6.1.4.1.37950.1.1.5.12.9.4.5.1.2
-- 1.3.6.1.4.1.37950.1.1.5.12.9.4.5.1.2
-- 1.3.6.1.4.1.37950.1.1.5.12.9.4.5.1.2
-- 1.3.6.1.4.1.37950.1.1.5.12.9.4.5.1.2
-- 1.3.6.1.4.1.37950.1.1.5.12.9.4.5.1.2
-- 1.3.6.1.4.1.37950.1.1.5.12.9.4.5.1.2
-- 1.3.6.1.4.1.37950.1.1.5.12.9.4.5.1.2
-- 1.3.6.1.4.1.37950.1.1.5.12.9.4.5.1.2
-- 1.3.6.1.4.1.37950.1.1.5.12.9.4.5.1.2
		-- 1.3.6.1.4.1.37950.1.1.5.12.9.4.5.1.2
		alarmPortNoS OBJECT-TYPE
			SYNTAX INTEGER (1..255)
			MAX-ACCESS read-only
			STATUS current
			DESCRIPTION
				"Description."
			::= { alarmPortPFEntry 2 }

		
--          1.3.6.1.4.1.37950.1.1.5.12.9.4.5.1.3
-- 1.3.6.1.4.1.37950.1.1.5.12.9.4.5.1.3
-- 1.3.6.1.4.1.37950.1.1.5.12.9.4.5.1.3
-- 1.3.6.1.4.1.37950.1.1.5.12.9.4.5.1.3
-- 1.3.6.1.4.1.37950.1.1.5.12.9.4.5.1.3
-- 1.3.6.1.4.1.37950.1.1.5.12.9.4.5.1.3
-- 1.3.6.1.4.1.37950.1.1.5.12.9.4.5.1.3
-- 1.3.6.1.4.1.37950.1.1.5.12.9.4.5.1.3
-- 1.3.6.1.4.1.37950.1.1.5.12.9.4.5.1.3
		-- 1.3.6.1.4.1.37950.1.1.5.12.9.4.5.1.3
		alarmPortTpyeS OBJECT-TYPE
			SYNTAX INTEGER
				{
				ethPortAutoNegFailure(1),
				ethPortLos(2),
				ethPortFailure(3),
				ethPortLoopback(4),
				ethPortCongestion(5)
				}
			MAX-ACCESS read-only
			STATUS current
			DESCRIPTION
				"Description."
			::= { alarmPortPFEntry 3 }

		
--          1.3.6.1.4.1.37950.1.1.5.12.9.4.5.1.4
-- 1.3.6.1.4.1.37950.1.1.5.12.9.4.5.1.4
-- 1.3.6.1.4.1.37950.1.1.5.12.9.4.5.1.4
-- 1.3.6.1.4.1.37950.1.1.5.12.9.4.5.1.4
-- 1.3.6.1.4.1.37950.1.1.5.12.9.4.5.1.4
-- 1.3.6.1.4.1.37950.1.1.5.12.9.4.5.1.4
-- 1.3.6.1.4.1.37950.1.1.5.12.9.4.5.1.4
-- 1.3.6.1.4.1.37950.1.1.5.12.9.4.5.1.4
-- 1.3.6.1.4.1.37950.1.1.5.12.9.4.5.1.4
		-- 1.3.6.1.4.1.37950.1.1.5.12.9.4.5.1.4
		alarmPortEnableS OBJECT-TYPE
			SYNTAX INTEGER
				{
				disable(0),
				enable(1)
				}
			MAX-ACCESS read-only
			STATUS current
			DESCRIPTION
				"Description."
			::= { alarmPortPFEntry 4 }

		
--          1.3.6.1.4.1.37950.1.1.5.12.9.4.6
-- 1.3.6.1.4.1.37950.1.1.5.12.9.4.6
-- 1.3.6.1.4.1.37950.1.1.5.12.9.4.6
-- 1.3.6.1.4.1.37950.1.1.5.12.9.4.6
-- 1.3.6.1.4.1.37950.1.1.5.12.9.4.6
-- 1.3.6.1.4.1.37950.1.1.5.12.9.4.6
-- 1.3.6.1.4.1.37950.1.1.5.12.9.4.6
-- 1.3.6.1.4.1.37950.1.1.5.12.9.4.6
-- 1.3.6.1.4.1.37950.1.1.5.12.9.4.6
		-- 1.3.6.1.4.1.37950.1.1.5.12.9.4.6
		alarmPortStatPFTable OBJECT-TYPE
			SYNTAX SEQUENCE OF AlarmPortStatPFEntry
			MAX-ACCESS not-accessible
			STATUS current
			DESCRIPTION
				"Description."
			::= { alarmProfileShow 6 }

		
--          1.3.6.1.4.1.37950.1.1.5.12.9.4.6.1
-- 1.3.6.1.4.1.37950.1.1.5.12.9.4.6.1
-- 1.3.6.1.4.1.37950.1.1.5.12.9.4.6.1
-- 1.3.6.1.4.1.37950.1.1.5.12.9.4.6.1
-- 1.3.6.1.4.1.37950.1.1.5.12.9.4.6.1
-- 1.3.6.1.4.1.37950.1.1.5.12.9.4.6.1
-- 1.3.6.1.4.1.37950.1.1.5.12.9.4.6.1
-- 1.3.6.1.4.1.37950.1.1.5.12.9.4.6.1
-- 1.3.6.1.4.1.37950.1.1.5.12.9.4.6.1
		-- 1.3.6.1.4.1.37950.1.1.5.12.9.4.6.1
		alarmPortStatPFEntry OBJECT-TYPE
			SYNTAX AlarmPortStatPFEntry
			MAX-ACCESS not-accessible
			STATUS current
			DESCRIPTION
				"Description."
			INDEX { alarmPortStatAlarmID, alarmPortStatEthNoS, alarmPortStatTypeS }
			::= { alarmPortStatPFTable 1 }

		
		AlarmPortStatPFEntry ::=
			SEQUENCE { 
				alarmPortStatAlarmID
					Integer32,
				alarmPortStatEthNoS
					INTEGER,
				alarmPortStatTypeS
					INTEGER,
				alarmPortStatEnableS
					INTEGER,
				alarmPortStatTrldS
					INTEGER
			 }

--          1.3.6.1.4.1.37950.1.1.5.12.9.4.6.1.1
-- 1.3.6.1.4.1.37950.1.1.5.12.9.4.6.1.1
-- 1.3.6.1.4.1.37950.1.1.5.12.9.4.6.1.1
-- 1.3.6.1.4.1.37950.1.1.5.12.9.4.6.1.1
-- 1.3.6.1.4.1.37950.1.1.5.12.9.4.6.1.1
-- 1.3.6.1.4.1.37950.1.1.5.12.9.4.6.1.1
-- 1.3.6.1.4.1.37950.1.1.5.12.9.4.6.1.1
-- 1.3.6.1.4.1.37950.1.1.5.12.9.4.6.1.1
-- 1.3.6.1.4.1.37950.1.1.5.12.9.4.6.1.1
		-- 1.3.6.1.4.1.37950.1.1.5.12.9.4.6.1.1
		alarmPortStatAlarmID OBJECT-TYPE
			SYNTAX Integer32 (0..65535)
			MAX-ACCESS read-only
			STATUS current
			DESCRIPTION
				"Description."
			::= { alarmPortStatPFEntry 1 }

		
--          1.3.6.1.4.1.37950.1.1.5.12.9.4.6.1.2
-- 1.3.6.1.4.1.37950.1.1.5.12.9.4.6.1.2
-- 1.3.6.1.4.1.37950.1.1.5.12.9.4.6.1.2
-- 1.3.6.1.4.1.37950.1.1.5.12.9.4.6.1.2
-- 1.3.6.1.4.1.37950.1.1.5.12.9.4.6.1.2
-- 1.3.6.1.4.1.37950.1.1.5.12.9.4.6.1.2
-- 1.3.6.1.4.1.37950.1.1.5.12.9.4.6.1.2
-- 1.3.6.1.4.1.37950.1.1.5.12.9.4.6.1.2
-- 1.3.6.1.4.1.37950.1.1.5.12.9.4.6.1.2
		-- 1.3.6.1.4.1.37950.1.1.5.12.9.4.6.1.2
		alarmPortStatEthNoS OBJECT-TYPE
			SYNTAX INTEGER (1..255)
			MAX-ACCESS read-only
			STATUS current
			DESCRIPTION
				"Description."
			::= { alarmPortStatPFEntry 2 }

		
--          1.3.6.1.4.1.37950.1.1.5.12.9.4.6.1.3
-- 1.3.6.1.4.1.37950.1.1.5.12.9.4.6.1.3
-- 1.3.6.1.4.1.37950.1.1.5.12.9.4.6.1.3
-- 1.3.6.1.4.1.37950.1.1.5.12.9.4.6.1.3
-- 1.3.6.1.4.1.37950.1.1.5.12.9.4.6.1.3
-- 1.3.6.1.4.1.37950.1.1.5.12.9.4.6.1.3
-- 1.3.6.1.4.1.37950.1.1.5.12.9.4.6.1.3
-- 1.3.6.1.4.1.37950.1.1.5.12.9.4.6.1.3
-- 1.3.6.1.4.1.37950.1.1.5.12.9.4.6.1.3
		-- 1.3.6.1.4.1.37950.1.1.5.12.9.4.6.1.3
		alarmPortStatTypeS OBJECT-TYPE
			SYNTAX INTEGER
				{
				downstreamDropEventsAlarm(1),
				upstreamDropEventsAlarm(2),
				downstreamCRCErrorFramesAlarm(3),
				upstreamCRCErrorFramesAlarm(4),
				downstreamUndersizeFramesAlarm(5),
				upstreamUndersizeFramesAlarm(6),
				downstreamOversizeFramesAlarm(7),
				upstreamOversizeFramesAlarm(8),
				downstreamFragmentsAlarm(9),
				upstreamFragmentsAlarm(10),
				downstreamJabbersAlarm(11),
				upstreamJabbersAlarm(12),
				downstreamDiscardsAlarm(13),
				upstreamDiscardsAlarm(14),
				downstreamErrorsAlarm(15),
				upstreamErrorsAlarm(16),
				statusChangeTimesAlarm(17),
				downstreamDropEventsWarning(18),
				upstreamDropEventsWarning(19),
				downstreamCRCErrorFramesWarning(20),
				upstreamCRCErrorFramesWarning(21),
				downstreamUndersizeFramesWarning(22),
				upstreamUndersizeFramesWarning(23),
				downstreamOversizeFramesWarning(24),
				upstreamOversizeFramesWarning(25),
				downstreamFragmentsWarning(26),
				upstreamFragmentsWarning(27),
				downstreamJabbersWarning(28),
				upstreamJabbersWarning(29),
				downstreamDiscardsWarning(30),
				upstreamDiscardsWarning(31),
				downstreamErrorsWarning(32),
				upstreamErrorsWarning(33),
				statusChangeTimesWarning(34)
				}
			MAX-ACCESS read-only
			STATUS current
			DESCRIPTION
				"Description."
			::= { alarmPortStatPFEntry 3 }

		
--          1.3.6.1.4.1.37950.1.1.5.12.9.4.6.1.4
-- 1.3.6.1.4.1.37950.1.1.5.12.9.4.6.1.4
-- 1.3.6.1.4.1.37950.1.1.5.12.9.4.6.1.4
-- 1.3.6.1.4.1.37950.1.1.5.12.9.4.6.1.4
-- 1.3.6.1.4.1.37950.1.1.5.12.9.4.6.1.4
-- 1.3.6.1.4.1.37950.1.1.5.12.9.4.6.1.4
-- 1.3.6.1.4.1.37950.1.1.5.12.9.4.6.1.4
-- 1.3.6.1.4.1.37950.1.1.5.12.9.4.6.1.4
-- 1.3.6.1.4.1.37950.1.1.5.12.9.4.6.1.4
		-- 1.3.6.1.4.1.37950.1.1.5.12.9.4.6.1.4
		alarmPortStatEnableS OBJECT-TYPE
			SYNTAX INTEGER
				{
				disable(0),
				enable(1)
				}
			MAX-ACCESS read-only
			STATUS current
			DESCRIPTION
				"Description."
			::= { alarmPortStatPFEntry 4 }

		
--          1.3.6.1.4.1.37950.1.1.5.12.9.4.6.1.5
-- 1.3.6.1.4.1.37950.1.1.5.12.9.4.6.1.5
-- 1.3.6.1.4.1.37950.1.1.5.12.9.4.6.1.5
-- 1.3.6.1.4.1.37950.1.1.5.12.9.4.6.1.5
-- 1.3.6.1.4.1.37950.1.1.5.12.9.4.6.1.5
-- 1.3.6.1.4.1.37950.1.1.5.12.9.4.6.1.5
-- 1.3.6.1.4.1.37950.1.1.5.12.9.4.6.1.5
-- 1.3.6.1.4.1.37950.1.1.5.12.9.4.6.1.5
-- 1.3.6.1.4.1.37950.1.1.5.12.9.4.6.1.5
		-- 1.3.6.1.4.1.37950.1.1.5.12.9.4.6.1.5
		alarmPortStatTrldS OBJECT-TYPE
			SYNTAX INTEGER (0..65535)
			MAX-ACCESS read-only
			STATUS current
			DESCRIPTION
				"Description."
			::= { alarmPortStatPFEntry 5 }

		
--          1.3.6.1.4.1.37950.1.1.5.12.9.4.7
-- 1.3.6.1.4.1.37950.1.1.5.12.9.4.7
-- 1.3.6.1.4.1.37950.1.1.5.12.9.4.7
-- 1.3.6.1.4.1.37950.1.1.5.12.9.4.7
-- 1.3.6.1.4.1.37950.1.1.5.12.9.4.7
-- 1.3.6.1.4.1.37950.1.1.5.12.9.4.7
-- 1.3.6.1.4.1.37950.1.1.5.12.9.4.7
-- 1.3.6.1.4.1.37950.1.1.5.12.9.4.7
-- 1.3.6.1.4.1.37950.1.1.5.12.9.4.7
		-- 1.3.6.1.4.1.37950.1.1.5.12.9.4.7
		alarmPotsPFTable OBJECT-TYPE
			SYNTAX SEQUENCE OF AlarmPotsPFEntry
			MAX-ACCESS not-accessible
			STATUS current
			DESCRIPTION
				"Description."
			::= { alarmProfileShow 7 }

		
--          1.3.6.1.4.1.37950.1.1.5.12.9.4.7.1
-- 1.3.6.1.4.1.37950.1.1.5.12.9.4.7.1
-- 1.3.6.1.4.1.37950.1.1.5.12.9.4.7.1
-- 1.3.6.1.4.1.37950.1.1.5.12.9.4.7.1
-- 1.3.6.1.4.1.37950.1.1.5.12.9.4.7.1
-- 1.3.6.1.4.1.37950.1.1.5.12.9.4.7.1
-- 1.3.6.1.4.1.37950.1.1.5.12.9.4.7.1
-- 1.3.6.1.4.1.37950.1.1.5.12.9.4.7.1
-- 1.3.6.1.4.1.37950.1.1.5.12.9.4.7.1
		-- 1.3.6.1.4.1.37950.1.1.5.12.9.4.7.1
		alarmPotsPFEntry OBJECT-TYPE
			SYNTAX AlarmPotsPFEntry
			MAX-ACCESS not-accessible
			STATUS current
			DESCRIPTION
				"Description."
			INDEX { alarmPotsAlarmId, alarmPotsNoS }
			::= { alarmPotsPFTable 1 }

		
		AlarmPotsPFEntry ::=
			SEQUENCE { 
				alarmPotsAlarmId
					Integer32,
				alarmPotsNoS
					INTEGER,
				alarmPotsFailEnableS
					INTEGER
			 }

--          1.3.6.1.4.1.37950.1.1.5.12.9.4.7.1.1
-- 1.3.6.1.4.1.37950.1.1.5.12.9.4.7.1.1
-- 1.3.6.1.4.1.37950.1.1.5.12.9.4.7.1.1
-- 1.3.6.1.4.1.37950.1.1.5.12.9.4.7.1.1
-- 1.3.6.1.4.1.37950.1.1.5.12.9.4.7.1.1
-- 1.3.6.1.4.1.37950.1.1.5.12.9.4.7.1.1
-- 1.3.6.1.4.1.37950.1.1.5.12.9.4.7.1.1
-- 1.3.6.1.4.1.37950.1.1.5.12.9.4.7.1.1
-- 1.3.6.1.4.1.37950.1.1.5.12.9.4.7.1.1
		-- 1.3.6.1.4.1.37950.1.1.5.12.9.4.7.1.1
		alarmPotsAlarmId OBJECT-TYPE
			SYNTAX Integer32 (0..65535)
			MAX-ACCESS read-only
			STATUS current
			DESCRIPTION
				"Description."
			::= { alarmPotsPFEntry 1 }

		
--          1.3.6.1.4.1.37950.1.1.5.12.9.4.7.1.2
-- 1.3.6.1.4.1.37950.1.1.5.12.9.4.7.1.2
-- 1.3.6.1.4.1.37950.1.1.5.12.9.4.7.1.2
-- 1.3.6.1.4.1.37950.1.1.5.12.9.4.7.1.2
-- 1.3.6.1.4.1.37950.1.1.5.12.9.4.7.1.2
-- 1.3.6.1.4.1.37950.1.1.5.12.9.4.7.1.2
-- 1.3.6.1.4.1.37950.1.1.5.12.9.4.7.1.2
-- 1.3.6.1.4.1.37950.1.1.5.12.9.4.7.1.2
-- 1.3.6.1.4.1.37950.1.1.5.12.9.4.7.1.2
		-- 1.3.6.1.4.1.37950.1.1.5.12.9.4.7.1.2
		alarmPotsNoS OBJECT-TYPE
			SYNTAX INTEGER (1..64)
			MAX-ACCESS read-only
			STATUS current
			DESCRIPTION
				"Description."
			::= { alarmPotsPFEntry 2 }

		
--          1.3.6.1.4.1.37950.1.1.5.12.9.4.7.1.3
-- 1.3.6.1.4.1.37950.1.1.5.12.9.4.7.1.3
-- 1.3.6.1.4.1.37950.1.1.5.12.9.4.7.1.3
-- 1.3.6.1.4.1.37950.1.1.5.12.9.4.7.1.3
-- 1.3.6.1.4.1.37950.1.1.5.12.9.4.7.1.3
-- 1.3.6.1.4.1.37950.1.1.5.12.9.4.7.1.3
-- 1.3.6.1.4.1.37950.1.1.5.12.9.4.7.1.3
-- 1.3.6.1.4.1.37950.1.1.5.12.9.4.7.1.3
-- 1.3.6.1.4.1.37950.1.1.5.12.9.4.7.1.3
		-- 1.3.6.1.4.1.37950.1.1.5.12.9.4.7.1.3
		alarmPotsFailEnableS OBJECT-TYPE
			SYNTAX INTEGER
				{
				disable(0),
				enable(1)
				}
			MAX-ACCESS read-only
			STATUS current
			DESCRIPTION
				"Description."
			::= { alarmPotsPFEntry 3 }

		
--          1.3.6.1.4.1.37950.1.1.5.12.9.4.8
-- 1.3.6.1.4.1.37950.1.1.5.12.9.4.8
-- 1.3.6.1.4.1.37950.1.1.5.12.9.4.8
-- 1.3.6.1.4.1.37950.1.1.5.12.9.4.8
-- 1.3.6.1.4.1.37950.1.1.5.12.9.4.8
-- 1.3.6.1.4.1.37950.1.1.5.12.9.4.8
-- 1.3.6.1.4.1.37950.1.1.5.12.9.4.8
-- 1.3.6.1.4.1.37950.1.1.5.12.9.4.8
-- 1.3.6.1.4.1.37950.1.1.5.12.9.4.8
		-- 1.3.6.1.4.1.37950.1.1.5.12.9.4.8
		alarmE1PFTable OBJECT-TYPE
			SYNTAX SEQUENCE OF AlarmE1PFEntry
			MAX-ACCESS not-accessible
			STATUS current
			DESCRIPTION
				"Description."
			::= { alarmProfileShow 8 }

		
--          1.3.6.1.4.1.37950.1.1.5.12.9.4.8.1
-- 1.3.6.1.4.1.37950.1.1.5.12.9.4.8.1
-- 1.3.6.1.4.1.37950.1.1.5.12.9.4.8.1
-- 1.3.6.1.4.1.37950.1.1.5.12.9.4.8.1
-- 1.3.6.1.4.1.37950.1.1.5.12.9.4.8.1
-- 1.3.6.1.4.1.37950.1.1.5.12.9.4.8.1
-- 1.3.6.1.4.1.37950.1.1.5.12.9.4.8.1
-- 1.3.6.1.4.1.37950.1.1.5.12.9.4.8.1
-- 1.3.6.1.4.1.37950.1.1.5.12.9.4.8.1
		-- 1.3.6.1.4.1.37950.1.1.5.12.9.4.8.1
		alarmE1PFEntry OBJECT-TYPE
			SYNTAX AlarmE1PFEntry
			MAX-ACCESS not-accessible
			STATUS current
			DESCRIPTION
				"Description."
			INDEX { alarmE1AlarmId, alarmE1NoS, alarmE1TypeS }
			::= { alarmE1PFTable 1 }

		
		AlarmE1PFEntry ::=
			SEQUENCE { 
				alarmE1AlarmId
					Integer32,
				alarmE1NoS
					INTEGER,
				alarmE1TypeS
					INTEGER,
				alarmE1EnableS
					INTEGER
			 }

--          1.3.6.1.4.1.37950.1.1.5.12.9.4.8.1.1
-- 1.3.6.1.4.1.37950.1.1.5.12.9.4.8.1.1
-- 1.3.6.1.4.1.37950.1.1.5.12.9.4.8.1.1
-- 1.3.6.1.4.1.37950.1.1.5.12.9.4.8.1.1
-- 1.3.6.1.4.1.37950.1.1.5.12.9.4.8.1.1
-- 1.3.6.1.4.1.37950.1.1.5.12.9.4.8.1.1
-- 1.3.6.1.4.1.37950.1.1.5.12.9.4.8.1.1
-- 1.3.6.1.4.1.37950.1.1.5.12.9.4.8.1.1
-- 1.3.6.1.4.1.37950.1.1.5.12.9.4.8.1.1
		-- 1.3.6.1.4.1.37950.1.1.5.12.9.4.8.1.1
		alarmE1AlarmId OBJECT-TYPE
			SYNTAX Integer32 (0..65535)
			MAX-ACCESS read-only
			STATUS current
			DESCRIPTION
				"Description."
			::= { alarmE1PFEntry 1 }

		
--          1.3.6.1.4.1.37950.1.1.5.12.9.4.8.1.2
-- 1.3.6.1.4.1.37950.1.1.5.12.9.4.8.1.2
-- 1.3.6.1.4.1.37950.1.1.5.12.9.4.8.1.2
-- 1.3.6.1.4.1.37950.1.1.5.12.9.4.8.1.2
-- 1.3.6.1.4.1.37950.1.1.5.12.9.4.8.1.2
-- 1.3.6.1.4.1.37950.1.1.5.12.9.4.8.1.2
-- 1.3.6.1.4.1.37950.1.1.5.12.9.4.8.1.2
-- 1.3.6.1.4.1.37950.1.1.5.12.9.4.8.1.2
-- 1.3.6.1.4.1.37950.1.1.5.12.9.4.8.1.2
		-- 1.3.6.1.4.1.37950.1.1.5.12.9.4.8.1.2
		alarmE1NoS OBJECT-TYPE
			SYNTAX INTEGER (1..16)
			MAX-ACCESS read-only
			STATUS current
			DESCRIPTION
				"Description."
			::= { alarmE1PFEntry 2 }

		
--          1.3.6.1.4.1.37950.1.1.5.12.9.4.8.1.3
-- 1.3.6.1.4.1.37950.1.1.5.12.9.4.8.1.3
-- 1.3.6.1.4.1.37950.1.1.5.12.9.4.8.1.3
-- 1.3.6.1.4.1.37950.1.1.5.12.9.4.8.1.3
-- 1.3.6.1.4.1.37950.1.1.5.12.9.4.8.1.3
-- 1.3.6.1.4.1.37950.1.1.5.12.9.4.8.1.3
-- 1.3.6.1.4.1.37950.1.1.5.12.9.4.8.1.3
-- 1.3.6.1.4.1.37950.1.1.5.12.9.4.8.1.3
-- 1.3.6.1.4.1.37950.1.1.5.12.9.4.8.1.3
		-- 1.3.6.1.4.1.37950.1.1.5.12.9.4.8.1.3
		alarmE1TypeS OBJECT-TYPE
			SYNTAX INTEGER
				{
				e1PortFailure(1),
				e1TimingUnlock(2),
				e1Los(3)
				}
			MAX-ACCESS read-only
			STATUS current
			DESCRIPTION
				"Description."
			::= { alarmE1PFEntry 3 }

		
--          1.3.6.1.4.1.37950.1.1.5.12.9.4.8.1.4
-- 1.3.6.1.4.1.37950.1.1.5.12.9.4.8.1.4
-- 1.3.6.1.4.1.37950.1.1.5.12.9.4.8.1.4
-- 1.3.6.1.4.1.37950.1.1.5.12.9.4.8.1.4
-- 1.3.6.1.4.1.37950.1.1.5.12.9.4.8.1.4
-- 1.3.6.1.4.1.37950.1.1.5.12.9.4.8.1.4
-- 1.3.6.1.4.1.37950.1.1.5.12.9.4.8.1.4
-- 1.3.6.1.4.1.37950.1.1.5.12.9.4.8.1.4
-- 1.3.6.1.4.1.37950.1.1.5.12.9.4.8.1.4
		-- 1.3.6.1.4.1.37950.1.1.5.12.9.4.8.1.4
		alarmE1EnableS OBJECT-TYPE
			SYNTAX INTEGER
				{
				enable(1),
				disable(2)
				}
			MAX-ACCESS read-only
			STATUS current
			DESCRIPTION
				"Description."
			::= { alarmE1PFEntry 4 }

		
--          1.3.6.1.4.1.37950.1.1.5.12.9.5
-- 1.3.6.1.4.1.37950.1.1.5.12.9.5
-- 1.3.6.1.4.1.37950.1.1.5.12.9.5
-- 1.3.6.1.4.1.37950.1.1.5.12.9.5
-- 1.3.6.1.4.1.37950.1.1.5.12.9.5
-- 1.3.6.1.4.1.37950.1.1.5.12.9.5
-- 1.3.6.1.4.1.37950.1.1.5.12.9.5
-- 1.3.6.1.4.1.37950.1.1.5.12.9.5
-- 1.3.6.1.4.1.37950.1.1.5.12.9.5
		-- 1.3.6.1.4.1.37950.1.1.5.12.9.5
		profileManualBindShow OBJECT IDENTIFIER ::= { onuProfileShow 5 }

		
--          1.3.6.1.4.1.37950.1.1.5.12.9.5.1
-- 1.3.6.1.4.1.37950.1.1.5.12.9.5.1
-- 1.3.6.1.4.1.37950.1.1.5.12.9.5.1
-- 1.3.6.1.4.1.37950.1.1.5.12.9.5.1
-- 1.3.6.1.4.1.37950.1.1.5.12.9.5.1
-- 1.3.6.1.4.1.37950.1.1.5.12.9.5.1
-- 1.3.6.1.4.1.37950.1.1.5.12.9.5.1
-- 1.3.6.1.4.1.37950.1.1.5.12.9.5.1
-- 1.3.6.1.4.1.37950.1.1.5.12.9.5.1
		-- 1.3.6.1.4.1.37950.1.1.5.12.9.5.1
		profileBindTable OBJECT-TYPE
			SYNTAX SEQUENCE OF ProfileBindEntry
			MAX-ACCESS not-accessible
			STATUS current
			DESCRIPTION
				"Description."
			::= { profileManualBindShow 1 }

		
--          1.3.6.1.4.1.37950.1.1.5.12.9.5.1.1
-- 1.3.6.1.4.1.37950.1.1.5.12.9.5.1.1
-- 1.3.6.1.4.1.37950.1.1.5.12.9.5.1.1
-- 1.3.6.1.4.1.37950.1.1.5.12.9.5.1.1
-- 1.3.6.1.4.1.37950.1.1.5.12.9.5.1.1
-- 1.3.6.1.4.1.37950.1.1.5.12.9.5.1.1
-- 1.3.6.1.4.1.37950.1.1.5.12.9.5.1.1
-- 1.3.6.1.4.1.37950.1.1.5.12.9.5.1.1
-- 1.3.6.1.4.1.37950.1.1.5.12.9.5.1.1
		-- 1.3.6.1.4.1.37950.1.1.5.12.9.5.1.1
		profileBindEntry OBJECT-TYPE
			SYNTAX ProfileBindEntry
			MAX-ACCESS not-accessible
			STATUS current
			DESCRIPTION
				"Description."
			INDEX { profileBindPonS, profileBindOnuS, profileBindTypeS }
			::= { profileBindTable 1 }

		
		ProfileBindEntry ::=
			SEQUENCE { 
				profileBindPonS
					Integer32,
				profileBindOnuS
					INTEGER,
				profileBindTypeS
					INTEGER,
				profileBindIdS
					INTEGER
			 }

--          1.3.6.1.4.1.37950.1.1.5.12.9.5.1.1.1
-- 1.3.6.1.4.1.37950.1.1.5.12.9.5.1.1.1
-- 1.3.6.1.4.1.37950.1.1.5.12.9.5.1.1.1
-- 1.3.6.1.4.1.37950.1.1.5.12.9.5.1.1.1
-- 1.3.6.1.4.1.37950.1.1.5.12.9.5.1.1.1
-- 1.3.6.1.4.1.37950.1.1.5.12.9.5.1.1.1
-- 1.3.6.1.4.1.37950.1.1.5.12.9.5.1.1.1
-- 1.3.6.1.4.1.37950.1.1.5.12.9.5.1.1.1
-- 1.3.6.1.4.1.37950.1.1.5.12.9.5.1.1.1
		-- 1.3.6.1.4.1.37950.1.1.5.12.9.5.1.1.1
		profileBindPonS OBJECT-TYPE
			SYNTAX Integer32 (1..16)
			MAX-ACCESS read-only
			STATUS current
			DESCRIPTION
				"Description."
			::= { profileBindEntry 1 }

		
--          1.3.6.1.4.1.37950.1.1.5.12.9.5.1.1.2
-- 1.3.6.1.4.1.37950.1.1.5.12.9.5.1.1.2
-- 1.3.6.1.4.1.37950.1.1.5.12.9.5.1.1.2
-- 1.3.6.1.4.1.37950.1.1.5.12.9.5.1.1.2
-- 1.3.6.1.4.1.37950.1.1.5.12.9.5.1.1.2
-- 1.3.6.1.4.1.37950.1.1.5.12.9.5.1.1.2
-- 1.3.6.1.4.1.37950.1.1.5.12.9.5.1.1.2
-- 1.3.6.1.4.1.37950.1.1.5.12.9.5.1.1.2
-- 1.3.6.1.4.1.37950.1.1.5.12.9.5.1.1.2
		-- 1.3.6.1.4.1.37950.1.1.5.12.9.5.1.1.2
		profileBindOnuS OBJECT-TYPE
			SYNTAX INTEGER (1..65535)
			MAX-ACCESS read-only
			STATUS current
			DESCRIPTION
				"Description."
			::= { profileBindEntry 2 }

		
--          1.3.6.1.4.1.37950.1.1.5.12.9.5.1.1.3
-- 1.3.6.1.4.1.37950.1.1.5.12.9.5.1.1.3
-- 1.3.6.1.4.1.37950.1.1.5.12.9.5.1.1.3
-- 1.3.6.1.4.1.37950.1.1.5.12.9.5.1.1.3
-- 1.3.6.1.4.1.37950.1.1.5.12.9.5.1.1.3
-- 1.3.6.1.4.1.37950.1.1.5.12.9.5.1.1.3
-- 1.3.6.1.4.1.37950.1.1.5.12.9.5.1.1.3
-- 1.3.6.1.4.1.37950.1.1.5.12.9.5.1.1.3
-- 1.3.6.1.4.1.37950.1.1.5.12.9.5.1.1.3
		-- 1.3.6.1.4.1.37950.1.1.5.12.9.5.1.1.3
		profileBindTypeS OBJECT-TYPE
			SYNTAX INTEGER
				{
				dba(1),
				srv(2),
				voip(3),
				alarm(4)
				}
			MAX-ACCESS read-only
			STATUS current
			DESCRIPTION
				"Description."
			::= { profileBindEntry 3 }

		
--          1.3.6.1.4.1.37950.1.1.5.12.9.5.1.1.4
-- 1.3.6.1.4.1.37950.1.1.5.12.9.5.1.1.4
-- 1.3.6.1.4.1.37950.1.1.5.12.9.5.1.1.4
-- 1.3.6.1.4.1.37950.1.1.5.12.9.5.1.1.4
-- 1.3.6.1.4.1.37950.1.1.5.12.9.5.1.1.4
-- 1.3.6.1.4.1.37950.1.1.5.12.9.5.1.1.4
-- 1.3.6.1.4.1.37950.1.1.5.12.9.5.1.1.4
-- 1.3.6.1.4.1.37950.1.1.5.12.9.5.1.1.4
-- 1.3.6.1.4.1.37950.1.1.5.12.9.5.1.1.4
		-- 1.3.6.1.4.1.37950.1.1.5.12.9.5.1.1.4
		profileBindIdS OBJECT-TYPE
			SYNTAX INTEGER (0..65535)
			MAX-ACCESS read-only
			STATUS current
			DESCRIPTION
				"Description."
			::= { profileBindEntry 4 }

		
--          1.3.6.1.4.1.37950.1.1.5.12.9.6
-- 1.3.6.1.4.1.37950.1.1.5.12.9.6
-- 1.3.6.1.4.1.37950.1.1.5.12.9.6
-- 1.3.6.1.4.1.37950.1.1.5.12.9.6
-- 1.3.6.1.4.1.37950.1.1.5.12.9.6
-- 1.3.6.1.4.1.37950.1.1.5.12.9.6
-- 1.3.6.1.4.1.37950.1.1.5.12.9.6
-- 1.3.6.1.4.1.37950.1.1.5.12.9.6
-- 1.3.6.1.4.1.37950.1.1.5.12.9.6
		-- 1.3.6.1.4.1.37950.1.1.5.12.9.6
		profileAutoBindShow OBJECT IDENTIFIER ::= { onuProfileShow 6 }

		
--          1.3.6.1.4.1.37950.1.1.5.12.9.6.1
-- 1.3.6.1.4.1.37950.1.1.5.12.9.6.1
-- 1.3.6.1.4.1.37950.1.1.5.12.9.6.1
-- 1.3.6.1.4.1.37950.1.1.5.12.9.6.1
-- 1.3.6.1.4.1.37950.1.1.5.12.9.6.1
-- 1.3.6.1.4.1.37950.1.1.5.12.9.6.1
-- 1.3.6.1.4.1.37950.1.1.5.12.9.6.1
-- 1.3.6.1.4.1.37950.1.1.5.12.9.6.1
-- 1.3.6.1.4.1.37950.1.1.5.12.9.6.1
		-- 1.3.6.1.4.1.37950.1.1.5.12.9.6.1
		profileAutoBindTable OBJECT-TYPE
			SYNTAX SEQUENCE OF ProfileAutoBindEntry
			MAX-ACCESS not-accessible
			STATUS current
			DESCRIPTION
				"Description."
			::= { profileAutoBindShow 1 }

		
--          1.3.6.1.4.1.37950.1.1.5.12.9.6.1.1
-- 1.3.6.1.4.1.37950.1.1.5.12.9.6.1.1
-- 1.3.6.1.4.1.37950.1.1.5.12.9.6.1.1
-- 1.3.6.1.4.1.37950.1.1.5.12.9.6.1.1
-- 1.3.6.1.4.1.37950.1.1.5.12.9.6.1.1
-- 1.3.6.1.4.1.37950.1.1.5.12.9.6.1.1
-- 1.3.6.1.4.1.37950.1.1.5.12.9.6.1.1
-- 1.3.6.1.4.1.37950.1.1.5.12.9.6.1.1
-- 1.3.6.1.4.1.37950.1.1.5.12.9.6.1.1
		-- 1.3.6.1.4.1.37950.1.1.5.12.9.6.1.1
		profileAutoBindEntry OBJECT-TYPE
			SYNTAX ProfileAutoBindEntry
			MAX-ACCESS not-accessible
			STATUS current
			DESCRIPTION
				"Description."
			INDEX { profileAutoBindId }
			::= { profileAutoBindTable 1 }

		
		ProfileAutoBindEntry ::=
			SEQUENCE { 
				profileAutoBindId
					INTEGER,
				profileAutoBindDbaS
					INTEGER,
				profileAutoBindSrvS
					INTEGER,
				profileAutoBindVoipS
					INTEGER,
				profileAutoBindAlarmS
					INTEGER,
				profileOnuTypeS
					OCTET STRING
			 }

--          1.3.6.1.4.1.37950.1.1.5.12.9.6.1.1.1
-- 1.3.6.1.4.1.37950.1.1.5.12.9.6.1.1.1
-- 1.3.6.1.4.1.37950.1.1.5.12.9.6.1.1.1
-- 1.3.6.1.4.1.37950.1.1.5.12.9.6.1.1.1
-- 1.3.6.1.4.1.37950.1.1.5.12.9.6.1.1.1
-- 1.3.6.1.4.1.37950.1.1.5.12.9.6.1.1.1
-- 1.3.6.1.4.1.37950.1.1.5.12.9.6.1.1.1
-- 1.3.6.1.4.1.37950.1.1.5.12.9.6.1.1.1
-- 1.3.6.1.4.1.37950.1.1.5.12.9.6.1.1.1
		-- 1.3.6.1.4.1.37950.1.1.5.12.9.6.1.1.1
		profileAutoBindId OBJECT-TYPE
			SYNTAX INTEGER
			MAX-ACCESS read-only
			STATUS current
			DESCRIPTION
				"Description."
			::= { profileAutoBindEntry 1 }

		
--          1.3.6.1.4.1.37950.1.1.5.12.9.6.1.1.2
-- 1.3.6.1.4.1.37950.1.1.5.12.9.6.1.1.2
-- 1.3.6.1.4.1.37950.1.1.5.12.9.6.1.1.2
-- 1.3.6.1.4.1.37950.1.1.5.12.9.6.1.1.2
-- 1.3.6.1.4.1.37950.1.1.5.12.9.6.1.1.2
-- 1.3.6.1.4.1.37950.1.1.5.12.9.6.1.1.2
-- 1.3.6.1.4.1.37950.1.1.5.12.9.6.1.1.2
-- 1.3.6.1.4.1.37950.1.1.5.12.9.6.1.1.2
-- 1.3.6.1.4.1.37950.1.1.5.12.9.6.1.1.2
		-- 1.3.6.1.4.1.37950.1.1.5.12.9.6.1.1.2
		profileAutoBindDbaS OBJECT-TYPE
			SYNTAX INTEGER (0..65535)
			MAX-ACCESS read-only
			STATUS current
			DESCRIPTION
				"Description."
			::= { profileAutoBindEntry 2 }

		
--          1.3.6.1.4.1.37950.1.1.5.12.9.6.1.1.3
-- 1.3.6.1.4.1.37950.1.1.5.12.9.6.1.1.3
-- 1.3.6.1.4.1.37950.1.1.5.12.9.6.1.1.3
-- 1.3.6.1.4.1.37950.1.1.5.12.9.6.1.1.3
-- 1.3.6.1.4.1.37950.1.1.5.12.9.6.1.1.3
-- 1.3.6.1.4.1.37950.1.1.5.12.9.6.1.1.3
-- 1.3.6.1.4.1.37950.1.1.5.12.9.6.1.1.3
-- 1.3.6.1.4.1.37950.1.1.5.12.9.6.1.1.3
-- 1.3.6.1.4.1.37950.1.1.5.12.9.6.1.1.3
		-- 1.3.6.1.4.1.37950.1.1.5.12.9.6.1.1.3
		profileAutoBindSrvS OBJECT-TYPE
			SYNTAX INTEGER (0..65535)
			MAX-ACCESS read-only
			STATUS current
			DESCRIPTION
				"Description."
			::= { profileAutoBindEntry 3 }

		
--          1.3.6.1.4.1.37950.1.1.5.12.9.6.1.1.4
-- 1.3.6.1.4.1.37950.1.1.5.12.9.6.1.1.4
-- 1.3.6.1.4.1.37950.1.1.5.12.9.6.1.1.4
-- 1.3.6.1.4.1.37950.1.1.5.12.9.6.1.1.4
-- 1.3.6.1.4.1.37950.1.1.5.12.9.6.1.1.4
-- 1.3.6.1.4.1.37950.1.1.5.12.9.6.1.1.4
-- 1.3.6.1.4.1.37950.1.1.5.12.9.6.1.1.4
-- 1.3.6.1.4.1.37950.1.1.5.12.9.6.1.1.4
-- 1.3.6.1.4.1.37950.1.1.5.12.9.6.1.1.4
		-- 1.3.6.1.4.1.37950.1.1.5.12.9.6.1.1.4
		profileAutoBindVoipS OBJECT-TYPE
			SYNTAX INTEGER (0..65535)
			MAX-ACCESS read-only
			STATUS current
			DESCRIPTION
				"Description."
			::= { profileAutoBindEntry 4 }

		
--          1.3.6.1.4.1.37950.1.1.5.12.9.6.1.1.5
-- 1.3.6.1.4.1.37950.1.1.5.12.9.6.1.1.5
-- 1.3.6.1.4.1.37950.1.1.5.12.9.6.1.1.5
-- 1.3.6.1.4.1.37950.1.1.5.12.9.6.1.1.5
-- 1.3.6.1.4.1.37950.1.1.5.12.9.6.1.1.5
-- 1.3.6.1.4.1.37950.1.1.5.12.9.6.1.1.5
-- 1.3.6.1.4.1.37950.1.1.5.12.9.6.1.1.5
-- 1.3.6.1.4.1.37950.1.1.5.12.9.6.1.1.5
-- 1.3.6.1.4.1.37950.1.1.5.12.9.6.1.1.5
		-- 1.3.6.1.4.1.37950.1.1.5.12.9.6.1.1.5
		profileAutoBindAlarmS OBJECT-TYPE
			SYNTAX INTEGER (0..65535)
			MAX-ACCESS read-only
			STATUS current
			DESCRIPTION
				"Description."
			::= { profileAutoBindEntry 5 }

		
--          1.3.6.1.4.1.37950.1.1.5.12.9.6.1.1.6
-- 1.3.6.1.4.1.37950.1.1.5.12.9.6.1.1.6
-- 1.3.6.1.4.1.37950.1.1.5.12.9.6.1.1.6
-- 1.3.6.1.4.1.37950.1.1.5.12.9.6.1.1.6
-- 1.3.6.1.4.1.37950.1.1.5.12.9.6.1.1.6
-- 1.3.6.1.4.1.37950.1.1.5.12.9.6.1.1.6
-- 1.3.6.1.4.1.37950.1.1.5.12.9.6.1.1.6
-- 1.3.6.1.4.1.37950.1.1.5.12.9.6.1.1.6
-- 1.3.6.1.4.1.37950.1.1.5.12.9.6.1.1.6
		-- 1.3.6.1.4.1.37950.1.1.5.12.9.6.1.1.6
		profileOnuTypeS OBJECT-TYPE
			SYNTAX OCTET STRING
			MAX-ACCESS read-only
			STATUS current
			DESCRIPTION
				"Description."
			::= { profileAutoBindEntry 6 }

		
--          1.3.6.1.4.1.37950.1.1.5.12.9.7
-- 1.3.6.1.4.1.37950.1.1.5.12.9.7
-- 1.3.6.1.4.1.37950.1.1.5.12.9.7
-- 1.3.6.1.4.1.37950.1.1.5.12.9.7
-- 1.3.6.1.4.1.37950.1.1.5.12.9.7
-- 1.3.6.1.4.1.37950.1.1.5.12.9.7
-- 1.3.6.1.4.1.37950.1.1.5.12.9.7
-- 1.3.6.1.4.1.37950.1.1.5.12.9.7
-- 1.3.6.1.4.1.37950.1.1.5.12.9.7
		-- 1.3.6.1.4.1.37950.1.1.5.12.9.7
		profileShow OBJECT IDENTIFIER ::= { onuProfileShow 7 }

		
--          1.3.6.1.4.1.37950.1.1.5.12.9.7.1
-- 1.3.6.1.4.1.37950.1.1.5.12.9.7.1
-- 1.3.6.1.4.1.37950.1.1.5.12.9.7.1
-- 1.3.6.1.4.1.37950.1.1.5.12.9.7.1
-- 1.3.6.1.4.1.37950.1.1.5.12.9.7.1
-- 1.3.6.1.4.1.37950.1.1.5.12.9.7.1
-- 1.3.6.1.4.1.37950.1.1.5.12.9.7.1
-- 1.3.6.1.4.1.37950.1.1.5.12.9.7.1
-- 1.3.6.1.4.1.37950.1.1.5.12.9.7.1
		-- 1.3.6.1.4.1.37950.1.1.5.12.9.7.1
		profileTable OBJECT-TYPE
			SYNTAX SEQUENCE OF ProfileEntry
			MAX-ACCESS not-accessible
			STATUS current
			DESCRIPTION
				"Description."
			::= { profileShow 1 }

		
--          1.3.6.1.4.1.37950.1.1.5.12.9.7.1.1
-- 1.3.6.1.4.1.37950.1.1.5.12.9.7.1.1
-- 1.3.6.1.4.1.37950.1.1.5.12.9.7.1.1
-- 1.3.6.1.4.1.37950.1.1.5.12.9.7.1.1
-- 1.3.6.1.4.1.37950.1.1.5.12.9.7.1.1
-- 1.3.6.1.4.1.37950.1.1.5.12.9.7.1.1
-- 1.3.6.1.4.1.37950.1.1.5.12.9.7.1.1
-- 1.3.6.1.4.1.37950.1.1.5.12.9.7.1.1
-- 1.3.6.1.4.1.37950.1.1.5.12.9.7.1.1
		-- 1.3.6.1.4.1.37950.1.1.5.12.9.7.1.1
		profileEntry OBJECT-TYPE
			SYNTAX ProfileEntry
			MAX-ACCESS not-accessible
			STATUS current
			DESCRIPTION
				"Description."
			INDEX { profileIdexShow }
			::= { profileTable 1 }

		
		ProfileEntry ::=
			SEQUENCE { 
				profileIdexShow
					Integer32,
				profileTypeShow
					INTEGER,
				profileIdShow
					Integer32,
				profileIdDescr
					OCTET STRING
			 }

--          1.3.6.1.4.1.37950.1.1.5.12.9.7.1.1.1
-- 1.3.6.1.4.1.37950.1.1.5.12.9.7.1.1.1
-- 1.3.6.1.4.1.37950.1.1.5.12.9.7.1.1.1
-- 1.3.6.1.4.1.37950.1.1.5.12.9.7.1.1.1
-- 1.3.6.1.4.1.37950.1.1.5.12.9.7.1.1.1
-- 1.3.6.1.4.1.37950.1.1.5.12.9.7.1.1.1
-- 1.3.6.1.4.1.37950.1.1.5.12.9.7.1.1.1
-- 1.3.6.1.4.1.37950.1.1.5.12.9.7.1.1.1
-- 1.3.6.1.4.1.37950.1.1.5.12.9.7.1.1.1
		-- 1.3.6.1.4.1.37950.1.1.5.12.9.7.1.1.1
		profileIdexShow OBJECT-TYPE
			SYNTAX Integer32
			MAX-ACCESS read-write
			STATUS current
			DESCRIPTION
				"Description."
			::= { profileEntry 1 }

		
--          1.3.6.1.4.1.37950.1.1.5.12.9.7.1.1.2
-- 1.3.6.1.4.1.37950.1.1.5.12.9.7.1.1.2
-- 1.3.6.1.4.1.37950.1.1.5.12.9.7.1.1.2
-- 1.3.6.1.4.1.37950.1.1.5.12.9.7.1.1.2
-- 1.3.6.1.4.1.37950.1.1.5.12.9.7.1.1.2
-- 1.3.6.1.4.1.37950.1.1.5.12.9.7.1.1.2
-- 1.3.6.1.4.1.37950.1.1.5.12.9.7.1.1.2
-- 1.3.6.1.4.1.37950.1.1.5.12.9.7.1.1.2
-- 1.3.6.1.4.1.37950.1.1.5.12.9.7.1.1.2
		-- 1.3.6.1.4.1.37950.1.1.5.12.9.7.1.1.2
		profileTypeShow OBJECT-TYPE
			SYNTAX INTEGER
				{
				dba(1),
				srv(2),
				voip(3),
				alarm(4)
				}
			MAX-ACCESS read-write
			STATUS current
			DESCRIPTION
				"Description."
			::= { profileEntry 2 }

		
--          1.3.6.1.4.1.37950.1.1.5.12.9.7.1.1.3
-- 1.3.6.1.4.1.37950.1.1.5.12.9.7.1.1.3
-- 1.3.6.1.4.1.37950.1.1.5.12.9.7.1.1.3
-- 1.3.6.1.4.1.37950.1.1.5.12.9.7.1.1.3
-- 1.3.6.1.4.1.37950.1.1.5.12.9.7.1.1.3
-- 1.3.6.1.4.1.37950.1.1.5.12.9.7.1.1.3
-- 1.3.6.1.4.1.37950.1.1.5.12.9.7.1.1.3
-- 1.3.6.1.4.1.37950.1.1.5.12.9.7.1.1.3
-- 1.3.6.1.4.1.37950.1.1.5.12.9.7.1.1.3
		-- 1.3.6.1.4.1.37950.1.1.5.12.9.7.1.1.3
		profileIdShow OBJECT-TYPE
			SYNTAX Integer32 (1..32767)
			MAX-ACCESS read-write
			STATUS current
			DESCRIPTION
				"Description."
			::= { profileEntry 3 }

		
--          1.3.6.1.4.1.37950.1.1.5.12.9.7.1.1.4
-- 1.3.6.1.4.1.37950.1.1.5.12.9.7.1.1.4
-- 1.3.6.1.4.1.37950.1.1.5.12.9.7.1.1.4
-- 1.3.6.1.4.1.37950.1.1.5.12.9.7.1.1.4
-- 1.3.6.1.4.1.37950.1.1.5.12.9.7.1.1.4
-- 1.3.6.1.4.1.37950.1.1.5.12.9.7.1.1.4
-- 1.3.6.1.4.1.37950.1.1.5.12.9.7.1.1.4
-- 1.3.6.1.4.1.37950.1.1.5.12.9.7.1.1.4
-- 1.3.6.1.4.1.37950.1.1.5.12.9.7.1.1.4
		-- 1.3.6.1.4.1.37950.1.1.5.12.9.7.1.1.4
		profileIdDescr OBJECT-TYPE
			SYNTAX OCTET STRING
			MAX-ACCESS read-write
			STATUS current
			DESCRIPTION
				"Description."
			::= { profileEntry 4 }

		
--         1.3.6.1.4.1.37950.2
-- 1.3.6.1.4.1.37950.2
-- 1.3.6.1.4.1.37950.2
-- 1.3.6.1.4.1.37950.2
-- 1.3.6.1.4.1.37950.2
-- 1.3.6.1.4.1.37950.2
-- 1.3.6.1.4.1.37950.2
-- 1.3.6.1.4.1.37950.2
		-- 1.3.6.1.4.1.37950.2
		enterpriseID OBJECT IDENTIFIER ::= { vsolution 2 }

		
--         1.3.6.1.4.1.37950.2.1
-- 1.3.6.1.4.1.37950.2.1
-- 1.3.6.1.4.1.37950.2.1
-- 1.3.6.1.4.1.37950.2.1
-- 1.3.6.1.4.1.37950.2.1
-- 1.3.6.1.4.1.37950.2.1
-- 1.3.6.1.4.1.37950.2.1
-- 1.3.6.1.4.1.37950.2.1
		-- 1.3.6.1.4.1.37950.2.1
		snmpEnterpriseID OBJECT-TYPE
			SYNTAX Unsigned32
			MAX-ACCESS read-write
			STATUS current
			DESCRIPTION
				"Description."
			::= { enterpriseID 1 }

		
	
	END

--
-- V1600D-20230413.my
--
