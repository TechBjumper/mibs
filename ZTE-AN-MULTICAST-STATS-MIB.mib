ZTE-AN-MULTICAST-STATS-MIB DEFINITIONS ::= BEGIN

    IMPORTS 
        MODULE-IDENTITY,Integer32,Counter32,OBJECT-TYPE 
                                                        FROM SNMPv2-SMI
        RowStatus                                       FROM SNMPv2-TC
        InetAddress,InetAddressType                     FROM INET-ADDRESS-MIB
        zxAnMulticast                                   FROM ZTE-AN-SMI;

    zxAnMulticastStatsMib MODULE-IDENTITY    
        LAST-UPDATED  "201401131430Z"
        ORGANIZATION  "ZTE Corporation"
        CONTACT-INFO  "Xu Jinlin
                       Mail: xu.jinlin@zte.com.cn
                       Tel : 13818526596"
        DESCRIPTION   "The MIB module for the management of multicast 
                       statistics."
        REVISION      "201401131430Z"
        DESCRIPTION   "Initial version of this MIB module."
        ::= {zxAnMulticast 11}

-------------------------------------------------------------------------------
-- Following management objects are defined.
-- 1. Multicast Group Statistics Objects
-- 1.1 Multicast Group Traffic Table
-------------------------------------------------------------------------------

    zxAnMulticastStatsObjects    OBJECT IDENTIFIER ::= {zxAnMulticastStatsMib 2}

-------------------------------------------------------------------------------
-- 1. Multicast Group Statistics Objects
-------------------------------------------------------------------------------
    
    zxAnMulticastGroupStatsObjects
                             OBJECT IDENTIFIER ::= {zxAnMulticastStatsObjects 2}

-------------------------------------------------------------------------------
-- 1.1 Multicast Group Traffic Table
-------------------------------------------------------------------------------

    zxAnMcastGrpTrafficTable  OBJECT-TYPE
        SYNTAX      SEQUENCE OF ZxAnMcastGrpTrafficEntry
        MAX-ACCESS  not-accessible
        STATUS      current
        DESCRIPTION
            "Multicast group traffic table."
        ::= { zxAnMulticastGroupStatsObjects 2 }

    zxAnMcastGrpTrafficEntry OBJECT-TYPE
        SYNTAX      ZxAnMcastGrpTrafficEntry
        MAX-ACCESS  not-accessible
        STATUS      current
        DESCRIPTION
            "Multicast group traffic entry."
        INDEX 
        { 
            zxAnMCastGrpTrafficMVid,
            zxAnMCastGrpTrafficGrpIpType,
            zxAnMCastGrpTrafficGrpIpAddr
        }
        ::= { zxAnMcastGrpTrafficTable 1 }
        
    ZxAnMcastGrpTrafficEntry ::= SEQUENCE {
        zxAnMCastGrpTrafficMVid         Integer32,
        zxAnMCastGrpTrafficGrpIpType    InetAddressType,
        zxAnMCastGrpTrafficGrpIpAddr    InetAddress,
        zxAnMCastGrpTrafficUnit         INTEGER,
        zxAnMCastGrpTrafficPeakRate     Integer32,
        zxAnMCastGrpTrafficAvgRate      Integer32,
        zxAnMCastGrpTrafficCurrRate     Integer32,
        zxAnMCastGrpTrafficMinRate      Integer32,
        zxAnMCastGrpTrafficRowStatus    RowStatus
    }
    
    zxAnMCastGrpTrafficMVid   OBJECT-TYPE
        SYNTAX      Integer32(1..4094)
        MAX-ACCESS  not-accessible
        STATUS      current
        DESCRIPTION 
            "Multicast VLAN ID."
        ::= { zxAnMcastGrpTrafficEntry 1 }
    
    zxAnMCastGrpTrafficGrpIpType   OBJECT-TYPE
        SYNTAX      InetAddressType
        MAX-ACCESS  not-accessible
        STATUS      current
        DESCRIPTION 
            "Multicast group IP address type."
        ::= { zxAnMcastGrpTrafficEntry 2 }
        
    zxAnMCastGrpTrafficGrpIpAddr   OBJECT-TYPE
        SYNTAX      InetAddress
        MAX-ACCESS  not-accessible
        STATUS      current
        DESCRIPTION 
            "Multicast group IP address."
        ::= { zxAnMcastGrpTrafficEntry 3 }  
    
    zxAnMCastGrpTrafficUnit OBJECT-TYPE
        SYNTAX      INTEGER {
            pps(1),
            kbps(2)
        }
        MAX-ACCESS  read-only
        STATUS      current
        DESCRIPTION
            "The unit of multicast traffic."
        ::= { zxAnMcastGrpTrafficEntry 4 }
    
    zxAnMCastGrpTrafficPeakRate  OBJECT-TYPE 
        SYNTAX      Integer32
        MAX-ACCESS  read-only
        STATUS      current
        DESCRIPTION     
            "The peak rate of multicast group.
            The unit is determined by the zxAnMCastGrpTrafficUnit."
        ::=  { zxAnMcastGrpTrafficEntry 5 }        
        
    zxAnMCastGrpTrafficAvgRate  OBJECT-TYPE 
        SYNTAX      Integer32
        MAX-ACCESS  read-only
        STATUS      current
        DESCRIPTION     
            "The average rate of multicast group.
            The unit is determined by the zxAnMCastGrpTrafficUnit."
        ::=  { zxAnMcastGrpTrafficEntry 6 }
    
    zxAnMCastGrpTrafficCurrRate  OBJECT-TYPE 
        SYNTAX      Integer32
        MAX-ACCESS  read-only
        STATUS      current
        DESCRIPTION     
            "The current rate of multicast group.
            The unit is determined by the zxAnMCastGrpTrafficUnit."
        ::=  { zxAnMcastGrpTrafficEntry 7 }
        
    zxAnMCastGrpTrafficMinRate  OBJECT-TYPE 
        SYNTAX      Integer32
        MAX-ACCESS  read-only
        STATUS      current
        DESCRIPTION     
            "The minimum rate of multicast group.
            The unit is determined by the zxAnMCastGrpTrafficUnit."
        ::=  { zxAnMcastGrpTrafficEntry 8 }
    
    zxAnMCastGrpTrafficRowStatus   OBJECT-TYPE
        SYNTAX         RowStatus
        MAX-ACCESS     read-create
        STATUS         current
        DESCRIPTION
            "The status of this conceptual row.
            
            The supported actions of this conceptual row only include:
            'createAndGo' and 'destroy'.

            To create a row in this table, a manager must set this object to 
            createAndGo(4), and must comply with the multi-variables binding 
            rule described in zxAnMcastGrpTrafficEntry.
    
            To delete a row in this table, a manager must set this object to 
            destroy(6). 
             
            To get this object, the agent always returns active(1)."
        ::= { zxAnMcastGrpTrafficEntry 50 }

END
