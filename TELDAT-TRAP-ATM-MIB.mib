-- file automatically created


TELDAT-TRAP-ATM-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


atmTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the ATM event subsystem."
    REVISION "201401200930Z"
    DESCRIPTION "Initial implementation"
        ::= { telEventTraps 136 }


atmEventsGroup	OBJECT IDENTIFIER	::= { atmTrapsMIB 1 }

atmNotifications	OBJECT IDENTIFIER	::= { atmTrapsMIB 2 }
atmNotificationsPrefix	OBJECT IDENTIFIER	::= { atmNotifications 0 }

atmEventObjects1 OBJECT-IDENTITY
    STATUS current
    DESCRIPTION
        "Event ATM.1
        An ATM cell has been received."
    ::= { atmEventsGroup 1 }

atm1-mnemonic OBJECT-TYPE
    SYNTAX DisplayString
    MAX-ACCESS accessible-for-notify
    STATUS current
    DESCRIPTION
        "Parameter 'mnemonic' in event ATM.1"
    ::= { atmEventObjects1 1 }

atm1-vpi OBJECT-TYPE
    SYNTAX Integer32
    MAX-ACCESS accessible-for-notify
    STATUS current
    DESCRIPTION
        "Parameter 'vpi' in event ATM.1"
    ::= { atmEventObjects1 2 }

atm1-vci OBJECT-TYPE
    SYNTAX Integer32
    MAX-ACCESS accessible-for-notify
    STATUS current
    DESCRIPTION
        "Parameter 'vci' in event ATM.1"
    ::= { atmEventObjects1 3 }

atm1-data-ptr OBJECT-TYPE
    SYNTAX Integer32
    MAX-ACCESS accessible-for-notify
    STATUS current
    DESCRIPTION
        "Parameter 'data-ptr' in event ATM.1"
    ::= { atmEventObjects1 4 }

atm1-buffer OBJECT-TYPE
    SYNTAX DisplayString
    MAX-ACCESS accessible-for-notify
    STATUS current
    DESCRIPTION
        "Parameter 'buffer' in event ATM.1"
    ::= { atmEventObjects1 5 }

atmEventObjects2 OBJECT-IDENTITY
    STATUS current
    DESCRIPTION
        "Event ATM.2
        An AAL5 CPCS frame has been received."
    ::= { atmEventsGroup 2 }

atm2-mnemonic OBJECT-TYPE
    SYNTAX DisplayString
    MAX-ACCESS accessible-for-notify
    STATUS current
    DESCRIPTION
        "Parameter 'mnemonic' in event ATM.2"
    ::= { atmEventObjects2 1 }

atm2-vpi OBJECT-TYPE
    SYNTAX Integer32
    MAX-ACCESS accessible-for-notify
    STATUS current
    DESCRIPTION
        "Parameter 'vpi' in event ATM.2"
    ::= { atmEventObjects2 2 }

atm2-vci OBJECT-TYPE
    SYNTAX Integer32
    MAX-ACCESS accessible-for-notify
    STATUS current
    DESCRIPTION
        "Parameter 'vci' in event ATM.2"
    ::= { atmEventObjects2 3 }

atm2-data-ptr OBJECT-TYPE
    SYNTAX Integer32
    MAX-ACCESS accessible-for-notify
    STATUS current
    DESCRIPTION
        "Parameter 'data-ptr' in event ATM.2"
    ::= { atmEventObjects2 4 }

atm2-len OBJECT-TYPE
    SYNTAX Integer32
    MAX-ACCESS accessible-for-notify
    STATUS current
    DESCRIPTION
        "Parameter 'len' in event ATM.2"
    ::= { atmEventObjects2 5 }

atm2-buffer OBJECT-TYPE
    SYNTAX DisplayString
    MAX-ACCESS accessible-for-notify
    STATUS current
    DESCRIPTION
        "Parameter 'buffer' in event ATM.2"
    ::= { atmEventObjects2 6 }

atmEventObjects3 OBJECT-IDENTITY
    STATUS current
    DESCRIPTION
        "Event ATM.3
        An ATM cell has been transmitted."
    ::= { atmEventsGroup 3 }

atm3-mnemonic OBJECT-TYPE
    SYNTAX DisplayString
    MAX-ACCESS accessible-for-notify
    STATUS current
    DESCRIPTION
        "Parameter 'mnemonic' in event ATM.3"
    ::= { atmEventObjects3 1 }

atm3-vpi OBJECT-TYPE
    SYNTAX Integer32
    MAX-ACCESS accessible-for-notify
    STATUS current
    DESCRIPTION
        "Parameter 'vpi' in event ATM.3"
    ::= { atmEventObjects3 2 }

atm3-vci OBJECT-TYPE
    SYNTAX Integer32
    MAX-ACCESS accessible-for-notify
    STATUS current
    DESCRIPTION
        "Parameter 'vci' in event ATM.3"
    ::= { atmEventObjects3 3 }

atm3-data-ptr OBJECT-TYPE
    SYNTAX Integer32
    MAX-ACCESS accessible-for-notify
    STATUS current
    DESCRIPTION
        "Parameter 'data-ptr' in event ATM.3"
    ::= { atmEventObjects3 4 }

atm3-buffer OBJECT-TYPE
    SYNTAX DisplayString
    MAX-ACCESS accessible-for-notify
    STATUS current
    DESCRIPTION
        "Parameter 'buffer' in event ATM.3"
    ::= { atmEventObjects3 5 }

atmEventObjects4 OBJECT-IDENTITY
    STATUS current
    DESCRIPTION
        "Event ATM.4
        An AAL5 CPCS frame has been transmitted."
    ::= { atmEventsGroup 4 }

atm4-mnemonic OBJECT-TYPE
    SYNTAX DisplayString
    MAX-ACCESS accessible-for-notify
    STATUS current
    DESCRIPTION
        "Parameter 'mnemonic' in event ATM.4"
    ::= { atmEventObjects4 1 }

atm4-vpi OBJECT-TYPE
    SYNTAX Integer32
    MAX-ACCESS accessible-for-notify
    STATUS current
    DESCRIPTION
        "Parameter 'vpi' in event ATM.4"
    ::= { atmEventObjects4 2 }

atm4-vci OBJECT-TYPE
    SYNTAX Integer32
    MAX-ACCESS accessible-for-notify
    STATUS current
    DESCRIPTION
        "Parameter 'vci' in event ATM.4"
    ::= { atmEventObjects4 3 }

atm4-data-ptr OBJECT-TYPE
    SYNTAX Integer32
    MAX-ACCESS accessible-for-notify
    STATUS current
    DESCRIPTION
        "Parameter 'data-ptr' in event ATM.4"
    ::= { atmEventObjects4 4 }

atm4-len OBJECT-TYPE
    SYNTAX Integer32
    MAX-ACCESS accessible-for-notify
    STATUS current
    DESCRIPTION
        "Parameter 'len' in event ATM.4"
    ::= { atmEventObjects4 5 }

atm4-buffer OBJECT-TYPE
    SYNTAX DisplayString
    MAX-ACCESS accessible-for-notify
    STATUS current
    DESCRIPTION
        "Parameter 'buffer' in event ATM.4"
    ::= { atmEventObjects4 6 }

atmEventObjects5 OBJECT-IDENTITY
    STATUS current
    DESCRIPTION
        "Event ATM.5
        Detailed info about cell reception."
    ::= { atmEventsGroup 5 }

atm5-mnemonic OBJECT-TYPE
    SYNTAX DisplayString
    MAX-ACCESS accessible-for-notify
    STATUS current
    DESCRIPTION
        "Parameter 'mnemonic' in event ATM.5"
    ::= { atmEventObjects5 1 }

atm5-vpi OBJECT-TYPE
    SYNTAX Integer32
    MAX-ACCESS accessible-for-notify
    STATUS current
    DESCRIPTION
        "Parameter 'vpi' in event ATM.5"
    ::= { atmEventObjects5 2 }

atm5-vci OBJECT-TYPE
    SYNTAX Integer32
    MAX-ACCESS accessible-for-notify
    STATUS current
    DESCRIPTION
        "Parameter 'vci' in event ATM.5"
    ::= { atmEventObjects5 3 }

atm5-data-ptr OBJECT-TYPE
    SYNTAX Integer32
    MAX-ACCESS accessible-for-notify
    STATUS current
    DESCRIPTION
        "Parameter 'data-ptr' in event ATM.5"
    ::= { atmEventObjects5 4 }

atm5-descr OBJECT-TYPE
    SYNTAX DisplayString
    MAX-ACCESS accessible-for-notify
    STATUS current
    DESCRIPTION
        "Parameter 'descr' in event ATM.5"
    ::= { atmEventObjects5 5 }

atmEventObjects6 OBJECT-IDENTITY
    STATUS current
    DESCRIPTION
        "Event ATM.6
        Detailed info about AAL5 CPCS frame reception."
    ::= { atmEventsGroup 6 }

atm6-mnemonic OBJECT-TYPE
    SYNTAX DisplayString
    MAX-ACCESS accessible-for-notify
    STATUS current
    DESCRIPTION
        "Parameter 'mnemonic' in event ATM.6"
    ::= { atmEventObjects6 1 }

atm6-vpi OBJECT-TYPE
    SYNTAX Integer32
    MAX-ACCESS accessible-for-notify
    STATUS current
    DESCRIPTION
        "Parameter 'vpi' in event ATM.6"
    ::= { atmEventObjects6 2 }

atm6-vci OBJECT-TYPE
    SYNTAX Integer32
    MAX-ACCESS accessible-for-notify
    STATUS current
    DESCRIPTION
        "Parameter 'vci' in event ATM.6"
    ::= { atmEventObjects6 3 }

atm6-data-ptr OBJECT-TYPE
    SYNTAX Integer32
    MAX-ACCESS accessible-for-notify
    STATUS current
    DESCRIPTION
        "Parameter 'data-ptr' in event ATM.6"
    ::= { atmEventObjects6 4 }

atm6-descr OBJECT-TYPE
    SYNTAX DisplayString
    MAX-ACCESS accessible-for-notify
    STATUS current
    DESCRIPTION
        "Parameter 'descr' in event ATM.6"
    ::= { atmEventObjects6 5 }

atmEventObjects7 OBJECT-IDENTITY
    STATUS current
    DESCRIPTION
        "Event ATM.7
        Detailed info about cell transmission."
    ::= { atmEventsGroup 7 }

atm7-mnemonic OBJECT-TYPE
    SYNTAX DisplayString
    MAX-ACCESS accessible-for-notify
    STATUS current
    DESCRIPTION
        "Parameter 'mnemonic' in event ATM.7"
    ::= { atmEventObjects7 1 }

atm7-vpi OBJECT-TYPE
    SYNTAX Integer32
    MAX-ACCESS accessible-for-notify
    STATUS current
    DESCRIPTION
        "Parameter 'vpi' in event ATM.7"
    ::= { atmEventObjects7 2 }

atm7-vci OBJECT-TYPE
    SYNTAX Integer32
    MAX-ACCESS accessible-for-notify
    STATUS current
    DESCRIPTION
        "Parameter 'vci' in event ATM.7"
    ::= { atmEventObjects7 3 }

atm7-data-ptr OBJECT-TYPE
    SYNTAX Integer32
    MAX-ACCESS accessible-for-notify
    STATUS current
    DESCRIPTION
        "Parameter 'data-ptr' in event ATM.7"
    ::= { atmEventObjects7 4 }

atm7-descr OBJECT-TYPE
    SYNTAX DisplayString
    MAX-ACCESS accessible-for-notify
    STATUS current
    DESCRIPTION
        "Parameter 'descr' in event ATM.7"
    ::= { atmEventObjects7 5 }

atmEventObjects8 OBJECT-IDENTITY
    STATUS current
    DESCRIPTION
        "Event ATM.8
        Detailed info about AAL5 CPCS frame transmission."
    ::= { atmEventsGroup 8 }

atm8-mnemonic OBJECT-TYPE
    SYNTAX DisplayString
    MAX-ACCESS accessible-for-notify
    STATUS current
    DESCRIPTION
        "Parameter 'mnemonic' in event ATM.8"
    ::= { atmEventObjects8 1 }

atm8-vpi OBJECT-TYPE
    SYNTAX Integer32
    MAX-ACCESS accessible-for-notify
    STATUS current
    DESCRIPTION
        "Parameter 'vpi' in event ATM.8"
    ::= { atmEventObjects8 2 }

atm8-vci OBJECT-TYPE
    SYNTAX Integer32
    MAX-ACCESS accessible-for-notify
    STATUS current
    DESCRIPTION
        "Parameter 'vci' in event ATM.8"
    ::= { atmEventObjects8 3 }

atm8-data-ptr OBJECT-TYPE
    SYNTAX Integer32
    MAX-ACCESS accessible-for-notify
    STATUS current
    DESCRIPTION
        "Parameter 'data-ptr' in event ATM.8"
    ::= { atmEventObjects8 4 }

atm8-descr OBJECT-TYPE
    SYNTAX DisplayString
    MAX-ACCESS accessible-for-notify
    STATUS current
    DESCRIPTION
        "Parameter 'descr' in event ATM.8"
    ::= { atmEventObjects8 5 }

atmEventObjects9 OBJECT-IDENTITY
    STATUS current
    DESCRIPTION
        "Event ATM.9
        A transmission request has been rejected."
    ::= { atmEventsGroup 9 }

atm9-mnemonic OBJECT-TYPE
    SYNTAX DisplayString
    MAX-ACCESS accessible-for-notify
    STATUS current
    DESCRIPTION
        "Parameter 'mnemonic' in event ATM.9"
    ::= { atmEventObjects9 1 }

atm9-vpi OBJECT-TYPE
    SYNTAX Integer32
    MAX-ACCESS accessible-for-notify
    STATUS current
    DESCRIPTION
        "Parameter 'vpi' in event ATM.9"
    ::= { atmEventObjects9 2 }

atm9-vci OBJECT-TYPE
    SYNTAX Integer32
    MAX-ACCESS accessible-for-notify
    STATUS current
    DESCRIPTION
        "Parameter 'vci' in event ATM.9"
    ::= { atmEventObjects9 3 }

atm9-data-ptr OBJECT-TYPE
    SYNTAX Integer32
    MAX-ACCESS accessible-for-notify
    STATUS current
    DESCRIPTION
        "Parameter 'data-ptr' in event ATM.9"
    ::= { atmEventObjects9 4 }

atm9-len OBJECT-TYPE
    SYNTAX Integer32
    MAX-ACCESS accessible-for-notify
    STATUS current
    DESCRIPTION
        "Parameter 'len' in event ATM.9"
    ::= { atmEventObjects9 5 }

atm9-descr OBJECT-TYPE
    SYNTAX DisplayString
    MAX-ACCESS accessible-for-notify
    STATUS current
    DESCRIPTION
        "Parameter 'descr' in event ATM.9"
    ::= { atmEventObjects9 6 }

atmEventObjects10 OBJECT-IDENTITY
    STATUS current
    DESCRIPTION
        "Event ATM.10
        Unexpected software behaviour."
    ::= { atmEventsGroup 10 }

atm10-mnemonic OBJECT-TYPE
    SYNTAX DisplayString
    MAX-ACCESS accessible-for-notify
    STATUS current
    DESCRIPTION
        "Parameter 'mnemonic' in event ATM.10"
    ::= { atmEventObjects10 1 }

atm10-soft-descr OBJECT-TYPE
    SYNTAX DisplayString
    MAX-ACCESS accessible-for-notify
    STATUS current
    DESCRIPTION
        "Parameter 'soft-descr' in event ATM.10"
    ::= { atmEventObjects10 2 }

atm10-event-descr OBJECT-TYPE
    SYNTAX DisplayString
    MAX-ACCESS accessible-for-notify
    STATUS current
    DESCRIPTION
        "Parameter 'event-descr' in event ATM.10"
    ::= { atmEventObjects10 3 }

atmEventObjects11 OBJECT-IDENTITY
    STATUS current
    DESCRIPTION
        "Event ATM.11
        The frame received has been detected as errored at subinterface level."
    ::= { atmEventsGroup 11 }

atm11-mnemonic OBJECT-TYPE
    SYNTAX DisplayString
    MAX-ACCESS accessible-for-notify
    STATUS current
    DESCRIPTION
        "Parameter 'mnemonic' in event ATM.11"
    ::= { atmEventObjects11 1 }

atm11-rsn-descr OBJECT-TYPE
    SYNTAX DisplayString
    MAX-ACCESS accessible-for-notify
    STATUS current
    DESCRIPTION
        "Parameter 'rsn-descr' in event ATM.11"
    ::= { atmEventObjects11 2 }

atmEventObjects12 OBJECT-IDENTITY
    STATUS current
    DESCRIPTION
        "Event ATM.12
        Event at ATM interface level: up, down."
    ::= { atmEventsGroup 12 }

atm12-mnemonic OBJECT-TYPE
    SYNTAX DisplayString
    MAX-ACCESS accessible-for-notify
    STATUS current
    DESCRIPTION
        "Parameter 'mnemonic' in event ATM.12"
    ::= { atmEventObjects12 1 }

atm12-event-descr OBJECT-TYPE
    SYNTAX DisplayString
    MAX-ACCESS accessible-for-notify
    STATUS current
    DESCRIPTION
        "Parameter 'event-descr' in event ATM.12"
    ::= { atmEventObjects12 2 }

atmEventObjects13 OBJECT-IDENTITY
    STATUS current
    DESCRIPTION
        "Event ATM.13
        Event at ATM VCC level."
    ::= { atmEventsGroup 13 }

atm13-mnemonic OBJECT-TYPE
    SYNTAX DisplayString
    MAX-ACCESS accessible-for-notify
    STATUS current
    DESCRIPTION
        "Parameter 'mnemonic' in event ATM.13"
    ::= { atmEventObjects13 1 }

atm13-vpi OBJECT-TYPE
    SYNTAX Integer32
    MAX-ACCESS accessible-for-notify
    STATUS current
    DESCRIPTION
        "Parameter 'vpi' in event ATM.13"
    ::= { atmEventObjects13 2 }

atm13-vci OBJECT-TYPE
    SYNTAX Integer32
    MAX-ACCESS accessible-for-notify
    STATUS current
    DESCRIPTION
        "Parameter 'vci' in event ATM.13"
    ::= { atmEventObjects13 3 }

atm13-event-descr OBJECT-TYPE
    SYNTAX DisplayString
    MAX-ACCESS accessible-for-notify
    STATUS current
    DESCRIPTION
        "Parameter 'event-descr' in event ATM.13"
    ::= { atmEventObjects13 4 }

atmEventObjects14 OBJECT-IDENTITY
    STATUS current
    DESCRIPTION
        "Event ATM.14
        An AAL5 SAR cell has been transmitted."
    ::= { atmEventsGroup 14 }

atm14-mnemonic OBJECT-TYPE
    SYNTAX DisplayString
    MAX-ACCESS accessible-for-notify
    STATUS current
    DESCRIPTION
        "Parameter 'mnemonic' in event ATM.14"
    ::= { atmEventObjects14 1 }

atm14-vpi OBJECT-TYPE
    SYNTAX Integer32
    MAX-ACCESS accessible-for-notify
    STATUS current
    DESCRIPTION
        "Parameter 'vpi' in event ATM.14"
    ::= { atmEventObjects14 2 }

atm14-vci OBJECT-TYPE
    SYNTAX Integer32
    MAX-ACCESS accessible-for-notify
    STATUS current
    DESCRIPTION
        "Parameter 'vci' in event ATM.14"
    ::= { atmEventObjects14 3 }

atm14-data-ptr OBJECT-TYPE
    SYNTAX Integer32
    MAX-ACCESS accessible-for-notify
    STATUS current
    DESCRIPTION
        "Parameter 'data-ptr' in event ATM.14"
    ::= { atmEventObjects14 4 }

atm14-details OBJECT-TYPE
    SYNTAX DisplayString
    MAX-ACCESS accessible-for-notify
    STATUS current
    DESCRIPTION
        "Parameter 'details' in event ATM.14"
    ::= { atmEventObjects14 5 }

atmEventObjects15 OBJECT-IDENTITY
    STATUS current
    DESCRIPTION
        "Event ATM.15
        Event related to the SAR unit"
    ::= { atmEventsGroup 15 }

atm15-mnemonic OBJECT-TYPE
    SYNTAX DisplayString
    MAX-ACCESS accessible-for-notify
    STATUS current
    DESCRIPTION
        "Parameter 'mnemonic' in event ATM.15"
    ::= { atmEventObjects15 1 }

atm15-event-descr OBJECT-TYPE
    SYNTAX DisplayString
    MAX-ACCESS accessible-for-notify
    STATUS current
    DESCRIPTION
        "Parameter 'event-descr' in event ATM.15"
    ::= { atmEventObjects15 2 }


atmNotification1 NOTIFICATION-TYPE
    OBJECTS { 
              atm1-mnemonic, 
              atm1-vpi,
              atm1-vci,
              atm1-data-ptr,
              atm1-buffer 
            }
    STATUS current
    DESCRIPTION
        "Notification of Event ATM.1

        Message: '$1 ATM cell received ($2..$3) data=$4: $5'

        Parameters list:
              $1: atm1-mnemonic
              $2: atm1-vpi
              $3: atm1-vci
              $4: atm1-data-ptr
              $5: atm1-buffer

        An ATM cell has been received."
    ::= { atmNotificationsPrefix 1 }

atmNotification2 NOTIFICATION-TYPE
    OBJECTS { 
              atm2-mnemonic, 
              atm2-vpi,
              atm2-vci,
              atm2-data-ptr,
              atm2-len,
              atm2-buffer 
            }
    STATUS current
    DESCRIPTION
        "Notification of Event ATM.2

        Message: '$1 AAL5 CPCS frame Received ($2..$3) data=$4 len=$5: $6'

        Parameters list:
              $1: atm2-mnemonic
              $2: atm2-vpi
              $3: atm2-vci
              $4: atm2-data-ptr
              $5: atm2-len
              $6: atm2-buffer

        An AAL5 CPCS frame has been received."
    ::= { atmNotificationsPrefix 2 }

atmNotification3 NOTIFICATION-TYPE
    OBJECTS { 
              atm3-mnemonic, 
              atm3-vpi,
              atm3-vci,
              atm3-data-ptr,
              atm3-buffer 
            }
    STATUS current
    DESCRIPTION
        "Notification of Event ATM.3

        Message: '$1 ATM cell transmission ($2..$3) data=$4: $5'

        Parameters list:
              $1: atm3-mnemonic
              $2: atm3-vpi
              $3: atm3-vci
              $4: atm3-data-ptr
              $5: atm3-buffer

        An ATM cell has been transmitted."
    ::= { atmNotificationsPrefix 3 }

atmNotification4 NOTIFICATION-TYPE
    OBJECTS { 
              atm4-mnemonic, 
              atm4-vpi,
              atm4-vci,
              atm4-data-ptr,
              atm4-len,
              atm4-buffer 
            }
    STATUS current
    DESCRIPTION
        "Notification of Event ATM.4

        Message: '$1 AAL5 CPCS frame transmission ($2..$3) data=$4 len=$5: $6'

        Parameters list:
              $1: atm4-mnemonic
              $2: atm4-vpi
              $3: atm4-vci
              $4: atm4-data-ptr
              $5: atm4-len
              $6: atm4-buffer

        An AAL5 CPCS frame has been transmitted."
    ::= { atmNotificationsPrefix 4 }

atmNotification5 NOTIFICATION-TYPE
    OBJECTS { 
              atm5-mnemonic, 
              atm5-vpi,
              atm5-vci,
              atm5-data-ptr,
              atm5-descr 
            }
    STATUS current
    DESCRIPTION
        "Notification of Event ATM.5

        Message: '$1 ATM cell received ($2..$3) data=$4 $5'

        Parameters list:
              $1: atm5-mnemonic
              $2: atm5-vpi
              $3: atm5-vci
              $4: atm5-data-ptr
              $5: atm5-descr

        Detailed info about cell reception."
    ::= { atmNotificationsPrefix 5 }

atmNotification6 NOTIFICATION-TYPE
    OBJECTS { 
              atm6-mnemonic, 
              atm6-vpi,
              atm6-vci,
              atm6-data-ptr,
              atm6-descr 
            }
    STATUS current
    DESCRIPTION
        "Notification of Event ATM.6

        Message: '$1 AAL5 CPCS frame received ($2..$3) data=$4 $5'

        Parameters list:
              $1: atm6-mnemonic
              $2: atm6-vpi
              $3: atm6-vci
              $4: atm6-data-ptr
              $5: atm6-descr

        Detailed info about AAL5 CPCS frame reception."
    ::= { atmNotificationsPrefix 6 }

atmNotification7 NOTIFICATION-TYPE
    OBJECTS { 
              atm7-mnemonic, 
              atm7-vpi,
              atm7-vci,
              atm7-data-ptr,
              atm7-descr 
            }
    STATUS current
    DESCRIPTION
        "Notification of Event ATM.7

        Message: '$1 ATM cell transmission ($2..$3) data=$4 $5'

        Parameters list:
              $1: atm7-mnemonic
              $2: atm7-vpi
              $3: atm7-vci
              $4: atm7-data-ptr
              $5: atm7-descr

        Detailed info about cell transmission."
    ::= { atmNotificationsPrefix 7 }

atmNotification8 NOTIFICATION-TYPE
    OBJECTS { 
              atm8-mnemonic, 
              atm8-vpi,
              atm8-vci,
              atm8-data-ptr,
              atm8-descr 
            }
    STATUS current
    DESCRIPTION
        "Notification of Event ATM.8

        Message: '$1 AAL5 CPCS frame transmission ($2..$3) data=$4 $5'

        Parameters list:
              $1: atm8-mnemonic
              $2: atm8-vpi
              $3: atm8-vci
              $4: atm8-data-ptr
              $5: atm8-descr

        Detailed info about AAL5 CPCS frame transmission."
    ::= { atmNotificationsPrefix 8 }

atmNotification9 NOTIFICATION-TYPE
    OBJECTS { 
              atm9-mnemonic, 
              atm9-vpi,
              atm9-vci,
              atm9-data-ptr,
              atm9-len,
              atm9-descr 
            }
    STATUS current
    DESCRIPTION
        "Notification of Event ATM.9

        Message: '$1 Transmission rejected ($2..$3) data=$4 len=$5 rsn=$6'

        Parameters list:
              $1: atm9-mnemonic
              $2: atm9-vpi
              $3: atm9-vci
              $4: atm9-data-ptr
              $5: atm9-len
              $6: atm9-descr

        A transmission request has been rejected."
    ::= { atmNotificationsPrefix 9 }

atmNotification10 NOTIFICATION-TYPE
    OBJECTS { 
              atm10-mnemonic, 
              atm10-soft-descr,
              atm10-event-descr 
            }
    STATUS current
    DESCRIPTION
        "Notification of Event ATM.10

        Message: '$1 Unexpected $2 software event $3'

        Parameters list:
              $1: atm10-mnemonic
              $2: atm10-soft-descr
              $3: atm10-event-descr

        Unexpected software behaviour."
    ::= { atmNotificationsPrefix 10 }

atmNotification11 NOTIFICATION-TYPE
    OBJECTS { 
              atm11-mnemonic, 
              atm11-rsn-descr 
            }
    STATUS current
    DESCRIPTION
        "Notification of Event ATM.11

        Message: '$1 reception with error Reason=$2'

        Parameters list:
              $1: atm11-mnemonic
              $2: atm11-rsn-descr

        The frame received has been detected as errored at subinterface level."
    ::= { atmNotificationsPrefix 11 }

atmNotification12 NOTIFICATION-TYPE
    OBJECTS { 
              atm12-mnemonic, 
              atm12-event-descr 
            }
    STATUS current
    DESCRIPTION
        "Notification of Event ATM.12

        Message: '$1 $2'

        Parameters list:
              $1: atm12-mnemonic
              $2: atm12-event-descr

        Event at ATM interface level: up, down."
    ::= { atmNotificationsPrefix 12 }

atmNotification13 NOTIFICATION-TYPE
    OBJECTS { 
              atm13-mnemonic, 
              atm13-vpi,
              atm13-vci,
              atm13-event-descr 
            }
    STATUS current
    DESCRIPTION
        "Notification of Event ATM.13

        Message: '$1 VPI=$2 VCI=$3 $4'

        Parameters list:
              $1: atm13-mnemonic
              $2: atm13-vpi
              $3: atm13-vci
              $4: atm13-event-descr

        Event at ATM VCC level."
    ::= { atmNotificationsPrefix 13 }

atmNotification14 NOTIFICATION-TYPE
    OBJECTS { 
              atm14-mnemonic, 
              atm14-vpi,
              atm14-vci,
              atm14-data-ptr,
              atm14-details 
            }
    STATUS current
    DESCRIPTION
        "Notification of Event ATM.14

        Message: '$1 AAL5 SAR cell transmission ($2..$3) data=$4 $5'

        Parameters list:
              $1: atm14-mnemonic
              $2: atm14-vpi
              $3: atm14-vci
              $4: atm14-data-ptr
              $5: atm14-details

        An AAL5 SAR cell has been transmitted."
    ::= { atmNotificationsPrefix 14 }

atmNotification15 NOTIFICATION-TYPE
    OBJECTS { 
              atm15-mnemonic, 
              atm15-event-descr 
            }
    STATUS current
    DESCRIPTION
        "Notification of Event ATM.15

        Message: '$1 $2'

        Parameters list:
              $1: atm15-mnemonic
              $2: atm15-event-descr

        Event related to the SAR unit"
    ::= { atmNotificationsPrefix 15 }


END
