-- file automatically created


TELDAT-TRAP-SIP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


sipTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the SIP event subsystem."
    REVISION "201401200930Z"
    DESCRIPTION "Initial implementation"
        ::= { telEventTraps 180 }


sipEventsGroup	OBJECT IDENTIFIER	::= { sipTrapsMIB 1 }

sipNotifications	OBJECT IDENTIFIER	::= { sipTrapsMIB 2 }
sipNotificationsPrefix	OBJECT IDENTIFIER	::= { sipNotifications 0 }

sipEventObjects1 OBJECT-IDENTITY
    STATUS current
    DESCRIPTION
        "Event SIP.1
        Event related with task creation/deletion."
    ::= { sipEventsGroup 1 }

sip1-description OBJECT-TYPE
    SYNTAX DisplayString
    MAX-ACCESS accessible-for-notify
    STATUS current
    DESCRIPTION
        "Parameter 'description' in event SIP.1"
    ::= { sipEventObjects1 1 }

sip1-task OBJECT-TYPE
    SYNTAX DisplayString
    MAX-ACCESS accessible-for-notify
    STATUS current
    DESCRIPTION
        "Parameter 'task' in event SIP.1"
    ::= { sipEventObjects1 2 }

sipEventObjects2 OBJECT-IDENTITY
    STATUS current
    DESCRIPTION
        "Event SIP.2
        Event related with message processing."
    ::= { sipEventsGroup 2 }

sip2-description OBJECT-TYPE
    SYNTAX DisplayString
    MAX-ACCESS accessible-for-notify
    STATUS current
    DESCRIPTION
        "Parameter 'description' in event SIP.2"
    ::= { sipEventObjects2 1 }

sip2-message OBJECT-TYPE
    SYNTAX DisplayString
    MAX-ACCESS accessible-for-notify
    STATUS current
    DESCRIPTION
        "Parameter 'message' in event SIP.2"
    ::= { sipEventObjects2 2 }

sip2-task OBJECT-TYPE
    SYNTAX DisplayString
    MAX-ACCESS accessible-for-notify
    STATUS current
    DESCRIPTION
        "Parameter 'task' in event SIP.2"
    ::= { sipEventObjects2 3 }

sip2-cdr OBJECT-TYPE
    SYNTAX Integer32
    MAX-ACCESS accessible-for-notify
    STATUS current
    DESCRIPTION
        "Parameter 'cdr' in event SIP.2"
    ::= { sipEventObjects2 4 }

sipEventObjects3 OBJECT-IDENTITY
    STATUS current
    DESCRIPTION
        "Event SIP.3
        Error related with task creation/deletion."
    ::= { sipEventsGroup 3 }

sip3-error OBJECT-TYPE
    SYNTAX DisplayString
    MAX-ACCESS accessible-for-notify
    STATUS current
    DESCRIPTION
        "Parameter 'error' in event SIP.3"
    ::= { sipEventObjects3 1 }

sip3-task OBJECT-TYPE
    SYNTAX DisplayString
    MAX-ACCESS accessible-for-notify
    STATUS current
    DESCRIPTION
        "Parameter 'task' in event SIP.3"
    ::= { sipEventObjects3 2 }

sipEventObjects4 OBJECT-IDENTITY
    STATUS current
    DESCRIPTION
        "Event SIP.4
        Error related with message processing."
    ::= { sipEventsGroup 4 }

sip4-description OBJECT-TYPE
    SYNTAX DisplayString
    MAX-ACCESS accessible-for-notify
    STATUS current
    DESCRIPTION
        "Parameter 'description' in event SIP.4"
    ::= { sipEventObjects4 1 }

sip4-error OBJECT-TYPE
    SYNTAX DisplayString
    MAX-ACCESS accessible-for-notify
    STATUS current
    DESCRIPTION
        "Parameter 'error' in event SIP.4"
    ::= { sipEventObjects4 2 }

sip4-task OBJECT-TYPE
    SYNTAX DisplayString
    MAX-ACCESS accessible-for-notify
    STATUS current
    DESCRIPTION
        "Parameter 'task' in event SIP.4"
    ::= { sipEventObjects4 3 }

sip4-cdr OBJECT-TYPE
    SYNTAX Integer32
    MAX-ACCESS accessible-for-notify
    STATUS current
    DESCRIPTION
        "Parameter 'cdr' in event SIP.4"
    ::= { sipEventObjects4 4 }

sipEventObjects5 OBJECT-IDENTITY
    STATUS current
    DESCRIPTION
        "Event SIP.5
        Event related with queues."
    ::= { sipEventsGroup 5 }

sip5-queue OBJECT-TYPE
    SYNTAX DisplayString
    MAX-ACCESS accessible-for-notify
    STATUS current
    DESCRIPTION
        "Parameter 'queue' in event SIP.5"
    ::= { sipEventObjects5 1 }

sip5-description OBJECT-TYPE
    SYNTAX DisplayString
    MAX-ACCESS accessible-for-notify
    STATUS current
    DESCRIPTION
        "Parameter 'description' in event SIP.5"
    ::= { sipEventObjects5 2 }

sip5-total-msgs OBJECT-TYPE
    SYNTAX Integer32
    MAX-ACCESS accessible-for-notify
    STATUS current
    DESCRIPTION
        "Parameter 'total-msgs' in event SIP.5"
    ::= { sipEventObjects5 3 }

sip5-task OBJECT-TYPE
    SYNTAX DisplayString
    MAX-ACCESS accessible-for-notify
    STATUS current
    DESCRIPTION
        "Parameter 'task' in event SIP.5"
    ::= { sipEventObjects5 4 }

sipEventObjects6 OBJECT-IDENTITY
    STATUS current
    DESCRIPTION
        "Event SIP.6
        Event showing type of message in process."
    ::= { sipEventsGroup 6 }

sip6-app OBJECT-TYPE
    SYNTAX DisplayString
    MAX-ACCESS accessible-for-notify
    STATUS current
    DESCRIPTION
        "Parameter 'app' in event SIP.6"
    ::= { sipEventObjects6 1 }

sip6-type OBJECT-TYPE
    SYNTAX DisplayString
    MAX-ACCESS accessible-for-notify
    STATUS current
    DESCRIPTION
        "Parameter 'type' in event SIP.6"
    ::= { sipEventObjects6 2 }

sip6-cdr OBJECT-TYPE
    SYNTAX Integer32
    MAX-ACCESS accessible-for-notify
    STATUS current
    DESCRIPTION
        "Parameter 'cdr' in event SIP.6"
    ::= { sipEventObjects6 3 }

sipEventObjects7 OBJECT-IDENTITY
    STATUS current
    DESCRIPTION
        "Event SIP.7
        Event related with client registration or unregistration received."
    ::= { sipEventsGroup 7 }

sip7-description OBJECT-TYPE
    SYNTAX DisplayString
    MAX-ACCESS accessible-for-notify
    STATUS current
    DESCRIPTION
        "Parameter 'description' in event SIP.7"
    ::= { sipEventObjects7 1 }

sip7-user OBJECT-TYPE
    SYNTAX DisplayString
    MAX-ACCESS accessible-for-notify
    STATUS current
    DESCRIPTION
        "Parameter 'user' in event SIP.7"
    ::= { sipEventObjects7 2 }

sip7-user-host OBJECT-TYPE
    SYNTAX DisplayString
    MAX-ACCESS accessible-for-notify
    STATUS current
    DESCRIPTION
        "Parameter 'user-host' in event SIP.7"
    ::= { sipEventObjects7 3 }

sip7-location OBJECT-TYPE
    SYNTAX DisplayString
    MAX-ACCESS accessible-for-notify
    STATUS current
    DESCRIPTION
        "Parameter 'location' in event SIP.7"
    ::= { sipEventObjects7 4 }

sip7-location-host OBJECT-TYPE
    SYNTAX DisplayString
    MAX-ACCESS accessible-for-notify
    STATUS current
    DESCRIPTION
        "Parameter 'location-host' in event SIP.7"
    ::= { sipEventObjects7 5 }

sip7-time-to-live OBJECT-TYPE
    SYNTAX Integer32
    MAX-ACCESS accessible-for-notify
    STATUS current
    DESCRIPTION
        "Parameter 'time-to-live' in event SIP.7"
    ::= { sipEventObjects7 6 }

sipEventObjects8 OBJECT-IDENTITY
    STATUS current
    DESCRIPTION
        "Event SIP.8
        SIP Stack event."
    ::= { sipEventsGroup 8 }

sip8-event-type OBJECT-TYPE
    SYNTAX DisplayString
    MAX-ACCESS accessible-for-notify
    STATUS current
    DESCRIPTION
        "Parameter 'event-type' in event SIP.8"
    ::= { sipEventObjects8 1 }

sip8-event OBJECT-TYPE
    SYNTAX DisplayString
    MAX-ACCESS accessible-for-notify
    STATUS current
    DESCRIPTION
        "Parameter 'event' in event SIP.8"
    ::= { sipEventObjects8 2 }

sipEventObjects9 OBJECT-IDENTITY
    STATUS current
    DESCRIPTION
        "Event SIP.9
        Event related with call state."
    ::= { sipEventsGroup 9 }

sip9-app OBJECT-TYPE
    SYNTAX DisplayString
    MAX-ACCESS accessible-for-notify
    STATUS current
    DESCRIPTION
        "Parameter 'app' in event SIP.9"
    ::= { sipEventObjects9 1 }

sip9-call-id OBJECT-TYPE
    SYNTAX Integer32
    MAX-ACCESS accessible-for-notify
    STATUS current
    DESCRIPTION
        "Parameter 'call-id' in event SIP.9"
    ::= { sipEventObjects9 2 }

sip9-org OBJECT-TYPE
    SYNTAX DisplayString
    MAX-ACCESS accessible-for-notify
    STATUS current
    DESCRIPTION
        "Parameter 'org' in event SIP.9"
    ::= { sipEventObjects9 3 }

sip9-dest OBJECT-TYPE
    SYNTAX DisplayString
    MAX-ACCESS accessible-for-notify
    STATUS current
    DESCRIPTION
        "Parameter 'dest' in event SIP.9"
    ::= { sipEventObjects9 4 }

sip9-state OBJECT-TYPE
    SYNTAX DisplayString
    MAX-ACCESS accessible-for-notify
    STATUS current
    DESCRIPTION
        "Parameter 'state' in event SIP.9"
    ::= { sipEventObjects9 5 }

sipEventObjects10 OBJECT-IDENTITY
    STATUS current
    DESCRIPTION
        "Event SIP.10
        Event related with application state."
    ::= { sipEventsGroup 10 }

sip10-app OBJECT-TYPE
    SYNTAX DisplayString
    MAX-ACCESS accessible-for-notify
    STATUS current
    DESCRIPTION
        "Parameter 'app' in event SIP.10"
    ::= { sipEventObjects10 1 }

sip10-state OBJECT-TYPE
    SYNTAX DisplayString
    MAX-ACCESS accessible-for-notify
    STATUS current
    DESCRIPTION
        "Parameter 'state' in event SIP.10"
    ::= { sipEventObjects10 2 }

sipEventObjects11 OBJECT-IDENTITY
    STATUS current
    DESCRIPTION
        "Event SIP.11
        Event showing type of message sent."
    ::= { sipEventsGroup 11 }

sip11-app OBJECT-TYPE
    SYNTAX DisplayString
    MAX-ACCESS accessible-for-notify
    STATUS current
    DESCRIPTION
        "Parameter 'app' in event SIP.11"
    ::= { sipEventObjects11 1 }

sip11-type OBJECT-TYPE
    SYNTAX DisplayString
    MAX-ACCESS accessible-for-notify
    STATUS current
    DESCRIPTION
        "Parameter 'type' in event SIP.11"
    ::= { sipEventObjects11 2 }

sip11-cdr OBJECT-TYPE
    SYNTAX Integer32
    MAX-ACCESS accessible-for-notify
    STATUS current
    DESCRIPTION
        "Parameter 'cdr' in event SIP.11"
    ::= { sipEventObjects11 3 }

sipEventObjects12 OBJECT-IDENTITY
    STATUS current
    DESCRIPTION
        "Event SIP.12
        Event showing media negotiation events."
    ::= { sipEventsGroup 12 }

sip12-event OBJECT-TYPE
    SYNTAX DisplayString
    MAX-ACCESS accessible-for-notify
    STATUS current
    DESCRIPTION
        "Parameter 'event' in event SIP.12"
    ::= { sipEventObjects12 1 }

sipEventObjects13 OBJECT-IDENTITY
    STATUS current
    DESCRIPTION
        "Event SIP.13
        Event related with registration or unregistration in external server."
    ::= { sipEventsGroup 13 }

sip13-description OBJECT-TYPE
    SYNTAX DisplayString
    MAX-ACCESS accessible-for-notify
    STATUS current
    DESCRIPTION
        "Parameter 'description' in event SIP.13"
    ::= { sipEventObjects13 1 }

sip13-user OBJECT-TYPE
    SYNTAX DisplayString
    MAX-ACCESS accessible-for-notify
    STATUS current
    DESCRIPTION
        "Parameter 'user' in event SIP.13"
    ::= { sipEventObjects13 2 }

sip13-dial-peer OBJECT-TYPE
    SYNTAX Integer32
    MAX-ACCESS accessible-for-notify
    STATUS current
    DESCRIPTION
        "Parameter 'dial-peer' in event SIP.13"
    ::= { sipEventObjects13 3 }

sip13-time-to-live OBJECT-TYPE
    SYNTAX Integer32
    MAX-ACCESS accessible-for-notify
    STATUS current
    DESCRIPTION
        "Parameter 'time-to-live' in event SIP.13"
    ::= { sipEventObjects13 4 }

sipEventObjects16 OBJECT-IDENTITY
    STATUS current
    DESCRIPTION
        "Event SIP.16
        Event showing call finnished due to keepalive failed"
    ::= { sipEventsGroup 16 }

sip16-cdr OBJECT-TYPE
    SYNTAX Integer32
    MAX-ACCESS accessible-for-notify
    STATUS current
    DESCRIPTION
        "Parameter 'cdr' in event SIP.16"
    ::= { sipEventObjects16 1 }

sipEventObjects17 OBJECT-IDENTITY
    STATUS current
    DESCRIPTION
        "Event SIP.17
        A register has expired"
    ::= { sipEventsGroup 17 }

sip17-user OBJECT-TYPE
    SYNTAX DisplayString
    MAX-ACCESS accessible-for-notify
    STATUS current
    DESCRIPTION
        "Parameter 'user' in event SIP.17"
    ::= { sipEventObjects17 1 }

sip17-user-host OBJECT-TYPE
    SYNTAX DisplayString
    MAX-ACCESS accessible-for-notify
    STATUS current
    DESCRIPTION
        "Parameter 'user-host' in event SIP.17"
    ::= { sipEventObjects17 2 }

sip17-location OBJECT-TYPE
    SYNTAX DisplayString
    MAX-ACCESS accessible-for-notify
    STATUS current
    DESCRIPTION
        "Parameter 'location' in event SIP.17"
    ::= { sipEventObjects17 3 }

sip17-location-host OBJECT-TYPE
    SYNTAX DisplayString
    MAX-ACCESS accessible-for-notify
    STATUS current
    DESCRIPTION
        "Parameter 'location-host' in event SIP.17"
    ::= { sipEventObjects17 4 }

sipEventObjects18 OBJECT-IDENTITY
    STATUS current
    DESCRIPTION
        "Event SIP.18
        Socket connect event, local connection."
    ::= { sipEventsGroup 18 }

sip18-type OBJECT-TYPE
    SYNTAX DisplayString
    MAX-ACCESS accessible-for-notify
    STATUS current
    DESCRIPTION
        "Parameter 'type' in event SIP.18"
    ::= { sipEventObjects18 1 }

sip18-identifier OBJECT-TYPE
    SYNTAX Integer32
    MAX-ACCESS accessible-for-notify
    STATUS current
    DESCRIPTION
        "Parameter 'identifier' in event SIP.18"
    ::= { sipEventObjects18 2 }

sip18-description OBJECT-TYPE
    SYNTAX DisplayString
    MAX-ACCESS accessible-for-notify
    STATUS current
    DESCRIPTION
        "Parameter 'description' in event SIP.18"
    ::= { sipEventObjects18 3 }

sipEventObjects19 OBJECT-IDENTITY
    STATUS current
    DESCRIPTION
        "Event SIP.19
        Socket accept event, remote connection."
    ::= { sipEventsGroup 19 }

sip19-type OBJECT-TYPE
    SYNTAX DisplayString
    MAX-ACCESS accessible-for-notify
    STATUS current
    DESCRIPTION
        "Parameter 'type' in event SIP.19"
    ::= { sipEventObjects19 1 }

sip19-identifier OBJECT-TYPE
    SYNTAX Integer32
    MAX-ACCESS accessible-for-notify
    STATUS current
    DESCRIPTION
        "Parameter 'identifier' in event SIP.19"
    ::= { sipEventObjects19 2 }

sip19-description OBJECT-TYPE
    SYNTAX DisplayString
    MAX-ACCESS accessible-for-notify
    STATUS current
    DESCRIPTION
        "Parameter 'description' in event SIP.19"
    ::= { sipEventObjects19 3 }

sipEventObjects20 OBJECT-IDENTITY
    STATUS current
    DESCRIPTION
        "Event SIP.20
        Socket close local event."
    ::= { sipEventsGroup 20 }

sip20-type OBJECT-TYPE
    SYNTAX DisplayString
    MAX-ACCESS accessible-for-notify
    STATUS current
    DESCRIPTION
        "Parameter 'type' in event SIP.20"
    ::= { sipEventObjects20 1 }

sip20-identifier OBJECT-TYPE
    SYNTAX Integer32
    MAX-ACCESS accessible-for-notify
    STATUS current
    DESCRIPTION
        "Parameter 'identifier' in event SIP.20"
    ::= { sipEventObjects20 2 }

sipEventObjects21 OBJECT-IDENTITY
    STATUS current
    DESCRIPTION
        "Event SIP.21
        Socket close local event."
    ::= { sipEventsGroup 21 }

sip21-type OBJECT-TYPE
    SYNTAX DisplayString
    MAX-ACCESS accessible-for-notify
    STATUS current
    DESCRIPTION
        "Parameter 'type' in event SIP.21"
    ::= { sipEventObjects21 1 }

sip21-identifier OBJECT-TYPE
    SYNTAX Integer32
    MAX-ACCESS accessible-for-notify
    STATUS current
    DESCRIPTION
        "Parameter 'identifier' in event SIP.21"
    ::= { sipEventObjects21 2 }

sipEventObjects22 OBJECT-IDENTITY
    STATUS current
    DESCRIPTION
        "Event SIP.22
        A certificate has been loaded or unloaded"
    ::= { sipEventsGroup 22 }

sip22-name OBJECT-TYPE
    SYNTAX DisplayString
    MAX-ACCESS accessible-for-notify
    STATUS current
    DESCRIPTION
        "Parameter 'name' in event SIP.22"
    ::= { sipEventObjects22 1 }

sip22-loaded OBJECT-TYPE
    SYNTAX DisplayString
    MAX-ACCESS accessible-for-notify
    STATUS current
    DESCRIPTION
        "Parameter 'loaded' in event SIP.22"
    ::= { sipEventObjects22 2 }

sipEventObjects23 OBJECT-IDENTITY
    STATUS current
    DESCRIPTION
        "Event SIP.23
        An error has happenned while loading a certificate"
    ::= { sipEventsGroup 23 }

sip23-name OBJECT-TYPE
    SYNTAX DisplayString
    MAX-ACCESS accessible-for-notify
    STATUS current
    DESCRIPTION
        "Parameter 'name' in event SIP.23"
    ::= { sipEventObjects23 1 }

sip23-error OBJECT-TYPE
    SYNTAX DisplayString
    MAX-ACCESS accessible-for-notify
    STATUS current
    DESCRIPTION
        "Parameter 'error' in event SIP.23"
    ::= { sipEventObjects23 2 }


sipNotification1 NOTIFICATION-TYPE
    OBJECTS { 
              sip1-description, 
              sip1-task 
            }
    STATUS current
    DESCRIPTION
        "Notification of Event SIP.1

        Message: 'Task: $1 $2'

        Parameters list:
              $1: sip1-description
              $2: sip1-task

        Event related with task creation/deletion."
    ::= { sipNotificationsPrefix 1 }

sipNotification2 NOTIFICATION-TYPE
    OBJECTS { 
              sip2-description, 
              sip2-message,
              sip2-task,
              sip2-cdr 
            }
    STATUS current
    DESCRIPTION
        "Notification of Event SIP.2

        Message: 'Msg: $1 $2 Task:$3, cdr $4'

        Parameters list:
              $1: sip2-description
              $2: sip2-message
              $3: sip2-task
              $4: sip2-cdr

        Event related with message processing."
    ::= { sipNotificationsPrefix 2 }

sipNotification3 NOTIFICATION-TYPE
    OBJECTS { 
              sip3-error, 
              sip3-task 
            }
    STATUS current
    DESCRIPTION
        "Notification of Event SIP.3

        Message: 'Task: $1 $2'

        Parameters list:
              $1: sip3-error
              $2: sip3-task

        Error related with task creation/deletion."
    ::= { sipNotificationsPrefix 3 }

sipNotification4 NOTIFICATION-TYPE
    OBJECTS { 
              sip4-description, 
              sip4-error,
              sip4-task,
              sip4-cdr 
            }
    STATUS current
    DESCRIPTION
        "Notification of Event SIP.4

        Message: 'Msg: $1 $2 Task:$3, cdr $4'

        Parameters list:
              $1: sip4-description
              $2: sip4-error
              $3: sip4-task
              $4: sip4-cdr

        Error related with message processing."
    ::= { sipNotificationsPrefix 4 }

sipNotification5 NOTIFICATION-TYPE
    OBJECTS { 
              sip5-queue, 
              sip5-description,
              sip5-total-msgs,
              sip5-task 
            }
    STATUS current
    DESCRIPTION
        "Notification of Event SIP.5

        Message: 'Queue: $1 $2 Msgs:$3  Task: $4'

        Parameters list:
              $1: sip5-queue
              $2: sip5-description
              $3: sip5-total-msgs
              $4: sip5-task

        Event related with queues."
    ::= { sipNotificationsPrefix 5 }

sipNotification6 NOTIFICATION-TYPE
    OBJECTS { 
              sip6-app, 
              sip6-type,
              sip6-cdr 
            }
    STATUS current
    DESCRIPTION
        "Notification of Event SIP.6

        Message: '$1 Processing Msg: $2, cdr $3'

        Parameters list:
              $1: sip6-app
              $2: sip6-type
              $3: sip6-cdr

        Event showing type of message in process."
    ::= { sipNotificationsPrefix 6 }

sipNotification7 NOTIFICATION-TYPE
    OBJECTS { 
              sip7-description, 
              sip7-user,
              sip7-user-host,
              sip7-location,
              sip7-location-host,
              sip7-time-to-live 
            }
    STATUS current
    DESCRIPTION
        "Notification of Event SIP.7

        Message: '$1: $2@$3 location $4@$5 ttl: $6'

        Parameters list:
              $1: sip7-description
              $2: sip7-user
              $3: sip7-user-host
              $4: sip7-location
              $5: sip7-location-host
              $6: sip7-time-to-live

        Event related with client registration or unregistration received."
    ::= { sipNotificationsPrefix 7 }

sipNotification8 NOTIFICATION-TYPE
    OBJECTS { 
              sip8-event-type, 
              sip8-event 
            }
    STATUS current
    DESCRIPTION
        "Notification of Event SIP.8

        Message: '$1: $2'

        Parameters list:
              $1: sip8-event-type
              $2: sip8-event

        SIP Stack event."
    ::= { sipNotificationsPrefix 8 }

sipNotification9 NOTIFICATION-TYPE
    OBJECTS { 
              sip9-app, 
              sip9-call-id,
              sip9-org,
              sip9-dest,
              sip9-state 
            }
    STATUS current
    DESCRIPTION
        "Notification of Event SIP.9

        Message: '$1: Call $2 from $3 to $4 $5'

        Parameters list:
              $1: sip9-app
              $2: sip9-call-id
              $3: sip9-org
              $4: sip9-dest
              $5: sip9-state

        Event related with call state."
    ::= { sipNotificationsPrefix 9 }

sipNotification10 NOTIFICATION-TYPE
    OBJECTS { 
              sip10-app, 
              sip10-state 
            }
    STATUS current
    DESCRIPTION
        "Notification of Event SIP.10

        Message: '$1: $2'

        Parameters list:
              $1: sip10-app
              $2: sip10-state

        Event related with application state."
    ::= { sipNotificationsPrefix 10 }

sipNotification11 NOTIFICATION-TYPE
    OBJECTS { 
              sip11-app, 
              sip11-type,
              sip11-cdr 
            }
    STATUS current
    DESCRIPTION
        "Notification of Event SIP.11

        Message: '$1 Sending Msg: $2, cdr $3'

        Parameters list:
              $1: sip11-app
              $2: sip11-type
              $3: sip11-cdr

        Event showing type of message sent."
    ::= { sipNotificationsPrefix 11 }

sipNotification12 NOTIFICATION-TYPE
    OBJECTS { 
              sip12-event 
            }
    STATUS current
    DESCRIPTION
        "Notification of Event SIP.12

        Message: 'SDP: $1'

        Parameters list:
              $1: sip12-event

        Event showing media negotiation events."
    ::= { sipNotificationsPrefix 12 }

sipNotification13 NOTIFICATION-TYPE
    OBJECTS { 
              sip13-description, 
              sip13-user,
              sip13-dial-peer,
              sip13-time-to-live 
            }
    STATUS current
    DESCRIPTION
        "Notification of Event SIP.13

        Message: '$1: User $2 dial-peer $3 ttl: $4'

        Parameters list:
              $1: sip13-description
              $2: sip13-user
              $3: sip13-dial-peer
              $4: sip13-time-to-live

        Event related with registration or unregistration in external server."
    ::= { sipNotificationsPrefix 13 }

sipNotification14 NOTIFICATION-TYPE
    STATUS current
    DESCRIPTION
        "Notification of Event SIP.14

        Message: 'Server: Survival ON'

        SIP server application enters survival mode."
    ::= { sipNotificationsPrefix 14 }

sipNotification15 NOTIFICATION-TYPE
    STATUS current
    DESCRIPTION
        "Notification of Event SIP.15

        Message: 'Server: Survival OFF'

        SIP server application finish survival mode."
    ::= { sipNotificationsPrefix 15 }

sipNotification16 NOTIFICATION-TYPE
    OBJECTS { 
              sip16-cdr 
            }
    STATUS current
    DESCRIPTION
        "Notification of Event SIP.16

        Message: 'Keep-alive failed, call finnished cdr $1'

        Parameters list:
              $1: sip16-cdr

        Event showing call finnished due to keepalive failed"
    ::= { sipNotificationsPrefix 16 }

sipNotification17 NOTIFICATION-TYPE
    OBJECTS { 
              sip17-user, 
              sip17-user-host,
              sip17-location,
              sip17-location-host 
            }
    STATUS current
    DESCRIPTION
        "Notification of Event SIP.17

        Message: 'Unregister User: $1@$2 location $3@$4'

        Parameters list:
              $1: sip17-user
              $2: sip17-user-host
              $3: sip17-location
              $4: sip17-location-host

        A register has expired"
    ::= { sipNotificationsPrefix 17 }

sipNotification18 NOTIFICATION-TYPE
    OBJECTS { 
              sip18-type, 
              sip18-identifier,
              sip18-description 
            }
    STATUS current
    DESCRIPTION
        "Notification of Event SIP.18

        Message: 'Socket $1 id:$2 open connect $3'

        Parameters list:
              $1: sip18-type
              $2: sip18-identifier
              $3: sip18-description

        Socket connect event, local connection."
    ::= { sipNotificationsPrefix 18 }

sipNotification19 NOTIFICATION-TYPE
    OBJECTS { 
              sip19-type, 
              sip19-identifier,
              sip19-description 
            }
    STATUS current
    DESCRIPTION
        "Notification of Event SIP.19

        Message: 'Socket $1 id:$2 open accept $3'

        Parameters list:
              $1: sip19-type
              $2: sip19-identifier
              $3: sip19-description

        Socket accept event, remote connection."
    ::= { sipNotificationsPrefix 19 }

sipNotification20 NOTIFICATION-TYPE
    OBJECTS { 
              sip20-type, 
              sip20-identifier 
            }
    STATUS current
    DESCRIPTION
        "Notification of Event SIP.20

        Message: 'Socket $1 id:$2 close local'

        Parameters list:
              $1: sip20-type
              $2: sip20-identifier

        Socket close local event."
    ::= { sipNotificationsPrefix 20 }

sipNotification21 NOTIFICATION-TYPE
    OBJECTS { 
              sip21-type, 
              sip21-identifier 
            }
    STATUS current
    DESCRIPTION
        "Notification of Event SIP.21

        Message: 'Socket $1 id:$2 close remote'

        Parameters list:
              $1: sip21-type
              $2: sip21-identifier

        Socket close local event."
    ::= { sipNotificationsPrefix 21 }

sipNotification22 NOTIFICATION-TYPE
    OBJECTS { 
              sip22-name, 
              sip22-loaded 
            }
    STATUS current
    DESCRIPTION
        "Notification of Event SIP.22

        Message: 'Certificate $1 $2'

        Parameters list:
              $1: sip22-name
              $2: sip22-loaded

        A certificate has been loaded or unloaded"
    ::= { sipNotificationsPrefix 22 }

sipNotification23 NOTIFICATION-TYPE
    OBJECTS { 
              sip23-name, 
              sip23-error 
            }
    STATUS current
    DESCRIPTION
        "Notification of Event SIP.23

        Message: 'Certificate $1 loading error: $2'

        Parameters list:
              $1: sip23-name
              $2: sip23-error

        An error has happenned while loading a certificate"
    ::= { sipNotificationsPrefix 23 }


END
