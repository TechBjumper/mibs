-- extracted from draft-lai-mpls-ldp-hist-mib-00.txt
-- at Thu Oct 23 06:15:15 2003

   MPLS-LDP-HIST-STD-MIB DEFINITIONS ::= BEGIN 
    
   IMPORTS 
       OBJECT-TYPE, MODULE-IDENTITY, NOTIFICATION-TYPE, 
       Counter32 
           FROM SNMPv2-SMI 
       MODULE-COMPLIANCE, OBJECT-GROUP, NOTIFICATION-GROUP 
           FROM SNMPv2-CONF 
    
       mplsStdMIB 
           FROM MPLS-TC-STD-MIB 
    
       mplsLdpEntityTable, 
       mplsLdpSessionTable 
           FROM MPLS-LDP-STD-MIB; 
    
   mplsLdpHistStdMIB MODULE-IDENTITY 
       LAST-UPDATED "200310171200Z"  -- 17 October 2003 
       ORGANIZATION "Multiprotocol Label Switching (mpls) 
                     Working Group" 
    
       CONTACT-INFO 
           "Wai Sum Lai (wlai@att.com) 
            AT&T 
             
            Working Group Chairs: 
            George Swallow,   email: swallow@cisco.com 
            Loa Andersson,    email: loa@pi.se 
    
            MPLS Working Group, email: mpls@uu.net" 
    
       DESCRIPTION 
           "Copyright (C) The Internet Society (2003).  This 
           version of this MIB module is part of RFCXXX; see 
           the RFC itself for full legal notices. 
    
           This MIB Module contains managed object definitions for the 
           'Multiprotocol Label Switching, Label Distribution 
           Protocol, LDP History Module' document." 
    
   -- Revision History 
    
       REVISION "200310171200Z"  -- 17 October 2003 
       DESCRIPTION 
           "Initial draft version." 
    
       ::= { mplsStdMIB 1 } -- to be assigned by IANA 
    
   --**************************************************************** 
    
   mplsLdpHistObjects   OBJECT IDENTIFIER ::= { mplsLdpHistStdMIB 1 } 
    
   --**************************************************************** 
   -- MPLS LDP History Module Objects 
   --**************************************************************** 
    
   -- 
   -- The MPLS LDP Entity History Table 
   -- 
   mplsLdpEntityHistTable OBJECT-TYPE 
       SYNTAX      SEQUENCE OF MplsLdpEntityHistEntry 
       MAX-ACCESS  not-accessible 
       STATUS      current 
       DESCRIPTION 
           "This table is a read-only table which augments 
           the mplsLdpEntityTable.  The purpose of this 
           table is to keep historical statistics information 
           about the LDP Entities on the LSR." 
       ::= { mplsLdpHistObjects 1 } 
    
   mplsLdpEntityHistEntry OBJECT-TYPE 
       SYNTAX      MplsLdpEntityHistEntry 
       MAX-ACCESS  not-accessible 
       STATUS      current 
       DESCRIPTION 
           "A row in this table contains statistical information 
           about an LDP Entity." 
       AUGMENTS       {   mplsLdpEntityEntry  } 
       ::= { mplsLdpEntityHistTable 1 } 
    
   MplsLdpEntityHistEntry ::= SEQUENCE { 
       mplsLdpEntityHistAttemptedSession     Counter32, 
       mplsLdpEntityHistEstablishedSessions  Counter32, 
       mplsLdpEntityHistTerminatedSessions   Counter32 
   } 
    
   mplsLdpEntityHistAttemptedSessions OBJECT-TYPE 
       SYNTAX      Counter32 
       MAX-ACCESS  read-only 
       STATUS      current 
       DESCRIPTION 
           "This value indicates the specific number of attempts made 
           to establish LDP Sessions between two peers in the 
           corresponding label space, whether those attempts are 
           successful or not.  This is a running counter that is only 
           re-initialized whenever the LDP Entity is initialized." 
       ::= { mplsLdpEntityHistEntry 1 } 
    
   mplsLdpEntityHistEstablishedSessions OBJECT-TYPE 
       SYNTAX      Counter32 
       MAX-ACCESS  read-only 
       STATUS      current 
       DESCRIPTION 
           "This value indicates the specific number of successful 
           attempts made to establish LDP Sessions between two peers 
           in the corresponding label space.  This is a running 
           counter that is only re-initialized whenever the LDP Entity 
           is initialized." 
       ::= { mplsLdpEntityHistEntry 2 } 
    
   mplsLdpEntityHistTerminatedSessions OBJECT-TYPE 
       SYNTAX      Counter32 
       MAX-ACCESS  read-only 
       STATUS      current 
       DESCRIPTION 
           "This value indicates the specific number of terminated 
           LDP sessions between two peers in the corresponding label 
           space.  This is a running counter that is only 
           re-initialized whenever the LDP Entity is initialized." 
       ::= { mplsLdpEntityHistEntry 3 } 
    
   -- 
   -- The MPLS LDP Session History Table 
   -- 
    
   mplsLdpSessionHistTable OBJECT-TYPE 
       SYNTAX      SEQUENCE OF MplsLdpSessionHistEntry 
       MAX-ACCESS  not-accessible 
       STATUS      current 
       DESCRIPTION 
           "A table of historical statistical information 
           for Sessions between the LDP Entities 
           and LDP Peers.  This table AUGMENTS the 
           mplsLdpSessionTable.  Each row in this table 
           represents a single session." 
       ::= { mplsLdpHistObjects 2 } 
    
   mplsLdpSessionHistEntry OBJECT-TYPE 
       SYNTAX      MplsLdpSessionHistEntry 
       MAX-ACCESS  not-accessible 
       STATUS      current 
       DESCRIPTION 
           "An entry in this table represents information on a 
           single session between an LDP Entity and LDP Peer. 
           The information contained in a row is read-only. "
       AUGMENTS { mplsLdpSessionEntry } 
       ::= { mplsLdpSessionHistTable 1 } 
    
   MplsLdpSessionHistEntry ::= SEQUENCE { 
       mplsLdpSessionHistSucessPackets     Counter32, 
       mplsLdpSessionHistUnsuccessPackets  Counter32 
   } 
    
   mplsLdpSessionHistSucessPackets OBJECT-TYPE 
       SYNTAX      Counter32 
       MAX-ACCESS  read-only 
       STATUS      current 
       DESCRIPTION 
           "This value indicates the specific number of 
           packets successfully sent over the LDP Sessions. 
           This is a running counter that is only 
           re-initialized whenever the associated LDP Entity 
           is initialized." 
       ::= { mplsLdpSessionHistEntry 1 } 

   mplsLdpSessionHistUnsuccessPackets OBJECT-TYPE 
       SYNTAX      Counter32 
       MAX-ACCESS  read-only 
       STATUS      current 
       DESCRIPTION 
           "This value indicates the specific number of 
           packets unsuccessfully sent over the LDP Sessions. 
           This is a running counter that is only 
           re-initialized whenever the associated LDP Entity 
           is initialized." 
       ::= { mplsLdpSessionHistEntry 2 } 
    
   END 

--  
-- 
--    "Copyright (C) The Internet Society (date). All Rights Reserved. 
--    This document and translations of it may be copied and furnished to 
--    others, and derivative works that comment on or otherwise explain it 
--    or assist in its implmentation may be prepared, copied, published 
--    and distributed, in whole or in part, without restriction of any 
--    kind, provided that the above copyright notice and this paragraph 
--    are included on all such copies and derivative works. However, this 
--    document itself may not be modified in any way, such as by removing 
--    the copyright notice or references to the Internet Society or other 
--    Internet organizations, except as needed for the purpose of 
--    developing Internet standards in which case the procedures for 
--    copyrights defined in the Internet Standards process must be 
--    followed, or as required to translate it into languages other than 
--    English. 
--     
--    The limited permissions granted above are perpetual and will not be 
--    revoked by the Internet Society or its successors or assigns. 
--     
--    This document and the information contained herein is provided on an 
--    "AS IS" basis and THE INTERNET SOCIETY AND THE INTERNET ENGINEERING 
--    TASK FORCE DISCLAIMS ALL WARRANTIES, EXPRESS OR IMPLIED, INCLUDING 
--    BUT NOT LIMITED TO ANY WARRANTY THAT THE USE OF THE INFORMATION 
--    HEREIN WILL NOT INFRINGE ANY RIGHTS OR ANY IMPLIED WARRANTIES OF 
--    MERCHANTABILITY OR FITNESS FOR A PARTICULAR PURPOSE.
