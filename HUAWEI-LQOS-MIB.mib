--
-- HUAWEI-LQOS-MIB.my
-- MIB generated by MG-SOFT Visual MIB Builder Version 3.0 Build 253
-- Sunday, January 16, 2005 at 15:50:04
--

--  HUAWEI-QOS-MIB.my
-- MIB generated by MG-SOFT Visual MIB Builder Version 3.0 Build 253
-- Tuesday, January 04, 2005 at 16:41:24
-- 

	HUAWEI-LQOS-MIB DEFINITIONS ::= BEGIN
 
		IMPORTS
			huaweiMgmt			
				FROM HUAWEI-MIB			
			Counter64, OBJECT-TYPE, MODULE-IDENTITY			
				FROM SNMPv2-SMI			
			TruthValue, RowStatus			
				FROM SNMPv2-TC;
	
	
--   Following is for Node:hwLswQosMib 
-- November 19, 2002 at 00:00 GMT
-- November 19, 2002 at 00:00 GMT
		hwLswQosAclMib MODULE-IDENTITY 
			LAST-UPDATED "200211190000Z"		-- November 19, 2002 at 00:00 GMT
			ORGANIZATION 
				"HUAWEI LANSWITCH"
			CONTACT-INFO 
				"huawei beiyan"
			DESCRIPTION 
				"Module node for qos and acl."
			REVISION "200211190000Z"		-- November 19, 2002 at 00:00 GMT
			DESCRIPTION
				"none"
			::= { huaweiMgmt 2 }
		
	
	
--
-- Node definitions
--
	
--  Node definitions
-- 
-- 1.3.6.1.4.1.2011.5.2.2
		-- 1.3.6.1.4.1.2011.5.2.2
		hwQueueTable OBJECT-TYPE
			SYNTAX SEQUENCE OF HwQueueTableEntry
			MAX-ACCESS not-accessible
			STATUS current
			DESCRIPTION
				""
			::= { hwLswQosAclMib 2 }
		
--  1.3.6.1.4.1.2011.5.2.2.1
		-- 1.3.6.1.4.1.2011.5.2.2.1
		hwQueueTableEntry OBJECT-TYPE
			SYNTAX HwQueueTableEntry
			MAX-ACCESS not-accessible
			STATUS current
			DESCRIPTION
				" "
			INDEX { hwQueueIfIndex }
			::= { hwQueueTable 1 }
		
		HwQueueTableEntry ::=
			SEQUENCE { 
				hwQueueIfIndex
					INTEGER,
				hwQueueScheduleMode
					INTEGER,
				hwQueueWeight1
					INTEGER,
				hwQueueWeight2
					INTEGER,
				hwQueueWeight3
					INTEGER,
				hwQueueWeight4
					INTEGER,
				hwQueueWeight5
					INTEGER,
				hwQueueWeight6
					INTEGER,
				hwQueueWeight7
					INTEGER,
				hwQueueWeight8
					INTEGER,
				hwWFQMaxWeight1
					INTEGER,
				hwWFQMaxWeight2
					INTEGER,
				hwWFQMaxWeight3
					INTEGER,
				hwWFQMaxWeight4
					INTEGER,
				hwWFQMaxWeight5
					INTEGER,
				hwWFQMaxWeight6
					INTEGER,
				hwWFQMaxWeight7
					INTEGER,
				hwWFQMaxWeight8
					INTEGER,
				hwQueueMaxDelay
					INTEGER
			 }

--  1.3.6.1.4.1.2011.5.2.2.1.1
		-- 1.3.6.1.4.1.2011.5.2.2.1.1
		hwQueueIfIndex OBJECT-TYPE
			SYNTAX INTEGER (1..255)
			MAX-ACCESS read-only
			STATUS current
			DESCRIPTION
				""
			::= { hwQueueTableEntry 1 }
		
--  1.3.6.1.4.1.2011.5.2.2.1.2
		-- 1.3.6.1.4.1.2011.5.2.2.1.2
		hwQueueScheduleMode OBJECT-TYPE
			SYNTAX INTEGER
				{
				sp(1),
				wrr(2),
				wfq(8)
				}
			MAX-ACCESS read-write
			STATUS current
			DESCRIPTION
				""
			DEFVAL { sp }
			::= { hwQueueTableEntry 2 }
		
--  1.3.6.1.4.1.2011.5.2.2.1.3
		-- 1.3.6.1.4.1.2011.5.2.2.1.3
		hwQueueWeight1 OBJECT-TYPE
			SYNTAX INTEGER (0..100)
			MAX-ACCESS read-write
			STATUS current
			DESCRIPTION
				""
			::= { hwQueueTableEntry 3 }
		
--  1.3.6.1.4.1.2011.5.2.2.1.4
		-- 1.3.6.1.4.1.2011.5.2.2.1.4
		hwQueueWeight2 OBJECT-TYPE
			SYNTAX INTEGER (0..100)
			MAX-ACCESS read-write
			STATUS current
			DESCRIPTION
				""
			::= { hwQueueTableEntry 4 }
		
--  1.3.6.1.4.1.2011.5.2.2.1.5
		-- 1.3.6.1.4.1.2011.5.2.2.1.5
		hwQueueWeight3 OBJECT-TYPE
			SYNTAX INTEGER (0..100)
			MAX-ACCESS read-write
			STATUS current
			DESCRIPTION
				""
			::= { hwQueueTableEntry 5 }
		
--  1.3.6.1.4.1.2011.5.2.2.1.6
		-- 1.3.6.1.4.1.2011.5.2.2.1.6
		hwQueueWeight4 OBJECT-TYPE
			SYNTAX INTEGER (0..100)
			MAX-ACCESS read-write
			STATUS current
			DESCRIPTION
				""
			::= { hwQueueTableEntry 6 }
		
--  1.3.6.1.4.1.2011.5.2.2.1.7
		-- 1.3.6.1.4.1.2011.5.2.2.1.7
		hwQueueWeight5 OBJECT-TYPE
			SYNTAX INTEGER (0..100)
			MAX-ACCESS read-write
			STATUS current
			DESCRIPTION
				""
			::= { hwQueueTableEntry 7 }
		
--  1.3.6.1.4.1.2011.5.2.2.1.8
		-- 1.3.6.1.4.1.2011.5.2.2.1.8
		hwQueueWeight6 OBJECT-TYPE
			SYNTAX INTEGER (0..100)
			MAX-ACCESS read-write
			STATUS current
			DESCRIPTION
				""
			::= { hwQueueTableEntry 8 }
		
--  1.3.6.1.4.1.2011.5.2.2.1.9
		-- 1.3.6.1.4.1.2011.5.2.2.1.9
		hwQueueWeight7 OBJECT-TYPE
			SYNTAX INTEGER (0..100)
			MAX-ACCESS read-write
			STATUS current
			DESCRIPTION
				""
			::= { hwQueueTableEntry 9 }
		
--  1.3.6.1.4.1.2011.5.2.2.1.10
		-- 1.3.6.1.4.1.2011.5.2.2.1.10
		hwQueueWeight8 OBJECT-TYPE
			SYNTAX INTEGER (0..100)
			MAX-ACCESS read-write
			STATUS current
			DESCRIPTION
				""
			::= { hwQueueTableEntry 10 }

		
--  1.3.6.1.4.1.2011.5.2.2.1.11
		-- 1.3.6.1.4.1.2011.5.2.2.1.11
		hwWFQMaxWeight1 OBJECT-TYPE
			SYNTAX INTEGER (0..100)
			MAX-ACCESS read-write
			STATUS current
			DESCRIPTION
				""
			::= { hwQueueTableEntry 11 }
		
--  1.3.6.1.4.1.2011.5.2.2.1.12
		-- 1.3.6.1.4.1.2011.5.2.2.1.12
		hwWFQMaxWeight2 OBJECT-TYPE
			SYNTAX INTEGER (0..100)
			MAX-ACCESS read-write
			STATUS current
			DESCRIPTION
				""
			::= { hwQueueTableEntry 12 }
		
--  1.3.6.1.4.1.2011.5.2.2.1.13
		-- 1.3.6.1.4.1.2011.5.2.2.1.13
		hwWFQMaxWeight3 OBJECT-TYPE
			SYNTAX INTEGER (0..100)
			MAX-ACCESS read-write
			STATUS current
			DESCRIPTION
				""
			::= { hwQueueTableEntry 13 }
		
--  1.3.6.1.4.1.2011.5.2.2.1.14
		-- 1.3.6.1.4.1.2011.5.2.2.1.14
		hwWFQMaxWeight4 OBJECT-TYPE
			SYNTAX INTEGER (0..100)
			MAX-ACCESS read-write
			STATUS current
			DESCRIPTION
				""
			::= { hwQueueTableEntry 14 }
		
--  1.3.6.1.4.1.2011.5.2.2.1.15
		-- 1.3.6.1.4.1.2011.5.2.2.1.15
		hwWFQMaxWeight5 OBJECT-TYPE
			SYNTAX INTEGER (0..100)
			MAX-ACCESS read-write
			STATUS current
			DESCRIPTION
				""
			::= { hwQueueTableEntry 15 }
		
--  1.3.6.1.4.1.2011.5.2.2.1.16
		-- 1.3.6.1.4.1.2011.5.2.2.1.16
		hwWFQMaxWeight6 OBJECT-TYPE
			SYNTAX INTEGER (0..100)
			MAX-ACCESS read-write
			STATUS current
			DESCRIPTION
				""
			::= { hwQueueTableEntry 16 }
		
--  1.3.6.1.4.1.2011.5.2.2.1.17
		-- 1.3.6.1.4.1.2011.5.2.2.1.17
		hwWFQMaxWeight7 OBJECT-TYPE
			SYNTAX INTEGER (0..100)
			MAX-ACCESS read-write
			STATUS current
			DESCRIPTION
				""
			::= { hwQueueTableEntry 17 }
		
--  1.3.6.1.4.1.2011.5.2.2.1.18
		-- 1.3.6.1.4.1.2011.5.2.2.1.18
		hwWFQMaxWeight8 OBJECT-TYPE
			SYNTAX INTEGER (0..100)
			MAX-ACCESS read-write
			STATUS current
			DESCRIPTION
				""
			::= { hwQueueTableEntry 18 }
		
--  1.3.6.1.4.1.2011.5.2.2.1.19
		-- 1.3.6.1.4.1.2011.5.2.2.1.19
		hwQueueMaxDelay OBJECT-TYPE
			SYNTAX INTEGER (0..4080)
			MAX-ACCESS read-only
			STATUS current
			DESCRIPTION
				""
			::= { hwQueueTableEntry 19 }
		
--   TABLE: hwQueueTable 
--  TABLE: hwRateLimitTable 
-- 1.3.6.1.4.1.2011.5.2.3
		-- 1.3.6.1.4.1.2011.5.2.3
		hwRateLimitTable OBJECT-TYPE
			SYNTAX SEQUENCE OF HwRateLimitTableEntry
			MAX-ACCESS not-accessible
			STATUS current
			DESCRIPTION
				""
			::= { hwLswQosAclMib 3 }
		
--  1.3.6.1.4.1.2011.5.2.3.1
		-- 1.3.6.1.4.1.2011.5.2.3.1
		hwRateLimitTableEntry OBJECT-TYPE
			SYNTAX HwRateLimitTableEntry
			MAX-ACCESS not-accessible
			STATUS current
			DESCRIPTION
				" "
			INDEX { hwRateLimitAclIndex, hwRateLimitIfIndex, hwRateLimitDirection }
			::= { hwRateLimitTable 1 }
		
		HwRateLimitTableEntry ::=
			SEQUENCE { 
				hwRateLimitAclIndex
					INTEGER,
				hwRateLimitIfIndex
					INTEGER,
				hwRateLimitDirection
					INTEGER,
				hwRateLimitUserAclNum
					INTEGER,
				hwRateLimitUserAclSubitem
					INTEGER,
				hwRateLimitIpAclNum
					INTEGER,
				hwRateLimitIpAclSubitem
					INTEGER,
				hwRateLimitLinkAclNum
					INTEGER,
				hwRateLimitLinkAclSubitem
					INTEGER,
				hwRateLimitTargetRate
					INTEGER,
				hwRateLimitExceedDrop
					TruthValue,
				hwRateLimitExceedDscp
					INTEGER,
				hwRateLimitRuntime
					TruthValue,
				hwRateLimitRowStatus
					RowStatus
			 }

--  1.3.6.1.4.1.2011.5.2.3.1.1
		-- 1.3.6.1.4.1.2011.5.2.3.1.1
		hwRateLimitAclIndex OBJECT-TYPE
			SYNTAX INTEGER (0..2999)
			MAX-ACCESS read-only
			STATUS current
			DESCRIPTION
				""
			::= { hwRateLimitTableEntry 1 }
		
--  1.3.6.1.4.1.2011.5.2.3.1.2
		-- 1.3.6.1.4.1.2011.5.2.3.1.2
		hwRateLimitIfIndex OBJECT-TYPE
			SYNTAX INTEGER (0..4294967295)
			MAX-ACCESS read-only
			STATUS current
			DESCRIPTION
				""
			::= { hwRateLimitTableEntry 2 }
		
--  1.3.6.1.4.1.2011.5.2.3.1.3
		-- 1.3.6.1.4.1.2011.5.2.3.1.3
		hwRateLimitDirection OBJECT-TYPE
			SYNTAX INTEGER
				{
				input(1),
				invalid(0)
				}
			MAX-ACCESS read-only
			STATUS current
			DESCRIPTION
				""
			::= { hwRateLimitTableEntry 3 }
		
--  1.3.6.1.4.1.2011.5.2.3.1.4
		-- 1.3.6.1.4.1.2011.5.2.3.1.4
		hwRateLimitUserAclNum OBJECT-TYPE
			SYNTAX INTEGER (0 | 5000..5999)
			MAX-ACCESS read-create
			STATUS current
			DESCRIPTION
				""
			::= { hwRateLimitTableEntry 4 }
		
--  1.3.6.1.4.1.2011.5.2.3.1.5
		-- 1.3.6.1.4.1.2011.5.2.3.1.5
		hwRateLimitUserAclSubitem OBJECT-TYPE
			SYNTAX INTEGER (0..4294967295)
			MAX-ACCESS read-create
			STATUS current
			DESCRIPTION
				""
			::= { hwRateLimitTableEntry 5 }
		
--  1.3.6.1.4.1.2011.5.2.3.1.6
		-- 1.3.6.1.4.1.2011.5.2.3.1.6
		hwRateLimitIpAclNum OBJECT-TYPE
			SYNTAX INTEGER (0 | 2000..3999)
			MAX-ACCESS read-create
			STATUS current
			DESCRIPTION
				""
			::= { hwRateLimitTableEntry 6 }
		
--  1.3.6.1.4.1.2011.5.2.3.1.7
		-- 1.3.6.1.4.1.2011.5.2.3.1.7
		hwRateLimitIpAclSubitem OBJECT-TYPE
			SYNTAX INTEGER (0..4294967295)
			MAX-ACCESS read-create
			STATUS current
			DESCRIPTION
				""
			::= { hwRateLimitTableEntry 7 }
		
--  1.3.6.1.4.1.2011.5.2.3.1.8
		-- 1.3.6.1.4.1.2011.5.2.3.1.8
		hwRateLimitLinkAclNum OBJECT-TYPE
			SYNTAX INTEGER (0 | 4000..4999)
			MAX-ACCESS read-create
			STATUS current
			DESCRIPTION
				""
			::= { hwRateLimitTableEntry 8 }
		
--  1.3.6.1.4.1.2011.5.2.3.1.9
		-- 1.3.6.1.4.1.2011.5.2.3.1.9
		hwRateLimitLinkAclSubitem OBJECT-TYPE
			SYNTAX INTEGER (0..4294967295)
			MAX-ACCESS read-create
			STATUS current
			DESCRIPTION
				""
			::= { hwRateLimitTableEntry 9 }
		
--  1.3.6.1.4.1.2011.5.2.3.1.10
		-- 1.3.6.1.4.1.2011.5.2.3.1.10
		hwRateLimitTargetRate OBJECT-TYPE
			SYNTAX INTEGER (64..1000000)
			MAX-ACCESS read-create
			STATUS current
			DESCRIPTION
				""
			::= { hwRateLimitTableEntry 10 }
		
--  1.3.6.1.4.1.2011.5.2.3.1.11
		-- 1.3.6.1.4.1.2011.5.2.3.1.11
		hwRateLimitExceedDrop OBJECT-TYPE
			SYNTAX TruthValue
			MAX-ACCESS read-create
			STATUS current
			DESCRIPTION
				""
			DEFVAL { 1 }
			::= { hwRateLimitTableEntry 11 }
		
--  1.3.6.1.4.1.2011.5.2.3.1.12
		-- 1.3.6.1.4.1.2011.5.2.3.1.12
		hwRateLimitExceedDscp OBJECT-TYPE
			SYNTAX INTEGER (0..63 | 255)
			MAX-ACCESS read-create
			STATUS current
			DESCRIPTION
				""
			DEFVAL { 255 }
			::= { hwRateLimitTableEntry 12 }
		
--  1.3.6.1.4.1.2011.5.2.3.1.13
		-- 1.3.6.1.4.1.2011.5.2.3.1.13
		hwRateLimitRuntime OBJECT-TYPE
			SYNTAX TruthValue
			MAX-ACCESS read-only
			STATUS current
			DESCRIPTION
				""
			::= { hwRateLimitTableEntry 13 }
		
--  1.3.6.1.4.1.2011.5.2.3.1.14
		-- 1.3.6.1.4.1.2011.5.2.3.1.14
		hwRateLimitRowStatus OBJECT-TYPE
			SYNTAX RowStatus
			MAX-ACCESS read-create
			STATUS current
			DESCRIPTION
				""
			::= { hwRateLimitTableEntry 14 }
		
--   TABLE: hwPriorityTable 
-- 1.3.6.1.4.1.2011.5.2.4
		-- 1.3.6.1.4.1.2011.5.2.4
		hwPriorityTable OBJECT-TYPE
			SYNTAX SEQUENCE OF HwPriorityTableEntry
			MAX-ACCESS not-accessible
			STATUS current
			DESCRIPTION
				""
			::= { hwLswQosAclMib 4 }
		
--  1.3.6.1.4.1.2011.5.2.4.1
		-- 1.3.6.1.4.1.2011.5.2.4.1
		hwPriorityTableEntry OBJECT-TYPE
			SYNTAX HwPriorityTableEntry
			MAX-ACCESS not-accessible
			STATUS current
			DESCRIPTION
				" "
			INDEX { hwPriorityAclIndex, hwPriorityIfIndex, hwPriorityDirection }
			::= { hwPriorityTable 1 }
		
		HwPriorityTableEntry ::=
			SEQUENCE { 
				hwPriorityAclIndex
					INTEGER,
				hwPriorityIfIndex
					INTEGER,
				hwPriorityDirection
					INTEGER,
				hwPriorityUserAclNum
					INTEGER,
				hwPriorityUserAclSubitem
					INTEGER,
				hwPriorityIpAclNum
					INTEGER,
				hwPriorityIpAclSubitem
					INTEGER,
				hwPriorityLinkAclNum
					INTEGER,
				hwPriorityLinkAclSubitem
					INTEGER,
				hwPriorityDscp
					INTEGER,
				hwPriorityIpPreValue
					INTEGER,
				hwPriorityIpPreFromCos
					TruthValue,
				hwPriorityCosValue
					INTEGER,
				hwPriorityCosFromIpPre
					TruthValue,
				hwPriorityLocalPre
					INTEGER,
				hwPriorityRuntime
					TruthValue,
				hwPriorityRowStatus
					RowStatus
			 }

--  1.3.6.1.4.1.2011.5.2.4.1.1
		-- 1.3.6.1.4.1.2011.5.2.4.1.1
		hwPriorityAclIndex OBJECT-TYPE
			SYNTAX INTEGER (0..2999)
			MAX-ACCESS read-only
			STATUS current
			DESCRIPTION
				""
			::= { hwPriorityTableEntry 1 }
		
--  1.3.6.1.4.1.2011.5.2.4.1.2
		-- 1.3.6.1.4.1.2011.5.2.4.1.2
		hwPriorityIfIndex OBJECT-TYPE
			SYNTAX INTEGER (0..4294967295)
			MAX-ACCESS read-only
			STATUS current
			DESCRIPTION
				""
			::= { hwPriorityTableEntry 2 }
		
--  1.3.6.1.4.1.2011.5.2.4.1.3
		-- 1.3.6.1.4.1.2011.5.2.4.1.3
		hwPriorityDirection OBJECT-TYPE
			SYNTAX INTEGER
				{
				input(1),
				output(2),
				invalid(0)
				}
			MAX-ACCESS read-only
			STATUS current
			DESCRIPTION
				""
			::= { hwPriorityTableEntry 3 }
		
--  1.3.6.1.4.1.2011.5.2.4.1.4
		-- 1.3.6.1.4.1.2011.5.2.4.1.4
		hwPriorityUserAclNum OBJECT-TYPE
			SYNTAX INTEGER (0 | 5000..5999)
			MAX-ACCESS read-create
			STATUS current
			DESCRIPTION
				""
			::= { hwPriorityTableEntry 4 }
		
--  1.3.6.1.4.1.2011.5.2.4.1.5
		-- 1.3.6.1.4.1.2011.5.2.4.1.5
		hwPriorityUserAclSubitem OBJECT-TYPE
			SYNTAX INTEGER (0..4294967295)
			MAX-ACCESS read-create
			STATUS current
			DESCRIPTION
				""
			::= { hwPriorityTableEntry 5 }
		
--  1.3.6.1.4.1.2011.5.2.4.1.6
		-- 1.3.6.1.4.1.2011.5.2.4.1.6
		hwPriorityIpAclNum OBJECT-TYPE
			SYNTAX INTEGER (0 | 2000..3999)
			MAX-ACCESS read-create
			STATUS current
			DESCRIPTION
				""
			::= { hwPriorityTableEntry 6 }
		
--  1.3.6.1.4.1.2011.5.2.4.1.7
		-- 1.3.6.1.4.1.2011.5.2.4.1.7
		hwPriorityIpAclSubitem OBJECT-TYPE
			SYNTAX INTEGER (0..4294967295)
			MAX-ACCESS read-create
			STATUS current
			DESCRIPTION
				""
			::= { hwPriorityTableEntry 7 }
		
--  1.3.6.1.4.1.2011.5.2.4.1.8
		-- 1.3.6.1.4.1.2011.5.2.4.1.8
		hwPriorityLinkAclNum OBJECT-TYPE
			SYNTAX INTEGER (0 | 4000..4999)
			MAX-ACCESS read-create
			STATUS current
			DESCRIPTION
				""
			::= { hwPriorityTableEntry 8 }
		
--  1.3.6.1.4.1.2011.5.2.4.1.9
		-- 1.3.6.1.4.1.2011.5.2.4.1.9
		hwPriorityLinkAclSubitem OBJECT-TYPE
			SYNTAX INTEGER (0..4294967295)
			MAX-ACCESS read-create
			STATUS current
			DESCRIPTION
				""
			::= { hwPriorityTableEntry 9 }
		
--  1.3.6.1.4.1.2011.5.2.4.1.10
		-- 1.3.6.1.4.1.2011.5.2.4.1.10
		hwPriorityDscp OBJECT-TYPE
			SYNTAX INTEGER (0..63 | 255)
			MAX-ACCESS read-create
			STATUS current
			DESCRIPTION
				"
				af1                   Specify Assured Forwarding 1 service(10)
				af2                   Specify Assured Forwarding 2 service(18)
				af3                   Specify Assured Forwarding 3 service(26)
				af4                   Specify Assured Forwarding 4 service(34)
				be                    Specify Best Effort service(0)
				cs1                   Specify Class Seletor 1 service(8)
				cs2                   Specify Class Seletor 2 service(16)
				cs3                   Specify Class Seletor 3 service(24)
				cs4                   Specify Class Seletor 4 service(32)
				cs5                   Specify Class Seletor 5 service(40)
				cs6                   Specify Class Seletor 6 service(48)
				cs7                   Specify Class Seletor 7 service(56)
				ef                    Specify Expedited Forwarding service(46)      "
			DEFVAL { 255 }
			::= { hwPriorityTableEntry 10 }
		
--  1.3.6.1.4.1.2011.5.2.4.1.11
		-- 1.3.6.1.4.1.2011.5.2.4.1.11
		hwPriorityIpPreValue OBJECT-TYPE
			SYNTAX INTEGER (0..7 | 255)
			MAX-ACCESS read-create
			STATUS current
			DESCRIPTION
				"
				critical              Specify critical precedence(5)
				flash                 Specify flash precedence(3)
				flash-override        Specify flash-override precedence(4)
				from-cos              Specify IP precedence same as 802.1p priority
				immediate             Specify immediate precedence(2)
				internet              Specify internetwork control precedence(6)
				network               Specify network control precedence(7)
				priority              Specify priority precedence(1)
				routine               Specify routine precedence(0)  "
			DEFVAL { 255 }
			::= { hwPriorityTableEntry 11 }
		
--  1.3.6.1.4.1.2011.5.2.4.1.12
		-- 1.3.6.1.4.1.2011.5.2.4.1.12
		hwPriorityIpPreFromCos OBJECT-TYPE
			SYNTAX TruthValue
			MAX-ACCESS read-create
			STATUS current
			DESCRIPTION
				""
			DEFVAL { 2 }
			::= { hwPriorityTableEntry 12 }
		
--  1.3.6.1.4.1.2011.5.2.4.1.13
		-- 1.3.6.1.4.1.2011.5.2.4.1.13
		hwPriorityCosValue OBJECT-TYPE
			SYNTAX INTEGER (0..7 | 255)
			MAX-ACCESS read-create
			STATUS current
			DESCRIPTION
				"
				<0-7>                 802.1p priority value
				background            Specify background priority(1)
				best-effort           Specify best-effort priority(0)
				controlled-load       Specify controlled-load priority(4)
				excellent-effort      Specify excellent-effort priority(3)
				from-ipprec           Specify 802.1p priority same as IP precedence
				network-management    Specify network-management priority(7)
				spare                 Specify spare priority(2)
				video                 Specify video priority(5)
				voice                 Specify voice priority(6)      "
			DEFVAL { 255 }
			::= { hwPriorityTableEntry 13 }
		
--  1.3.6.1.4.1.2011.5.2.4.1.14
		-- 1.3.6.1.4.1.2011.5.2.4.1.14
		hwPriorityCosFromIpPre OBJECT-TYPE
			SYNTAX TruthValue
			MAX-ACCESS read-create
			STATUS current
			DESCRIPTION
				""
			DEFVAL { 2 }
			::= { hwPriorityTableEntry 14 }
		
--  1.3.6.1.4.1.2011.5.2.4.1.15
		-- 1.3.6.1.4.1.2011.5.2.4.1.15
		hwPriorityLocalPre OBJECT-TYPE
			SYNTAX INTEGER (0..7 | 255)
			MAX-ACCESS read-create
			STATUS current
			DESCRIPTION
				""
			DEFVAL { 255 }
			::= { hwPriorityTableEntry 15 }
		
--  1.3.6.1.4.1.2011.5.2.4.1.16
		-- 1.3.6.1.4.1.2011.5.2.4.1.16
		hwPriorityRuntime OBJECT-TYPE
			SYNTAX TruthValue
			MAX-ACCESS read-only
			STATUS current
			DESCRIPTION
				""
			::= { hwPriorityTableEntry 16 }
		
--  1.3.6.1.4.1.2011.5.2.4.1.17
		-- 1.3.6.1.4.1.2011.5.2.4.1.17
		hwPriorityRowStatus OBJECT-TYPE
			SYNTAX RowStatus
			MAX-ACCESS read-create
			STATUS current
			DESCRIPTION
				""
			::= { hwPriorityTableEntry 17 }
		
--   TABLE: hwRedirectTable 
-- 1.3.6.1.4.1.2011.5.2.5
		-- 1.3.6.1.4.1.2011.5.2.5
		hwRedirectTable OBJECT-TYPE
			SYNTAX SEQUENCE OF HwRedirectTableEntry
			MAX-ACCESS not-accessible
			STATUS current
			DESCRIPTION
				""
			::= { hwLswQosAclMib 5 }
		
--  1.3.6.1.4.1.2011.5.2.5.1
		-- 1.3.6.1.4.1.2011.5.2.5.1
		hwRedirectTableEntry OBJECT-TYPE
			SYNTAX HwRedirectTableEntry
			MAX-ACCESS not-accessible
			STATUS current
			DESCRIPTION
				" "
			INDEX { hwRedirectAclIndex, hwRedirectIfIndex, hwRedirectDirection }
			::= { hwRedirectTable 1 }
		
		HwRedirectTableEntry ::=
			SEQUENCE { 
				hwRedirectAclIndex
					INTEGER,
				hwRedirectIfIndex
					INTEGER,
				hwRedirectDirection
					INTEGER,
				hwRedirectUserAclNum
					INTEGER,
				hwRedirectUserAclSubitem
					INTEGER,
				hwRedirectIpAclNum
					INTEGER,
				hwRedirectIpAclSubitem
					INTEGER,
				hwRedirectLinkAclNum
					INTEGER,
				hwRedirectLinkAclSubitem
					INTEGER,
				hwRedirectToCpu
					TruthValue,
				hwRedirectToIfIndex
					INTEGER,
				hwRedirectRuntime
					TruthValue,
				hwRedirectRowStatus
					RowStatus
			 }

--  1.3.6.1.4.1.2011.5.2.5.1.1
		-- 1.3.6.1.4.1.2011.5.2.5.1.1
		hwRedirectAclIndex OBJECT-TYPE
			SYNTAX INTEGER (0..2999)
			MAX-ACCESS read-only
			STATUS current
			DESCRIPTION
				""
			::= { hwRedirectTableEntry 1 }
		
--  1.3.6.1.4.1.2011.5.2.5.1.2
		-- 1.3.6.1.4.1.2011.5.2.5.1.2
		hwRedirectIfIndex OBJECT-TYPE
			SYNTAX INTEGER (0..4294967295)
			MAX-ACCESS read-only
			STATUS current
			DESCRIPTION
				""
			::= { hwRedirectTableEntry 2 }
		
--  1.3.6.1.4.1.2011.5.2.5.1.3
		-- 1.3.6.1.4.1.2011.5.2.5.1.3
		hwRedirectDirection OBJECT-TYPE
			SYNTAX INTEGER
				{
				input(1),
				output(2),
				invalid(0)
				}
			MAX-ACCESS read-only
			STATUS current
			DESCRIPTION
				""
			::= { hwRedirectTableEntry 3 }
		
--  1.3.6.1.4.1.2011.5.2.5.1.4
		-- 1.3.6.1.4.1.2011.5.2.5.1.4
		hwRedirectUserAclNum OBJECT-TYPE
			SYNTAX INTEGER (0 | 5000..5999)
			MAX-ACCESS read-create
			STATUS current
			DESCRIPTION
				""
			::= { hwRedirectTableEntry 4 }
		
--  1.3.6.1.4.1.2011.5.2.5.1.5
		-- 1.3.6.1.4.1.2011.5.2.5.1.5
		hwRedirectUserAclSubitem OBJECT-TYPE
			SYNTAX INTEGER (0..4294967295)
			MAX-ACCESS read-create
			STATUS current
			DESCRIPTION
				""
			::= { hwRedirectTableEntry 5 }
		
--  1.3.6.1.4.1.2011.5.2.5.1.6
		-- 1.3.6.1.4.1.2011.5.2.5.1.6
		hwRedirectIpAclNum OBJECT-TYPE
			SYNTAX INTEGER (0 | 2000..3999)
			MAX-ACCESS read-create
			STATUS current
			DESCRIPTION
				""
			::= { hwRedirectTableEntry 6 }
		
--  1.3.6.1.4.1.2011.5.2.5.1.7
		-- 1.3.6.1.4.1.2011.5.2.5.1.7
		hwRedirectIpAclSubitem OBJECT-TYPE
			SYNTAX INTEGER (0..4294967295)
			MAX-ACCESS read-create
			STATUS current
			DESCRIPTION
				""
			::= { hwRedirectTableEntry 7 }
		
--  1.3.6.1.4.1.2011.5.2.5.1.8
		-- 1.3.6.1.4.1.2011.5.2.5.1.8
		hwRedirectLinkAclNum OBJECT-TYPE
			SYNTAX INTEGER (0 | 4000..4999)
			MAX-ACCESS read-create
			STATUS current
			DESCRIPTION
				""
			::= { hwRedirectTableEntry 8 }
		
--  1.3.6.1.4.1.2011.5.2.5.1.9
		-- 1.3.6.1.4.1.2011.5.2.5.1.9
		hwRedirectLinkAclSubitem OBJECT-TYPE
			SYNTAX INTEGER (0..4294967295)
			MAX-ACCESS read-create
			STATUS current
			DESCRIPTION
				""
			::= { hwRedirectTableEntry 9 }
		
--  1.3.6.1.4.1.2011.5.2.5.1.10
		-- 1.3.6.1.4.1.2011.5.2.5.1.10
		hwRedirectToCpu OBJECT-TYPE
			SYNTAX TruthValue
			MAX-ACCESS read-create
			STATUS current
			DESCRIPTION
				""
			DEFVAL { 2 }
			::= { hwRedirectTableEntry 10 }
		
--  1.3.6.1.4.1.2011.5.2.5.1.11
		-- 1.3.6.1.4.1.2011.5.2.5.1.11
		hwRedirectToIfIndex OBJECT-TYPE
			SYNTAX INTEGER (0..4294967295)
			MAX-ACCESS read-create
			STATUS current
			DESCRIPTION
				""
			::= { hwRedirectTableEntry 11 }
		
--  1.3.6.1.4.1.2011.5.2.5.1.12
		-- 1.3.6.1.4.1.2011.5.2.5.1.12
		hwRedirectRuntime OBJECT-TYPE
			SYNTAX TruthValue
			MAX-ACCESS read-only
			STATUS current
			DESCRIPTION
				""
			::= { hwRedirectTableEntry 12 }
		
--  1.3.6.1.4.1.2011.5.2.5.1.13
		-- 1.3.6.1.4.1.2011.5.2.5.1.13
		hwRedirectRowStatus OBJECT-TYPE
			SYNTAX RowStatus
			MAX-ACCESS read-create
			STATUS current
			DESCRIPTION
				""
			::= { hwRedirectTableEntry 13 }
		
--   TABLE: hwStatisticTable 
-- 1.3.6.1.4.1.2011.5.2.6
		-- 1.3.6.1.4.1.2011.5.2.6
		hwStatisticTable OBJECT-TYPE
			SYNTAX SEQUENCE OF HwStatisticTableEntry
			MAX-ACCESS not-accessible
			STATUS current
			DESCRIPTION
				""
			::= { hwLswQosAclMib 6 }
		
--  1.3.6.1.4.1.2011.5.2.6.1
		-- 1.3.6.1.4.1.2011.5.2.6.1
		hwStatisticTableEntry OBJECT-TYPE
			SYNTAX HwStatisticTableEntry
			MAX-ACCESS not-accessible
			STATUS current
			DESCRIPTION
				" "
			INDEX { hwStatisticAclIndex, hwStatisticIfIndex, hwStatisticDirection }
			::= { hwStatisticTable 1 }
		
		HwStatisticTableEntry ::=
			SEQUENCE { 
				hwStatisticAclIndex
					INTEGER,
				hwStatisticIfIndex
					INTEGER,
				hwStatisticDirection
					INTEGER,
				hwStatisticUserAclNum
					INTEGER,
				hwStatisticUserAclSubitem
					INTEGER,
				hwStatisticIpAclNum
					INTEGER,
				hwStatisticIpAclSubitem
					INTEGER,
				hwStatisticLinkAclNum
					INTEGER,
				hwStatisticLinkAclSubitem
					INTEGER,
				hwStatisticRuntime
					TruthValue,
				hwStatisticPacketCount
					Counter64,
				hwStatisticCountClear
					INTEGER,
				hwStatisticRowStatus
					RowStatus
			 }

--  1.3.6.1.4.1.2011.5.2.6.1.1
		-- 1.3.6.1.4.1.2011.5.2.6.1.1
		hwStatisticAclIndex OBJECT-TYPE
			SYNTAX INTEGER (0..2999)
			MAX-ACCESS read-only
			STATUS current
			DESCRIPTION
				""
			::= { hwStatisticTableEntry 1 }
		
--  1.3.6.1.4.1.2011.5.2.6.1.2
		-- 1.3.6.1.4.1.2011.5.2.6.1.2
		hwStatisticIfIndex OBJECT-TYPE
			SYNTAX INTEGER (0..4294967295)
			MAX-ACCESS read-only
			STATUS current
			DESCRIPTION
				""
			::= { hwStatisticTableEntry 2 }
		
--  1.3.6.1.4.1.2011.5.2.6.1.3
		-- 1.3.6.1.4.1.2011.5.2.6.1.3
		hwStatisticDirection OBJECT-TYPE
			SYNTAX INTEGER
				{
				input(1),
				output(2),
				invalid(0)
				}
			MAX-ACCESS read-only
			STATUS current
			DESCRIPTION
				""
			::= { hwStatisticTableEntry 3 }
		
--  1.3.6.1.4.1.2011.5.2.6.1.4
		-- 1.3.6.1.4.1.2011.5.2.6.1.4
		hwStatisticUserAclNum OBJECT-TYPE
			SYNTAX INTEGER (0 | 5000..5999)
			MAX-ACCESS read-create
			STATUS current
			DESCRIPTION
				""
			::= { hwStatisticTableEntry 4 }
		
--  1.3.6.1.4.1.2011.5.2.6.1.5
		-- 1.3.6.1.4.1.2011.5.2.6.1.5
		hwStatisticUserAclSubitem OBJECT-TYPE
			SYNTAX INTEGER (0..4294967295)
			MAX-ACCESS read-create
			STATUS current
			DESCRIPTION
				""
			::= { hwStatisticTableEntry 5 }
		
--  1.3.6.1.4.1.2011.5.2.6.1.6
		-- 1.3.6.1.4.1.2011.5.2.6.1.6
		hwStatisticIpAclNum OBJECT-TYPE
			SYNTAX INTEGER (0 | 2000..3999)
			MAX-ACCESS read-create
			STATUS current
			DESCRIPTION
				""
			::= { hwStatisticTableEntry 6 }
		
--  1.3.6.1.4.1.2011.5.2.6.1.7
		-- 1.3.6.1.4.1.2011.5.2.6.1.7
		hwStatisticIpAclSubitem OBJECT-TYPE
			SYNTAX INTEGER (0..4294967295)
			MAX-ACCESS read-create
			STATUS current
			DESCRIPTION
				""
			::= { hwStatisticTableEntry 7 }
		
--  1.3.6.1.4.1.2011.5.2.6.1.8
		-- 1.3.6.1.4.1.2011.5.2.6.1.8
		hwStatisticLinkAclNum OBJECT-TYPE
			SYNTAX INTEGER (0 | 4000..4999)
			MAX-ACCESS read-create
			STATUS current
			DESCRIPTION
				""
			::= { hwStatisticTableEntry 8 }
		
--  1.3.6.1.4.1.2011.5.2.6.1.9
		-- 1.3.6.1.4.1.2011.5.2.6.1.9
		hwStatisticLinkAclSubitem OBJECT-TYPE
			SYNTAX INTEGER (0..4294967295)
			MAX-ACCESS read-create
			STATUS current
			DESCRIPTION
				""
			::= { hwStatisticTableEntry 9 }
		
--  1.3.6.1.4.1.2011.5.2.6.1.10
		-- 1.3.6.1.4.1.2011.5.2.6.1.10
		hwStatisticRuntime OBJECT-TYPE
			SYNTAX TruthValue
			MAX-ACCESS read-only
			STATUS current
			DESCRIPTION
				""
			::= { hwStatisticTableEntry 10 }
		
--  1.3.6.1.4.1.2011.5.2.6.1.11
		-- 1.3.6.1.4.1.2011.5.2.6.1.11
		hwStatisticPacketCount OBJECT-TYPE
			SYNTAX Counter64
			MAX-ACCESS read-only
			STATUS current
			DESCRIPTION
				""
			::= { hwStatisticTableEntry 11 }
		
--  1.3.6.1.4.1.2011.5.2.6.1.12
		-- 1.3.6.1.4.1.2011.5.2.6.1.12
		hwStatisticCountClear OBJECT-TYPE
			SYNTAX INTEGER
				{
				cleared(1),
				nouse(2)
				}
			MAX-ACCESS read-write
			STATUS current
			DESCRIPTION
				""
			::= { hwStatisticTableEntry 12 }
		
--  1.3.6.1.4.1.2011.5.2.6.1.13
		-- 1.3.6.1.4.1.2011.5.2.6.1.13
		hwStatisticRowStatus OBJECT-TYPE
			SYNTAX RowStatus
			MAX-ACCESS read-create
			STATUS current
			DESCRIPTION
				""
			::= { hwStatisticTableEntry 13 }
		
--   TABLE: hwMirrorTable 
-- 1.3.6.1.4.1.2011.5.2.7
		-- 1.3.6.1.4.1.2011.5.2.7
		hwMirrorTable OBJECT-TYPE
			SYNTAX SEQUENCE OF HwMirrorTableEntry
			MAX-ACCESS not-accessible
			STATUS current
			DESCRIPTION
				""
			::= { hwLswQosAclMib 7 }
		
--  1.3.6.1.4.1.2011.5.2.7.1
		-- 1.3.6.1.4.1.2011.5.2.7.1
		hwMirrorTableEntry OBJECT-TYPE
			SYNTAX HwMirrorTableEntry
			MAX-ACCESS not-accessible
			STATUS current
			DESCRIPTION
				" "
			INDEX { hwMirrorAclIndex, hwMirrorIfIndex, hwMirrorDirection }
			::= { hwMirrorTable 1 }
		
		HwMirrorTableEntry ::=
			SEQUENCE { 
				hwMirrorAclIndex
					INTEGER,
				hwMirrorIfIndex
					INTEGER,
				hwMirrorDirection
					INTEGER,
				hwMirrorUserAclNum
					INTEGER,
				hwMirrorUserAclSubitem
					INTEGER,
				hwMirrorIpAclNum
					INTEGER,
				hwMirrorIpAclSubitem
					INTEGER,
				hwMirrorLinkAclNum
					INTEGER,
				hwMirrorLinkAclSubitem
					INTEGER,
				hwMirrorToIfIndex
					INTEGER,
				hwMirrorRuntime
					TruthValue,
				hwMirrorRowStatus
					RowStatus
			 }

--  1.3.6.1.4.1.2011.5.2.7.1.1
		-- 1.3.6.1.4.1.2011.5.2.7.1.1
		hwMirrorAclIndex OBJECT-TYPE
			SYNTAX INTEGER (0..2999)
			MAX-ACCESS read-only
			STATUS current
			DESCRIPTION
				""
			::= { hwMirrorTableEntry 1 }
		
--  1.3.6.1.4.1.2011.5.2.7.1.2
		-- 1.3.6.1.4.1.2011.5.2.7.1.2
		hwMirrorIfIndex OBJECT-TYPE
			SYNTAX INTEGER (0..4294967295)
			MAX-ACCESS read-only
			STATUS current
			DESCRIPTION
				""
			::= { hwMirrorTableEntry 2 }
		
--  1.3.6.1.4.1.2011.5.2.7.1.3
		-- 1.3.6.1.4.1.2011.5.2.7.1.3
		hwMirrorDirection OBJECT-TYPE
			SYNTAX INTEGER
				{
				input(1),
				output(2),
				invalid(0)
				}
			MAX-ACCESS read-only
			STATUS current
			DESCRIPTION
				""
			::= { hwMirrorTableEntry 3 }
		
--  1.3.6.1.4.1.2011.5.2.7.1.4
		-- 1.3.6.1.4.1.2011.5.2.7.1.4
		hwMirrorUserAclNum OBJECT-TYPE
			SYNTAX INTEGER (0 | 5000..5999)
			MAX-ACCESS read-create
			STATUS current
			DESCRIPTION
				""
			::= { hwMirrorTableEntry 4 }
		
--  1.3.6.1.4.1.2011.5.2.7.1.5
		-- 1.3.6.1.4.1.2011.5.2.7.1.5
		hwMirrorUserAclSubitem OBJECT-TYPE
			SYNTAX INTEGER (0..4294967295)
			MAX-ACCESS read-create
			STATUS current
			DESCRIPTION
				""
			::= { hwMirrorTableEntry 5 }
		
--  1.3.6.1.4.1.2011.5.2.7.1.6
		-- 1.3.6.1.4.1.2011.5.2.7.1.6
		hwMirrorIpAclNum OBJECT-TYPE
			SYNTAX INTEGER (0 | 2000..3999)
			MAX-ACCESS read-create
			STATUS current
			DESCRIPTION
				""
			::= { hwMirrorTableEntry 6 }
		
--  1.3.6.1.4.1.2011.5.2.7.1.7
		-- 1.3.6.1.4.1.2011.5.2.7.1.7
		hwMirrorIpAclSubitem OBJECT-TYPE
			SYNTAX INTEGER (0..4294967295)
			MAX-ACCESS read-create
			STATUS current
			DESCRIPTION
				""
			::= { hwMirrorTableEntry 7 }
		
--  1.3.6.1.4.1.2011.5.2.7.1.8
		-- 1.3.6.1.4.1.2011.5.2.7.1.8
		hwMirrorLinkAclNum OBJECT-TYPE
			SYNTAX INTEGER (0 | 4000..4999)
			MAX-ACCESS read-create
			STATUS current
			DESCRIPTION
				""
			::= { hwMirrorTableEntry 8 }
		
--  1.3.6.1.4.1.2011.5.2.7.1.9
		-- 1.3.6.1.4.1.2011.5.2.7.1.9
		hwMirrorLinkAclSubitem OBJECT-TYPE
			SYNTAX INTEGER (0..4294967295)
			MAX-ACCESS read-create
			STATUS current
			DESCRIPTION
				""
			::= { hwMirrorTableEntry 9 }
		
--  1.3.6.1.4.1.2011.5.2.7.1.10
		-- 1.3.6.1.4.1.2011.5.2.7.1.10
		hwMirrorToIfIndex OBJECT-TYPE
			SYNTAX INTEGER (0..4294967295)
			MAX-ACCESS read-create
			STATUS current
			DESCRIPTION
				""
			::= { hwMirrorTableEntry 10 }
		
--  1.3.6.1.4.1.2011.5.2.7.1.11
		-- 1.3.6.1.4.1.2011.5.2.7.1.11
		hwMirrorRuntime OBJECT-TYPE
			SYNTAX TruthValue
			MAX-ACCESS read-only
			STATUS current
			DESCRIPTION
				""
			::= { hwMirrorTableEntry 11 }
		
--  1.3.6.1.4.1.2011.5.2.7.1.12
		-- 1.3.6.1.4.1.2011.5.2.7.1.12
		hwMirrorRowStatus OBJECT-TYPE
			SYNTAX RowStatus
			MAX-ACCESS read-create
			STATUS current
			DESCRIPTION
				""
			::= { hwMirrorTableEntry 12 }
		
--   TABLE: hwLineRateTable 
-- 1.3.6.1.4.1.2011.5.2.9
		-- 1.3.6.1.4.1.2011.5.2.9
		hwLineRateTable OBJECT-TYPE
			SYNTAX SEQUENCE OF HwLineRateTableEntry
			MAX-ACCESS not-accessible
			STATUS current
			DESCRIPTION
				" "
			::= { hwLswQosAclMib 9 }
		
--  1.3.6.1.4.1.2011.5.2.9.1
		-- 1.3.6.1.4.1.2011.5.2.9.1
		hwLineRateTableEntry OBJECT-TYPE
			SYNTAX HwLineRateTableEntry
			MAX-ACCESS not-accessible
			STATUS current
			DESCRIPTION
				" "
			INDEX { hwLineRateIfIndex }
			::= { hwLineRateTable 1 }
		
		HwLineRateTableEntry ::=
			SEQUENCE { 
				hwLineRateIfIndex
					INTEGER,
				hwLineRateValue
					INTEGER,
				hwLineRateRowStatus
					RowStatus
			 }

--  1.3.6.1.4.1.2011.5.2.9.1.1
		-- 1.3.6.1.4.1.2011.5.2.9.1.1
		hwLineRateIfIndex OBJECT-TYPE
			SYNTAX INTEGER (0..4294967295)
			MAX-ACCESS read-only
			STATUS current
			DESCRIPTION
				""
			::= { hwLineRateTableEntry 1 }
		
--  1.3.6.1.4.1.2011.5.2.9.1.2
		-- 1.3.6.1.4.1.2011.5.2.9.1.2
		hwLineRateValue OBJECT-TYPE
			SYNTAX INTEGER (64..1000000)
			MAX-ACCESS read-create
			STATUS current
			DESCRIPTION
				""
			::= { hwLineRateTableEntry 2 }
		
--  1.3.6.1.4.1.2011.5.2.9.1.3
		-- 1.3.6.1.4.1.2011.5.2.9.1.3
		hwLineRateRowStatus OBJECT-TYPE
			SYNTAX RowStatus
			MAX-ACCESS read-create
			STATUS current
			DESCRIPTION
				""
			::= { hwLineRateTableEntry 3 }
		
	
	END

--
-- HUAWEI-LQOS-MIB.my
--
