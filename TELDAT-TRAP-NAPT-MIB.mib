-- file automatically created


TELDAT-TRAP-NAPT-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


naptTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the NAPT event subsystem."
    REVISION "201401200930Z"
    DESCRIPTION "Initial implementation"
        ::= { telEventTraps 154 }


naptEventsGroup	OBJECT IDENTIFIER	::= { naptTrapsMIB 1 }

naptNotifications	OBJECT IDENTIFIER	::= { naptTrapsMIB 2 }
naptNotificationsPrefix	OBJECT IDENTIFIER	::= { naptNotifications 0 }

naptEventObjects1 OBJECT-IDENTITY
    STATUS current
    DESCRIPTION
        "Event NAPT.1
        NAPT for outgoing IP packet."
    ::= { naptEventsGroup 1 }

napt1-internal-ip OBJECT-TYPE
    SYNTAX IpAddress
    MAX-ACCESS accessible-for-notify
    STATUS current
    DESCRIPTION
        "Parameter 'internal-ip' in event NAPT.1"
    ::= { naptEventObjects1 1 }

napt1-internal-port OBJECT-TYPE
    SYNTAX Integer32
    MAX-ACCESS accessible-for-notify
    STATUS current
    DESCRIPTION
        "Parameter 'internal-port' in event NAPT.1"
    ::= { naptEventObjects1 2 }

napt1-external-ip OBJECT-TYPE
    SYNTAX IpAddress
    MAX-ACCESS accessible-for-notify
    STATUS current
    DESCRIPTION
        "Parameter 'external-ip' in event NAPT.1"
    ::= { naptEventObjects1 3 }

napt1-external-port OBJECT-TYPE
    SYNTAX Integer32
    MAX-ACCESS accessible-for-notify
    STATUS current
    DESCRIPTION
        "Parameter 'external-port' in event NAPT.1"
    ::= { naptEventObjects1 4 }

naptEventObjects2 OBJECT-IDENTITY
    STATUS current
    DESCRIPTION
        "Event NAPT.2
        NAPT for incoming IP packet."
    ::= { naptEventsGroup 2 }

napt2-external-ip OBJECT-TYPE
    SYNTAX IpAddress
    MAX-ACCESS accessible-for-notify
    STATUS current
    DESCRIPTION
        "Parameter 'external-ip' in event NAPT.2"
    ::= { naptEventObjects2 1 }

napt2-external-port OBJECT-TYPE
    SYNTAX Integer32
    MAX-ACCESS accessible-for-notify
    STATUS current
    DESCRIPTION
        "Parameter 'external-port' in event NAPT.2"
    ::= { naptEventObjects2 2 }

napt2-internal-ip OBJECT-TYPE
    SYNTAX IpAddress
    MAX-ACCESS accessible-for-notify
    STATUS current
    DESCRIPTION
        "Parameter 'internal-ip' in event NAPT.2"
    ::= { naptEventObjects2 3 }

napt2-internal-port OBJECT-TYPE
    SYNTAX Integer32
    MAX-ACCESS accessible-for-notify
    STATUS current
    DESCRIPTION
        "Parameter 'internal-port' in event NAPT.2"
    ::= { naptEventObjects2 4 }

naptEventObjects3 OBJECT-IDENTITY
    STATUS current
    DESCRIPTION
        "Event NAPT.3
        Translation for outgoing ICMP packet."
    ::= { naptEventsGroup 3 }

napt3-internal-ip OBJECT-TYPE
    SYNTAX IpAddress
    MAX-ACCESS accessible-for-notify
    STATUS current
    DESCRIPTION
        "Parameter 'internal-ip' in event NAPT.3"
    ::= { naptEventObjects3 1 }

napt3-internal-ident OBJECT-TYPE
    SYNTAX Integer32
    MAX-ACCESS accessible-for-notify
    STATUS current
    DESCRIPTION
        "Parameter 'internal-ident' in event NAPT.3"
    ::= { naptEventObjects3 2 }

napt3-external-ip OBJECT-TYPE
    SYNTAX IpAddress
    MAX-ACCESS accessible-for-notify
    STATUS current
    DESCRIPTION
        "Parameter 'external-ip' in event NAPT.3"
    ::= { naptEventObjects3 3 }

napt3-external-ident OBJECT-TYPE
    SYNTAX Integer32
    MAX-ACCESS accessible-for-notify
    STATUS current
    DESCRIPTION
        "Parameter 'external-ident' in event NAPT.3"
    ::= { naptEventObjects3 4 }

naptEventObjects4 OBJECT-IDENTITY
    STATUS current
    DESCRIPTION
        "Event NAPT.4
        Translation for incoming ICMP packet."
    ::= { naptEventsGroup 4 }

napt4-external-ip OBJECT-TYPE
    SYNTAX IpAddress
    MAX-ACCESS accessible-for-notify
    STATUS current
    DESCRIPTION
        "Parameter 'external-ip' in event NAPT.4"
    ::= { naptEventObjects4 1 }

napt4-external-ident OBJECT-TYPE
    SYNTAX Integer32
    MAX-ACCESS accessible-for-notify
    STATUS current
    DESCRIPTION
        "Parameter 'external-ident' in event NAPT.4"
    ::= { naptEventObjects4 2 }

napt4-internal-ip OBJECT-TYPE
    SYNTAX IpAddress
    MAX-ACCESS accessible-for-notify
    STATUS current
    DESCRIPTION
        "Parameter 'internal-ip' in event NAPT.4"
    ::= { naptEventObjects4 3 }

napt4-internal-ident OBJECT-TYPE
    SYNTAX Integer32
    MAX-ACCESS accessible-for-notify
    STATUS current
    DESCRIPTION
        "Parameter 'internal-ident' in event NAPT.4"
    ::= { naptEventObjects4 4 }

naptEventObjects7 OBJECT-IDENTITY
    STATUS current
    DESCRIPTION
        "Event NAPT.7
        Received TCP packet with bad TCP checksum."
    ::= { naptEventsGroup 7 }

napt7-internal-ip OBJECT-TYPE
    SYNTAX IpAddress
    MAX-ACCESS accessible-for-notify
    STATUS current
    DESCRIPTION
        "Parameter 'internal-ip' in event NAPT.7"
    ::= { naptEventObjects7 1 }

napt7-internal-port OBJECT-TYPE
    SYNTAX Integer32
    MAX-ACCESS accessible-for-notify
    STATUS current
    DESCRIPTION
        "Parameter 'internal-port' in event NAPT.7"
    ::= { naptEventObjects7 2 }

napt7-external-ip OBJECT-TYPE
    SYNTAX IpAddress
    MAX-ACCESS accessible-for-notify
    STATUS current
    DESCRIPTION
        "Parameter 'external-ip' in event NAPT.7"
    ::= { naptEventObjects7 3 }

napt7-external-port OBJECT-TYPE
    SYNTAX Integer32
    MAX-ACCESS accessible-for-notify
    STATUS current
    DESCRIPTION
        "Parameter 'external-port' in event NAPT.7"
    ::= { naptEventObjects7 4 }

napt7-sequence OBJECT-TYPE
    SYNTAX Integer32
    MAX-ACCESS accessible-for-notify
    STATUS current
    DESCRIPTION
        "Parameter 'sequence' in event NAPT.7"
    ::= { naptEventObjects7 5 }

napt7-ack-sequence OBJECT-TYPE
    SYNTAX Integer32
    MAX-ACCESS accessible-for-notify
    STATUS current
    DESCRIPTION
        "Parameter 'ack-sequence' in event NAPT.7"
    ::= { naptEventObjects7 6 }

naptEventObjects8 OBJECT-IDENTITY
    STATUS current
    DESCRIPTION
        "Event NAPT.8
        It is not allowed to do NAPT in some firewalling cases: RIP, OSPF..."
    ::= { naptEventsGroup 8 }

napt8-Drop-noNaptto OBJECT-TYPE
    SYNTAX DisplayString
    MAX-ACCESS accessible-for-notify
    STATUS current
    DESCRIPTION
        "Parameter 'Drop-noNaptto' in event NAPT.8"
    ::= { naptEventObjects8 1 }

napt8-packet-type OBJECT-TYPE
    SYNTAX DisplayString
    MAX-ACCESS accessible-for-notify
    STATUS current
    DESCRIPTION
        "Parameter 'packet-type' in event NAPT.8"
    ::= { naptEventObjects8 2 }

naptEventObjects9 OBJECT-IDENTITY
    STATUS current
    DESCRIPTION
        "Event NAPT.9
        Sent TCP SYNC."
    ::= { naptEventsGroup 9 }

napt9-application OBJECT-TYPE
    SYNTAX DisplayString
    MAX-ACCESS accessible-for-notify
    STATUS current
    DESCRIPTION
        "Parameter 'application' in event NAPT.9"
    ::= { naptEventObjects9 1 }

napt9-source-ip OBJECT-TYPE
    SYNTAX IpAddress
    MAX-ACCESS accessible-for-notify
    STATUS current
    DESCRIPTION
        "Parameter 'source-ip' in event NAPT.9"
    ::= { naptEventObjects9 2 }

napt9-source-port OBJECT-TYPE
    SYNTAX Integer32
    MAX-ACCESS accessible-for-notify
    STATUS current
    DESCRIPTION
        "Parameter 'source-port' in event NAPT.9"
    ::= { naptEventObjects9 3 }

napt9-target-ip OBJECT-TYPE
    SYNTAX IpAddress
    MAX-ACCESS accessible-for-notify
    STATUS current
    DESCRIPTION
        "Parameter 'target-ip' in event NAPT.9"
    ::= { naptEventObjects9 4 }

napt9-target-port OBJECT-TYPE
    SYNTAX Integer32
    MAX-ACCESS accessible-for-notify
    STATUS current
    DESCRIPTION
        "Parameter 'target-port' in event NAPT.9"
    ::= { naptEventObjects9 5 }

napt9-sequence OBJECT-TYPE
    SYNTAX Integer32
    MAX-ACCESS accessible-for-notify
    STATUS current
    DESCRIPTION
        "Parameter 'sequence' in event NAPT.9"
    ::= { naptEventObjects9 6 }

napt9-ack-sequence OBJECT-TYPE
    SYNTAX Integer32
    MAX-ACCESS accessible-for-notify
    STATUS current
    DESCRIPTION
        "Parameter 'ack-sequence' in event NAPT.9"
    ::= { naptEventObjects9 7 }

naptEventObjects10 OBJECT-IDENTITY
    STATUS current
    DESCRIPTION
        "Event NAPT.10
        Received or sent TCP FIN/RST."
    ::= { naptEventsGroup 10 }

napt10-application OBJECT-TYPE
    SYNTAX DisplayString
    MAX-ACCESS accessible-for-notify
    STATUS current
    DESCRIPTION
        "Parameter 'application' in event NAPT.10"
    ::= { naptEventObjects10 1 }

napt10-source-ip OBJECT-TYPE
    SYNTAX IpAddress
    MAX-ACCESS accessible-for-notify
    STATUS current
    DESCRIPTION
        "Parameter 'source-ip' in event NAPT.10"
    ::= { naptEventObjects10 2 }

napt10-source-port OBJECT-TYPE
    SYNTAX Integer32
    MAX-ACCESS accessible-for-notify
    STATUS current
    DESCRIPTION
        "Parameter 'source-port' in event NAPT.10"
    ::= { naptEventObjects10 3 }

napt10-target-ip OBJECT-TYPE
    SYNTAX IpAddress
    MAX-ACCESS accessible-for-notify
    STATUS current
    DESCRIPTION
        "Parameter 'target-ip' in event NAPT.10"
    ::= { naptEventObjects10 4 }

napt10-target-port OBJECT-TYPE
    SYNTAX Integer32
    MAX-ACCESS accessible-for-notify
    STATUS current
    DESCRIPTION
        "Parameter 'target-port' in event NAPT.10"
    ::= { naptEventObjects10 5 }

naptEventObjects11 OBJECT-IDENTITY
    STATUS current
    DESCRIPTION
        "Event NAPT.11
        Received bad IP header field."
    ::= { naptEventsGroup 11 }

napt11-IP-field OBJECT-TYPE
    SYNTAX DisplayString
    MAX-ACCESS accessible-for-notify
    STATUS current
    DESCRIPTION
        "Parameter 'IP-field' in event NAPT.11"
    ::= { naptEventObjects11 1 }

napt11-field-value OBJECT-TYPE
    SYNTAX Integer32
    MAX-ACCESS accessible-for-notify
    STATUS current
    DESCRIPTION
        "Parameter 'field-value' in event NAPT.11"
    ::= { naptEventObjects11 2 }

naptEventObjects12 OBJECT-IDENTITY
    STATUS current
    DESCRIPTION
        "Event NAPT.12
        Received a packet that does not match any IP connection."
    ::= { naptEventsGroup 12 }

napt12-target-address OBJECT-TYPE
    SYNTAX IpAddress
    MAX-ACCESS accessible-for-notify
    STATUS current
    DESCRIPTION
        "Parameter 'target-address' in event NAPT.12"
    ::= { naptEventObjects12 1 }

naptEventObjects13 OBJECT-IDENTITY
    STATUS current
    DESCRIPTION
        "Event NAPT.13
        NAPT entry or ICMP identifier timeout."
    ::= { naptEventsGroup 13 }

napt13-type OBJECT-TYPE
    SYNTAX DisplayString
    MAX-ACCESS accessible-for-notify
    STATUS current
    DESCRIPTION
        "Parameter 'type' in event NAPT.13"
    ::= { naptEventObjects13 1 }

napt13-source-ip OBJECT-TYPE
    SYNTAX IpAddress
    MAX-ACCESS accessible-for-notify
    STATUS current
    DESCRIPTION
        "Parameter 'source-ip' in event NAPT.13"
    ::= { naptEventObjects13 2 }

napt13-source-port OBJECT-TYPE
    SYNTAX Integer32
    MAX-ACCESS accessible-for-notify
    STATUS current
    DESCRIPTION
        "Parameter 'source-port' in event NAPT.13"
    ::= { naptEventObjects13 3 }

napt13-source-napted-ip OBJECT-TYPE
    SYNTAX IpAddress
    MAX-ACCESS accessible-for-notify
    STATUS current
    DESCRIPTION
        "Parameter 'source-napted-ip' in event NAPT.13"
    ::= { naptEventObjects13 4 }

napt13-source-napted-port OBJECT-TYPE
    SYNTAX Integer32
    MAX-ACCESS accessible-for-notify
    STATUS current
    DESCRIPTION
        "Parameter 'source-napted-port' in event NAPT.13"
    ::= { naptEventObjects13 5 }

naptEventObjects14 OBJECT-IDENTITY
    STATUS current
    DESCRIPTION
        "Event NAPT.14
        Received IP packet for an unused external port."
    ::= { naptEventsGroup 14 }

napt14-target-port OBJECT-TYPE
    SYNTAX Integer32
    MAX-ACCESS accessible-for-notify
    STATUS current
    DESCRIPTION
        "Parameter 'target-port' in event NAPT.14"
    ::= { naptEventObjects14 1 }

naptEventObjects15 OBJECT-IDENTITY
    STATUS current
    DESCRIPTION
        "Event NAPT.15
        Received ICMP packet for an unused external identifier."
    ::= { naptEventsGroup 15 }

napt15-target-identifier OBJECT-TYPE
    SYNTAX Integer32
    MAX-ACCESS accessible-for-notify
    STATUS current
    DESCRIPTION
        "Parameter 'target-identifier' in event NAPT.15"
    ::= { naptEventObjects15 1 }

naptEventObjects16 OBJECT-IDENTITY
    STATUS current
    DESCRIPTION
        "Event NAPT.16
        Host exceeds max allowed NAPT entries."
    ::= { naptEventsGroup 16 }

napt16-ip-address OBJECT-TYPE
    SYNTAX IpAddress
    MAX-ACCESS accessible-for-notify
    STATUS current
    DESCRIPTION
        "Parameter 'ip-address' in event NAPT.16"
    ::= { naptEventObjects16 1 }

naptEventObjects17 OBJECT-IDENTITY
    STATUS current
    DESCRIPTION
        "Event NAPT.17
        NAPT for PPTP traces."
    ::= { naptEventsGroup 17 }

napt17-description OBJECT-TYPE
    SYNTAX DisplayString
    MAX-ACCESS accessible-for-notify
    STATUS current
    DESCRIPTION
        "Parameter 'description' in event NAPT.17"
    ::= { naptEventObjects17 1 }

naptEventObjects18 OBJECT-IDENTITY
    STATUS current
    DESCRIPTION
        "Event NAPT.18
        NAPT for an incoming fragment (without port translation)."
    ::= { naptEventsGroup 18 }

napt18-external-ip OBJECT-TYPE
    SYNTAX IpAddress
    MAX-ACCESS accessible-for-notify
    STATUS current
    DESCRIPTION
        "Parameter 'external-ip' in event NAPT.18"
    ::= { naptEventObjects18 1 }

napt18-internal-ip OBJECT-TYPE
    SYNTAX IpAddress
    MAX-ACCESS accessible-for-notify
    STATUS current
    DESCRIPTION
        "Parameter 'internal-ip' in event NAPT.18"
    ::= { naptEventObjects18 2 }

napt18-fragment-indication OBJECT-TYPE
    SYNTAX DisplayString
    MAX-ACCESS accessible-for-notify
    STATUS current
    DESCRIPTION
        "Parameter 'fragment-indication' in event NAPT.18"
    ::= { naptEventObjects18 3 }

naptEventObjects19 OBJECT-IDENTITY
    STATUS current
    DESCRIPTION
        "Event NAPT.19
        Dropping outgoing packet that does not match any IP connection."
    ::= { naptEventsGroup 19 }

napt19-source-ip OBJECT-TYPE
    SYNTAX IpAddress
    MAX-ACCESS accessible-for-notify
    STATUS current
    DESCRIPTION
        "Parameter 'source-ip' in event NAPT.19"
    ::= { naptEventObjects19 1 }

napt19-destination-ip OBJECT-TYPE
    SYNTAX IpAddress
    MAX-ACCESS accessible-for-notify
    STATUS current
    DESCRIPTION
        "Parameter 'destination-ip' in event NAPT.19"
    ::= { naptEventObjects19 2 }

naptEventObjects20 OBJECT-IDENTITY
    STATUS current
    DESCRIPTION
        "Event NAPT.20
        It is not allowed to do incoming/outgoing NAPT to locally originated
        packets. No translation is performed."
    ::= { naptEventsGroup 20 }

napt20-incoming-outcoming OBJECT-TYPE
    SYNTAX DisplayString
    MAX-ACCESS accessible-for-notify
    STATUS current
    DESCRIPTION
        "Parameter 'incoming-outcoming' in event NAPT.20"
    ::= { naptEventObjects20 1 }

napt20-source-ip OBJECT-TYPE
    SYNTAX IpAddress
    MAX-ACCESS accessible-for-notify
    STATUS current
    DESCRIPTION
        "Parameter 'source-ip' in event NAPT.20"
    ::= { naptEventObjects20 2 }

napt20-destination-ip OBJECT-TYPE
    SYNTAX IpAddress
    MAX-ACCESS accessible-for-notify
    STATUS current
    DESCRIPTION
        "Parameter 'destination-ip' in event NAPT.20"
    ::= { naptEventObjects20 3 }

naptEventObjects21 OBJECT-IDENTITY
    STATUS current
    DESCRIPTION
        "Event NAPT.21
        Assignated destination address is not accesible. Packets are dropped."
    ::= { naptEventsGroup 21 }

napt21-source-ip OBJECT-TYPE
    SYNTAX IpAddress
    MAX-ACCESS accessible-for-notify
    STATUS current
    DESCRIPTION
        "Parameter 'source-ip' in event NAPT.21"
    ::= { naptEventObjects21 1 }

napt21-destination-ip OBJECT-TYPE
    SYNTAX IpAddress
    MAX-ACCESS accessible-for-notify
    STATUS current
    DESCRIPTION
        "Parameter 'destination-ip' in event NAPT.21"
    ::= { naptEventObjects21 2 }

napt21-assignated-destination-ip OBJECT-TYPE
    SYNTAX IpAddress
    MAX-ACCESS accessible-for-notify
    STATUS current
    DESCRIPTION
        "Parameter 'assignated-destination-ip' in event NAPT.21"
    ::= { naptEventObjects21 3 }

naptEventObjects22 OBJECT-IDENTITY
    STATUS current
    DESCRIPTION
        "Event NAPT.22
        Virtual destination NAPT for outgoing IP packet."
    ::= { naptEventsGroup 22 }

napt22-virtual-dest-ip OBJECT-TYPE
    SYNTAX IpAddress
    MAX-ACCESS accessible-for-notify
    STATUS current
    DESCRIPTION
        "Parameter 'virtual-dest-ip' in event NAPT.22"
    ::= { naptEventObjects22 1 }

napt22-virtual-dest-port OBJECT-TYPE
    SYNTAX Integer32
    MAX-ACCESS accessible-for-notify
    STATUS current
    DESCRIPTION
        "Parameter 'virtual-dest-port' in event NAPT.22"
    ::= { naptEventObjects22 2 }

napt22-new-dest-ip OBJECT-TYPE
    SYNTAX IpAddress
    MAX-ACCESS accessible-for-notify
    STATUS current
    DESCRIPTION
        "Parameter 'new-dest-ip' in event NAPT.22"
    ::= { naptEventObjects22 3 }

napt22-new-dest-port OBJECT-TYPE
    SYNTAX Integer32
    MAX-ACCESS accessible-for-notify
    STATUS current
    DESCRIPTION
        "Parameter 'new-dest-port' in event NAPT.22"
    ::= { naptEventObjects22 4 }

naptEventObjects23 OBJECT-IDENTITY
    STATUS current
    DESCRIPTION
        "Event NAPT.23
        Virtual destination NAPT for incoming IP packet."
    ::= { naptEventsGroup 23 }

napt23-new-dest-ip OBJECT-TYPE
    SYNTAX IpAddress
    MAX-ACCESS accessible-for-notify
    STATUS current
    DESCRIPTION
        "Parameter 'new-dest-ip' in event NAPT.23"
    ::= { naptEventObjects23 1 }

napt23-new-dest-port OBJECT-TYPE
    SYNTAX Integer32
    MAX-ACCESS accessible-for-notify
    STATUS current
    DESCRIPTION
        "Parameter 'new-dest-port' in event NAPT.23"
    ::= { naptEventObjects23 2 }

napt23-virtual-dest-ip OBJECT-TYPE
    SYNTAX IpAddress
    MAX-ACCESS accessible-for-notify
    STATUS current
    DESCRIPTION
        "Parameter 'virtual-dest-ip' in event NAPT.23"
    ::= { naptEventObjects23 3 }

napt23-virtual-dest-port OBJECT-TYPE
    SYNTAX Integer32
    MAX-ACCESS accessible-for-notify
    STATUS current
    DESCRIPTION
        "Parameter 'virtual-dest-port' in event NAPT.23"
    ::= { naptEventObjects23 4 }

naptEventObjects24 OBJECT-IDENTITY
    STATUS current
    DESCRIPTION
        "Event NAPT.24
        Dropping or passing through without NAPT an incoming packet
        that does not match any IP connection."
    ::= { naptEventsGroup 24 }

napt24-Drop-noNAPTto OBJECT-TYPE
    SYNTAX DisplayString
    MAX-ACCESS accessible-for-notify
    STATUS current
    DESCRIPTION
        "Parameter 'Drop-noNAPTto' in event NAPT.24"
    ::= { naptEventObjects24 1 }

napt24-source-ip OBJECT-TYPE
    SYNTAX IpAddress
    MAX-ACCESS accessible-for-notify
    STATUS current
    DESCRIPTION
        "Parameter 'source-ip' in event NAPT.24"
    ::= { naptEventObjects24 2 }

napt24-destination-ip OBJECT-TYPE
    SYNTAX IpAddress
    MAX-ACCESS accessible-for-notify
    STATUS current
    DESCRIPTION
        "Parameter 'destination-ip' in event NAPT.24"
    ::= { naptEventObjects24 3 }

naptEventObjects25 OBJECT-IDENTITY
    STATUS current
    DESCRIPTION
        "Event NAPT.25
        Creating or deleting NAPT fragmentation entry."
    ::= { naptEventsGroup 25 }

napt25-action OBJECT-TYPE
    SYNTAX DisplayString
    MAX-ACCESS accessible-for-notify
    STATUS current
    DESCRIPTION
        "Parameter 'action' in event NAPT.25"
    ::= { naptEventObjects25 1 }

napt25-fragmentation-entry OBJECT-TYPE
    SYNTAX Integer32
    MAX-ACCESS accessible-for-notify
    STATUS current
    DESCRIPTION
        "Parameter 'fragmentation-entry' in event NAPT.25"
    ::= { naptEventObjects25 2 }

napt25-ip-id OBJECT-TYPE
    SYNTAX Integer32
    MAX-ACCESS accessible-for-notify
    STATUS current
    DESCRIPTION
        "Parameter 'ip-id' in event NAPT.25"
    ::= { naptEventObjects25 3 }

napt25-ip-address OBJECT-TYPE
    SYNTAX IpAddress
    MAX-ACCESS accessible-for-notify
    STATUS current
    DESCRIPTION
        "Parameter 'ip-address' in event NAPT.25"
    ::= { naptEventObjects25 4 }

naptEventObjects26 OBJECT-IDENTITY
    STATUS current
    DESCRIPTION
        "Event NAPT.26
        Action done to a packet by a fragmentation entry."
    ::= { naptEventsGroup 26 }

napt26-action OBJECT-TYPE
    SYNTAX DisplayString
    MAX-ACCESS accessible-for-notify
    STATUS current
    DESCRIPTION
        "Parameter 'action' in event NAPT.26"
    ::= { naptEventObjects26 1 }

napt26-fragmentation-entry OBJECT-TYPE
    SYNTAX Integer32
    MAX-ACCESS accessible-for-notify
    STATUS current
    DESCRIPTION
        "Parameter 'fragmentation-entry' in event NAPT.26"
    ::= { naptEventObjects26 2 }

napt26-ip-id OBJECT-TYPE
    SYNTAX Integer32
    MAX-ACCESS accessible-for-notify
    STATUS current
    DESCRIPTION
        "Parameter 'ip-id' in event NAPT.26"
    ::= { naptEventObjects26 3 }

napt26-ip-address OBJECT-TYPE
    SYNTAX IpAddress
    MAX-ACCESS accessible-for-notify
    STATUS current
    DESCRIPTION
        "Parameter 'ip-address' in event NAPT.26"
    ::= { naptEventObjects26 4 }

napt26-ip-offset OBJECT-TYPE
    SYNTAX Integer32
    MAX-ACCESS accessible-for-notify
    STATUS current
    DESCRIPTION
        "Parameter 'ip-offset' in event NAPT.26"
    ::= { naptEventObjects26 5 }

naptEventObjects27 OBJECT-IDENTITY
    STATUS current
    DESCRIPTION
        "Event NAPT.27
        An incoming packet matching a NAPT entry with virtual dest active
        has been droped because its source address was diferent from
        the assigned destination."
    ::= { naptEventsGroup 27 }

napt27-source-ip OBJECT-TYPE
    SYNTAX IpAddress
    MAX-ACCESS accessible-for-notify
    STATUS current
    DESCRIPTION
        "Parameter 'source-ip' in event NAPT.27"
    ::= { naptEventObjects27 1 }

napt27-destination-ip OBJECT-TYPE
    SYNTAX IpAddress
    MAX-ACCESS accessible-for-notify
    STATUS current
    DESCRIPTION
        "Parameter 'destination-ip' in event NAPT.27"
    ::= { naptEventObjects27 2 }

napt27-assignated-destination-ip OBJECT-TYPE
    SYNTAX IpAddress
    MAX-ACCESS accessible-for-notify
    STATUS current
    DESCRIPTION
        "Parameter 'assignated-destination-ip' in event NAPT.27"
    ::= { naptEventObjects27 3 }

napt27-src-address OBJECT-TYPE
    SYNTAX IpAddress
    MAX-ACCESS accessible-for-notify
    STATUS current
    DESCRIPTION
        "Parameter 'src-address' in event NAPT.27"
    ::= { naptEventObjects27 4 }

naptEventObjects28 OBJECT-IDENTITY
    STATUS current
    DESCRIPTION
        "Event NAPT.28
        An incoming packet has been drop or past through without NAPT because
        its destination port is out of the range of NAPT ports."
    ::= { naptEventsGroup 28 }

napt28-Drop-noNAPTto OBJECT-TYPE
    SYNTAX DisplayString
    MAX-ACCESS accessible-for-notify
    STATUS current
    DESCRIPTION
        "Parameter 'Drop-noNAPTto' in event NAPT.28"
    ::= { naptEventObjects28 1 }

napt28-source-ip OBJECT-TYPE
    SYNTAX IpAddress
    MAX-ACCESS accessible-for-notify
    STATUS current
    DESCRIPTION
        "Parameter 'source-ip' in event NAPT.28"
    ::= { naptEventObjects28 2 }

napt28-source-port OBJECT-TYPE
    SYNTAX Integer32
    MAX-ACCESS accessible-for-notify
    STATUS current
    DESCRIPTION
        "Parameter 'source-port' in event NAPT.28"
    ::= { naptEventObjects28 3 }

napt28-destination-ip OBJECT-TYPE
    SYNTAX IpAddress
    MAX-ACCESS accessible-for-notify
    STATUS current
    DESCRIPTION
        "Parameter 'destination-ip' in event NAPT.28"
    ::= { naptEventObjects28 4 }

napt28-destination-port OBJECT-TYPE
    SYNTAX Integer32
    MAX-ACCESS accessible-for-notify
    STATUS current
    DESCRIPTION
        "Parameter 'destination-port' in event NAPT.28"
    ::= { naptEventObjects28 5 }

naptEventObjects29 OBJECT-IDENTITY
    STATUS current
    DESCRIPTION
        "Event NAPT.29
        The MSS value of an outgoing TCP SYN packet has been adjusted."
    ::= { naptEventsGroup 29 }

napt29-source-ip OBJECT-TYPE
    SYNTAX IpAddress
    MAX-ACCESS accessible-for-notify
    STATUS current
    DESCRIPTION
        "Parameter 'source-ip' in event NAPT.29"
    ::= { naptEventObjects29 1 }

napt29-source-port OBJECT-TYPE
    SYNTAX Integer32
    MAX-ACCESS accessible-for-notify
    STATUS current
    DESCRIPTION
        "Parameter 'source-port' in event NAPT.29"
    ::= { naptEventObjects29 2 }

napt29-destination-ip OBJECT-TYPE
    SYNTAX IpAddress
    MAX-ACCESS accessible-for-notify
    STATUS current
    DESCRIPTION
        "Parameter 'destination-ip' in event NAPT.29"
    ::= { naptEventObjects29 3 }

napt29-destination-port OBJECT-TYPE
    SYNTAX Integer32
    MAX-ACCESS accessible-for-notify
    STATUS current
    DESCRIPTION
        "Parameter 'destination-port' in event NAPT.29"
    ::= { naptEventObjects29 4 }

napt29-old-mss OBJECT-TYPE
    SYNTAX Integer32
    MAX-ACCESS accessible-for-notify
    STATUS current
    DESCRIPTION
        "Parameter 'old-mss' in event NAPT.29"
    ::= { naptEventObjects29 5 }

napt29-new-mss OBJECT-TYPE
    SYNTAX Integer32
    MAX-ACCESS accessible-for-notify
    STATUS current
    DESCRIPTION
        "Parameter 'new-mss' in event NAPT.29"
    ::= { naptEventObjects29 6 }

naptEventObjects30 OBJECT-IDENTITY
    STATUS current
    DESCRIPTION
        "Event NAPT.30
        An incoming packet matching a NAPT entry with virtual destination active
        has been droped because its source port was diferent from the assigned
        destination port."
    ::= { naptEventsGroup 30 }

napt30-source-ip OBJECT-TYPE
    SYNTAX IpAddress
    MAX-ACCESS accessible-for-notify
    STATUS current
    DESCRIPTION
        "Parameter 'source-ip' in event NAPT.30"
    ::= { naptEventObjects30 1 }

napt30-source-port OBJECT-TYPE
    SYNTAX Integer32
    MAX-ACCESS accessible-for-notify
    STATUS current
    DESCRIPTION
        "Parameter 'source-port' in event NAPT.30"
    ::= { naptEventObjects30 2 }

napt30-destination-ip OBJECT-TYPE
    SYNTAX IpAddress
    MAX-ACCESS accessible-for-notify
    STATUS current
    DESCRIPTION
        "Parameter 'destination-ip' in event NAPT.30"
    ::= { naptEventObjects30 3 }

napt30-destination-port OBJECT-TYPE
    SYNTAX Integer32
    MAX-ACCESS accessible-for-notify
    STATUS current
    DESCRIPTION
        "Parameter 'destination-port' in event NAPT.30"
    ::= { naptEventObjects30 4 }

napt30-assignated-destination-port OBJECT-TYPE
    SYNTAX Integer32
    MAX-ACCESS accessible-for-notify
    STATUS current
    DESCRIPTION
        "Parameter 'assignated-destination-port' in event NAPT.30"
    ::= { naptEventObjects30 5 }

napt30-src-port OBJECT-TYPE
    SYNTAX Integer32
    MAX-ACCESS accessible-for-notify
    STATUS current
    DESCRIPTION
        "Parameter 'src-port' in event NAPT.30"
    ::= { naptEventObjects30 6 }


naptNotification1 NOTIFICATION-TYPE
    OBJECTS { 
              napt1-internal-ip, 
              napt1-internal-port,
              napt1-external-ip,
              napt1-external-port 
            }
    STATUS current
    DESCRIPTION
        "Notification of Event NAPT.1

        Message: 'Out ($1:$2 => $3:$4)'

        Parameters list:
              $1: napt1-internal-ip
              $2: napt1-internal-port
              $3: napt1-external-ip
              $4: napt1-external-port

        NAPT for outgoing IP packet."
    ::= { naptNotificationsPrefix 1 }

naptNotification2 NOTIFICATION-TYPE
    OBJECTS { 
              napt2-external-ip, 
              napt2-external-port,
              napt2-internal-ip,
              napt2-internal-port 
            }
    STATUS current
    DESCRIPTION
        "Notification of Event NAPT.2

        Message: 'In ($1:$2 => $3:$4)'

        Parameters list:
              $1: napt2-external-ip
              $2: napt2-external-port
              $3: napt2-internal-ip
              $4: napt2-internal-port

        NAPT for incoming IP packet."
    ::= { naptNotificationsPrefix 2 }

naptNotification3 NOTIFICATION-TYPE
    OBJECTS { 
              napt3-internal-ip, 
              napt3-internal-ident,
              napt3-external-ip,
              napt3-external-ident 
            }
    STATUS current
    DESCRIPTION
        "Notification of Event NAPT.3

        Message: 'Out ($1[$2] => $3[$4])'

        Parameters list:
              $1: napt3-internal-ip
              $2: napt3-internal-ident
              $3: napt3-external-ip
              $4: napt3-external-ident

        Translation for outgoing ICMP packet."
    ::= { naptNotificationsPrefix 3 }

naptNotification4 NOTIFICATION-TYPE
    OBJECTS { 
              napt4-external-ip, 
              napt4-external-ident,
              napt4-internal-ip,
              napt4-internal-ident 
            }
    STATUS current
    DESCRIPTION
        "Notification of Event NAPT.4

        Message: 'In ($1[$2] => $3[$4])'

        Parameters list:
              $1: napt4-external-ip
              $2: napt4-external-ident
              $3: napt4-internal-ip
              $4: napt4-internal-ident

        Translation for incoming ICMP packet."
    ::= { naptNotificationsPrefix 4 }

naptNotification5 NOTIFICATION-TYPE
    STATUS current
    DESCRIPTION
        "Notification of Event NAPT.5

        Message: 'No NAPT entries free'

        Unable to find NAPT entries free (all of them are used)."
    ::= { naptNotificationsPrefix 5 }

naptNotification6 NOTIFICATION-TYPE
    STATUS current
    DESCRIPTION
        "Notification of Event NAPT.6

        Message: 'No ICMP identifiers free'

        Unable to find ICMP identifiers free (all of them are used)."
    ::= { naptNotificationsPrefix 6 }

naptNotification7 NOTIFICATION-TYPE
    OBJECTS { 
              napt7-internal-ip, 
              napt7-internal-port,
              napt7-external-ip,
              napt7-external-port,
              napt7-sequence,
              napt7-ack-sequence 
            }
    STATUS current
    DESCRIPTION
        "Notification of Event NAPT.7

        Message: 'Bad TCP checksum ($1:$2 -> $3:$4) seq $5, ack $6'

        Parameters list:
              $1: napt7-internal-ip
              $2: napt7-internal-port
              $3: napt7-external-ip
              $4: napt7-external-port
              $5: napt7-sequence
              $6: napt7-ack-sequence

        Received TCP packet with bad TCP checksum."
    ::= { naptNotificationsPrefix 7 }

naptNotification8 NOTIFICATION-TYPE
    OBJECTS { 
              napt8-Drop-noNaptto, 
              napt8-packet-type 
            }
    STATUS current
    DESCRIPTION
        "Notification of Event NAPT.8

        Message: '$1 $2 packet'

        Parameters list:
              $1: napt8-Drop-noNaptto
              $2: napt8-packet-type

        It is not allowed to do NAPT in some firewalling cases: RIP, OSPF..."
    ::= { naptNotificationsPrefix 8 }

naptNotification9 NOTIFICATION-TYPE
    OBJECTS { 
              napt9-application, 
              napt9-source-ip,
              napt9-source-port,
              napt9-target-ip,
              napt9-target-port,
              napt9-sequence,
              napt9-ack-sequence 
            }
    STATUS current
    DESCRIPTION
        "Notification of Event NAPT.9

        Message: '[$1]TCP SYNC ($2:$3 -> $4:$5) seq:$6, ack:$7'

        Parameters list:
              $1: napt9-application
              $2: napt9-source-ip
              $3: napt9-source-port
              $4: napt9-target-ip
              $5: napt9-target-port
              $6: napt9-sequence
              $7: napt9-ack-sequence

        Sent TCP SYNC."
    ::= { naptNotificationsPrefix 9 }

naptNotification10 NOTIFICATION-TYPE
    OBJECTS { 
              napt10-application, 
              napt10-source-ip,
              napt10-source-port,
              napt10-target-ip,
              napt10-target-port 
            }
    STATUS current
    DESCRIPTION
        "Notification of Event NAPT.10

        Message: '[$1]TCP FIN/RST ($2:$3 -> $4:$5)'

        Parameters list:
              $1: napt10-application
              $2: napt10-source-ip
              $3: napt10-source-port
              $4: napt10-target-ip
              $5: napt10-target-port

        Received or sent TCP FIN/RST."
    ::= { naptNotificationsPrefix 10 }

naptNotification11 NOTIFICATION-TYPE
    OBJECTS { 
              napt11-IP-field, 
              napt11-field-value 
            }
    STATUS current
    DESCRIPTION
        "Notification of Event NAPT.11

        Message: 'Bad IP $1 0x$2'

        Parameters list:
              $1: napt11-IP-field
              $2: napt11-field-value

        Received bad IP header field."
    ::= { naptNotificationsPrefix 11 }

naptNotification12 NOTIFICATION-TYPE
    OBJECTS { 
              napt12-target-address 
            }
    STATUS current
    DESCRIPTION
        "Notification of Event NAPT.12

        Message: 'In $1 does not match external IP'

        Parameters list:
              $1: napt12-target-address

        Received a packet that does not match any IP connection."
    ::= { naptNotificationsPrefix 12 }

naptNotification13 NOTIFICATION-TYPE
    OBJECTS { 
              napt13-type, 
              napt13-source-ip,
              napt13-source-port,
              napt13-source-napted-ip,
              napt13-source-napted-port 
            }
    STATUS current
    DESCRIPTION
        "Notification of Event NAPT.13

        Message: '[$1] timeout ($2:$3 => $4:$5)'

        Parameters list:
              $1: napt13-type
              $2: napt13-source-ip
              $3: napt13-source-port
              $4: napt13-source-napted-ip
              $5: napt13-source-napted-port

        NAPT entry or ICMP identifier timeout."
    ::= { naptNotificationsPrefix 13 }

naptNotification14 NOTIFICATION-TYPE
    OBJECTS { 
              napt14-target-port 
            }
    STATUS current
    DESCRIPTION
        "Notification of Event NAPT.14

        Message: 'In unknown PORT $1'

        Parameters list:
              $1: napt14-target-port

        Received IP packet for an unused external port."
    ::= { naptNotificationsPrefix 14 }

naptNotification15 NOTIFICATION-TYPE
    OBJECTS { 
              napt15-target-identifier 
            }
    STATUS current
    DESCRIPTION
        "Notification of Event NAPT.15

        Message: 'In unknown IDENT $1'

        Parameters list:
              $1: napt15-target-identifier

        Received ICMP packet for an unused external identifier."
    ::= { naptNotificationsPrefix 15 }

naptNotification16 NOTIFICATION-TYPE
    OBJECTS { 
              napt16-ip-address 
            }
    STATUS current
    DESCRIPTION
        "Notification of Event NAPT.16

        Message: 'Out $1 exceeds max allowed entries'

        Parameters list:
              $1: napt16-ip-address

        Host exceeds max allowed NAPT entries."
    ::= { naptNotificationsPrefix 16 }

naptNotification17 NOTIFICATION-TYPE
    OBJECTS { 
              napt17-description 
            }
    STATUS current
    DESCRIPTION
        "Notification of Event NAPT.17

        Message: 'PPTP: $1'

        Parameters list:
              $1: napt17-description

        NAPT for PPTP traces."
    ::= { naptNotificationsPrefix 17 }

naptNotification18 NOTIFICATION-TYPE
    OBJECTS { 
              napt18-external-ip, 
              napt18-internal-ip,
              napt18-fragment-indication 
            }
    STATUS current
    DESCRIPTION
        "Notification of Event NAPT.18

        Message: 'In ($1 => $2) $3'

        Parameters list:
              $1: napt18-external-ip
              $2: napt18-internal-ip
              $3: napt18-fragment-indication

        NAPT for an incoming fragment (without port translation)."
    ::= { naptNotificationsPrefix 18 }

naptNotification19 NOTIFICATION-TYPE
    OBJECTS { 
              napt19-source-ip, 
              napt19-destination-ip 
            }
    STATUS current
    DESCRIPTION
        "Notification of Event NAPT.19

        Message: 'Dropping outgoing packet ($1 -> $2) due to connection unknown'

        Parameters list:
              $1: napt19-source-ip
              $2: napt19-destination-ip

        Dropping outgoing packet that does not match any IP connection."
    ::= { naptNotificationsPrefix 19 }

naptNotification20 NOTIFICATION-TYPE
    OBJECTS { 
              napt20-incoming-outcoming, 
              napt20-source-ip,
              napt20-destination-ip 
            }
    STATUS current
    DESCRIPTION
        "Notification of Event NAPT.20

        Message: '$1 packet ($2 -> $3) was locally generated, no NAPT is performed'

        Parameters list:
              $1: napt20-incoming-outcoming
              $2: napt20-source-ip
              $3: napt20-destination-ip

        It is not allowed to do incoming/outgoing NAPT to locally originated
        packets. No translation is performed."
    ::= { naptNotificationsPrefix 20 }

naptNotification21 NOTIFICATION-TYPE
    OBJECTS { 
              napt21-source-ip, 
              napt21-destination-ip,
              napt21-assignated-destination-ip 
            }
    STATUS current
    DESCRIPTION
        "Notification of Event NAPT.21

        Message: 'Dropping virtual destination outgoing packet ($1 -> $2) due to assigned destination is inactive ($3)'

        Parameters list:
              $1: napt21-source-ip
              $2: napt21-destination-ip
              $3: napt21-assignated-destination-ip

        Assignated destination address is not accesible. Packets are dropped."
    ::= { naptNotificationsPrefix 21 }

naptNotification22 NOTIFICATION-TYPE
    OBJECTS { 
              napt22-virtual-dest-ip, 
              napt22-virtual-dest-port,
              napt22-new-dest-ip,
              napt22-new-dest-port 
            }
    STATUS current
    DESCRIPTION
        "Notification of Event NAPT.22

        Message: 'Out virtual destination ($1:$2 => $3:$4)'

        Parameters list:
              $1: napt22-virtual-dest-ip
              $2: napt22-virtual-dest-port
              $3: napt22-new-dest-ip
              $4: napt22-new-dest-port

        Virtual destination NAPT for outgoing IP packet."
    ::= { naptNotificationsPrefix 22 }

naptNotification23 NOTIFICATION-TYPE
    OBJECTS { 
              napt23-new-dest-ip, 
              napt23-new-dest-port,
              napt23-virtual-dest-ip,
              napt23-virtual-dest-port 
            }
    STATUS current
    DESCRIPTION
        "Notification of Event NAPT.23

        Message: 'Incoming virtual destination ($1:$2 => $3:$4)'

        Parameters list:
              $1: napt23-new-dest-ip
              $2: napt23-new-dest-port
              $3: napt23-virtual-dest-ip
              $4: napt23-virtual-dest-port

        Virtual destination NAPT for incoming IP packet."
    ::= { naptNotificationsPrefix 23 }

naptNotification24 NOTIFICATION-TYPE
    OBJECTS { 
              napt24-Drop-noNAPTto, 
              napt24-source-ip,
              napt24-destination-ip 
            }
    STATUS current
    DESCRIPTION
        "Notification of Event NAPT.24

        Message: '$1 Incoming packet ($2 -> $3) due to connection unknown'

        Parameters list:
              $1: napt24-Drop-noNAPTto
              $2: napt24-source-ip
              $3: napt24-destination-ip

        Dropping or passing through without NAPT an incoming packet
        that does not match any IP connection."
    ::= { naptNotificationsPrefix 24 }

naptNotification25 NOTIFICATION-TYPE
    OBJECTS { 
              napt25-action, 
              napt25-fragmentation-entry,
              napt25-ip-id,
              napt25-ip-address 
            }
    STATUS current
    DESCRIPTION
        "Notification of Event NAPT.25

        Message: '$1: Fragmentation entry 0X$2 ip fragmentation id $3 ip address $4'

        Parameters list:
              $1: napt25-action
              $2: napt25-fragmentation-entry
              $3: napt25-ip-id
              $4: napt25-ip-address

        Creating or deleting NAPT fragmentation entry."
    ::= { naptNotificationsPrefix 25 }

naptNotification26 NOTIFICATION-TYPE
    OBJECTS { 
              napt26-action, 
              napt26-fragmentation-entry,
              napt26-ip-id,
              napt26-ip-address,
              napt26-ip-offset 
            }
    STATUS current
    DESCRIPTION
        "Notification of Event NAPT.26

        Message: '$1: Fragmentation entry 0X$2 ip fragmentation id $3 ip address $4 ip header offset $5'

        Parameters list:
              $1: napt26-action
              $2: napt26-fragmentation-entry
              $3: napt26-ip-id
              $4: napt26-ip-address
              $5: napt26-ip-offset

        Action done to a packet by a fragmentation entry."
    ::= { naptNotificationsPrefix 26 }

naptNotification27 NOTIFICATION-TYPE
    OBJECTS { 
              napt27-source-ip, 
              napt27-destination-ip,
              napt27-assignated-destination-ip,
              napt27-src-address 
            }
    STATUS current
    DESCRIPTION
        "Notification of Event NAPT.27

        Message: 'Dropping virtual destination incoming packet ($1 -> $2), assigned destination ($3) not equal to source ($4)'

        Parameters list:
              $1: napt27-source-ip
              $2: napt27-destination-ip
              $3: napt27-assignated-destination-ip
              $4: napt27-src-address

        An incoming packet matching a NAPT entry with virtual dest active
        has been droped because its source address was diferent from
        the assigned destination."
    ::= { naptNotificationsPrefix 27 }

naptNotification28 NOTIFICATION-TYPE
    OBJECTS { 
              napt28-Drop-noNAPTto, 
              napt28-source-ip,
              napt28-source-port,
              napt28-destination-ip,
              napt28-destination-port 
            }
    STATUS current
    DESCRIPTION
        "Notification of Event NAPT.28

        Message: '$1 incoming packet ($2:$3 -> $4:$5) with no napt destination port'

        Parameters list:
              $1: napt28-Drop-noNAPTto
              $2: napt28-source-ip
              $3: napt28-source-port
              $4: napt28-destination-ip
              $5: napt28-destination-port

        An incoming packet has been drop or past through without NAPT because
        its destination port is out of the range of NAPT ports."
    ::= { naptNotificationsPrefix 28 }

naptNotification29 NOTIFICATION-TYPE
    OBJECTS { 
              napt29-source-ip, 
              napt29-source-port,
              napt29-destination-ip,
              napt29-destination-port,
              napt29-old-mss,
              napt29-new-mss 
            }
    STATUS current
    DESCRIPTION
        "Notification of Event NAPT.29

        Message: 'TCP SYN MSS Adjusted ($1:$2 -> $3:$4) ($5 => $6)'

        Parameters list:
              $1: napt29-source-ip
              $2: napt29-source-port
              $3: napt29-destination-ip
              $4: napt29-destination-port
              $5: napt29-old-mss
              $6: napt29-new-mss

        The MSS value of an outgoing TCP SYN packet has been adjusted."
    ::= { naptNotificationsPrefix 29 }

naptNotification30 NOTIFICATION-TYPE
    OBJECTS { 
              napt30-source-ip, 
              napt30-source-port,
              napt30-destination-ip,
              napt30-destination-port,
              napt30-assignated-destination-port,
              napt30-src-port 
            }
    STATUS current
    DESCRIPTION
        "Notification of Event NAPT.30

        Message: 'Dropping virtual destination incoming packet ($1:$2 -> $3:$4), assigned destination port ($5) not equal to source port ($6)'

        Parameters list:
              $1: napt30-source-ip
              $2: napt30-source-port
              $3: napt30-destination-ip
              $4: napt30-destination-port
              $5: napt30-assignated-destination-port
              $6: napt30-src-port

        An incoming packet matching a NAPT entry with virtual destination active
        has been droped because its source port was diferent from the assigned
        destination port."
    ::= { naptNotificationsPrefix 30 }


END
