-- file automatically created


TELDAT-TRAP-NBS-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


nbsTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the NBS event subsystem."
    REVISION "201401200930Z"
    DESCRIPTION "Initial implementation"
        ::= { telEventTraps 110 }


nbsEventsGroup	OBJECT IDENTIFIER	::= { nbsTrapsMIB 1 }

nbsNotifications	OBJECT IDENTIFIER	::= { nbsTrapsMIB 2 }
nbsNotificationsPrefix	OBJECT IDENTIFIER	::= { nbsNotifications 0 }

nbsEventObjects1 OBJECT-IDENTITY
    STATUS current
    DESCRIPTION
        "Event NBS.1
        The NetBIOS software received a NetBIOS Add-Name-Query frame
        from the bridged network."
    ::= { nbsEventsGroup 1 }

nbs1-source-nbname OBJECT-TYPE
    SYNTAX DisplayString
    MAX-ACCESS accessible-for-notify
    STATUS current
    DESCRIPTION
        "Parameter 'source-nbname' in event NBS.1"
    ::= { nbsEventObjects1 1 }

nbs1-source-macaddr OBJECT-TYPE
    SYNTAX DisplayString
    MAX-ACCESS accessible-for-notify
    STATUS current
    DESCRIPTION
        "Parameter 'source-macaddr' in event NBS.1"
    ::= { nbsEventObjects1 2 }

nbs1-dest-nbname OBJECT-TYPE
    SYNTAX DisplayString
    MAX-ACCESS accessible-for-notify
    STATUS current
    DESCRIPTION
        "Parameter 'dest-nbname' in event NBS.1"
    ::= { nbsEventObjects1 3 }

nbs1-dest-macaddr OBJECT-TYPE
    SYNTAX DisplayString
    MAX-ACCESS accessible-for-notify
    STATUS current
    DESCRIPTION
        "Parameter 'dest-macaddr' in event NBS.1"
    ::= { nbsEventObjects1 4 }

nbsEventObjects2 OBJECT-IDENTITY
    STATUS current
    DESCRIPTION
        "Event NBS.2
        The NetBIOS software received a NetBIOS Add-Group-Name-Query frame
        from the bridged network."
    ::= { nbsEventsGroup 2 }

nbs2-source-nbname OBJECT-TYPE
    SYNTAX DisplayString
    MAX-ACCESS accessible-for-notify
    STATUS current
    DESCRIPTION
        "Parameter 'source-nbname' in event NBS.2"
    ::= { nbsEventObjects2 1 }

nbs2-source-macaddr OBJECT-TYPE
    SYNTAX DisplayString
    MAX-ACCESS accessible-for-notify
    STATUS current
    DESCRIPTION
        "Parameter 'source-macaddr' in event NBS.2"
    ::= { nbsEventObjects2 2 }

nbs2-dest-nbname OBJECT-TYPE
    SYNTAX DisplayString
    MAX-ACCESS accessible-for-notify
    STATUS current
    DESCRIPTION
        "Parameter 'dest-nbname' in event NBS.2"
    ::= { nbsEventObjects2 3 }

nbs2-dest-macaddr OBJECT-TYPE
    SYNTAX DisplayString
    MAX-ACCESS accessible-for-notify
    STATUS current
    DESCRIPTION
        "Parameter 'dest-macaddr' in event NBS.2"
    ::= { nbsEventObjects2 4 }

nbsEventObjects3 OBJECT-IDENTITY
    STATUS current
    DESCRIPTION
        "Event NBS.3
        The NetBIOS software received a NetBIOS Add-Name-Response frame
        from the bridged network."
    ::= { nbsEventsGroup 3 }

nbs3-source-nbname OBJECT-TYPE
    SYNTAX DisplayString
    MAX-ACCESS accessible-for-notify
    STATUS current
    DESCRIPTION
        "Parameter 'source-nbname' in event NBS.3"
    ::= { nbsEventObjects3 1 }

nbs3-source-macaddr OBJECT-TYPE
    SYNTAX DisplayString
    MAX-ACCESS accessible-for-notify
    STATUS current
    DESCRIPTION
        "Parameter 'source-macaddr' in event NBS.3"
    ::= { nbsEventObjects3 2 }

nbs3-dest-nbname OBJECT-TYPE
    SYNTAX DisplayString
    MAX-ACCESS accessible-for-notify
    STATUS current
    DESCRIPTION
        "Parameter 'dest-nbname' in event NBS.3"
    ::= { nbsEventObjects3 3 }

nbs3-dest-macaddr OBJECT-TYPE
    SYNTAX DisplayString
    MAX-ACCESS accessible-for-notify
    STATUS current
    DESCRIPTION
        "Parameter 'dest-macaddr' in event NBS.3"
    ::= { nbsEventObjects3 4 }

nbsEventObjects4 OBJECT-IDENTITY
    STATUS current
    DESCRIPTION
        "Event NBS.4
        The NetBIOS software received a NetBIOS Name-Query frame
        from the bridged network."
    ::= { nbsEventsGroup 4 }

nbs4-source-nbname OBJECT-TYPE
    SYNTAX DisplayString
    MAX-ACCESS accessible-for-notify
    STATUS current
    DESCRIPTION
        "Parameter 'source-nbname' in event NBS.4"
    ::= { nbsEventObjects4 1 }

nbs4-source-macaddr OBJECT-TYPE
    SYNTAX DisplayString
    MAX-ACCESS accessible-for-notify
    STATUS current
    DESCRIPTION
        "Parameter 'source-macaddr' in event NBS.4"
    ::= { nbsEventObjects4 2 }

nbs4-dest-nbname OBJECT-TYPE
    SYNTAX DisplayString
    MAX-ACCESS accessible-for-notify
    STATUS current
    DESCRIPTION
        "Parameter 'dest-nbname' in event NBS.4"
    ::= { nbsEventObjects4 3 }

nbs4-dest-macaddr OBJECT-TYPE
    SYNTAX DisplayString
    MAX-ACCESS accessible-for-notify
    STATUS current
    DESCRIPTION
        "Parameter 'dest-macaddr' in event NBS.4"
    ::= { nbsEventObjects4 4 }

nbsEventObjects5 OBJECT-IDENTITY
    STATUS current
    DESCRIPTION
        "Event NBS.5
        The NetBIOS software received a NetBIOS Name-Recognized frame
        from the bridged network."
    ::= { nbsEventsGroup 5 }

nbs5-source-nbname OBJECT-TYPE
    SYNTAX DisplayString
    MAX-ACCESS accessible-for-notify
    STATUS current
    DESCRIPTION
        "Parameter 'source-nbname' in event NBS.5"
    ::= { nbsEventObjects5 1 }

nbs5-source-macaddr OBJECT-TYPE
    SYNTAX DisplayString
    MAX-ACCESS accessible-for-notify
    STATUS current
    DESCRIPTION
        "Parameter 'source-macaddr' in event NBS.5"
    ::= { nbsEventObjects5 2 }

nbs5-dest-nbname OBJECT-TYPE
    SYNTAX DisplayString
    MAX-ACCESS accessible-for-notify
    STATUS current
    DESCRIPTION
        "Parameter 'dest-nbname' in event NBS.5"
    ::= { nbsEventObjects5 3 }

nbs5-dest-macaddr OBJECT-TYPE
    SYNTAX DisplayString
    MAX-ACCESS accessible-for-notify
    STATUS current
    DESCRIPTION
        "Parameter 'dest-macaddr' in event NBS.5"
    ::= { nbsEventObjects5 4 }

nbsEventObjects6 OBJECT-IDENTITY
    STATUS current
    DESCRIPTION
        "Event NBS.6
        The NetBIOS software received a NetBIOS Name-In-Conflict frame
        from the bridged network."
    ::= { nbsEventsGroup 6 }

nbs6-source-nbname OBJECT-TYPE
    SYNTAX DisplayString
    MAX-ACCESS accessible-for-notify
    STATUS current
    DESCRIPTION
        "Parameter 'source-nbname' in event NBS.6"
    ::= { nbsEventObjects6 1 }

nbs6-source-macaddr OBJECT-TYPE
    SYNTAX DisplayString
    MAX-ACCESS accessible-for-notify
    STATUS current
    DESCRIPTION
        "Parameter 'source-macaddr' in event NBS.6"
    ::= { nbsEventObjects6 2 }

nbs6-dest-nbname OBJECT-TYPE
    SYNTAX DisplayString
    MAX-ACCESS accessible-for-notify
    STATUS current
    DESCRIPTION
        "Parameter 'dest-nbname' in event NBS.6"
    ::= { nbsEventObjects6 3 }

nbs6-dest-macaddr OBJECT-TYPE
    SYNTAX DisplayString
    MAX-ACCESS accessible-for-notify
    STATUS current
    DESCRIPTION
        "Parameter 'dest-macaddr' in event NBS.6"
    ::= { nbsEventObjects6 4 }

nbsEventObjects7 OBJECT-IDENTITY
    STATUS current
    DESCRIPTION
        "Event NBS.7
        The NetBIOS software received a NetBIOS Status-Query frame
        from the bridged network."
    ::= { nbsEventsGroup 7 }

nbs7-source-nbname OBJECT-TYPE
    SYNTAX DisplayString
    MAX-ACCESS accessible-for-notify
    STATUS current
    DESCRIPTION
        "Parameter 'source-nbname' in event NBS.7"
    ::= { nbsEventObjects7 1 }

nbs7-source-macaddr OBJECT-TYPE
    SYNTAX DisplayString
    MAX-ACCESS accessible-for-notify
    STATUS current
    DESCRIPTION
        "Parameter 'source-macaddr' in event NBS.7"
    ::= { nbsEventObjects7 2 }

nbs7-dest-nbname OBJECT-TYPE
    SYNTAX DisplayString
    MAX-ACCESS accessible-for-notify
    STATUS current
    DESCRIPTION
        "Parameter 'dest-nbname' in event NBS.7"
    ::= { nbsEventObjects7 3 }

nbs7-dest-macaddr OBJECT-TYPE
    SYNTAX DisplayString
    MAX-ACCESS accessible-for-notify
    STATUS current
    DESCRIPTION
        "Parameter 'dest-macaddr' in event NBS.7"
    ::= { nbsEventObjects7 4 }

nbsEventObjects8 OBJECT-IDENTITY
    STATUS current
    DESCRIPTION
        "Event NBS.8
        The NetBIOS software received a NetBIOS Status-Response frame
        from the bridged network."
    ::= { nbsEventsGroup 8 }

nbs8-source-nbname OBJECT-TYPE
    SYNTAX DisplayString
    MAX-ACCESS accessible-for-notify
    STATUS current
    DESCRIPTION
        "Parameter 'source-nbname' in event NBS.8"
    ::= { nbsEventObjects8 1 }

nbs8-source-macaddr OBJECT-TYPE
    SYNTAX DisplayString
    MAX-ACCESS accessible-for-notify
    STATUS current
    DESCRIPTION
        "Parameter 'source-macaddr' in event NBS.8"
    ::= { nbsEventObjects8 2 }

nbs8-dest-nbname OBJECT-TYPE
    SYNTAX DisplayString
    MAX-ACCESS accessible-for-notify
    STATUS current
    DESCRIPTION
        "Parameter 'dest-nbname' in event NBS.8"
    ::= { nbsEventObjects8 3 }

nbs8-dest-macaddr OBJECT-TYPE
    SYNTAX DisplayString
    MAX-ACCESS accessible-for-notify
    STATUS current
    DESCRIPTION
        "Parameter 'dest-macaddr' in event NBS.8"
    ::= { nbsEventObjects8 4 }

nbsEventObjects9 OBJECT-IDENTITY
    STATUS current
    DESCRIPTION
        "Event NBS.9
        The NetBIOS software received a NetBIOS Datagram
        frame from the bridged network."
    ::= { nbsEventsGroup 9 }

nbs9-source-nbname OBJECT-TYPE
    SYNTAX DisplayString
    MAX-ACCESS accessible-for-notify
    STATUS current
    DESCRIPTION
        "Parameter 'source-nbname' in event NBS.9"
    ::= { nbsEventObjects9 1 }

nbs9-source-macaddr OBJECT-TYPE
    SYNTAX DisplayString
    MAX-ACCESS accessible-for-notify
    STATUS current
    DESCRIPTION
        "Parameter 'source-macaddr' in event NBS.9"
    ::= { nbsEventObjects9 2 }

nbs9-dest-nbname OBJECT-TYPE
    SYNTAX DisplayString
    MAX-ACCESS accessible-for-notify
    STATUS current
    DESCRIPTION
        "Parameter 'dest-nbname' in event NBS.9"
    ::= { nbsEventObjects9 3 }

nbs9-dest-macaddr OBJECT-TYPE
    SYNTAX DisplayString
    MAX-ACCESS accessible-for-notify
    STATUS current
    DESCRIPTION
        "Parameter 'dest-macaddr' in event NBS.9"
    ::= { nbsEventObjects9 4 }

nbsEventObjects10 OBJECT-IDENTITY
    STATUS current
    DESCRIPTION
        "Event NBS.10
        The NetBIOS software received a NetBIOS Datagram-Broadcast frame
        from the bridged network."
    ::= { nbsEventsGroup 10 }

nbs10-source-nbname OBJECT-TYPE
    SYNTAX DisplayString
    MAX-ACCESS accessible-for-notify
    STATUS current
    DESCRIPTION
        "Parameter 'source-nbname' in event NBS.10"
    ::= { nbsEventObjects10 1 }

nbs10-source-macaddr OBJECT-TYPE
    SYNTAX DisplayString
    MAX-ACCESS accessible-for-notify
    STATUS current
    DESCRIPTION
        "Parameter 'source-macaddr' in event NBS.10"
    ::= { nbsEventObjects10 2 }

nbs10-dest-nbname OBJECT-TYPE
    SYNTAX DisplayString
    MAX-ACCESS accessible-for-notify
    STATUS current
    DESCRIPTION
        "Parameter 'dest-nbname' in event NBS.10"
    ::= { nbsEventObjects10 3 }

nbs10-dest-macaddr OBJECT-TYPE
    SYNTAX DisplayString
    MAX-ACCESS accessible-for-notify
    STATUS current
    DESCRIPTION
        "Parameter 'dest-macaddr' in event NBS.10"
    ::= { nbsEventObjects10 4 }

nbsEventObjects11 OBJECT-IDENTITY
    STATUS current
    DESCRIPTION
        "Event NBS.11
        The NetBIOS software received a NetBIOS Terminate-Trace-07 frame
        from the bridged network."
    ::= { nbsEventsGroup 11 }

nbs11-source-nbname OBJECT-TYPE
    SYNTAX DisplayString
    MAX-ACCESS accessible-for-notify
    STATUS current
    DESCRIPTION
        "Parameter 'source-nbname' in event NBS.11"
    ::= { nbsEventObjects11 1 }

nbs11-source-macaddr OBJECT-TYPE
    SYNTAX DisplayString
    MAX-ACCESS accessible-for-notify
    STATUS current
    DESCRIPTION
        "Parameter 'source-macaddr' in event NBS.11"
    ::= { nbsEventObjects11 2 }

nbs11-dest-nbname OBJECT-TYPE
    SYNTAX DisplayString
    MAX-ACCESS accessible-for-notify
    STATUS current
    DESCRIPTION
        "Parameter 'dest-nbname' in event NBS.11"
    ::= { nbsEventObjects11 3 }

nbs11-dest-macaddr OBJECT-TYPE
    SYNTAX DisplayString
    MAX-ACCESS accessible-for-notify
    STATUS current
    DESCRIPTION
        "Parameter 'dest-macaddr' in event NBS.11"
    ::= { nbsEventObjects11 4 }

nbsEventObjects12 OBJECT-IDENTITY
    STATUS current
    DESCRIPTION
        "Event NBS.12
        The NetBIOS software received a NetBIOS Terminate-Trace-13 frame
        from the bridged network."
    ::= { nbsEventsGroup 12 }

nbs12-source-nbname OBJECT-TYPE
    SYNTAX DisplayString
    MAX-ACCESS accessible-for-notify
    STATUS current
    DESCRIPTION
        "Parameter 'source-nbname' in event NBS.12"
    ::= { nbsEventObjects12 1 }

nbs12-source-macaddr OBJECT-TYPE
    SYNTAX DisplayString
    MAX-ACCESS accessible-for-notify
    STATUS current
    DESCRIPTION
        "Parameter 'source-macaddr' in event NBS.12"
    ::= { nbsEventObjects12 2 }

nbs12-dest-nbname OBJECT-TYPE
    SYNTAX DisplayString
    MAX-ACCESS accessible-for-notify
    STATUS current
    DESCRIPTION
        "Parameter 'dest-nbname' in event NBS.12"
    ::= { nbsEventObjects12 3 }

nbs12-dest-macaddr OBJECT-TYPE
    SYNTAX DisplayString
    MAX-ACCESS accessible-for-notify
    STATUS current
    DESCRIPTION
        "Parameter 'dest-macaddr' in event NBS.12"
    ::= { nbsEventObjects12 4 }

nbsEventObjects13 OBJECT-IDENTITY
    STATUS current
    DESCRIPTION
        "Event NBS.13
        The NetBIOS software received an unrecognized NetBIOS frame
        from the bridged network."
    ::= { nbsEventsGroup 13 }

nbs13-source-nbname OBJECT-TYPE
    SYNTAX DisplayString
    MAX-ACCESS accessible-for-notify
    STATUS current
    DESCRIPTION
        "Parameter 'source-nbname' in event NBS.13"
    ::= { nbsEventObjects13 1 }

nbs13-source-macaddr OBJECT-TYPE
    SYNTAX DisplayString
    MAX-ACCESS accessible-for-notify
    STATUS current
    DESCRIPTION
        "Parameter 'source-macaddr' in event NBS.13"
    ::= { nbsEventObjects13 2 }

nbs13-dest-nbname OBJECT-TYPE
    SYNTAX DisplayString
    MAX-ACCESS accessible-for-notify
    STATUS current
    DESCRIPTION
        "Parameter 'dest-nbname' in event NBS.13"
    ::= { nbsEventObjects13 3 }

nbs13-dest-macaddr OBJECT-TYPE
    SYNTAX DisplayString
    MAX-ACCESS accessible-for-notify
    STATUS current
    DESCRIPTION
        "Parameter 'dest-macaddr' in event NBS.13"
    ::= { nbsEventObjects13 4 }

nbsEventObjects14 OBJECT-IDENTITY
    STATUS current
    DESCRIPTION
        "Event NBS.14
        The NetBIOS software received a NetBIOS Add-Name-Query frame
        from the DLSw network."
    ::= { nbsEventsGroup 14 }

nbs14-source-nbname OBJECT-TYPE
    SYNTAX DisplayString
    MAX-ACCESS accessible-for-notify
    STATUS current
    DESCRIPTION
        "Parameter 'source-nbname' in event NBS.14"
    ::= { nbsEventObjects14 1 }

nbs14-source-macaddr OBJECT-TYPE
    SYNTAX DisplayString
    MAX-ACCESS accessible-for-notify
    STATUS current
    DESCRIPTION
        "Parameter 'source-macaddr' in event NBS.14"
    ::= { nbsEventObjects14 2 }

nbs14-dest-nbname OBJECT-TYPE
    SYNTAX DisplayString
    MAX-ACCESS accessible-for-notify
    STATUS current
    DESCRIPTION
        "Parameter 'dest-nbname' in event NBS.14"
    ::= { nbsEventObjects14 3 }

nbs14-dest-macaddr OBJECT-TYPE
    SYNTAX DisplayString
    MAX-ACCESS accessible-for-notify
    STATUS current
    DESCRIPTION
        "Parameter 'dest-macaddr' in event NBS.14"
    ::= { nbsEventObjects14 4 }

nbsEventObjects15 OBJECT-IDENTITY
    STATUS current
    DESCRIPTION
        "Event NBS.15
        The NetBIOS software received a NetBIOS Add-Group-Name-Query frame
        from the DLSw network."
    ::= { nbsEventsGroup 15 }

nbs15-source-nbname OBJECT-TYPE
    SYNTAX DisplayString
    MAX-ACCESS accessible-for-notify
    STATUS current
    DESCRIPTION
        "Parameter 'source-nbname' in event NBS.15"
    ::= { nbsEventObjects15 1 }

nbs15-source-macaddr OBJECT-TYPE
    SYNTAX DisplayString
    MAX-ACCESS accessible-for-notify
    STATUS current
    DESCRIPTION
        "Parameter 'source-macaddr' in event NBS.15"
    ::= { nbsEventObjects15 2 }

nbs15-dest-nbname OBJECT-TYPE
    SYNTAX DisplayString
    MAX-ACCESS accessible-for-notify
    STATUS current
    DESCRIPTION
        "Parameter 'dest-nbname' in event NBS.15"
    ::= { nbsEventObjects15 3 }

nbs15-dest-macaddr OBJECT-TYPE
    SYNTAX DisplayString
    MAX-ACCESS accessible-for-notify
    STATUS current
    DESCRIPTION
        "Parameter 'dest-macaddr' in event NBS.15"
    ::= { nbsEventObjects15 4 }

nbsEventObjects16 OBJECT-IDENTITY
    STATUS current
    DESCRIPTION
        "Event NBS.16
        The NetBIOS software received a NetBIOS Add-Name-Response frame
        from the DLSw network."
    ::= { nbsEventsGroup 16 }

nbs16-source-nbname OBJECT-TYPE
    SYNTAX DisplayString
    MAX-ACCESS accessible-for-notify
    STATUS current
    DESCRIPTION
        "Parameter 'source-nbname' in event NBS.16"
    ::= { nbsEventObjects16 1 }

nbs16-source-macaddr OBJECT-TYPE
    SYNTAX DisplayString
    MAX-ACCESS accessible-for-notify
    STATUS current
    DESCRIPTION
        "Parameter 'source-macaddr' in event NBS.16"
    ::= { nbsEventObjects16 2 }

nbs16-dest-nbname OBJECT-TYPE
    SYNTAX DisplayString
    MAX-ACCESS accessible-for-notify
    STATUS current
    DESCRIPTION
        "Parameter 'dest-nbname' in event NBS.16"
    ::= { nbsEventObjects16 3 }

nbs16-dest-macaddr OBJECT-TYPE
    SYNTAX DisplayString
    MAX-ACCESS accessible-for-notify
    STATUS current
    DESCRIPTION
        "Parameter 'dest-macaddr' in event NBS.16"
    ::= { nbsEventObjects16 4 }

nbsEventObjects17 OBJECT-IDENTITY
    STATUS current
    DESCRIPTION
        "Event NBS.17
        The NetBIOS software received a NetBIOS Name-Query frame
        from the DLSw network."
    ::= { nbsEventsGroup 17 }

nbs17-source-nbname OBJECT-TYPE
    SYNTAX DisplayString
    MAX-ACCESS accessible-for-notify
    STATUS current
    DESCRIPTION
        "Parameter 'source-nbname' in event NBS.17"
    ::= { nbsEventObjects17 1 }

nbs17-source-macaddr OBJECT-TYPE
    SYNTAX DisplayString
    MAX-ACCESS accessible-for-notify
    STATUS current
    DESCRIPTION
        "Parameter 'source-macaddr' in event NBS.17"
    ::= { nbsEventObjects17 2 }

nbs17-dest-nbname OBJECT-TYPE
    SYNTAX DisplayString
    MAX-ACCESS accessible-for-notify
    STATUS current
    DESCRIPTION
        "Parameter 'dest-nbname' in event NBS.17"
    ::= { nbsEventObjects17 3 }

nbs17-dest-macaddr OBJECT-TYPE
    SYNTAX DisplayString
    MAX-ACCESS accessible-for-notify
    STATUS current
    DESCRIPTION
        "Parameter 'dest-macaddr' in event NBS.17"
    ::= { nbsEventObjects17 4 }

nbsEventObjects18 OBJECT-IDENTITY
    STATUS current
    DESCRIPTION
        "Event NBS.18
        The NetBIOS software received a NetBIOS Name-Recognized frame
        from the DLSw network."
    ::= { nbsEventsGroup 18 }

nbs18-source-nbname OBJECT-TYPE
    SYNTAX DisplayString
    MAX-ACCESS accessible-for-notify
    STATUS current
    DESCRIPTION
        "Parameter 'source-nbname' in event NBS.18"
    ::= { nbsEventObjects18 1 }

nbs18-source-macaddr OBJECT-TYPE
    SYNTAX DisplayString
    MAX-ACCESS accessible-for-notify
    STATUS current
    DESCRIPTION
        "Parameter 'source-macaddr' in event NBS.18"
    ::= { nbsEventObjects18 2 }

nbs18-dest-nbname OBJECT-TYPE
    SYNTAX DisplayString
    MAX-ACCESS accessible-for-notify
    STATUS current
    DESCRIPTION
        "Parameter 'dest-nbname' in event NBS.18"
    ::= { nbsEventObjects18 3 }

nbs18-dest-macaddr OBJECT-TYPE
    SYNTAX DisplayString
    MAX-ACCESS accessible-for-notify
    STATUS current
    DESCRIPTION
        "Parameter 'dest-macaddr' in event NBS.18"
    ::= { nbsEventObjects18 4 }

nbsEventObjects19 OBJECT-IDENTITY
    STATUS current
    DESCRIPTION
        "Event NBS.19
        The NetBIOS software received a NetBIOS Name-In-Conflict frame
        from the DLSw network."
    ::= { nbsEventsGroup 19 }

nbs19-source-nbname OBJECT-TYPE
    SYNTAX DisplayString
    MAX-ACCESS accessible-for-notify
    STATUS current
    DESCRIPTION
        "Parameter 'source-nbname' in event NBS.19"
    ::= { nbsEventObjects19 1 }

nbs19-source-macaddr OBJECT-TYPE
    SYNTAX DisplayString
    MAX-ACCESS accessible-for-notify
    STATUS current
    DESCRIPTION
        "Parameter 'source-macaddr' in event NBS.19"
    ::= { nbsEventObjects19 2 }

nbs19-dest-nbname OBJECT-TYPE
    SYNTAX DisplayString
    MAX-ACCESS accessible-for-notify
    STATUS current
    DESCRIPTION
        "Parameter 'dest-nbname' in event NBS.19"
    ::= { nbsEventObjects19 3 }

nbs19-dest-macaddr OBJECT-TYPE
    SYNTAX DisplayString
    MAX-ACCESS accessible-for-notify
    STATUS current
    DESCRIPTION
        "Parameter 'dest-macaddr' in event NBS.19"
    ::= { nbsEventObjects19 4 }

nbsEventObjects20 OBJECT-IDENTITY
    STATUS current
    DESCRIPTION
        "Event NBS.20
        The NetBIOS software received a NetBIOS Status-Query frame
        from the DLSw network."
    ::= { nbsEventsGroup 20 }

nbs20-source-nbname OBJECT-TYPE
    SYNTAX DisplayString
    MAX-ACCESS accessible-for-notify
    STATUS current
    DESCRIPTION
        "Parameter 'source-nbname' in event NBS.20"
    ::= { nbsEventObjects20 1 }

nbs20-source-macaddr OBJECT-TYPE
    SYNTAX DisplayString
    MAX-ACCESS accessible-for-notify
    STATUS current
    DESCRIPTION
        "Parameter 'source-macaddr' in event NBS.20"
    ::= { nbsEventObjects20 2 }

nbs20-dest-nbname OBJECT-TYPE
    SYNTAX DisplayString
    MAX-ACCESS accessible-for-notify
    STATUS current
    DESCRIPTION
        "Parameter 'dest-nbname' in event NBS.20"
    ::= { nbsEventObjects20 3 }

nbs20-dest-macaddr OBJECT-TYPE
    SYNTAX DisplayString
    MAX-ACCESS accessible-for-notify
    STATUS current
    DESCRIPTION
        "Parameter 'dest-macaddr' in event NBS.20"
    ::= { nbsEventObjects20 4 }

nbsEventObjects21 OBJECT-IDENTITY
    STATUS current
    DESCRIPTION
        "Event NBS.21
        The NetBIOS software received a NetBIOS Status-Response frame
        from the DLSw network."
    ::= { nbsEventsGroup 21 }

nbs21-source-nbname OBJECT-TYPE
    SYNTAX DisplayString
    MAX-ACCESS accessible-for-notify
    STATUS current
    DESCRIPTION
        "Parameter 'source-nbname' in event NBS.21"
    ::= { nbsEventObjects21 1 }

nbs21-source-macaddr OBJECT-TYPE
    SYNTAX DisplayString
    MAX-ACCESS accessible-for-notify
    STATUS current
    DESCRIPTION
        "Parameter 'source-macaddr' in event NBS.21"
    ::= { nbsEventObjects21 2 }

nbs21-dest-nbname OBJECT-TYPE
    SYNTAX DisplayString
    MAX-ACCESS accessible-for-notify
    STATUS current
    DESCRIPTION
        "Parameter 'dest-nbname' in event NBS.21"
    ::= { nbsEventObjects21 3 }

nbs21-dest-macaddr OBJECT-TYPE
    SYNTAX DisplayString
    MAX-ACCESS accessible-for-notify
    STATUS current
    DESCRIPTION
        "Parameter 'dest-macaddr' in event NBS.21"
    ::= { nbsEventObjects21 4 }

nbsEventObjects22 OBJECT-IDENTITY
    STATUS current
    DESCRIPTION
        "Event NBS.22
        The NetBIOS software received a NetBIOS Datagram frame
        from the DLSw network."
    ::= { nbsEventsGroup 22 }

nbs22-source-nbname OBJECT-TYPE
    SYNTAX DisplayString
    MAX-ACCESS accessible-for-notify
    STATUS current
    DESCRIPTION
        "Parameter 'source-nbname' in event NBS.22"
    ::= { nbsEventObjects22 1 }

nbs22-source-macaddr OBJECT-TYPE
    SYNTAX DisplayString
    MAX-ACCESS accessible-for-notify
    STATUS current
    DESCRIPTION
        "Parameter 'source-macaddr' in event NBS.22"
    ::= { nbsEventObjects22 2 }

nbs22-dest-nbname OBJECT-TYPE
    SYNTAX DisplayString
    MAX-ACCESS accessible-for-notify
    STATUS current
    DESCRIPTION
        "Parameter 'dest-nbname' in event NBS.22"
    ::= { nbsEventObjects22 3 }

nbs22-dest-macaddr OBJECT-TYPE
    SYNTAX DisplayString
    MAX-ACCESS accessible-for-notify
    STATUS current
    DESCRIPTION
        "Parameter 'dest-macaddr' in event NBS.22"
    ::= { nbsEventObjects22 4 }

nbsEventObjects23 OBJECT-IDENTITY
    STATUS current
    DESCRIPTION
        "Event NBS.23
        The NetBIOS software received a NetBIOS Datagram-Broadcast frame
        from the DLSw network."
    ::= { nbsEventsGroup 23 }

nbs23-source-nbname OBJECT-TYPE
    SYNTAX DisplayString
    MAX-ACCESS accessible-for-notify
    STATUS current
    DESCRIPTION
        "Parameter 'source-nbname' in event NBS.23"
    ::= { nbsEventObjects23 1 }

nbs23-source-macaddr OBJECT-TYPE
    SYNTAX DisplayString
    MAX-ACCESS accessible-for-notify
    STATUS current
    DESCRIPTION
        "Parameter 'source-macaddr' in event NBS.23"
    ::= { nbsEventObjects23 2 }

nbs23-dest-nbname OBJECT-TYPE
    SYNTAX DisplayString
    MAX-ACCESS accessible-for-notify
    STATUS current
    DESCRIPTION
        "Parameter 'dest-nbname' in event NBS.23"
    ::= { nbsEventObjects23 3 }

nbs23-dest-macaddr OBJECT-TYPE
    SYNTAX DisplayString
    MAX-ACCESS accessible-for-notify
    STATUS current
    DESCRIPTION
        "Parameter 'dest-macaddr' in event NBS.23"
    ::= { nbsEventObjects23 4 }

nbsEventObjects24 OBJECT-IDENTITY
    STATUS current
    DESCRIPTION
        "Event NBS.24
        The NetBIOS software received a NetBIOS Terminate-Trace-07 frame
        from the DLSw network."
    ::= { nbsEventsGroup 24 }

nbs24-source-nbname OBJECT-TYPE
    SYNTAX DisplayString
    MAX-ACCESS accessible-for-notify
    STATUS current
    DESCRIPTION
        "Parameter 'source-nbname' in event NBS.24"
    ::= { nbsEventObjects24 1 }

nbs24-source-macaddr OBJECT-TYPE
    SYNTAX DisplayString
    MAX-ACCESS accessible-for-notify
    STATUS current
    DESCRIPTION
        "Parameter 'source-macaddr' in event NBS.24"
    ::= { nbsEventObjects24 2 }

nbs24-dest-nbname OBJECT-TYPE
    SYNTAX DisplayString
    MAX-ACCESS accessible-for-notify
    STATUS current
    DESCRIPTION
        "Parameter 'dest-nbname' in event NBS.24"
    ::= { nbsEventObjects24 3 }

nbs24-dest-macaddr OBJECT-TYPE
    SYNTAX DisplayString
    MAX-ACCESS accessible-for-notify
    STATUS current
    DESCRIPTION
        "Parameter 'dest-macaddr' in event NBS.24"
    ::= { nbsEventObjects24 4 }

nbsEventObjects25 OBJECT-IDENTITY
    STATUS current
    DESCRIPTION
        "Event NBS.25
        The NetBIOS software received a NetBIOS Terminate-Trace-13 frame
        from the DLSw network."
    ::= { nbsEventsGroup 25 }

nbs25-source-nbname OBJECT-TYPE
    SYNTAX DisplayString
    MAX-ACCESS accessible-for-notify
    STATUS current
    DESCRIPTION
        "Parameter 'source-nbname' in event NBS.25"
    ::= { nbsEventObjects25 1 }

nbs25-source-macaddr OBJECT-TYPE
    SYNTAX DisplayString
    MAX-ACCESS accessible-for-notify
    STATUS current
    DESCRIPTION
        "Parameter 'source-macaddr' in event NBS.25"
    ::= { nbsEventObjects25 2 }

nbs25-dest-nbname OBJECT-TYPE
    SYNTAX DisplayString
    MAX-ACCESS accessible-for-notify
    STATUS current
    DESCRIPTION
        "Parameter 'dest-nbname' in event NBS.25"
    ::= { nbsEventObjects25 3 }

nbs25-dest-macaddr OBJECT-TYPE
    SYNTAX DisplayString
    MAX-ACCESS accessible-for-notify
    STATUS current
    DESCRIPTION
        "Parameter 'dest-macaddr' in event NBS.25"
    ::= { nbsEventObjects25 4 }

nbsEventObjects26 OBJECT-IDENTITY
    STATUS current
    DESCRIPTION
        "Event NBS.26
        The NetBIOS software received an unrecognized NetBIOS frame
        from the DLSw network."
    ::= { nbsEventsGroup 26 }

nbs26-source-nbname OBJECT-TYPE
    SYNTAX DisplayString
    MAX-ACCESS accessible-for-notify
    STATUS current
    DESCRIPTION
        "Parameter 'source-nbname' in event NBS.26"
    ::= { nbsEventObjects26 1 }

nbs26-source-macaddr OBJECT-TYPE
    SYNTAX DisplayString
    MAX-ACCESS accessible-for-notify
    STATUS current
    DESCRIPTION
        "Parameter 'source-macaddr' in event NBS.26"
    ::= { nbsEventObjects26 2 }

nbs26-dest-nbname OBJECT-TYPE
    SYNTAX DisplayString
    MAX-ACCESS accessible-for-notify
    STATUS current
    DESCRIPTION
        "Parameter 'dest-nbname' in event NBS.26"
    ::= { nbsEventObjects26 3 }

nbs26-dest-macaddr OBJECT-TYPE
    SYNTAX DisplayString
    MAX-ACCESS accessible-for-notify
    STATUS current
    DESCRIPTION
        "Parameter 'dest-macaddr' in event NBS.26"
    ::= { nbsEventObjects26 4 }

nbsEventObjects27 OBJECT-IDENTITY
    STATUS current
    DESCRIPTION
        "Event NBS.27
        The NetBIOS software bridge frame type filter did not forward the given
        NetBIOS frame to the bridged network. It was filtered by
        the NetBIOS support bridge frame type filter."
    ::= { nbsEventsGroup 27 }

nbs27-source-nbname OBJECT-TYPE
    SYNTAX DisplayString
    MAX-ACCESS accessible-for-notify
    STATUS current
    DESCRIPTION
        "Parameter 'source-nbname' in event NBS.27"
    ::= { nbsEventObjects27 1 }

nbs27-dest-nbname OBJECT-TYPE
    SYNTAX DisplayString
    MAX-ACCESS accessible-for-notify
    STATUS current
    DESCRIPTION
        "Parameter 'dest-nbname' in event NBS.27"
    ::= { nbsEventObjects27 2 }

nbsEventObjects28 OBJECT-IDENTITY
    STATUS current
    DESCRIPTION
        "Event NBS.28
        The router did not forward the given NetBIOS frame to the DLSw network
        because it was filtered by the NetBIOS support DLSw frame type filter."
    ::= { nbsEventsGroup 28 }

nbs28-source-nbname OBJECT-TYPE
    SYNTAX DisplayString
    MAX-ACCESS accessible-for-notify
    STATUS current
    DESCRIPTION
        "Parameter 'source-nbname' in event NBS.28"
    ::= { nbsEventObjects28 1 }

nbs28-dest-nbname OBJECT-TYPE
    SYNTAX DisplayString
    MAX-ACCESS accessible-for-notify
    STATUS current
    DESCRIPTION
        "Parameter 'dest-nbname' in event NBS.28"
    ::= { nbsEventObjects28 2 }

nbsEventObjects29 OBJECT-IDENTITY
    STATUS current
    DESCRIPTION
        "Event NBS.29
        The router did not forward the given NetBIOS frame to the bridged
        network because it could not find or create a corresponding name
        cache entry."
    ::= { nbsEventsGroup 29 }

nbs29-source-nbname OBJECT-TYPE
    SYNTAX DisplayString
    MAX-ACCESS accessible-for-notify
    STATUS current
    DESCRIPTION
        "Parameter 'source-nbname' in event NBS.29"
    ::= { nbsEventObjects29 1 }

nbs29-dest-nbname OBJECT-TYPE
    SYNTAX DisplayString
    MAX-ACCESS accessible-for-notify
    STATUS current
    DESCRIPTION
        "Parameter 'dest-nbname' in event NBS.29"
    ::= { nbsEventObjects29 2 }

nbsEventObjects30 OBJECT-IDENTITY
    STATUS current
    DESCRIPTION
        "Event NBS.30
        The router did not forward the given NetBIOS frame to the DLSw network
        because it could not find or create a corresponding name cache entry."
    ::= { nbsEventsGroup 30 }

nbs30-source-nbname OBJECT-TYPE
    SYNTAX DisplayString
    MAX-ACCESS accessible-for-notify
    STATUS current
    DESCRIPTION
        "Parameter 'source-nbname' in event NBS.30"
    ::= { nbsEventObjects30 1 }

nbs30-dest-nbname OBJECT-TYPE
    SYNTAX DisplayString
    MAX-ACCESS accessible-for-notify
    STATUS current
    DESCRIPTION
        "Parameter 'dest-nbname' in event NBS.30"
    ::= { nbsEventObjects30 2 }

nbsEventObjects31 OBJECT-IDENTITY
    STATUS current
    DESCRIPTION
        "Event NBS.31
        The router did not forward the given NetBIOS frame to the bridged
        network because the router filtered it as a duplicate NetBIOS command
        frame."
    ::= { nbsEventsGroup 31 }

nbs31-source-nbname OBJECT-TYPE
    SYNTAX DisplayString
    MAX-ACCESS accessible-for-notify
    STATUS current
    DESCRIPTION
        "Parameter 'source-nbname' in event NBS.31"
    ::= { nbsEventObjects31 1 }

nbs31-dest-nbname OBJECT-TYPE
    SYNTAX DisplayString
    MAX-ACCESS accessible-for-notify
    STATUS current
    DESCRIPTION
        "Parameter 'dest-nbname' in event NBS.31"
    ::= { nbsEventObjects31 2 }

nbsEventObjects32 OBJECT-IDENTITY
    STATUS current
    DESCRIPTION
        "Event NBS.32
        The router did not forward the given NetBIOS frame to the DLSw network
        because the router filtered it as a duplicate NetBIOS command frame."
    ::= { nbsEventsGroup 32 }

nbs32-source-nbname OBJECT-TYPE
    SYNTAX DisplayString
    MAX-ACCESS accessible-for-notify
    STATUS current
    DESCRIPTION
        "Parameter 'source-nbname' in event NBS.32"
    ::= { nbsEventObjects32 1 }

nbs32-dest-nbname OBJECT-TYPE
    SYNTAX DisplayString
    MAX-ACCESS accessible-for-notify
    STATUS current
    DESCRIPTION
        "Parameter 'dest-nbname' in event NBS.32"
    ::= { nbsEventObjects32 2 }

nbsEventObjects33 OBJECT-IDENTITY
    STATUS current
    DESCRIPTION
        "Event NBS.33
        The router did not forward the given NetBIOS frame to the bridged
        network because the router could not find a command frame matching
        this response frame."
    ::= { nbsEventsGroup 33 }

nbs33-source-nbname OBJECT-TYPE
    SYNTAX DisplayString
    MAX-ACCESS accessible-for-notify
    STATUS current
    DESCRIPTION
        "Parameter 'source-nbname' in event NBS.33"
    ::= { nbsEventObjects33 1 }

nbs33-dest-nbname OBJECT-TYPE
    SYNTAX DisplayString
    MAX-ACCESS accessible-for-notify
    STATUS current
    DESCRIPTION
        "Parameter 'dest-nbname' in event NBS.33"
    ::= { nbsEventObjects33 2 }

nbsEventObjects34 OBJECT-IDENTITY
    STATUS current
    DESCRIPTION
        "Event NBS.34
        The router did not forward the given NetBIOS frame to the DLSw network
        because the router could not find a command frame matching this
        response frame."
    ::= { nbsEventsGroup 34 }

nbs34-source-nbname OBJECT-TYPE
    SYNTAX DisplayString
    MAX-ACCESS accessible-for-notify
    STATUS current
    DESCRIPTION
        "Parameter 'source-nbname' in event NBS.34"
    ::= { nbsEventObjects34 1 }

nbs34-dest-nbname OBJECT-TYPE
    SYNTAX DisplayString
    MAX-ACCESS accessible-for-notify
    STATUS current
    DESCRIPTION
        "Parameter 'dest-nbname' in event NBS.34"
    ::= { nbsEventObjects34 2 }

nbsEventObjects35 OBJECT-IDENTITY
    STATUS current
    DESCRIPTION
        "Event NBS.35
        The router did not forward the given NetBIOS frame to the bridged
        network because the name cache processing indicated the router should
        not forward it."
    ::= { nbsEventsGroup 35 }

nbs35-source-nbname OBJECT-TYPE
    SYNTAX DisplayString
    MAX-ACCESS accessible-for-notify
    STATUS current
    DESCRIPTION
        "Parameter 'source-nbname' in event NBS.35"
    ::= { nbsEventObjects35 1 }

nbs35-dest-nbname OBJECT-TYPE
    SYNTAX DisplayString
    MAX-ACCESS accessible-for-notify
    STATUS current
    DESCRIPTION
        "Parameter 'dest-nbname' in event NBS.35"
    ::= { nbsEventObjects35 2 }

nbsEventObjects36 OBJECT-IDENTITY
    STATUS current
    DESCRIPTION
        "Event NBS.36
        The router did not forward the given NetBIOS frame to the DLSw network
        because the name cache processing indicated the router should not
        forward it."
    ::= { nbsEventsGroup 36 }

nbs36-source-nbname OBJECT-TYPE
    SYNTAX DisplayString
    MAX-ACCESS accessible-for-notify
    STATUS current
    DESCRIPTION
        "Parameter 'source-nbname' in event NBS.36"
    ::= { nbsEventObjects36 1 }

nbs36-dest-nbname OBJECT-TYPE
    SYNTAX DisplayString
    MAX-ACCESS accessible-for-notify
    STATUS current
    DESCRIPTION
        "Parameter 'dest-nbname' in event NBS.36"
    ::= { nbsEventObjects36 2 }

nbsEventObjects37 OBJECT-IDENTITY
    STATUS current
    DESCRIPTION
        "Event NBS.37
        The router did not forward the given NetBIOS frame to the bridged
        network because the processing indicated the router should not
        forward it."
    ::= { nbsEventsGroup 37 }

nbs37-source-nbname OBJECT-TYPE
    SYNTAX DisplayString
    MAX-ACCESS accessible-for-notify
    STATUS current
    DESCRIPTION
        "Parameter 'source-nbname' in event NBS.37"
    ::= { nbsEventObjects37 1 }

nbs37-dest-nbname OBJECT-TYPE
    SYNTAX DisplayString
    MAX-ACCESS accessible-for-notify
    STATUS current
    DESCRIPTION
        "Parameter 'dest-nbname' in event NBS.37"
    ::= { nbsEventObjects37 2 }

nbsEventObjects38 OBJECT-IDENTITY
    STATUS current
    DESCRIPTION
        "Event NBS.38
        The router did not forward the given NetBIOS frame to the DLSw network
        because processing indicated the router should not forward it."
    ::= { nbsEventsGroup 38 }

nbs38-source-nbname OBJECT-TYPE
    SYNTAX DisplayString
    MAX-ACCESS accessible-for-notify
    STATUS current
    DESCRIPTION
        "Parameter 'source-nbname' in event NBS.38"
    ::= { nbsEventObjects38 1 }

nbs38-dest-nbname OBJECT-TYPE
    SYNTAX DisplayString
    MAX-ACCESS accessible-for-notify
    STATUS current
    DESCRIPTION
        "Parameter 'dest-nbname' in event NBS.38"
    ::= { nbsEventObjects38 2 }

nbsEventObjects39 OBJECT-IDENTITY
    STATUS current
    DESCRIPTION
        "Event NBS.39
        The NetBIOS software is associating a MAC address and RIF with
        a NetBIOS name. Find this association on NetBIOS Name-Querys,
        Name-Recognizeds, and Datagrams."
    ::= { nbsEventsGroup 39 }

nbs39-source-nbname OBJECT-TYPE
    SYNTAX DisplayString
    MAX-ACCESS accessible-for-notify
    STATUS current
    DESCRIPTION
        "Parameter 'source-nbname' in event NBS.39"
    ::= { nbsEventObjects39 1 }

nbs39-source-macaddr OBJECT-TYPE
    SYNTAX DisplayString
    MAX-ACCESS accessible-for-notify
    STATUS current
    DESCRIPTION
        "Parameter 'source-macaddr' in event NBS.39"
    ::= { nbsEventObjects39 2 }

nbs39-rif OBJECT-TYPE
    SYNTAX DisplayString
    MAX-ACCESS accessible-for-notify
    STATUS current
    DESCRIPTION
        "Parameter 'rif' in event NBS.39"
    ::= { nbsEventObjects39 3 }

nbsEventObjects40 OBJECT-IDENTITY
    STATUS current
    DESCRIPTION
        "Event NBS.40
        The router modified a NetBIOS frame to be forwarded to the bridged
        network by using the cached MAC address and routing information (if
        available). This modification takes place on NetBIOS Name-Querys,
        Status-Querys, and Datagrams."
    ::= { nbsEventsGroup 40 }

nbs40-dest-nbname OBJECT-TYPE
    SYNTAX DisplayString
    MAX-ACCESS accessible-for-notify
    STATUS current
    DESCRIPTION
        "Parameter 'dest-nbname' in event NBS.40"
    ::= { nbsEventObjects40 1 }

nbs40-dest-macaddr OBJECT-TYPE
    SYNTAX DisplayString
    MAX-ACCESS accessible-for-notify
    STATUS current
    DESCRIPTION
        "Parameter 'dest-macaddr' in event NBS.40"
    ::= { nbsEventObjects40 2 }

nbs40-rif OBJECT-TYPE
    SYNTAX DisplayString
    MAX-ACCESS accessible-for-notify
    STATUS current
    DESCRIPTION
        "Parameter 'rif' in event NBS.40"
    ::= { nbsEventObjects40 3 }

nbsEventObjects41 OBJECT-IDENTITY
    STATUS current
    DESCRIPTION
        "Event NBS.41
        The routed created a new NetBIOS name cache entry. This typically
        occurs on NetBIOS Name-Querys, Status-Querys, Add-Name-Querys,
        Add-Group-Name-Querys, and Datagrams."
    ::= { nbsEventsGroup 41 }

nbs41-nbname OBJECT-TYPE
    SYNTAX DisplayString
    MAX-ACCESS accessible-for-notify
    STATUS current
    DESCRIPTION
        "Parameter 'nbname' in event NBS.41"
    ::= { nbsEventObjects41 1 }

nbsEventObjects42 OBJECT-IDENTITY
    STATUS current
    DESCRIPTION
        "Event NBS.42
        The router created a new NetBIOS command/response entry. This typically
        occurs on NetBIOS Name-Querys, Status-Querys, and Datagrams."
    ::= { nbsEventsGroup 42 }

nbs42-nbname OBJECT-TYPE
    SYNTAX DisplayString
    MAX-ACCESS accessible-for-notify
    STATUS current
    DESCRIPTION
        "Parameter 'nbname' in event NBS.42"
    ::= { nbsEventObjects42 1 }

nbsEventObjects43 OBJECT-IDENTITY
    STATUS current
    DESCRIPTION
        "Event NBS.43
        A validation of the name cache entry indicated that the entry is
        invalid. That is, certain fields contain invalid values or invalid
        combinations of values. The possible reason codes are as follows:
        01 - bad nlist-search / name-type combination;
        02 - bad entry-type / name-type combination;
        03 - bad name-type value."
    ::= { nbsEventsGroup 43 }

nbs43-reason OBJECT-TYPE
    SYNTAX Integer32
    MAX-ACCESS accessible-for-notify
    STATUS current
    DESCRIPTION
        "Parameter 'reason' in event NBS.43"
    ::= { nbsEventObjects43 1 }

nbs43-nbname OBJECT-TYPE
    SYNTAX DisplayString
    MAX-ACCESS accessible-for-notify
    STATUS current
    DESCRIPTION
        "Parameter 'nbname' in event NBS.43"
    ::= { nbsEventObjects43 2 }

nbsEventObjects44 OBJECT-IDENTITY
    STATUS current
    DESCRIPTION
        "Event NBS.44
        The router deleted a NetBIOS name cache entry.
        This typically occurs as a result of it aging out."
    ::= { nbsEventsGroup 44 }

nbs44-nbname OBJECT-TYPE
    SYNTAX DisplayString
    MAX-ACCESS accessible-for-notify
    STATUS current
    DESCRIPTION
        "Parameter 'nbname' in event NBS.44"
    ::= { nbsEventObjects44 1 }

nbsEventObjects47 OBJECT-IDENTITY
    STATUS current
    DESCRIPTION
        "Event NBS.47
        You deleted a filter list, that was part of an already
        configured filter. You cannot enable the filter."
    ::= { nbsEventsGroup 47 }

nbs47-input-output OBJECT-TYPE
    SYNTAX DisplayString
    MAX-ACCESS accessible-for-notify
    STATUS current
    DESCRIPTION
        "Parameter 'input-output' in event NBS.47"
    ::= { nbsEventObjects47 1 }

nbs47-port-number OBJECT-TYPE
    SYNTAX Integer32
    MAX-ACCESS accessible-for-notify
    STATUS current
    DESCRIPTION
        "Parameter 'port-number' in event NBS.47"
    ::= { nbsEventObjects47 2 }

nbsEventObjects48 OBJECT-IDENTITY
    STATUS current
    DESCRIPTION
        "Event NBS.48
        You configured a NetBIOS filter for a particular port, but that
        port number is not configured."
    ::= { nbsEventsGroup 48 }

nbs48-input-output OBJECT-TYPE
    SYNTAX DisplayString
    MAX-ACCESS accessible-for-notify
    STATUS current
    DESCRIPTION
        "Parameter 'input-output' in event NBS.48"
    ::= { nbsEventObjects48 1 }

nbs48-port-number OBJECT-TYPE
    SYNTAX Integer32
    MAX-ACCESS accessible-for-notify
    STATUS current
    DESCRIPTION
        "Parameter 'port-number' in event NBS.48"
    ::= { nbsEventObjects48 2 }

nbsEventObjects49 OBJECT-IDENTITY
    STATUS current
    DESCRIPTION
        "Event NBS.49
        A NetBIOS packet has matched the criteria the router specified in a
        NetBIOS filter configuration record. The packet is dropped."
    ::= { nbsEventsGroup 49 }

nbs49-source-mac OBJECT-TYPE
    SYNTAX DisplayString
    MAX-ACCESS accessible-for-notify
    STATUS current
    DESCRIPTION
        "Parameter 'source-mac' in event NBS.49"
    ::= { nbsEventObjects49 1 }

nbs49-dest-mac OBJECT-TYPE
    SYNTAX DisplayString
    MAX-ACCESS accessible-for-notify
    STATUS current
    DESCRIPTION
        "Parameter 'dest-mac' in event NBS.49"
    ::= { nbsEventObjects49 2 }

nbs49-port OBJECT-TYPE
    SYNTAX Integer32
    MAX-ACCESS accessible-for-notify
    STATUS current
    DESCRIPTION
        "Parameter 'port' in event NBS.49"
    ::= { nbsEventObjects49 3 }

nbs49-interface OBJECT-TYPE
    SYNTAX DisplayString
    MAX-ACCESS accessible-for-notify
    STATUS current
    DESCRIPTION
        "Parameter 'interface' in event NBS.49"
    ::= { nbsEventObjects49 4 }


nbsNotification1 NOTIFICATION-TYPE
    OBJECTS { 
              nbs1-source-nbname, 
              nbs1-source-macaddr,
              nbs1-dest-nbname,
              nbs1-dest-macaddr 
            }
    STATUS current
    DESCRIPTION
        "Notification of Event NBS.1

        Message: 'NetBIOS Add-Name-Query received from bridge for source name(MAC) $1($2) -> target name(MAC) $3($4)'

        Parameters list:
              $1: nbs1-source-nbname
              $2: nbs1-source-macaddr
              $3: nbs1-dest-nbname
              $4: nbs1-dest-macaddr

        The NetBIOS software received a NetBIOS Add-Name-Query frame
        from the bridged network."
    ::= { nbsNotificationsPrefix 1 }

nbsNotification2 NOTIFICATION-TYPE
    OBJECTS { 
              nbs2-source-nbname, 
              nbs2-source-macaddr,
              nbs2-dest-nbname,
              nbs2-dest-macaddr 
            }
    STATUS current
    DESCRIPTION
        "Notification of Event NBS.2

        Message: 'NetBIOS Add-Group-Name-Query received from bridge for source name(MAC) $1($2) -> target name(MAC) $3($4)'

        Parameters list:
              $1: nbs2-source-nbname
              $2: nbs2-source-macaddr
              $3: nbs2-dest-nbname
              $4: nbs2-dest-macaddr

        The NetBIOS software received a NetBIOS Add-Group-Name-Query frame
        from the bridged network."
    ::= { nbsNotificationsPrefix 2 }

nbsNotification3 NOTIFICATION-TYPE
    OBJECTS { 
              nbs3-source-nbname, 
              nbs3-source-macaddr,
              nbs3-dest-nbname,
              nbs3-dest-macaddr 
            }
    STATUS current
    DESCRIPTION
        "Notification of Event NBS.3

        Message: 'NetBIOS Add-Name-Response received from bridge for source name(MAC) $1($2) -> target name(MAC) $3($4)'

        Parameters list:
              $1: nbs3-source-nbname
              $2: nbs3-source-macaddr
              $3: nbs3-dest-nbname
              $4: nbs3-dest-macaddr

        The NetBIOS software received a NetBIOS Add-Name-Response frame
        from the bridged network."
    ::= { nbsNotificationsPrefix 3 }

nbsNotification4 NOTIFICATION-TYPE
    OBJECTS { 
              nbs4-source-nbname, 
              nbs4-source-macaddr,
              nbs4-dest-nbname,
              nbs4-dest-macaddr 
            }
    STATUS current
    DESCRIPTION
        "Notification of Event NBS.4

        Message: 'NetBIOS Name-Query received from bridge for source name(MAC) $1($2) -> target name(MAC) $3($4)'

        Parameters list:
              $1: nbs4-source-nbname
              $2: nbs4-source-macaddr
              $3: nbs4-dest-nbname
              $4: nbs4-dest-macaddr

        The NetBIOS software received a NetBIOS Name-Query frame
        from the bridged network."
    ::= { nbsNotificationsPrefix 4 }

nbsNotification5 NOTIFICATION-TYPE
    OBJECTS { 
              nbs5-source-nbname, 
              nbs5-source-macaddr,
              nbs5-dest-nbname,
              nbs5-dest-macaddr 
            }
    STATUS current
    DESCRIPTION
        "Notification of Event NBS.5

        Message: 'NetBIOS Name-Recognized received from bridge for source name(MAC) $1($2) -> target name(MAC) $3($4)'

        Parameters list:
              $1: nbs5-source-nbname
              $2: nbs5-source-macaddr
              $3: nbs5-dest-nbname
              $4: nbs5-dest-macaddr

        The NetBIOS software received a NetBIOS Name-Recognized frame
        from the bridged network."
    ::= { nbsNotificationsPrefix 5 }

nbsNotification6 NOTIFICATION-TYPE
    OBJECTS { 
              nbs6-source-nbname, 
              nbs6-source-macaddr,
              nbs6-dest-nbname,
              nbs6-dest-macaddr 
            }
    STATUS current
    DESCRIPTION
        "Notification of Event NBS.6

        Message: 'NetBIOS Name-In-Conflict received from bridge for source name(MAC) $1($2) -> target name(MAC) $3($4)'

        Parameters list:
              $1: nbs6-source-nbname
              $2: nbs6-source-macaddr
              $3: nbs6-dest-nbname
              $4: nbs6-dest-macaddr

        The NetBIOS software received a NetBIOS Name-In-Conflict frame
        from the bridged network."
    ::= { nbsNotificationsPrefix 6 }

nbsNotification7 NOTIFICATION-TYPE
    OBJECTS { 
              nbs7-source-nbname, 
              nbs7-source-macaddr,
              nbs7-dest-nbname,
              nbs7-dest-macaddr 
            }
    STATUS current
    DESCRIPTION
        "Notification of Event NBS.7

        Message: 'NetBIOS Status-Query received from bridge for source name(MAC) $1($2) -> target name(MAC) $3($4)'

        Parameters list:
              $1: nbs7-source-nbname
              $2: nbs7-source-macaddr
              $3: nbs7-dest-nbname
              $4: nbs7-dest-macaddr

        The NetBIOS software received a NetBIOS Status-Query frame
        from the bridged network."
    ::= { nbsNotificationsPrefix 7 }

nbsNotification8 NOTIFICATION-TYPE
    OBJECTS { 
              nbs8-source-nbname, 
              nbs8-source-macaddr,
              nbs8-dest-nbname,
              nbs8-dest-macaddr 
            }
    STATUS current
    DESCRIPTION
        "Notification of Event NBS.8

        Message: 'NetBIOS Status-Response received from bridge for source name(MAC) $1($2) -> target name(MAC) $3($4)'

        Parameters list:
              $1: nbs8-source-nbname
              $2: nbs8-source-macaddr
              $3: nbs8-dest-nbname
              $4: nbs8-dest-macaddr

        The NetBIOS software received a NetBIOS Status-Response frame
        from the bridged network."
    ::= { nbsNotificationsPrefix 8 }

nbsNotification9 NOTIFICATION-TYPE
    OBJECTS { 
              nbs9-source-nbname, 
              nbs9-source-macaddr,
              nbs9-dest-nbname,
              nbs9-dest-macaddr 
            }
    STATUS current
    DESCRIPTION
        "Notification of Event NBS.9

        Message: 'NetBIOS Datagram received from bridge for source name(MAC) $1($2) -> target name(MAC) $3($4)'

        Parameters list:
              $1: nbs9-source-nbname
              $2: nbs9-source-macaddr
              $3: nbs9-dest-nbname
              $4: nbs9-dest-macaddr

        The NetBIOS software received a NetBIOS Datagram
        frame from the bridged network."
    ::= { nbsNotificationsPrefix 9 }

nbsNotification10 NOTIFICATION-TYPE
    OBJECTS { 
              nbs10-source-nbname, 
              nbs10-source-macaddr,
              nbs10-dest-nbname,
              nbs10-dest-macaddr 
            }
    STATUS current
    DESCRIPTION
        "Notification of Event NBS.10

        Message: 'NetBIOS Datagram-Broadcast received from bridge for source name(MAC) $1($2) -> target name(MAC) $3($4)'

        Parameters list:
              $1: nbs10-source-nbname
              $2: nbs10-source-macaddr
              $3: nbs10-dest-nbname
              $4: nbs10-dest-macaddr

        The NetBIOS software received a NetBIOS Datagram-Broadcast frame
        from the bridged network."
    ::= { nbsNotificationsPrefix 10 }

nbsNotification11 NOTIFICATION-TYPE
    OBJECTS { 
              nbs11-source-nbname, 
              nbs11-source-macaddr,
              nbs11-dest-nbname,
              nbs11-dest-macaddr 
            }
    STATUS current
    DESCRIPTION
        "Notification of Event NBS.11

        Message: 'NetBIOS Terminate-Trace-07 received from bridge for source name(MAC) $1($2) -> target name(MAC) $3($4)'

        Parameters list:
              $1: nbs11-source-nbname
              $2: nbs11-source-macaddr
              $3: nbs11-dest-nbname
              $4: nbs11-dest-macaddr

        The NetBIOS software received a NetBIOS Terminate-Trace-07 frame
        from the bridged network."
    ::= { nbsNotificationsPrefix 11 }

nbsNotification12 NOTIFICATION-TYPE
    OBJECTS { 
              nbs12-source-nbname, 
              nbs12-source-macaddr,
              nbs12-dest-nbname,
              nbs12-dest-macaddr 
            }
    STATUS current
    DESCRIPTION
        "Notification of Event NBS.12

        Message: 'NetBIOS Terminate-Trace-13 received from bridge for source name(MAC) $1($2) -> target name(MAC) $3($4)'

        Parameters list:
              $1: nbs12-source-nbname
              $2: nbs12-source-macaddr
              $3: nbs12-dest-nbname
              $4: nbs12-dest-macaddr

        The NetBIOS software received a NetBIOS Terminate-Trace-13 frame
        from the bridged network."
    ::= { nbsNotificationsPrefix 12 }

nbsNotification13 NOTIFICATION-TYPE
    OBJECTS { 
              nbs13-source-nbname, 
              nbs13-source-macaddr,
              nbs13-dest-nbname,
              nbs13-dest-macaddr 
            }
    STATUS current
    DESCRIPTION
        "Notification of Event NBS.13

        Message: 'Unrecognized NetBIOS frame received from bridge for source name(MAC) $1($2) -> target name(MAC) $3($4)'

        Parameters list:
              $1: nbs13-source-nbname
              $2: nbs13-source-macaddr
              $3: nbs13-dest-nbname
              $4: nbs13-dest-macaddr

        The NetBIOS software received an unrecognized NetBIOS frame
        from the bridged network."
    ::= { nbsNotificationsPrefix 13 }

nbsNotification14 NOTIFICATION-TYPE
    OBJECTS { 
              nbs14-source-nbname, 
              nbs14-source-macaddr,
              nbs14-dest-nbname,
              nbs14-dest-macaddr 
            }
    STATUS current
    DESCRIPTION
        "Notification of Event NBS.14

        Message: 'NetBIOS Add-Name-Query received from dlsw for source name(MAC) $1($2) -> target name(MAC) $3($4)'

        Parameters list:
              $1: nbs14-source-nbname
              $2: nbs14-source-macaddr
              $3: nbs14-dest-nbname
              $4: nbs14-dest-macaddr

        The NetBIOS software received a NetBIOS Add-Name-Query frame
        from the DLSw network."
    ::= { nbsNotificationsPrefix 14 }

nbsNotification15 NOTIFICATION-TYPE
    OBJECTS { 
              nbs15-source-nbname, 
              nbs15-source-macaddr,
              nbs15-dest-nbname,
              nbs15-dest-macaddr 
            }
    STATUS current
    DESCRIPTION
        "Notification of Event NBS.15

        Message: 'NetBIOS Add-Group-Name-Query received from dlsw for source name(MAC) $1($2) -> target name(MAC) $3($4)'

        Parameters list:
              $1: nbs15-source-nbname
              $2: nbs15-source-macaddr
              $3: nbs15-dest-nbname
              $4: nbs15-dest-macaddr

        The NetBIOS software received a NetBIOS Add-Group-Name-Query frame
        from the DLSw network."
    ::= { nbsNotificationsPrefix 15 }

nbsNotification16 NOTIFICATION-TYPE
    OBJECTS { 
              nbs16-source-nbname, 
              nbs16-source-macaddr,
              nbs16-dest-nbname,
              nbs16-dest-macaddr 
            }
    STATUS current
    DESCRIPTION
        "Notification of Event NBS.16

        Message: 'NetBIOS Add-Name-Response received from dlsw for source name(MAC) $1($2) -> target name(MAC) $3($4)'

        Parameters list:
              $1: nbs16-source-nbname
              $2: nbs16-source-macaddr
              $3: nbs16-dest-nbname
              $4: nbs16-dest-macaddr

        The NetBIOS software received a NetBIOS Add-Name-Response frame
        from the DLSw network."
    ::= { nbsNotificationsPrefix 16 }

nbsNotification17 NOTIFICATION-TYPE
    OBJECTS { 
              nbs17-source-nbname, 
              nbs17-source-macaddr,
              nbs17-dest-nbname,
              nbs17-dest-macaddr 
            }
    STATUS current
    DESCRIPTION
        "Notification of Event NBS.17

        Message: 'NetBIOS Name-Query received from dlsw for source name(MAC) $1($2) -> target name(MAC) $3($4)'

        Parameters list:
              $1: nbs17-source-nbname
              $2: nbs17-source-macaddr
              $3: nbs17-dest-nbname
              $4: nbs17-dest-macaddr

        The NetBIOS software received a NetBIOS Name-Query frame
        from the DLSw network."
    ::= { nbsNotificationsPrefix 17 }

nbsNotification18 NOTIFICATION-TYPE
    OBJECTS { 
              nbs18-source-nbname, 
              nbs18-source-macaddr,
              nbs18-dest-nbname,
              nbs18-dest-macaddr 
            }
    STATUS current
    DESCRIPTION
        "Notification of Event NBS.18

        Message: 'NetBIOS Name-Recognized received from dlsw for source name(MAC) $1($2) -> target name(MAC) $3($4)'

        Parameters list:
              $1: nbs18-source-nbname
              $2: nbs18-source-macaddr
              $3: nbs18-dest-nbname
              $4: nbs18-dest-macaddr

        The NetBIOS software received a NetBIOS Name-Recognized frame
        from the DLSw network."
    ::= { nbsNotificationsPrefix 18 }

nbsNotification19 NOTIFICATION-TYPE
    OBJECTS { 
              nbs19-source-nbname, 
              nbs19-source-macaddr,
              nbs19-dest-nbname,
              nbs19-dest-macaddr 
            }
    STATUS current
    DESCRIPTION
        "Notification of Event NBS.19

        Message: 'NetBIOS Name-In-Conflict received from dlsw for source name(MAC) $1($2) -> target name(MAC) $3($4)'

        Parameters list:
              $1: nbs19-source-nbname
              $2: nbs19-source-macaddr
              $3: nbs19-dest-nbname
              $4: nbs19-dest-macaddr

        The NetBIOS software received a NetBIOS Name-In-Conflict frame
        from the DLSw network."
    ::= { nbsNotificationsPrefix 19 }

nbsNotification20 NOTIFICATION-TYPE
    OBJECTS { 
              nbs20-source-nbname, 
              nbs20-source-macaddr,
              nbs20-dest-nbname,
              nbs20-dest-macaddr 
            }
    STATUS current
    DESCRIPTION
        "Notification of Event NBS.20

        Message: 'NetBIOS Status-Query received from dlsw for source name(MAC) $1($2) -> target name(MAC) $3($4)'

        Parameters list:
              $1: nbs20-source-nbname
              $2: nbs20-source-macaddr
              $3: nbs20-dest-nbname
              $4: nbs20-dest-macaddr

        The NetBIOS software received a NetBIOS Status-Query frame
        from the DLSw network."
    ::= { nbsNotificationsPrefix 20 }

nbsNotification21 NOTIFICATION-TYPE
    OBJECTS { 
              nbs21-source-nbname, 
              nbs21-source-macaddr,
              nbs21-dest-nbname,
              nbs21-dest-macaddr 
            }
    STATUS current
    DESCRIPTION
        "Notification of Event NBS.21

        Message: 'NetBIOS Status-Response received from dlsw for source name(MAC) $1($2) -> target name(MAC) $3($4)'

        Parameters list:
              $1: nbs21-source-nbname
              $2: nbs21-source-macaddr
              $3: nbs21-dest-nbname
              $4: nbs21-dest-macaddr

        The NetBIOS software received a NetBIOS Status-Response frame
        from the DLSw network."
    ::= { nbsNotificationsPrefix 21 }

nbsNotification22 NOTIFICATION-TYPE
    OBJECTS { 
              nbs22-source-nbname, 
              nbs22-source-macaddr,
              nbs22-dest-nbname,
              nbs22-dest-macaddr 
            }
    STATUS current
    DESCRIPTION
        "Notification of Event NBS.22

        Message: 'NetBIOS Datagram received from dlsw for source name(MAC) $1($2) -> target name(MAC) $3($4)'

        Parameters list:
              $1: nbs22-source-nbname
              $2: nbs22-source-macaddr
              $3: nbs22-dest-nbname
              $4: nbs22-dest-macaddr

        The NetBIOS software received a NetBIOS Datagram frame
        from the DLSw network."
    ::= { nbsNotificationsPrefix 22 }

nbsNotification23 NOTIFICATION-TYPE
    OBJECTS { 
              nbs23-source-nbname, 
              nbs23-source-macaddr,
              nbs23-dest-nbname,
              nbs23-dest-macaddr 
            }
    STATUS current
    DESCRIPTION
        "Notification of Event NBS.23

        Message: 'NetBIOS Datagram-Broadcast received from dlsw for source name(MAC) $1($2) -> target name(MAC) $3($4)'

        Parameters list:
              $1: nbs23-source-nbname
              $2: nbs23-source-macaddr
              $3: nbs23-dest-nbname
              $4: nbs23-dest-macaddr

        The NetBIOS software received a NetBIOS Datagram-Broadcast frame
        from the DLSw network."
    ::= { nbsNotificationsPrefix 23 }

nbsNotification24 NOTIFICATION-TYPE
    OBJECTS { 
              nbs24-source-nbname, 
              nbs24-source-macaddr,
              nbs24-dest-nbname,
              nbs24-dest-macaddr 
            }
    STATUS current
    DESCRIPTION
        "Notification of Event NBS.24

        Message: 'NetBIOS Terminate-Trace-07 received from dlsw for source name(MAC) $1($2) -> target name(MAC) $3($4)'

        Parameters list:
              $1: nbs24-source-nbname
              $2: nbs24-source-macaddr
              $3: nbs24-dest-nbname
              $4: nbs24-dest-macaddr

        The NetBIOS software received a NetBIOS Terminate-Trace-07 frame
        from the DLSw network."
    ::= { nbsNotificationsPrefix 24 }

nbsNotification25 NOTIFICATION-TYPE
    OBJECTS { 
              nbs25-source-nbname, 
              nbs25-source-macaddr,
              nbs25-dest-nbname,
              nbs25-dest-macaddr 
            }
    STATUS current
    DESCRIPTION
        "Notification of Event NBS.25

        Message: 'NetBIOS Terminate-Trace-13 received from dlsw for source name(MAC) $1($2) -> target name(MAC) $3($4)'

        Parameters list:
              $1: nbs25-source-nbname
              $2: nbs25-source-macaddr
              $3: nbs25-dest-nbname
              $4: nbs25-dest-macaddr

        The NetBIOS software received a NetBIOS Terminate-Trace-13 frame
        from the DLSw network."
    ::= { nbsNotificationsPrefix 25 }

nbsNotification26 NOTIFICATION-TYPE
    OBJECTS { 
              nbs26-source-nbname, 
              nbs26-source-macaddr,
              nbs26-dest-nbname,
              nbs26-dest-macaddr 
            }
    STATUS current
    DESCRIPTION
        "Notification of Event NBS.26

        Message: 'Unrecognized NetBIOS frame received from dlsw for source name(MAC) $1($2) -> target name(MAC) $3($4)'

        Parameters list:
              $1: nbs26-source-nbname
              $2: nbs26-source-macaddr
              $3: nbs26-dest-nbname
              $4: nbs26-dest-macaddr

        The NetBIOS software received an unrecognized NetBIOS frame
        from the DLSw network."
    ::= { nbsNotificationsPrefix 26 }

nbsNotification27 NOTIFICATION-TYPE
    OBJECTS { 
              nbs27-source-nbname, 
              nbs27-dest-nbname 
            }
    STATUS current
    DESCRIPTION
        "Notification of Event NBS.27

        Message: 'NetBIOS frame for source name $1 -> dest name $2 not forwarded to bridge due to frame type filter'

        Parameters list:
              $1: nbs27-source-nbname
              $2: nbs27-dest-nbname

        The NetBIOS software bridge frame type filter did not forward the given
        NetBIOS frame to the bridged network. It was filtered by
        the NetBIOS support bridge frame type filter."
    ::= { nbsNotificationsPrefix 27 }

nbsNotification28 NOTIFICATION-TYPE
    OBJECTS { 
              nbs28-source-nbname, 
              nbs28-dest-nbname 
            }
    STATUS current
    DESCRIPTION
        "Notification of Event NBS.28

        Message: 'NetBIOS frame for source name $1 -> dest name $2 not forwarded to DLSw due to frame type filter'

        Parameters list:
              $1: nbs28-source-nbname
              $2: nbs28-dest-nbname

        The router did not forward the given NetBIOS frame to the DLSw network
        because it was filtered by the NetBIOS support DLSw frame type filter."
    ::= { nbsNotificationsPrefix 28 }

nbsNotification29 NOTIFICATION-TYPE
    OBJECTS { 
              nbs29-source-nbname, 
              nbs29-dest-nbname 
            }
    STATUS current
    DESCRIPTION
        "Notification of Event NBS.29

        Message: 'NetBIOS frame for source name $1 -> dest name $2 not forwarded to bridge due to no matching name cache entry created'

        Parameters list:
              $1: nbs29-source-nbname
              $2: nbs29-dest-nbname

        The router did not forward the given NetBIOS frame to the bridged
        network because it could not find or create a corresponding name
        cache entry."
    ::= { nbsNotificationsPrefix 29 }

nbsNotification30 NOTIFICATION-TYPE
    OBJECTS { 
              nbs30-source-nbname, 
              nbs30-dest-nbname 
            }
    STATUS current
    DESCRIPTION
        "Notification of Event NBS.30

        Message: 'NetBIOS frame for source name $1 -> dest name $2 not forwarded to dlsw due to no matching name cache entry created'

        Parameters list:
              $1: nbs30-source-nbname
              $2: nbs30-dest-nbname

        The router did not forward the given NetBIOS frame to the DLSw network
        because it could not find or create a corresponding name cache entry."
    ::= { nbsNotificationsPrefix 30 }

nbsNotification31 NOTIFICATION-TYPE
    OBJECTS { 
              nbs31-source-nbname, 
              nbs31-dest-nbname 
            }
    STATUS current
    DESCRIPTION
        "Notification of Event NBS.31

        Message: 'NetBIOS frame for source name $1 -> dest name $2 not forwarded to bridge due to duplicate command frame processing'

        Parameters list:
              $1: nbs31-source-nbname
              $2: nbs31-dest-nbname

        The router did not forward the given NetBIOS frame to the bridged
        network because the router filtered it as a duplicate NetBIOS command
        frame."
    ::= { nbsNotificationsPrefix 31 }

nbsNotification32 NOTIFICATION-TYPE
    OBJECTS { 
              nbs32-source-nbname, 
              nbs32-dest-nbname 
            }
    STATUS current
    DESCRIPTION
        "Notification of Event NBS.32

        Message: 'NetBIOS frame for source name $1 -> dest name $2 not forwarded to dlsw due to duplicate command frame processing'

        Parameters list:
              $1: nbs32-source-nbname
              $2: nbs32-dest-nbname

        The router did not forward the given NetBIOS frame to the DLSw network
        because the router filtered it as a duplicate NetBIOS command frame."
    ::= { nbsNotificationsPrefix 32 }

nbsNotification33 NOTIFICATION-TYPE
    OBJECTS { 
              nbs33-source-nbname, 
              nbs33-dest-nbname 
            }
    STATUS current
    DESCRIPTION
        "Notification of Event NBS.33

        Message: 'NetBIOS frame for source name $1 -> dest name $2 not forwarded to bridge due to no command matching this response'

        Parameters list:
              $1: nbs33-source-nbname
              $2: nbs33-dest-nbname

        The router did not forward the given NetBIOS frame to the bridged
        network because the router could not find a command frame matching
        this response frame."
    ::= { nbsNotificationsPrefix 33 }

nbsNotification34 NOTIFICATION-TYPE
    OBJECTS { 
              nbs34-source-nbname, 
              nbs34-dest-nbname 
            }
    STATUS current
    DESCRIPTION
        "Notification of Event NBS.34

        Message: 'NetBIOS frame for source name $1 -> dest name $2 not forwarded to dlsw due to no command matching this response'

        Parameters list:
              $1: nbs34-source-nbname
              $2: nbs34-dest-nbname

        The router did not forward the given NetBIOS frame to the DLSw network
        because the router could not find a command frame matching this
        response frame."
    ::= { nbsNotificationsPrefix 34 }

nbsNotification35 NOTIFICATION-TYPE
    OBJECTS { 
              nbs35-source-nbname, 
              nbs35-dest-nbname 
            }
    STATUS current
    DESCRIPTION
        "Notification of Event NBS.35

        Message: 'NetBIOS frame for source name $1 -> dest name $2 not forwarded to bridge due to name cache processing checks'

        Parameters list:
              $1: nbs35-source-nbname
              $2: nbs35-dest-nbname

        The router did not forward the given NetBIOS frame to the bridged
        network because the name cache processing indicated the router should
        not forward it."
    ::= { nbsNotificationsPrefix 35 }

nbsNotification36 NOTIFICATION-TYPE
    OBJECTS { 
              nbs36-source-nbname, 
              nbs36-dest-nbname 
            }
    STATUS current
    DESCRIPTION
        "Notification of Event NBS.36

        Message: 'NetBIOS frame for source name $1 -> dest name $2 not forwarded to dlsw due to name cache processing checks'

        Parameters list:
              $1: nbs36-source-nbname
              $2: nbs36-dest-nbname

        The router did not forward the given NetBIOS frame to the DLSw network
        because the name cache processing indicated the router should not
        forward it."
    ::= { nbsNotificationsPrefix 36 }

nbsNotification37 NOTIFICATION-TYPE
    OBJECTS { 
              nbs37-source-nbname, 
              nbs37-dest-nbname 
            }
    STATUS current
    DESCRIPTION
        "Notification of Event NBS.37

        Message: 'NetBIOS frame for source name $1 -> dest name $2 not forwarded to bridge due to other processing checks'

        Parameters list:
              $1: nbs37-source-nbname
              $2: nbs37-dest-nbname

        The router did not forward the given NetBIOS frame to the bridged
        network because the processing indicated the router should not
        forward it."
    ::= { nbsNotificationsPrefix 37 }

nbsNotification38 NOTIFICATION-TYPE
    OBJECTS { 
              nbs38-source-nbname, 
              nbs38-dest-nbname 
            }
    STATUS current
    DESCRIPTION
        "Notification of Event NBS.38

        Message: 'NetBIOS frame for source name $1 -> dest name $2 not forwarded to dlsw due to other processing checks'

        Parameters list:
              $1: nbs38-source-nbname
              $2: nbs38-dest-nbname

        The router did not forward the given NetBIOS frame to the DLSw network
        because processing indicated the router should not forward it."
    ::= { nbsNotificationsPrefix 38 }

nbsNotification39 NOTIFICATION-TYPE
    OBJECTS { 
              nbs39-source-nbname, 
              nbs39-source-macaddr,
              nbs39-rif 
            }
    STATUS current
    DESCRIPTION
        "Notification of Event NBS.39

        Message: 'Learning new NetBIOS name to MAC address and RIF association for NetBIOSname $1 to MAC $2 / RIF $3'

        Parameters list:
              $1: nbs39-source-nbname
              $2: nbs39-source-macaddr
              $3: nbs39-rif

        The NetBIOS software is associating a MAC address and RIF with
        a NetBIOS name. Find this association on NetBIOS Name-Querys,
        Name-Recognizeds, and Datagrams."
    ::= { nbsNotificationsPrefix 39 }

nbsNotification40 NOTIFICATION-TYPE
    OBJECTS { 
              nbs40-dest-nbname, 
              nbs40-dest-macaddr,
              nbs40-rif 
            }
    STATUS current
    DESCRIPTION
        "Notification of Event NBS.40

        Message: 'NetBIOS frame for destination name $1 was modified with the new MAC ($2) and RIF ($3)'

        Parameters list:
              $1: nbs40-dest-nbname
              $2: nbs40-dest-macaddr
              $3: nbs40-rif

        The router modified a NetBIOS frame to be forwarded to the bridged
        network by using the cached MAC address and routing information (if
        available). This modification takes place on NetBIOS Name-Querys,
        Status-Querys, and Datagrams."
    ::= { nbsNotificationsPrefix 40 }

nbsNotification41 NOTIFICATION-TYPE
    OBJECTS { 
              nbs41-nbname 
            }
    STATUS current
    DESCRIPTION
        "Notification of Event NBS.41

        Message: 'NetBIOS name cache entry created for NetBIOS name $1'

        Parameters list:
              $1: nbs41-nbname

        The routed created a new NetBIOS name cache entry. This typically
        occurs on NetBIOS Name-Querys, Status-Querys, Add-Name-Querys,
        Add-Group-Name-Querys, and Datagrams."
    ::= { nbsNotificationsPrefix 41 }

nbsNotification42 NOTIFICATION-TYPE
    OBJECTS { 
              nbs42-nbname 
            }
    STATUS current
    DESCRIPTION
        "Notification of Event NBS.42

        Message: 'NetBIOS command/response entry created for NetBIOS name $1'

        Parameters list:
              $1: nbs42-nbname

        The router created a new NetBIOS command/response entry. This typically
        occurs on NetBIOS Name-Querys, Status-Querys, and Datagrams."
    ::= { nbsNotificationsPrefix 42 }

nbsNotification43 NOTIFICATION-TYPE
    OBJECTS { 
              nbs43-reason, 
              nbs43-nbname 
            }
    STATUS current
    DESCRIPTION
        "Notification of Event NBS.43

        Message: 'NetBIOS name cache entry validation error occurred (reason $1) for NetBIOS name $2'

        Parameters list:
              $1: nbs43-reason
              $2: nbs43-nbname

        A validation of the name cache entry indicated that the entry is
        invalid. That is, certain fields contain invalid values or invalid
        combinations of values. The possible reason codes are as follows:
        01 - bad nlist-search / name-type combination;
        02 - bad entry-type / name-type combination;
        03 - bad name-type value."
    ::= { nbsNotificationsPrefix 43 }

nbsNotification44 NOTIFICATION-TYPE
    OBJECTS { 
              nbs44-nbname 
            }
    STATUS current
    DESCRIPTION
        "Notification of Event NBS.44

        Message: 'NetBIOS name cache entry deleted for NetBIOS name $1'

        Parameters list:
              $1: nbs44-nbname

        The router deleted a NetBIOS name cache entry.
        This typically occurs as a result of it aging out."
    ::= { nbsNotificationsPrefix 44 }

nbsNotification45 NOTIFICATION-TYPE
    STATUS current
    DESCRIPTION
        "Notification of Event NBS.45

        Message: 'NetBIOS Support component is active'

        The NetBIOS software has now been activated and initialized."
    ::= { nbsNotificationsPrefix 45 }

nbsNotification46 NOTIFICATION-TYPE
    STATUS current
    DESCRIPTION
        "Notification of Event NBS.46

        Message: 'No memory to allocate a NETBIOS Filter'

        The router will not enable at least one configured NetBIOS filter,
        because there is not enough memory."
    ::= { nbsNotificationsPrefix 46 }

nbsNotification47 NOTIFICATION-TYPE
    OBJECTS { 
              nbs47-input-output, 
              nbs47-port-number 
            }
    STATUS current
    DESCRIPTION
        "Notification of Event NBS.47

        Message: '$1 NETBIOS filter list, for port $2, deleted by user. Filter will not be enabled'

        Parameters list:
              $1: nbs47-input-output
              $2: nbs47-port-number

        You deleted a filter list, that was part of an already
        configured filter. You cannot enable the filter."
    ::= { nbsNotificationsPrefix 47 }

nbsNotification48 NOTIFICATION-TYPE
    OBJECTS { 
              nbs48-input-output, 
              nbs48-port-number 
            }
    STATUS current
    DESCRIPTION
        "Notification of Event NBS.48

        Message: '$1 NETBIOS filter for port $2 is configured, but that port number is not configured'

        Parameters list:
              $1: nbs48-input-output
              $2: nbs48-port-number

        You configured a NetBIOS filter for a particular port, but that
        port number is not configured."
    ::= { nbsNotificationsPrefix 48 }

nbsNotification49 NOTIFICATION-TYPE
    OBJECTS { 
              nbs49-source-mac, 
              nbs49-dest-mac,
              nbs49-port,
              nbs49-interface 
            }
    STATUS current
    DESCRIPTION
        "Notification of Event NBS.49

        Message: 'NETBIOS Output Packet Filtered - $1->$2 , port $3, interface $4'

        Parameters list:
              $1: nbs49-source-mac
              $2: nbs49-dest-mac
              $3: nbs49-port
              $4: nbs49-interface

        A NetBIOS packet has matched the criteria the router specified in a
        NetBIOS filter configuration record. The packet is dropped."
    ::= { nbsNotificationsPrefix 49 }

nbsNotification50 NOTIFICATION-TYPE
    STATUS current
    DESCRIPTION
        "Notification of Event NBS.50

        Message: 'No memory to allocate information for NETBIOS Filter console display'

        The part of the router that handles NetBIOS console display cannot
        allocate enough memory to do the complete display from the T 5 process."
    ::= { nbsNotificationsPrefix 50 }


END
