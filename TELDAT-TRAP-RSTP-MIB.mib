-- file automatically created


TELDAT-TRAP-RSTP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


rstpTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the RSTP event subsystem."
    REVISION "201401200930Z"
    DESCRIPTION "Initial implementation"
        ::= { telEventTraps 196 }


rstpEventsGroup	OBJECT IDENTIFIER	::= { rstpTrapsMIB 1 }

rstpNotifications	OBJECT IDENTIFIER	::= { rstpTrapsMIB 2 }
rstpNotificationsPrefix	OBJECT IDENTIFIER	::= { rstpNotifications 0 }

rstpEventObjects1 OBJECT-IDENTITY
    STATUS current
    DESCRIPTION
        "Event RSTP.1
        Port receive state machine transition."
    ::= { rstpEventsGroup 1 }

rstp1-state-machine OBJECT-TYPE
    SYNTAX DisplayString
    MAX-ACCESS accessible-for-notify
    STATUS current
    DESCRIPTION
        "Parameter 'state-machine' in event RSTP.1"
    ::= { rstpEventObjects1 1 }

rstp1-state OBJECT-TYPE
    SYNTAX DisplayString
    MAX-ACCESS accessible-for-notify
    STATUS current
    DESCRIPTION
        "Parameter 'state' in event RSTP.1"
    ::= { rstpEventObjects1 2 }

rstp1-bridge-id OBJECT-TYPE
    SYNTAX Integer32
    MAX-ACCESS accessible-for-notify
    STATUS current
    DESCRIPTION
        "Parameter 'bridge-id' in event RSTP.1"
    ::= { rstpEventObjects1 3 }

rstp1-bridge-port OBJECT-TYPE
    SYNTAX Integer32
    MAX-ACCESS accessible-for-notify
    STATUS current
    DESCRIPTION
        "Parameter 'bridge-port' in event RSTP.1"
    ::= { rstpEventObjects1 4 }

rstp1-interface OBJECT-TYPE
    SYNTAX DisplayString
    MAX-ACCESS accessible-for-notify
    STATUS current
    DESCRIPTION
        "Parameter 'interface' in event RSTP.1"
    ::= { rstpEventObjects1 5 }

rstp1-circuit-name OBJECT-TYPE
    SYNTAX DisplayString
    MAX-ACCESS accessible-for-notify
    STATUS current
    DESCRIPTION
        "Parameter 'circuit-name' in event RSTP.1"
    ::= { rstpEventObjects1 6 }

rstpEventObjects2 OBJECT-IDENTITY
    STATUS current
    DESCRIPTION
        "Event RSTP.2
        Port protocol migration state machine transition."
    ::= { rstpEventsGroup 2 }

rstp2-state-machine OBJECT-TYPE
    SYNTAX DisplayString
    MAX-ACCESS accessible-for-notify
    STATUS current
    DESCRIPTION
        "Parameter 'state-machine' in event RSTP.2"
    ::= { rstpEventObjects2 1 }

rstp2-state OBJECT-TYPE
    SYNTAX DisplayString
    MAX-ACCESS accessible-for-notify
    STATUS current
    DESCRIPTION
        "Parameter 'state' in event RSTP.2"
    ::= { rstpEventObjects2 2 }

rstp2-bridge-id OBJECT-TYPE
    SYNTAX Integer32
    MAX-ACCESS accessible-for-notify
    STATUS current
    DESCRIPTION
        "Parameter 'bridge-id' in event RSTP.2"
    ::= { rstpEventObjects2 3 }

rstp2-bridge-port OBJECT-TYPE
    SYNTAX Integer32
    MAX-ACCESS accessible-for-notify
    STATUS current
    DESCRIPTION
        "Parameter 'bridge-port' in event RSTP.2"
    ::= { rstpEventObjects2 4 }

rstp2-interface OBJECT-TYPE
    SYNTAX DisplayString
    MAX-ACCESS accessible-for-notify
    STATUS current
    DESCRIPTION
        "Parameter 'interface' in event RSTP.2"
    ::= { rstpEventObjects2 5 }

rstp2-circuit-name OBJECT-TYPE
    SYNTAX DisplayString
    MAX-ACCESS accessible-for-notify
    STATUS current
    DESCRIPTION
        "Parameter 'circuit-name' in event RSTP.2"
    ::= { rstpEventObjects2 6 }

rstpEventObjects3 OBJECT-IDENTITY
    STATUS current
    DESCRIPTION
        "Event RSTP.3
        Bridge detection state machine transition."
    ::= { rstpEventsGroup 3 }

rstp3-state-machine OBJECT-TYPE
    SYNTAX DisplayString
    MAX-ACCESS accessible-for-notify
    STATUS current
    DESCRIPTION
        "Parameter 'state-machine' in event RSTP.3"
    ::= { rstpEventObjects3 1 }

rstp3-state OBJECT-TYPE
    SYNTAX DisplayString
    MAX-ACCESS accessible-for-notify
    STATUS current
    DESCRIPTION
        "Parameter 'state' in event RSTP.3"
    ::= { rstpEventObjects3 2 }

rstp3-bridge-id OBJECT-TYPE
    SYNTAX Integer32
    MAX-ACCESS accessible-for-notify
    STATUS current
    DESCRIPTION
        "Parameter 'bridge-id' in event RSTP.3"
    ::= { rstpEventObjects3 3 }

rstp3-bridge-port OBJECT-TYPE
    SYNTAX Integer32
    MAX-ACCESS accessible-for-notify
    STATUS current
    DESCRIPTION
        "Parameter 'bridge-port' in event RSTP.3"
    ::= { rstpEventObjects3 4 }

rstp3-interface OBJECT-TYPE
    SYNTAX DisplayString
    MAX-ACCESS accessible-for-notify
    STATUS current
    DESCRIPTION
        "Parameter 'interface' in event RSTP.3"
    ::= { rstpEventObjects3 5 }

rstp3-circuit-name OBJECT-TYPE
    SYNTAX DisplayString
    MAX-ACCESS accessible-for-notify
    STATUS current
    DESCRIPTION
        "Parameter 'circuit-name' in event RSTP.3"
    ::= { rstpEventObjects3 6 }

rstpEventObjects4 OBJECT-IDENTITY
    STATUS current
    DESCRIPTION
        "Event RSTP.4
        Port transmit state machine transition."
    ::= { rstpEventsGroup 4 }

rstp4-state-machine OBJECT-TYPE
    SYNTAX DisplayString
    MAX-ACCESS accessible-for-notify
    STATUS current
    DESCRIPTION
        "Parameter 'state-machine' in event RSTP.4"
    ::= { rstpEventObjects4 1 }

rstp4-state OBJECT-TYPE
    SYNTAX DisplayString
    MAX-ACCESS accessible-for-notify
    STATUS current
    DESCRIPTION
        "Parameter 'state' in event RSTP.4"
    ::= { rstpEventObjects4 2 }

rstp4-bridge-id OBJECT-TYPE
    SYNTAX Integer32
    MAX-ACCESS accessible-for-notify
    STATUS current
    DESCRIPTION
        "Parameter 'bridge-id' in event RSTP.4"
    ::= { rstpEventObjects4 3 }

rstp4-bridge-port OBJECT-TYPE
    SYNTAX Integer32
    MAX-ACCESS accessible-for-notify
    STATUS current
    DESCRIPTION
        "Parameter 'bridge-port' in event RSTP.4"
    ::= { rstpEventObjects4 4 }

rstp4-interface OBJECT-TYPE
    SYNTAX DisplayString
    MAX-ACCESS accessible-for-notify
    STATUS current
    DESCRIPTION
        "Parameter 'interface' in event RSTP.4"
    ::= { rstpEventObjects4 5 }

rstp4-circuit-name OBJECT-TYPE
    SYNTAX DisplayString
    MAX-ACCESS accessible-for-notify
    STATUS current
    DESCRIPTION
        "Parameter 'circuit-name' in event RSTP.4"
    ::= { rstpEventObjects4 6 }

rstpEventObjects5 OBJECT-IDENTITY
    STATUS current
    DESCRIPTION
        "Event RSTP.5
        Port information state machine transition."
    ::= { rstpEventsGroup 5 }

rstp5-state-machine OBJECT-TYPE
    SYNTAX DisplayString
    MAX-ACCESS accessible-for-notify
    STATUS current
    DESCRIPTION
        "Parameter 'state-machine' in event RSTP.5"
    ::= { rstpEventObjects5 1 }

rstp5-state OBJECT-TYPE
    SYNTAX DisplayString
    MAX-ACCESS accessible-for-notify
    STATUS current
    DESCRIPTION
        "Parameter 'state' in event RSTP.5"
    ::= { rstpEventObjects5 2 }

rstp5-bridge-id OBJECT-TYPE
    SYNTAX Integer32
    MAX-ACCESS accessible-for-notify
    STATUS current
    DESCRIPTION
        "Parameter 'bridge-id' in event RSTP.5"
    ::= { rstpEventObjects5 3 }

rstp5-bridge-port OBJECT-TYPE
    SYNTAX Integer32
    MAX-ACCESS accessible-for-notify
    STATUS current
    DESCRIPTION
        "Parameter 'bridge-port' in event RSTP.5"
    ::= { rstpEventObjects5 4 }

rstp5-interface OBJECT-TYPE
    SYNTAX DisplayString
    MAX-ACCESS accessible-for-notify
    STATUS current
    DESCRIPTION
        "Parameter 'interface' in event RSTP.5"
    ::= { rstpEventObjects5 5 }

rstp5-circuit-name OBJECT-TYPE
    SYNTAX DisplayString
    MAX-ACCESS accessible-for-notify
    STATUS current
    DESCRIPTION
        "Parameter 'circuit-name' in event RSTP.5"
    ::= { rstpEventObjects5 6 }

rstpEventObjects6 OBJECT-IDENTITY
    STATUS current
    DESCRIPTION
        "Event RSTP.6
        Port role selection state machine transition."
    ::= { rstpEventsGroup 6 }

rstp6-state-machine OBJECT-TYPE
    SYNTAX DisplayString
    MAX-ACCESS accessible-for-notify
    STATUS current
    DESCRIPTION
        "Parameter 'state-machine' in event RSTP.6"
    ::= { rstpEventObjects6 1 }

rstp6-state OBJECT-TYPE
    SYNTAX DisplayString
    MAX-ACCESS accessible-for-notify
    STATUS current
    DESCRIPTION
        "Parameter 'state' in event RSTP.6"
    ::= { rstpEventObjects6 2 }

rstp6-bridge-id OBJECT-TYPE
    SYNTAX Integer32
    MAX-ACCESS accessible-for-notify
    STATUS current
    DESCRIPTION
        "Parameter 'bridge-id' in event RSTP.6"
    ::= { rstpEventObjects6 3 }

rstpEventObjects7 OBJECT-IDENTITY
    STATUS current
    DESCRIPTION
        "Event RSTP.7
        Port role transitions state machine transition."
    ::= { rstpEventsGroup 7 }

rstp7-state-machine OBJECT-TYPE
    SYNTAX DisplayString
    MAX-ACCESS accessible-for-notify
    STATUS current
    DESCRIPTION
        "Parameter 'state-machine' in event RSTP.7"
    ::= { rstpEventObjects7 1 }

rstp7-state OBJECT-TYPE
    SYNTAX DisplayString
    MAX-ACCESS accessible-for-notify
    STATUS current
    DESCRIPTION
        "Parameter 'state' in event RSTP.7"
    ::= { rstpEventObjects7 2 }

rstp7-bridge-id OBJECT-TYPE
    SYNTAX Integer32
    MAX-ACCESS accessible-for-notify
    STATUS current
    DESCRIPTION
        "Parameter 'bridge-id' in event RSTP.7"
    ::= { rstpEventObjects7 3 }

rstp7-bridge-port OBJECT-TYPE
    SYNTAX Integer32
    MAX-ACCESS accessible-for-notify
    STATUS current
    DESCRIPTION
        "Parameter 'bridge-port' in event RSTP.7"
    ::= { rstpEventObjects7 4 }

rstp7-interface OBJECT-TYPE
    SYNTAX DisplayString
    MAX-ACCESS accessible-for-notify
    STATUS current
    DESCRIPTION
        "Parameter 'interface' in event RSTP.7"
    ::= { rstpEventObjects7 5 }

rstp7-circuit-name OBJECT-TYPE
    SYNTAX DisplayString
    MAX-ACCESS accessible-for-notify
    STATUS current
    DESCRIPTION
        "Parameter 'circuit-name' in event RSTP.7"
    ::= { rstpEventObjects7 6 }

rstpEventObjects8 OBJECT-IDENTITY
    STATUS current
    DESCRIPTION
        "Event RSTP.8
        Port state transition state machine transition."
    ::= { rstpEventsGroup 8 }

rstp8-state-machine OBJECT-TYPE
    SYNTAX DisplayString
    MAX-ACCESS accessible-for-notify
    STATUS current
    DESCRIPTION
        "Parameter 'state-machine' in event RSTP.8"
    ::= { rstpEventObjects8 1 }

rstp8-state OBJECT-TYPE
    SYNTAX DisplayString
    MAX-ACCESS accessible-for-notify
    STATUS current
    DESCRIPTION
        "Parameter 'state' in event RSTP.8"
    ::= { rstpEventObjects8 2 }

rstp8-bridge-id OBJECT-TYPE
    SYNTAX Integer32
    MAX-ACCESS accessible-for-notify
    STATUS current
    DESCRIPTION
        "Parameter 'bridge-id' in event RSTP.8"
    ::= { rstpEventObjects8 3 }

rstp8-bridge-port OBJECT-TYPE
    SYNTAX Integer32
    MAX-ACCESS accessible-for-notify
    STATUS current
    DESCRIPTION
        "Parameter 'bridge-port' in event RSTP.8"
    ::= { rstpEventObjects8 4 }

rstp8-interface OBJECT-TYPE
    SYNTAX DisplayString
    MAX-ACCESS accessible-for-notify
    STATUS current
    DESCRIPTION
        "Parameter 'interface' in event RSTP.8"
    ::= { rstpEventObjects8 5 }

rstp8-circuit-name OBJECT-TYPE
    SYNTAX DisplayString
    MAX-ACCESS accessible-for-notify
    STATUS current
    DESCRIPTION
        "Parameter 'circuit-name' in event RSTP.8"
    ::= { rstpEventObjects8 6 }

rstpEventObjects9 OBJECT-IDENTITY
    STATUS current
    DESCRIPTION
        "Event RSTP.9
        Topology change state machine transition."
    ::= { rstpEventsGroup 9 }

rstp9-state-machine OBJECT-TYPE
    SYNTAX DisplayString
    MAX-ACCESS accessible-for-notify
    STATUS current
    DESCRIPTION
        "Parameter 'state-machine' in event RSTP.9"
    ::= { rstpEventObjects9 1 }

rstp9-state OBJECT-TYPE
    SYNTAX DisplayString
    MAX-ACCESS accessible-for-notify
    STATUS current
    DESCRIPTION
        "Parameter 'state' in event RSTP.9"
    ::= { rstpEventObjects9 2 }

rstp9-bridge-id OBJECT-TYPE
    SYNTAX Integer32
    MAX-ACCESS accessible-for-notify
    STATUS current
    DESCRIPTION
        "Parameter 'bridge-id' in event RSTP.9"
    ::= { rstpEventObjects9 3 }

rstp9-bridge-port OBJECT-TYPE
    SYNTAX Integer32
    MAX-ACCESS accessible-for-notify
    STATUS current
    DESCRIPTION
        "Parameter 'bridge-port' in event RSTP.9"
    ::= { rstpEventObjects9 4 }

rstp9-interface OBJECT-TYPE
    SYNTAX DisplayString
    MAX-ACCESS accessible-for-notify
    STATUS current
    DESCRIPTION
        "Parameter 'interface' in event RSTP.9"
    ::= { rstpEventObjects9 5 }

rstp9-circuit-name OBJECT-TYPE
    SYNTAX DisplayString
    MAX-ACCESS accessible-for-notify
    STATUS current
    DESCRIPTION
        "Parameter 'circuit-name' in event RSTP.9"
    ::= { rstpEventObjects9 6 }

rstpEventObjects10 OBJECT-IDENTITY
    STATUS current
    DESCRIPTION
        "Event RSTP.10
        Generic informational event."
    ::= { rstpEventsGroup 10 }

rstp10-string OBJECT-TYPE
    SYNTAX DisplayString
    MAX-ACCESS accessible-for-notify
    STATUS current
    DESCRIPTION
        "Parameter 'string' in event RSTP.10"
    ::= { rstpEventObjects10 1 }


rstpNotification1 NOTIFICATION-TYPE
    OBJECTS { 
              rstp1-state-machine, 
              rstp1-state,
              rstp1-bridge-id,
              rstp1-bridge-port,
              rstp1-interface,
              rstp1-circuit-name 
            }
    STATUS current
    DESCRIPTION
        "Notification of Event RSTP.1

        Message: 'State Machine $1 entered state $2, bridge $3, port $4, ifc $5$6'

        Parameters list:
              $1: rstp1-state-machine
              $2: rstp1-state
              $3: rstp1-bridge-id
              $4: rstp1-bridge-port
              $5: rstp1-interface
              $6: rstp1-circuit-name

        Port receive state machine transition."
    ::= { rstpNotificationsPrefix 1 }

rstpNotification2 NOTIFICATION-TYPE
    OBJECTS { 
              rstp2-state-machine, 
              rstp2-state,
              rstp2-bridge-id,
              rstp2-bridge-port,
              rstp2-interface,
              rstp2-circuit-name 
            }
    STATUS current
    DESCRIPTION
        "Notification of Event RSTP.2

        Message: 'State Machine $1 entered state $2, bridge $3, port $4, ifc $5$6'

        Parameters list:
              $1: rstp2-state-machine
              $2: rstp2-state
              $3: rstp2-bridge-id
              $4: rstp2-bridge-port
              $5: rstp2-interface
              $6: rstp2-circuit-name

        Port protocol migration state machine transition."
    ::= { rstpNotificationsPrefix 2 }

rstpNotification3 NOTIFICATION-TYPE
    OBJECTS { 
              rstp3-state-machine, 
              rstp3-state,
              rstp3-bridge-id,
              rstp3-bridge-port,
              rstp3-interface,
              rstp3-circuit-name 
            }
    STATUS current
    DESCRIPTION
        "Notification of Event RSTP.3

        Message: 'State Machine $1 entered state $2, bridge $3, port $4, ifc $5$6'

        Parameters list:
              $1: rstp3-state-machine
              $2: rstp3-state
              $3: rstp3-bridge-id
              $4: rstp3-bridge-port
              $5: rstp3-interface
              $6: rstp3-circuit-name

        Bridge detection state machine transition."
    ::= { rstpNotificationsPrefix 3 }

rstpNotification4 NOTIFICATION-TYPE
    OBJECTS { 
              rstp4-state-machine, 
              rstp4-state,
              rstp4-bridge-id,
              rstp4-bridge-port,
              rstp4-interface,
              rstp4-circuit-name 
            }
    STATUS current
    DESCRIPTION
        "Notification of Event RSTP.4

        Message: 'State Machine $1 entered state $2, bridge $3, port $4, ifc $5$6'

        Parameters list:
              $1: rstp4-state-machine
              $2: rstp4-state
              $3: rstp4-bridge-id
              $4: rstp4-bridge-port
              $5: rstp4-interface
              $6: rstp4-circuit-name

        Port transmit state machine transition."
    ::= { rstpNotificationsPrefix 4 }

rstpNotification5 NOTIFICATION-TYPE
    OBJECTS { 
              rstp5-state-machine, 
              rstp5-state,
              rstp5-bridge-id,
              rstp5-bridge-port,
              rstp5-interface,
              rstp5-circuit-name 
            }
    STATUS current
    DESCRIPTION
        "Notification of Event RSTP.5

        Message: 'State Machine $1 entered state $2, bridge $3, port $4, ifc $5$6'

        Parameters list:
              $1: rstp5-state-machine
              $2: rstp5-state
              $3: rstp5-bridge-id
              $4: rstp5-bridge-port
              $5: rstp5-interface
              $6: rstp5-circuit-name

        Port information state machine transition."
    ::= { rstpNotificationsPrefix 5 }

rstpNotification6 NOTIFICATION-TYPE
    OBJECTS { 
              rstp6-state-machine, 
              rstp6-state,
              rstp6-bridge-id 
            }
    STATUS current
    DESCRIPTION
        "Notification of Event RSTP.6

        Message: 'State Machine $1 entered state $2, bridge $3'

        Parameters list:
              $1: rstp6-state-machine
              $2: rstp6-state
              $3: rstp6-bridge-id

        Port role selection state machine transition."
    ::= { rstpNotificationsPrefix 6 }

rstpNotification7 NOTIFICATION-TYPE
    OBJECTS { 
              rstp7-state-machine, 
              rstp7-state,
              rstp7-bridge-id,
              rstp7-bridge-port,
              rstp7-interface,
              rstp7-circuit-name 
            }
    STATUS current
    DESCRIPTION
        "Notification of Event RSTP.7

        Message: 'State Machine $1 entered state $2, bridge $3, port $4, ifc $5$6'

        Parameters list:
              $1: rstp7-state-machine
              $2: rstp7-state
              $3: rstp7-bridge-id
              $4: rstp7-bridge-port
              $5: rstp7-interface
              $6: rstp7-circuit-name

        Port role transitions state machine transition."
    ::= { rstpNotificationsPrefix 7 }

rstpNotification8 NOTIFICATION-TYPE
    OBJECTS { 
              rstp8-state-machine, 
              rstp8-state,
              rstp8-bridge-id,
              rstp8-bridge-port,
              rstp8-interface,
              rstp8-circuit-name 
            }
    STATUS current
    DESCRIPTION
        "Notification of Event RSTP.8

        Message: 'State Machine $1 entered state $2, bridge $3, port $4, ifc $5$6'

        Parameters list:
              $1: rstp8-state-machine
              $2: rstp8-state
              $3: rstp8-bridge-id
              $4: rstp8-bridge-port
              $5: rstp8-interface
              $6: rstp8-circuit-name

        Port state transition state machine transition."
    ::= { rstpNotificationsPrefix 8 }

rstpNotification9 NOTIFICATION-TYPE
    OBJECTS { 
              rstp9-state-machine, 
              rstp9-state,
              rstp9-bridge-id,
              rstp9-bridge-port,
              rstp9-interface,
              rstp9-circuit-name 
            }
    STATUS current
    DESCRIPTION
        "Notification of Event RSTP.9

        Message: 'State Machine $1 entered state $2, bridge $3, port $4, ifc $5$6'

        Parameters list:
              $1: rstp9-state-machine
              $2: rstp9-state
              $3: rstp9-bridge-id
              $4: rstp9-bridge-port
              $5: rstp9-interface
              $6: rstp9-circuit-name

        Topology change state machine transition."
    ::= { rstpNotificationsPrefix 9 }

rstpNotification10 NOTIFICATION-TYPE
    OBJECTS { 
              rstp10-string 
            }
    STATUS current
    DESCRIPTION
        "Notification of Event RSTP.10

        Message: '$1'

        Parameters list:
              $1: rstp10-string

        Generic informational event."
    ::= { rstpNotificationsPrefix 10 }


END
