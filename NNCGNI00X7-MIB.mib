-- @(#)GenericDevice.mib	9.1 10/16/98
--------------------------------------------------------------------------------
-- file: GenericDevice.mib
--
-- contents:
--	This file contains the Newbridge MIB extensions for a generic device
--	class.
--
-- history:
--	0.1 / 92.08.25 / J. Watt / Creation
--	0.2 / 93.04.26 / G. Celmainis / Added nncExtDevConnectedToUIName
--
-- Copyright 1992-1993 Newbridge Networks Corporation.  All Rights Reserved.
--------------------------------------------------------------------------------
NNCGNI00X7-MIB	DEFINITIONS ::= BEGIN


	IMPORTS
		nncExtDevice
			FROM NNCGNI00X1-SMI

		PositionIndex
			FROM NNCGNI00X4-MIB
			
		DisplayString
			FROM RFC1213-MIB
			
		OBJECT-TYPE
			FROM RFC-1212;
			
	
--	
--	Modules can have one (e.g. SDM, T1) or many (e.g. Repeater) ports
--	Each port can have associated with it one (e.g. SDM, Repeater) or
--	many (e.g. T1) circuits.
--
	PortIndex	::= INTEGER (1..12)
	CircuitIndex	::= INTEGER (1..33)
	
	
--	
--	Loopbacks supported are device-type dependant
--
	LoopbackType	::= INTEGER {
				 	devNoLoopback(1),
				 	devLoopbackA(2),
				 	devLoopbackB(3),
				 	devLoopBackC(4),
				 	devChannelLoopback(5),
				 	devDDSOCULoopback(6),
				 	devDDSDSULoopback(7),
				 	devDDSLatchOCULoopback(8),
				 	devDDSLatchCSULoopback(9),
					devDDSLatchDSOLoopback(10),
					devDDSLatchHL96Loopback(11),
					devDDSMJULoopback(12),
					devDD-BlkLoopback(13)
				     }
				     
--
--	Signalling bits are defined on a per device-type basis.  There
--	are never more than 16 bits of signalling.
--
	SignallingBits	::= INTEGER (0..65535)
	

	nncExtDeviceTable	OBJECT-TYPE
		SYNTAX	SEQUENCE OF NncExtDeviceEntry
		ACCESS	not-accessible
		STATUS	mandatory
		DESCRIPTION
			"Configuration information for the Rptr modules
			 in the system"
		::= { nncExtDevice 1 }
		
	
	nncExtDeviceEntry	OBJECT-TYPE
		SYNTAX	NncExtDeviceEntry
		ACCESS	not-accessible
		STATUS	mandatory
		DESCRIPTION
			"Configuration and status module for a device"
		INDEX { nncExtDevPosnIdx, nncExtDevPortIdx, nncExtDevCctIdx }
		::= { nncExtDeviceTable 1 }
		
		
	NncExtDeviceEntry 
		::= SEQUENCE {
			nncExtDevPosnIdx
				PositionIndex,
			nncExtDevPortIdx
				PortIndex,
			nncExtDevCctIdx
				CircuitIndex,
			nncExtDevName
				DisplayString,
			nncExtDevLoopback
				LoopbackType,
			nncExtDevCallStatus
				INTEGER,
			nncExtDevBusyOut
				INTEGER,
			nncExtDevOutputSignalling
				SignallingBits,
			nncExtDevInputSignalling
				SignallingBits,
			nncExtDevConnectedTo
				OCTET STRING,
			nncExtDevUIName
				DisplayString,
			nncExtDevUIType
				DisplayString,
			nncExtDevConnectedToUIName
				DisplayString			
			}
		
	nncExtDevPosnIdx	OBJECT-TYPE
		SYNTAX	PositionIndex
		ACCESS	read-only
		STATUS	mandatory
DESCRIPTION ""

		::= { nncExtDeviceEntry 1 }


	nncExtDevPortIdx	OBJECT-TYPE
		SYNTAX	PortIndex
		ACCESS	read-only
		STATUS	mandatory
DESCRIPTION ""

		::= { nncExtDeviceEntry 2 }
		
	
	nncExtDevCctIdx	OBJECT-TYPE
		SYNTAX	CircuitIndex
		ACCESS	read-only
		STATUS	mandatory
DESCRIPTION ""

		::= { nncExtDeviceEntry 3 }


	nncExtDevName	OBJECT-TYPE
		SYNTAX	DisplayString (SIZE(1..8))
		ACCESS	read-write
		STATUS	mandatory
DESCRIPTION ""

		::= { nncExtDeviceEntry 4 }
		
		
	nncExtDevLoopback	OBJECT-TYPE
		SYNTAX	INTEGER {
				 	devNoLoopback(1),
				 	devLoopbackA(2),
				 	devLoopbackB(3),
				 	devLoopBackC(4),
				 	devChannelLoopback(5),
				 	devDDSOCULoopback(6),
				 	devDDSDSULoopback(7),
				 	devDDSLatchOCULoopback(8),
				 	devDDSLatchCSULoopback(9),
					devDDSLatchDSOLoopback(10),
					devDDSLatchHL96Loopback(11),
					devDDSMJULoopback(12),
					devDD-BlkLoopback(13)
				     }
		ACCESS	read-write
		STATUS	mandatory
DESCRIPTION ""

		::= { nncExtDeviceEntry 5 }


	nncExtDevCallStatus	OBJECT-TYPE
		SYNTAX	INTEGER (0..255)
		ACCESS	read-only
		STATUS	mandatory
DESCRIPTION ""

		::= { nncExtDeviceEntry 6 }


	nncExtDevBusyOut	OBJECT-TYPE
		SYNTAX	INTEGER { enable(1), disable(2) }
		ACCESS	read-write
		STATUS	mandatory
DESCRIPTION ""

		::= { nncExtDeviceEntry 7 }
		
		
	nncExtDevOutputSignalling	OBJECT-TYPE
		SYNTAX	SignallingBits
		ACCESS	read-write
		STATUS	mandatory
DESCRIPTION ""

		::= { nncExtDeviceEntry 8 }

			 
	nncExtDevInputSignalling	OBJECT-TYPE
		SYNTAX	SignallingBits
		ACCESS	read-only
		STATUS	mandatory
DESCRIPTION ""

		::= { nncExtDeviceEntry 9 }
		
		
	nncExtDevConnectedTo	OBJECT-TYPE
		SYNTAX	OCTET STRING (SIZE(3..3))
		ACCESS	read-write
		STATUS	mandatory
DESCRIPTION ""

		::= { nncExtDeviceEntry 10 }
		
	
	nncExtDevUIName	OBJECT-TYPE
		SYNTAX	DisplayString (SIZE(3..6))
		ACCESS	read-only
		STATUS	mandatory
DESCRIPTION ""

		::= { nncExtDeviceEntry 11 }
	
	
	nncExtDevUIType	OBJECT-TYPE
		SYNTAX	DisplayString (SIZE(2..12))
		ACCESS	read-only
		STATUS	mandatory
DESCRIPTION ""

		::= { nncExtDeviceEntry 12 }


	nncExtDevConnectedToUIName	OBJECT-TYPE
		SYNTAX	DisplayString (SIZE(3..6))
		ACCESS	read-only
		STATUS	mandatory
DESCRIPTION ""

		::= { nncExtDeviceEntry 13 }
	END
