-- file automatically created


TELDAT-TRAP-PPP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


pppTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the PPP event subsystem."
    REVISION "201401200930Z"
    DESCRIPTION "Initial implementation"
        ::= { telEventTraps 95 }


pppEventsGroup	OBJECT IDENTIFIER	::= { pppTrapsMIB 1 }

pppNotifications	OBJECT IDENTIFIER	::= { pppTrapsMIB 2 }
pppNotificationsPrefix	OBJECT IDENTIFIER	::= { pppNotifications 0 }

pppEventObjects1 OBJECT-IDENTITY
    STATUS current
    DESCRIPTION
        "Event PPP.1
        Selftest successfully completed."
    ::= { pppEventsGroup 1 }

ppp1-interface OBJECT-TYPE
    SYNTAX DisplayString
    MAX-ACCESS accessible-for-notify
    STATUS current
    DESCRIPTION
        "Parameter 'interface' in event PPP.1"
    ::= { pppEventObjects1 1 }

pppEventObjects2 OBJECT-IDENTITY
    STATUS current
    DESCRIPTION
        "Event PPP.2
        The selftest indicates that the base interfaces are all down."
    ::= { pppEventsGroup 2 }

ppp2-interface OBJECT-TYPE
    SYNTAX DisplayString
    MAX-ACCESS accessible-for-notify
    STATUS current
    DESCRIPTION
        "Parameter 'interface' in event PPP.2"
    ::= { pppEventObjects2 1 }

pppEventObjects3 OBJECT-IDENTITY
    STATUS current
    DESCRIPTION
        "Event PPP.3
        The MRU has been exceeded in an incoming packet in the indicated link."
    ::= { pppEventsGroup 3 }

ppp3-linkPPP OBJECT-TYPE
    SYNTAX DisplayString
    MAX-ACCESS accessible-for-notify
    STATUS current
    DESCRIPTION
        "Parameter 'linkPPP' in event PPP.3"
    ::= { pppEventObjects3 1 }

ppp3-size OBJECT-TYPE
    SYNTAX Integer32
    MAX-ACCESS accessible-for-notify
    STATUS current
    DESCRIPTION
        "Parameter 'size' in event PPP.3"
    ::= { pppEventObjects3 2 }

ppp3-MRU OBJECT-TYPE
    SYNTAX Integer32
    MAX-ACCESS accessible-for-notify
    STATUS current
    DESCRIPTION
        "Parameter 'MRU' in event PPP.3"
    ::= { pppEventObjects3 3 }

pppEventObjects4 OBJECT-IDENTITY
    STATUS current
    DESCRIPTION
        "Event PPP.4
        A multilink PPP fragment has been received out-of-order. Queue is flushed
        or link reordered."
    ::= { pppEventsGroup 4 }

ppp4-linkPPP OBJECT-TYPE
    SYNTAX DisplayString
    MAX-ACCESS accessible-for-notify
    STATUS current
    DESCRIPTION
        "Parameter 'linkPPP' in event PPP.4"
    ::= { pppEventObjects4 1 }

ppp4-action OBJECT-TYPE
    SYNTAX DisplayString
    MAX-ACCESS accessible-for-notify
    STATUS current
    DESCRIPTION
        "Parameter 'action' in event PPP.4"
    ::= { pppEventObjects4 2 }

pppEventObjects5 OBJECT-IDENTITY
    STATUS current
    DESCRIPTION
        "Event PPP.5
        Multilink Header Format option description."
    ::= { pppEventsGroup 5 }

ppp5-link-name OBJECT-TYPE
    SYNTAX DisplayString
    MAX-ACCESS accessible-for-notify
    STATUS current
    DESCRIPTION
        "Parameter 'link name' in event PPP.5"
    ::= { pppEventObjects5 1 }

ppp5-sequence OBJECT-TYPE
    SYNTAX DisplayString
    MAX-ACCESS accessible-for-notify
    STATUS current
    DESCRIPTION
        "Parameter 'sequence' in event PPP.5"
    ::= { pppEventObjects5 2 }

ppp5-classes OBJECT-TYPE
    SYNTAX Integer32
    MAX-ACCESS accessible-for-notify
    STATUS current
    DESCRIPTION
        "Parameter 'classes' in event PPP.5"
    ::= { pppEventObjects5 3 }

ppp5-dump OBJECT-TYPE
    SYNTAX DisplayString
    MAX-ACCESS accessible-for-notify
    STATUS current
    DESCRIPTION
        "Parameter 'dump' in event PPP.5"
    ::= { pppEventObjects5 4 }

pppEventObjects6 OBJECT-IDENTITY
    STATUS current
    DESCRIPTION
        "Event PPP.6
        Multiclass Multilink negotiated in the MP bundle."
    ::= { pppEventsGroup 6 }

ppp6-linkPPP OBJECT-TYPE
    SYNTAX DisplayString
    MAX-ACCESS accessible-for-notify
    STATUS current
    DESCRIPTION
        "Parameter 'linkPPP' in event PPP.6"
    ::= { pppEventObjects6 1 }

pppEventObjects7 OBJECT-IDENTITY
    STATUS current
    DESCRIPTION
        "Event PPP.7
        MP Real Time Frame."
    ::= { pppEventsGroup 7 }

ppp7-linkPPP OBJECT-TYPE
    SYNTAX DisplayString
    MAX-ACCESS accessible-for-notify
    STATUS current
    DESCRIPTION
        "Parameter 'linkPPP' in event PPP.7"
    ::= { pppEventObjects7 1 }

pppEventObjects11 OBJECT-IDENTITY
    STATUS current
    DESCRIPTION
        "Event PPP.11
        Received/sent frame from the protocol specified by a PPP interface."
    ::= { pppEventsGroup 11 }

ppp11-linkPPP OBJECT-TYPE
    SYNTAX DisplayString
    MAX-ACCESS accessible-for-notify
    STATUS current
    DESCRIPTION
        "Parameter 'linkPPP' in event PPP.11"
    ::= { pppEventObjects11 1 }

ppp11-receivedIn-or-sentOut OBJECT-TYPE
    SYNTAX DisplayString
    MAX-ACCESS accessible-for-notify
    STATUS current
    DESCRIPTION
        "Parameter 'received(In) or sent(Out)' in event PPP.11"
    ::= { pppEventObjects11 2 }

ppp11-protocol OBJECT-TYPE
    SYNTAX Integer32
    MAX-ACCESS accessible-for-notify
    STATUS current
    DESCRIPTION
        "Parameter 'protocol' in event PPP.11"
    ::= { pppEventObjects11 3 }

ppp11-size OBJECT-TYPE
    SYNTAX Integer32
    MAX-ACCESS accessible-for-notify
    STATUS current
    DESCRIPTION
        "Parameter 'size' in event PPP.11"
    ::= { pppEventObjects11 4 }

pppEventObjects12 OBJECT-IDENTITY
    STATUS current
    DESCRIPTION
        "Event PPP.12
        Frame received with Protocol Field Compression (PFC)."
    ::= { pppEventsGroup 12 }

ppp12-linkPPP OBJECT-TYPE
    SYNTAX DisplayString
    MAX-ACCESS accessible-for-notify
    STATUS current
    DESCRIPTION
        "Parameter 'linkPPP' in event PPP.12"
    ::= { pppEventObjects12 1 }

ppp12-receivedIn-or-sentOut OBJECT-TYPE
    SYNTAX DisplayString
    MAX-ACCESS accessible-for-notify
    STATUS current
    DESCRIPTION
        "Parameter 'received(In) or sent(Out)' in event PPP.12"
    ::= { pppEventObjects12 2 }

ppp12-protocol OBJECT-TYPE
    SYNTAX Integer32
    MAX-ACCESS accessible-for-notify
    STATUS current
    DESCRIPTION
        "Parameter 'protocol' in event PPP.12"
    ::= { pppEventObjects12 3 }

ppp12-result OBJECT-TYPE
    SYNTAX DisplayString
    MAX-ACCESS accessible-for-notify
    STATUS current
    DESCRIPTION
        "Parameter 'result' in event PPP.12"
    ::= { pppEventObjects12 4 }

pppEventObjects13 OBJECT-IDENTITY
    STATUS current
    DESCRIPTION
        "Event PPP.13
        A Van Jacobson frame has been compressed/decompressed (indicating
        the result of the operation)."
    ::= { pppEventsGroup 13 }

ppp13-linkPPP OBJECT-TYPE
    SYNTAX DisplayString
    MAX-ACCESS accessible-for-notify
    STATUS current
    DESCRIPTION
        "Parameter 'linkPPP' in event PPP.13"
    ::= { pppEventObjects13 1 }

ppp13-compressedIn-or-uncompressedOut OBJECT-TYPE
    SYNTAX DisplayString
    MAX-ACCESS accessible-for-notify
    STATUS current
    DESCRIPTION
        "Parameter 'compressed(In) or uncompressed(Out)' in event PPP.13"
    ::= { pppEventObjects13 2 }

ppp13-action OBJECT-TYPE
    SYNTAX DisplayString
    MAX-ACCESS accessible-for-notify
    STATUS current
    DESCRIPTION
        "Parameter 'action' in event PPP.13"
    ::= { pppEventObjects13 3 }

ppp13-protocol OBJECT-TYPE
    SYNTAX Integer32
    MAX-ACCESS accessible-for-notify
    STATUS current
    DESCRIPTION
        "Parameter 'protocol' in event PPP.13"
    ::= { pppEventObjects13 4 }

ppp13-result OBJECT-TYPE
    SYNTAX DisplayString
    MAX-ACCESS accessible-for-notify
    STATUS current
    DESCRIPTION
        "Parameter 'result' in event PPP.13"
    ::= { pppEventObjects13 5 }

pppEventObjects14 OBJECT-IDENTITY
    STATUS current
    DESCRIPTION
        "Event PPP.14
        An IPHC frame has been compressed/decompressed (indicating the result
        of the operation)."
    ::= { pppEventsGroup 14 }

ppp14-linkPPP OBJECT-TYPE
    SYNTAX DisplayString
    MAX-ACCESS accessible-for-notify
    STATUS current
    DESCRIPTION
        "Parameter 'linkPPP' in event PPP.14"
    ::= { pppEventObjects14 1 }

ppp14-compressedIn-or-uncompressedOut OBJECT-TYPE
    SYNTAX DisplayString
    MAX-ACCESS accessible-for-notify
    STATUS current
    DESCRIPTION
        "Parameter 'compressed(In) or uncompressed(Out)' in event PPP.14"
    ::= { pppEventObjects14 2 }

ppp14-action OBJECT-TYPE
    SYNTAX DisplayString
    MAX-ACCESS accessible-for-notify
    STATUS current
    DESCRIPTION
        "Parameter 'action' in event PPP.14"
    ::= { pppEventObjects14 3 }

ppp14-protocol OBJECT-TYPE
    SYNTAX Integer32
    MAX-ACCESS accessible-for-notify
    STATUS current
    DESCRIPTION
        "Parameter 'protocol' in event PPP.14"
    ::= { pppEventObjects14 4 }

ppp14-result OBJECT-TYPE
    SYNTAX DisplayString
    MAX-ACCESS accessible-for-notify
    STATUS current
    DESCRIPTION
        "Parameter 'result' in event PPP.14"
    ::= { pppEventObjects14 5 }

pppEventObjects15 OBJECT-IDENTITY
    STATUS current
    DESCRIPTION
        "Event PPP.15
        A CCP frame has been compressed/decompressed (indicating the result
        of the operation)."
    ::= { pppEventsGroup 15 }

ppp15-linkPPP OBJECT-TYPE
    SYNTAX DisplayString
    MAX-ACCESS accessible-for-notify
    STATUS current
    DESCRIPTION
        "Parameter 'linkPPP' in event PPP.15"
    ::= { pppEventObjects15 1 }

ppp15-compressedIn-or-uncompressedOut OBJECT-TYPE
    SYNTAX DisplayString
    MAX-ACCESS accessible-for-notify
    STATUS current
    DESCRIPTION
        "Parameter 'compressed(In) or uncompressed(Out)' in event PPP.15"
    ::= { pppEventObjects15 2 }

ppp15-action OBJECT-TYPE
    SYNTAX DisplayString
    MAX-ACCESS accessible-for-notify
    STATUS current
    DESCRIPTION
        "Parameter 'action' in event PPP.15"
    ::= { pppEventObjects15 3 }

ppp15-protocol OBJECT-TYPE
    SYNTAX Integer32
    MAX-ACCESS accessible-for-notify
    STATUS current
    DESCRIPTION
        "Parameter 'protocol' in event PPP.15"
    ::= { pppEventObjects15 4 }

ppp15-result OBJECT-TYPE
    SYNTAX DisplayString
    MAX-ACCESS accessible-for-notify
    STATUS current
    DESCRIPTION
        "Parameter 'result' in event PPP.15"
    ::= { pppEventObjects15 5 }

pppEventObjects16 OBJECT-IDENTITY
    STATUS current
    DESCRIPTION
        "Event PPP.16
        Se ha enviado/recibido un CCP Reset Request/Ack."
    ::= { pppEventsGroup 16 }

ppp16-linkPPP OBJECT-TYPE
    SYNTAX DisplayString
    MAX-ACCESS accessible-for-notify
    STATUS current
    DESCRIPTION
        "Parameter 'linkPPP' in event PPP.16"
    ::= { pppEventObjects16 1 }

ppp16-receivedIn-or-sentOut OBJECT-TYPE
    SYNTAX DisplayString
    MAX-ACCESS accessible-for-notify
    STATUS current
    DESCRIPTION
        "Parameter 'received(In) or sent(Out)' in event PPP.16"
    ::= { pppEventObjects16 2 }

ppp16-request-ack OBJECT-TYPE
    SYNTAX DisplayString
    MAX-ACCESS accessible-for-notify
    STATUS current
    DESCRIPTION
        "Parameter 'request-ack' in event PPP.16"
    ::= { pppEventObjects16 3 }

pppEventObjects17 OBJECT-IDENTITY
    STATUS current
    DESCRIPTION
        "Event PPP.17
        An MP bundle has been created or eliminated."
    ::= { pppEventsGroup 17 }

ppp17-linkPPP OBJECT-TYPE
    SYNTAX DisplayString
    MAX-ACCESS accessible-for-notify
    STATUS current
    DESCRIPTION
        "Parameter 'linkPPP' in event PPP.17"
    ::= { pppEventObjects17 1 }

ppp17-created-or-deleted OBJECT-TYPE
    SYNTAX DisplayString
    MAX-ACCESS accessible-for-notify
    STATUS current
    DESCRIPTION
        "Parameter 'created or deleted' in event PPP.17"
    ::= { pppEventObjects17 2 }

pppEventObjects18 OBJECT-IDENTITY
    STATUS current
    DESCRIPTION
        "Event PPP.18
        MRRU negotiated in the MP bundle."
    ::= { pppEventsGroup 18 }

ppp18-linkPPP OBJECT-TYPE
    SYNTAX DisplayString
    MAX-ACCESS accessible-for-notify
    STATUS current
    DESCRIPTION
        "Parameter 'linkPPP' in event PPP.18"
    ::= { pppEventObjects18 1 }

ppp18-local-or-remote OBJECT-TYPE
    SYNTAX DisplayString
    MAX-ACCESS accessible-for-notify
    STATUS current
    DESCRIPTION
        "Parameter 'local or remote' in event PPP.18"
    ::= { pppEventObjects18 2 }

ppp18-MRRU OBJECT-TYPE
    SYNTAX Integer32
    MAX-ACCESS accessible-for-notify
    STATUS current
    DESCRIPTION
        "Parameter 'MRRU' in event PPP.18"
    ::= { pppEventObjects18 3 }

pppEventObjects19 OBJECT-IDENTITY
    STATUS current
    DESCRIPTION
        "Event PPP.19
        SSN format (Short Sequence Number) negotiated in the MP bundle."
    ::= { pppEventsGroup 19 }

ppp19-linkPPP OBJECT-TYPE
    SYNTAX DisplayString
    MAX-ACCESS accessible-for-notify
    STATUS current
    DESCRIPTION
        "Parameter 'linkPPP' in event PPP.19"
    ::= { pppEventObjects19 1 }

ppp19-local-or-remote OBJECT-TYPE
    SYNTAX DisplayString
    MAX-ACCESS accessible-for-notify
    STATUS current
    DESCRIPTION
        "Parameter 'local or remote' in event PPP.19"
    ::= { pppEventObjects19 2 }

pppEventObjects20 OBJECT-IDENTITY
    STATUS current
    DESCRIPTION
        "Event PPP.20
        Endpoint Discriminator used in the MP bundle."
    ::= { pppEventsGroup 20 }

ppp20-linkPPP OBJECT-TYPE
    SYNTAX DisplayString
    MAX-ACCESS accessible-for-notify
    STATUS current
    DESCRIPTION
        "Parameter 'linkPPP' in event PPP.20"
    ::= { pppEventObjects20 1 }

ppp20-local-or-remote OBJECT-TYPE
    SYNTAX DisplayString
    MAX-ACCESS accessible-for-notify
    STATUS current
    DESCRIPTION
        "Parameter 'local or remote' in event PPP.20"
    ::= { pppEventObjects20 2 }

ppp20-Endpoint-class OBJECT-TYPE
    SYNTAX Integer32
    MAX-ACCESS accessible-for-notify
    STATUS current
    DESCRIPTION
        "Parameter 'Endpoint class' in event PPP.20"
    ::= { pppEventObjects20 3 }

ppp20-Endpoint-value OBJECT-TYPE
    SYNTAX DisplayString
    MAX-ACCESS accessible-for-notify
    STATUS current
    DESCRIPTION
        "Parameter 'Endpoint value' in event PPP.20"
    ::= { pppEventObjects20 4 }

pppEventObjects21 OBJECT-IDENTITY
    STATUS current
    DESCRIPTION
        "Event PPP.21
        A PPP link has been added to or removed from an MP bundle."
    ::= { pppEventsGroup 21 }

ppp21-linkPPP OBJECT-TYPE
    SYNTAX DisplayString
    MAX-ACCESS accessible-for-notify
    STATUS current
    DESCRIPTION
        "Parameter 'linkPPP' in event PPP.21"
    ::= { pppEventObjects21 1 }

ppp21-added-or-removed OBJECT-TYPE
    SYNTAX DisplayString
    MAX-ACCESS accessible-for-notify
    STATUS current
    DESCRIPTION
        "Parameter 'added or removed' in event PPP.21"
    ::= { pppEventObjects21 2 }

pppEventObjects22 OBJECT-IDENTITY
    STATUS current
    DESCRIPTION
        "Event PPP.22
        A multilink PPP frame has been received with a determined sequence
        number (the expected sequence number is displayed and the corresponding
        action: accept, discard or queue). Includes the flags and
        the frame size."
    ::= { pppEventsGroup 22 }

ppp22-linkPPP OBJECT-TYPE
    SYNTAX DisplayString
    MAX-ACCESS accessible-for-notify
    STATUS current
    DESCRIPTION
        "Parameter 'linkPPP' in event PPP.22"
    ::= { pppEventObjects22 1 }

ppp22-flags OBJECT-TYPE
    SYNTAX Integer32
    MAX-ACCESS accessible-for-notify
    STATUS current
    DESCRIPTION
        "Parameter 'flags' in event PPP.22"
    ::= { pppEventObjects22 2 }

ppp22-received-sequence OBJECT-TYPE
    SYNTAX Integer32
    MAX-ACCESS accessible-for-notify
    STATUS current
    DESCRIPTION
        "Parameter 'received sequence' in event PPP.22"
    ::= { pppEventObjects22 3 }

ppp22-expected-sequence OBJECT-TYPE
    SYNTAX Integer32
    MAX-ACCESS accessible-for-notify
    STATUS current
    DESCRIPTION
        "Parameter 'expected sequence' in event PPP.22"
    ::= { pppEventObjects22 4 }

ppp22-action OBJECT-TYPE
    SYNTAX DisplayString
    MAX-ACCESS accessible-for-notify
    STATUS current
    DESCRIPTION
        "Parameter 'action' in event PPP.22"
    ::= { pppEventObjects22 5 }

ppp22-size OBJECT-TYPE
    SYNTAX Integer32
    MAX-ACCESS accessible-for-notify
    STATUS current
    DESCRIPTION
        "Parameter 'size' in event PPP.22"
    ::= { pppEventObjects22 6 }

pppEventObjects23 OBJECT-IDENTITY
    STATUS current
    DESCRIPTION
        "Event PPP.23
        A multilink PPP frame has been transmitted (the transmission sequence
        number, the flags and the frame size is displayed)."
    ::= { pppEventsGroup 23 }

ppp23-linkPPP OBJECT-TYPE
    SYNTAX DisplayString
    MAX-ACCESS accessible-for-notify
    STATUS current
    DESCRIPTION
        "Parameter 'linkPPP' in event PPP.23"
    ::= { pppEventObjects23 1 }

ppp23-flags OBJECT-TYPE
    SYNTAX Integer32
    MAX-ACCESS accessible-for-notify
    STATUS current
    DESCRIPTION
        "Parameter 'flags' in event PPP.23"
    ::= { pppEventObjects23 2 }

ppp23-transmission-sequence OBJECT-TYPE
    SYNTAX Integer32
    MAX-ACCESS accessible-for-notify
    STATUS current
    DESCRIPTION
        "Parameter 'transmission sequence' in event PPP.23"
    ::= { pppEventObjects23 3 }

ppp23-size OBJECT-TYPE
    SYNTAX Integer32
    MAX-ACCESS accessible-for-notify
    STATUS current
    DESCRIPTION
        "Parameter 'size' in event PPP.23"
    ::= { pppEventObjects23 4 }

pppEventObjects24 OBJECT-IDENTITY
    STATUS current
    DESCRIPTION
        "Event PPP.24
        The maximum number of queued multilink PPP fragments has been exceeded."
    ::= { pppEventsGroup 24 }

ppp24-linkPPP OBJECT-TYPE
    SYNTAX DisplayString
    MAX-ACCESS accessible-for-notify
    STATUS current
    DESCRIPTION
        "Parameter 'linkPPP' in event PPP.24"
    ::= { pppEventObjects24 1 }

pppEventObjects25 OBJECT-IDENTITY
    STATUS current
    DESCRIPTION
        "Event PPP.25
        A fragment with the MP frame end flag has been found (END) however
        the beginning part of the frame is not available."
    ::= { pppEventsGroup 25 }

ppp25-linkPPP OBJECT-TYPE
    SYNTAX DisplayString
    MAX-ACCESS accessible-for-notify
    STATUS current
    DESCRIPTION
        "Parameter 'linkPPP' in event PPP.25"
    ::= { pppEventObjects25 1 }

ppp25-sequence OBJECT-TYPE
    SYNTAX Integer32
    MAX-ACCESS accessible-for-notify
    STATUS current
    DESCRIPTION
        "Parameter 'sequence' in event PPP.25"
    ::= { pppEventObjects25 2 }

pppEventObjects26 OBJECT-IDENTITY
    STATUS current
    DESCRIPTION
        "Event PPP.26
        An error has been produced compressing/decompressing
        a Van Jacobson frame."
    ::= { pppEventsGroup 26 }

ppp26-linkPPP OBJECT-TYPE
    SYNTAX DisplayString
    MAX-ACCESS accessible-for-notify
    STATUS current
    DESCRIPTION
        "Parameter 'linkPPP' in event PPP.26"
    ::= { pppEventObjects26 1 }

ppp26-compressedIn-or-uncompressedOut OBJECT-TYPE
    SYNTAX DisplayString
    MAX-ACCESS accessible-for-notify
    STATUS current
    DESCRIPTION
        "Parameter 'compressed(In) or uncompressed(Out)' in event PPP.26"
    ::= { pppEventObjects26 2 }

ppp26-action OBJECT-TYPE
    SYNTAX DisplayString
    MAX-ACCESS accessible-for-notify
    STATUS current
    DESCRIPTION
        "Parameter 'action' in event PPP.26"
    ::= { pppEventObjects26 3 }

ppp26-protocol OBJECT-TYPE
    SYNTAX Integer32
    MAX-ACCESS accessible-for-notify
    STATUS current
    DESCRIPTION
        "Parameter 'protocol' in event PPP.26"
    ::= { pppEventObjects26 4 }

ppp26-result OBJECT-TYPE
    SYNTAX DisplayString
    MAX-ACCESS accessible-for-notify
    STATUS current
    DESCRIPTION
        "Parameter 'result' in event PPP.26"
    ::= { pppEventObjects26 5 }

pppEventObjects27 OBJECT-IDENTITY
    STATUS current
    DESCRIPTION
        "Event PPP.27
        An error has been produced compressing/decompressing a IPHC frame."
    ::= { pppEventsGroup 27 }

ppp27-linkPPP OBJECT-TYPE
    SYNTAX DisplayString
    MAX-ACCESS accessible-for-notify
    STATUS current
    DESCRIPTION
        "Parameter 'linkPPP' in event PPP.27"
    ::= { pppEventObjects27 1 }

ppp27-compressedIn-or-uncompressedOut OBJECT-TYPE
    SYNTAX DisplayString
    MAX-ACCESS accessible-for-notify
    STATUS current
    DESCRIPTION
        "Parameter 'compressed(In) or uncompressed(Out)' in event PPP.27"
    ::= { pppEventObjects27 2 }

ppp27-action OBJECT-TYPE
    SYNTAX DisplayString
    MAX-ACCESS accessible-for-notify
    STATUS current
    DESCRIPTION
        "Parameter 'action' in event PPP.27"
    ::= { pppEventObjects27 3 }

ppp27-protocol OBJECT-TYPE
    SYNTAX Integer32
    MAX-ACCESS accessible-for-notify
    STATUS current
    DESCRIPTION
        "Parameter 'protocol' in event PPP.27"
    ::= { pppEventObjects27 4 }

ppp27-result OBJECT-TYPE
    SYNTAX DisplayString
    MAX-ACCESS accessible-for-notify
    STATUS current
    DESCRIPTION
        "Parameter 'result' in event PPP.27"
    ::= { pppEventObjects27 5 }

pppEventObjects28 OBJECT-IDENTITY
    STATUS current
    DESCRIPTION
        "Event PPP.28
        An error has been produced compressing/decompressing a CCP frame."
    ::= { pppEventsGroup 28 }

ppp28-linkPPP OBJECT-TYPE
    SYNTAX DisplayString
    MAX-ACCESS accessible-for-notify
    STATUS current
    DESCRIPTION
        "Parameter 'linkPPP' in event PPP.28"
    ::= { pppEventObjects28 1 }

ppp28-compressedIn-or-uncompressedOut OBJECT-TYPE
    SYNTAX DisplayString
    MAX-ACCESS accessible-for-notify
    STATUS current
    DESCRIPTION
        "Parameter 'compressed(In) or uncompressed(Out)' in event PPP.28"
    ::= { pppEventObjects28 2 }

ppp28-action OBJECT-TYPE
    SYNTAX DisplayString
    MAX-ACCESS accessible-for-notify
    STATUS current
    DESCRIPTION
        "Parameter 'action' in event PPP.28"
    ::= { pppEventObjects28 3 }

ppp28-protocol OBJECT-TYPE
    SYNTAX Integer32
    MAX-ACCESS accessible-for-notify
    STATUS current
    DESCRIPTION
        "Parameter 'protocol' in event PPP.28"
    ::= { pppEventObjects28 4 }

ppp28-result OBJECT-TYPE
    SYNTAX DisplayString
    MAX-ACCESS accessible-for-notify
    STATUS current
    DESCRIPTION
        "Parameter 'result' in event PPP.28"
    ::= { pppEventObjects28 5 }

pppEventObjects29 OBJECT-IDENTITY
    STATUS current
    DESCRIPTION
        "Event PPP.29
        Indicates a request/establishment of an L2TP session."
    ::= { pppEventsGroup 29 }

ppp29-link-name OBJECT-TYPE
    SYNTAX DisplayString
    MAX-ACCESS accessible-for-notify
    STATUS current
    DESCRIPTION
        "Parameter 'link name' in event PPP.29"
    ::= { pppEventObjects29 1 }

ppp29-user OBJECT-TYPE
    SYNTAX DisplayString
    MAX-ACCESS accessible-for-notify
    STATUS current
    DESCRIPTION
        "Parameter 'user' in event PPP.29"
    ::= { pppEventObjects29 2 }

ppp29-action OBJECT-TYPE
    SYNTAX DisplayString
    MAX-ACCESS accessible-for-notify
    STATUS current
    DESCRIPTION
        "Parameter 'action' in event PPP.29"
    ::= { pppEventObjects29 3 }

pppEventObjects30 OBJECT-IDENTITY
    STATUS current
    DESCRIPTION
        "Event PPP.30
        Indicates an unusual situation in Multilink PPP."
    ::= { pppEventsGroup 30 }

ppp30-linkPPP OBJECT-TYPE
    SYNTAX DisplayString
    MAX-ACCESS accessible-for-notify
    STATUS current
    DESCRIPTION
        "Parameter 'linkPPP' in event PPP.30"
    ::= { pppEventObjects30 1 }

ppp30-information-message OBJECT-TYPE
    SYNTAX DisplayString
    MAX-ACCESS accessible-for-notify
    STATUS current
    DESCRIPTION
        "Parameter 'information message' in event PPP.30"
    ::= { pppEventObjects30 2 }

pppEventObjects31 OBJECT-IDENTITY
    STATUS current
    DESCRIPTION
        "Event PPP.31
        BCP packet description."
    ::= { pppEventsGroup 31 }

ppp31-link-name OBJECT-TYPE
    SYNTAX DisplayString
    MAX-ACCESS accessible-for-notify
    STATUS current
    DESCRIPTION
        "Parameter 'link name' in event PPP.31"
    ::= { pppEventObjects31 1 }

ppp31-direction OBJECT-TYPE
    SYNTAX DisplayString
    MAX-ACCESS accessible-for-notify
    STATUS current
    DESCRIPTION
        "Parameter 'direction' in event PPP.31"
    ::= { pppEventObjects31 2 }

ppp31-code OBJECT-TYPE
    SYNTAX DisplayString
    MAX-ACCESS accessible-for-notify
    STATUS current
    DESCRIPTION
        "Parameter 'code' in event PPP.31"
    ::= { pppEventObjects31 3 }

ppp31-BCP-state OBJECT-TYPE
    SYNTAX DisplayString
    MAX-ACCESS accessible-for-notify
    STATUS current
    DESCRIPTION
        "Parameter 'BCP state' in event PPP.31"
    ::= { pppEventObjects31 4 }

ppp31-identifier OBJECT-TYPE
    SYNTAX Integer32
    MAX-ACCESS accessible-for-notify
    STATUS current
    DESCRIPTION
        "Parameter 'identifier' in event PPP.31"
    ::= { pppEventObjects31 5 }

ppp31-length OBJECT-TYPE
    SYNTAX Integer32
    MAX-ACCESS accessible-for-notify
    STATUS current
    DESCRIPTION
        "Parameter 'length' in event PPP.31"
    ::= { pppEventObjects31 6 }

pppEventObjects32 OBJECT-IDENTITY
    STATUS current
    DESCRIPTION
        "Event PPP.32
        BCP Bridge ID option"
    ::= { pppEventsGroup 32 }

ppp32-link-name OBJECT-TYPE
    SYNTAX DisplayString
    MAX-ACCESS accessible-for-notify
    STATUS current
    DESCRIPTION
        "Parameter 'link name' in event PPP.32"
    ::= { pppEventObjects32 1 }

ppp32-id OBJECT-TYPE
    SYNTAX Integer32
    MAX-ACCESS accessible-for-notify
    STATUS current
    DESCRIPTION
        "Parameter 'id' in event PPP.32"
    ::= { pppEventObjects32 2 }

ppp32-dump OBJECT-TYPE
    SYNTAX DisplayString
    MAX-ACCESS accessible-for-notify
    STATUS current
    DESCRIPTION
        "Parameter 'dump' in event PPP.32"
    ::= { pppEventObjects32 3 }

pppEventObjects33 OBJECT-IDENTITY
    STATUS current
    DESCRIPTION
        "Event PPP.33
        BCP Line ID option."
    ::= { pppEventsGroup 33 }

ppp33-link-name OBJECT-TYPE
    SYNTAX DisplayString
    MAX-ACCESS accessible-for-notify
    STATUS current
    DESCRIPTION
        "Parameter 'link name' in event PPP.33"
    ::= { pppEventObjects33 1 }

ppp33-id OBJECT-TYPE
    SYNTAX Integer32
    MAX-ACCESS accessible-for-notify
    STATUS current
    DESCRIPTION
        "Parameter 'id' in event PPP.33"
    ::= { pppEventObjects33 2 }

ppp33-dump OBJECT-TYPE
    SYNTAX DisplayString
    MAX-ACCESS accessible-for-notify
    STATUS current
    DESCRIPTION
        "Parameter 'dump' in event PPP.33"
    ::= { pppEventObjects33 3 }

pppEventObjects34 OBJECT-IDENTITY
    STATUS current
    DESCRIPTION
        "Event PPP.34
        BCP MAC Support option."
    ::= { pppEventsGroup 34 }

ppp34-link-name OBJECT-TYPE
    SYNTAX DisplayString
    MAX-ACCESS accessible-for-notify
    STATUS current
    DESCRIPTION
        "Parameter 'link name' in event PPP.34"
    ::= { pppEventObjects34 1 }

ppp34-maccode OBJECT-TYPE
    SYNTAX Integer32
    MAX-ACCESS accessible-for-notify
    STATUS current
    DESCRIPTION
        "Parameter 'maccode' in event PPP.34"
    ::= { pppEventObjects34 2 }

ppp34-macname OBJECT-TYPE
    SYNTAX DisplayString
    MAX-ACCESS accessible-for-notify
    STATUS current
    DESCRIPTION
        "Parameter 'macname' in event PPP.34"
    ::= { pppEventObjects34 3 }

ppp34-dump OBJECT-TYPE
    SYNTAX DisplayString
    MAX-ACCESS accessible-for-notify
    STATUS current
    DESCRIPTION
        "Parameter 'dump' in event PPP.34"
    ::= { pppEventObjects34 4 }

pppEventObjects35 OBJECT-IDENTITY
    STATUS current
    DESCRIPTION
        "Event PPP.35
        BCP Tinygram compression option."
    ::= { pppEventsGroup 35 }

ppp35-link-name OBJECT-TYPE
    SYNTAX DisplayString
    MAX-ACCESS accessible-for-notify
    STATUS current
    DESCRIPTION
        "Parameter 'link name' in event PPP.35"
    ::= { pppEventObjects35 1 }

ppp35-comp OBJECT-TYPE
    SYNTAX DisplayString
    MAX-ACCESS accessible-for-notify
    STATUS current
    DESCRIPTION
        "Parameter 'comp' in event PPP.35"
    ::= { pppEventObjects35 2 }

ppp35-dump OBJECT-TYPE
    SYNTAX DisplayString
    MAX-ACCESS accessible-for-notify
    STATUS current
    DESCRIPTION
        "Parameter 'dump' in event PPP.35"
    ::= { pppEventObjects35 3 }

pppEventObjects36 OBJECT-IDENTITY
    STATUS current
    DESCRIPTION
        "Event PPP.36
        BCP LAN Identification option."
    ::= { pppEventsGroup 36 }

ppp36-link-name OBJECT-TYPE
    SYNTAX DisplayString
    MAX-ACCESS accessible-for-notify
    STATUS current
    DESCRIPTION
        "Parameter 'link name' in event PPP.36"
    ::= { pppEventObjects36 1 }

ppp36-lanid OBJECT-TYPE
    SYNTAX DisplayString
    MAX-ACCESS accessible-for-notify
    STATUS current
    DESCRIPTION
        "Parameter 'lanid' in event PPP.36"
    ::= { pppEventObjects36 2 }

ppp36-dump OBJECT-TYPE
    SYNTAX DisplayString
    MAX-ACCESS accessible-for-notify
    STATUS current
    DESCRIPTION
        "Parameter 'dump' in event PPP.36"
    ::= { pppEventObjects36 3 }

pppEventObjects37 OBJECT-IDENTITY
    STATUS current
    DESCRIPTION
        "Event PPP.37
        BCP MAC Address option."
    ::= { pppEventsGroup 37 }

ppp37-link-name OBJECT-TYPE
    SYNTAX DisplayString
    MAX-ACCESS accessible-for-notify
    STATUS current
    DESCRIPTION
        "Parameter 'link name' in event PPP.37"
    ::= { pppEventObjects37 1 }

ppp37-macaddr OBJECT-TYPE
    SYNTAX DisplayString
    MAX-ACCESS accessible-for-notify
    STATUS current
    DESCRIPTION
        "Parameter 'macaddr' in event PPP.37"
    ::= { pppEventObjects37 2 }

ppp37-dump OBJECT-TYPE
    SYNTAX DisplayString
    MAX-ACCESS accessible-for-notify
    STATUS current
    DESCRIPTION
        "Parameter 'dump' in event PPP.37"
    ::= { pppEventObjects37 3 }

pppEventObjects38 OBJECT-IDENTITY
    STATUS current
    DESCRIPTION
        "Event PPP.38
        BCP Old Spanning Tree Protocol option."
    ::= { pppEventsGroup 38 }

ppp38-link-name OBJECT-TYPE
    SYNTAX DisplayString
    MAX-ACCESS accessible-for-notify
    STATUS current
    DESCRIPTION
        "Parameter 'link name' in event PPP.38"
    ::= { pppEventObjects38 1 }

ppp38-oldstp OBJECT-TYPE
    SYNTAX DisplayString
    MAX-ACCESS accessible-for-notify
    STATUS current
    DESCRIPTION
        "Parameter 'oldstp' in event PPP.38"
    ::= { pppEventObjects38 2 }

ppp38-dump OBJECT-TYPE
    SYNTAX DisplayString
    MAX-ACCESS accessible-for-notify
    STATUS current
    DESCRIPTION
        "Parameter 'dump' in event PPP.38"
    ::= { pppEventObjects38 3 }

pppEventObjects39 OBJECT-IDENTITY
    STATUS current
    DESCRIPTION
        "Event PPP.39
        BCP Tagged Frame option."
    ::= { pppEventsGroup 39 }

ppp39-link-name OBJECT-TYPE
    SYNTAX DisplayString
    MAX-ACCESS accessible-for-notify
    STATUS current
    DESCRIPTION
        "Parameter 'link name' in event PPP.39"
    ::= { pppEventObjects39 1 }

ppp39-tagged OBJECT-TYPE
    SYNTAX DisplayString
    MAX-ACCESS accessible-for-notify
    STATUS current
    DESCRIPTION
        "Parameter 'tagged' in event PPP.39"
    ::= { pppEventObjects39 2 }

ppp39-dump OBJECT-TYPE
    SYNTAX DisplayString
    MAX-ACCESS accessible-for-notify
    STATUS current
    DESCRIPTION
        "Parameter 'dump' in event PPP.39"
    ::= { pppEventObjects39 3 }

pppEventObjects40 OBJECT-IDENTITY
    STATUS current
    DESCRIPTION
        "Event PPP.40
        BCP Management Inline support option."
    ::= { pppEventsGroup 40 }

ppp40-link-name OBJECT-TYPE
    SYNTAX DisplayString
    MAX-ACCESS accessible-for-notify
    STATUS current
    DESCRIPTION
        "Parameter 'link name' in event PPP.40"
    ::= { pppEventObjects40 1 }

ppp40-dump OBJECT-TYPE
    SYNTAX DisplayString
    MAX-ACCESS accessible-for-notify
    STATUS current
    DESCRIPTION
        "Parameter 'dump' in event PPP.40"
    ::= { pppEventObjects40 2 }

pppEventObjects41 OBJECT-IDENTITY
    STATUS current
    DESCRIPTION
        "Event PPP.41
        BCP unknown option."
    ::= { pppEventsGroup 41 }

ppp41-link-name OBJECT-TYPE
    SYNTAX DisplayString
    MAX-ACCESS accessible-for-notify
    STATUS current
    DESCRIPTION
        "Parameter 'link name' in event PPP.41"
    ::= { pppEventObjects41 1 }

ppp41-dump OBJECT-TYPE
    SYNTAX DisplayString
    MAX-ACCESS accessible-for-notify
    STATUS current
    DESCRIPTION
        "Parameter 'dump' in event PPP.41"
    ::= { pppEventObjects41 2 }

pppEventObjects42 OBJECT-IDENTITY
    STATUS current
    DESCRIPTION
        "Event PPP.42
        BCP information trace."
    ::= { pppEventsGroup 42 }

ppp42-link-name OBJECT-TYPE
    SYNTAX DisplayString
    MAX-ACCESS accessible-for-notify
    STATUS current
    DESCRIPTION
        "Parameter 'link name' in event PPP.42"
    ::= { pppEventObjects42 1 }

ppp42-information OBJECT-TYPE
    SYNTAX DisplayString
    MAX-ACCESS accessible-for-notify
    STATUS current
    DESCRIPTION
        "Parameter 'information' in event PPP.42"
    ::= { pppEventObjects42 2 }

pppEventObjects43 OBJECT-IDENTITY
    STATUS current
    DESCRIPTION
        "Event PPP.43
        A frame was received of a bridge type defined in RFC 2878.
        However, since bridging has not been enabled on this circuit, frame
        is being discarded."
    ::= { pppEventsGroup 43 }

ppp43-link-name OBJECT-TYPE
    SYNTAX DisplayString
    MAX-ACCESS accessible-for-notify
    STATUS current
    DESCRIPTION
        "Parameter 'link name' in event PPP.43"
    ::= { pppEventObjects43 1 }

pppEventObjects44 OBJECT-IDENTITY
    STATUS current
    DESCRIPTION
        "Event PPP.44
        A bridge frame is being discarded as a bridge port is not in
        forwarding state."
    ::= { pppEventsGroup 44 }

ppp44-link-name OBJECT-TYPE
    SYNTAX DisplayString
    MAX-ACCESS accessible-for-notify
    STATUS current
    DESCRIPTION
        "Parameter 'link name' in event PPP.44"
    ::= { pppEventObjects44 1 }

pppEventObjects45 OBJECT-IDENTITY
    STATUS current
    DESCRIPTION
        "Event PPP.45
        A bridged frame has been received and is being discarded due to mismatch
        in the frame type versus the bridge port behavior."
    ::= { pppEventsGroup 45 }

ppp45-link-name OBJECT-TYPE
    SYNTAX DisplayString
    MAX-ACCESS accessible-for-notify
    STATUS current
    DESCRIPTION
        "Parameter 'link name' in event PPP.45"
    ::= { pppEventObjects45 1 }

ppp45-source-mac OBJECT-TYPE
    SYNTAX DisplayString
    MAX-ACCESS accessible-for-notify
    STATUS current
    DESCRIPTION
        "Parameter 'source-mac' in event PPP.45"
    ::= { pppEventObjects45 2 }

ppp45-dest-mac OBJECT-TYPE
    SYNTAX DisplayString
    MAX-ACCESS accessible-for-notify
    STATUS current
    DESCRIPTION
        "Parameter 'dest-mac' in event PPP.45"
    ::= { pppEventObjects45 3 }

pppEventObjects46 OBJECT-IDENTITY
    STATUS current
    DESCRIPTION
        "Event PPP.46
        An unsupported bridge frame type has been encountered."
    ::= { pppEventsGroup 46 }

ppp46-link-name OBJECT-TYPE
    SYNTAX DisplayString
    MAX-ACCESS accessible-for-notify
    STATUS current
    DESCRIPTION
        "Parameter 'link name' in event PPP.46"
    ::= { pppEventObjects46 1 }

ppp46-type OBJECT-TYPE
    SYNTAX Integer32
    MAX-ACCESS accessible-for-notify
    STATUS current
    DESCRIPTION
        "Parameter 'type' in event PPP.46"
    ::= { pppEventObjects46 2 }

pppEventObjects49 OBJECT-IDENTITY
    STATUS current
    DESCRIPTION
        "Event PPP.49
        Unsupported LCP option description."
    ::= { pppEventsGroup 49 }

ppp49-link-name OBJECT-TYPE
    SYNTAX DisplayString
    MAX-ACCESS accessible-for-notify
    STATUS current
    DESCRIPTION
        "Parameter 'link name' in event PPP.49"
    ::= { pppEventObjects49 1 }

ppp49-option OBJECT-TYPE
    SYNTAX DisplayString
    MAX-ACCESS accessible-for-notify
    STATUS current
    DESCRIPTION
        "Parameter 'option' in event PPP.49"
    ::= { pppEventObjects49 2 }

ppp49-dump OBJECT-TYPE
    SYNTAX DisplayString
    MAX-ACCESS accessible-for-notify
    STATUS current
    DESCRIPTION
        "Parameter 'dump' in event PPP.49"
    ::= { pppEventObjects49 3 }

pppEventObjects50 OBJECT-IDENTITY
    STATUS current
    DESCRIPTION
        "Event PPP.50
        LCP packet data."
    ::= { pppEventsGroup 50 }

ppp50-link-name OBJECT-TYPE
    SYNTAX DisplayString
    MAX-ACCESS accessible-for-notify
    STATUS current
    DESCRIPTION
        "Parameter 'link name' in event PPP.50"
    ::= { pppEventObjects50 1 }

ppp50-dump OBJECT-TYPE
    SYNTAX DisplayString
    MAX-ACCESS accessible-for-notify
    STATUS current
    DESCRIPTION
        "Parameter 'dump' in event PPP.50"
    ::= { pppEventObjects50 2 }

pppEventObjects51 OBJECT-IDENTITY
    STATUS current
    DESCRIPTION
        "Event PPP.51
        LCP packet description."
    ::= { pppEventsGroup 51 }

ppp51-link-name OBJECT-TYPE
    SYNTAX DisplayString
    MAX-ACCESS accessible-for-notify
    STATUS current
    DESCRIPTION
        "Parameter 'link name' in event PPP.51"
    ::= { pppEventObjects51 1 }

ppp51-direction OBJECT-TYPE
    SYNTAX DisplayString
    MAX-ACCESS accessible-for-notify
    STATUS current
    DESCRIPTION
        "Parameter 'direction' in event PPP.51"
    ::= { pppEventObjects51 2 }

ppp51-code OBJECT-TYPE
    SYNTAX DisplayString
    MAX-ACCESS accessible-for-notify
    STATUS current
    DESCRIPTION
        "Parameter 'code' in event PPP.51"
    ::= { pppEventObjects51 3 }

ppp51-LCP-state OBJECT-TYPE
    SYNTAX DisplayString
    MAX-ACCESS accessible-for-notify
    STATUS current
    DESCRIPTION
        "Parameter 'LCP state' in event PPP.51"
    ::= { pppEventObjects51 4 }

ppp51-identifier OBJECT-TYPE
    SYNTAX Integer32
    MAX-ACCESS accessible-for-notify
    STATUS current
    DESCRIPTION
        "Parameter 'identifier' in event PPP.51"
    ::= { pppEventObjects51 5 }

ppp51-length OBJECT-TYPE
    SYNTAX Integer32
    MAX-ACCESS accessible-for-notify
    STATUS current
    DESCRIPTION
        "Parameter 'length' in event PPP.51"
    ::= { pppEventObjects51 6 }

pppEventObjects52 OBJECT-IDENTITY
    STATUS current
    DESCRIPTION
        "Event PPP.52
        MRU option description."
    ::= { pppEventsGroup 52 }

ppp52-link-name OBJECT-TYPE
    SYNTAX DisplayString
    MAX-ACCESS accessible-for-notify
    STATUS current
    DESCRIPTION
        "Parameter 'link name' in event PPP.52"
    ::= { pppEventObjects52 1 }

ppp52-mru OBJECT-TYPE
    SYNTAX Integer32
    MAX-ACCESS accessible-for-notify
    STATUS current
    DESCRIPTION
        "Parameter 'mru' in event PPP.52"
    ::= { pppEventObjects52 2 }

ppp52-dump OBJECT-TYPE
    SYNTAX DisplayString
    MAX-ACCESS accessible-for-notify
    STATUS current
    DESCRIPTION
        "Parameter 'dump' in event PPP.52"
    ::= { pppEventObjects52 3 }

pppEventObjects53 OBJECT-IDENTITY
    STATUS current
    DESCRIPTION
        "Event PPP.53
        Asynchronous Control Character Map (ACCM) option description."
    ::= { pppEventsGroup 53 }

ppp53-link-name OBJECT-TYPE
    SYNTAX DisplayString
    MAX-ACCESS accessible-for-notify
    STATUS current
    DESCRIPTION
        "Parameter 'link name' in event PPP.53"
    ::= { pppEventObjects53 1 }

ppp53-async-map OBJECT-TYPE
    SYNTAX Integer32
    MAX-ACCESS accessible-for-notify
    STATUS current
    DESCRIPTION
        "Parameter 'async. map' in event PPP.53"
    ::= { pppEventObjects53 2 }

ppp53-dump OBJECT-TYPE
    SYNTAX DisplayString
    MAX-ACCESS accessible-for-notify
    STATUS current
    DESCRIPTION
        "Parameter 'dump' in event PPP.53"
    ::= { pppEventObjects53 3 }

pppEventObjects54 OBJECT-IDENTITY
    STATUS current
    DESCRIPTION
        "Event PPP.54
        Authentication option description."
    ::= { pppEventsGroup 54 }

ppp54-link-name OBJECT-TYPE
    SYNTAX DisplayString
    MAX-ACCESS accessible-for-notify
    STATUS current
    DESCRIPTION
        "Parameter 'link name' in event PPP.54"
    ::= { pppEventObjects54 1 }

ppp54-auth-protocol OBJECT-TYPE
    SYNTAX DisplayString
    MAX-ACCESS accessible-for-notify
    STATUS current
    DESCRIPTION
        "Parameter 'auth. protocol' in event PPP.54"
    ::= { pppEventObjects54 2 }

ppp54-dump OBJECT-TYPE
    SYNTAX DisplayString
    MAX-ACCESS accessible-for-notify
    STATUS current
    DESCRIPTION
        "Parameter 'dump' in event PPP.54"
    ::= { pppEventObjects54 3 }

pppEventObjects55 OBJECT-IDENTITY
    STATUS current
    DESCRIPTION
        "Event PPP.55
        Magic Number option description."
    ::= { pppEventsGroup 55 }

ppp55-link-name OBJECT-TYPE
    SYNTAX DisplayString
    MAX-ACCESS accessible-for-notify
    STATUS current
    DESCRIPTION
        "Parameter 'link name' in event PPP.55"
    ::= { pppEventObjects55 1 }

ppp55-magic-number OBJECT-TYPE
    SYNTAX Integer32
    MAX-ACCESS accessible-for-notify
    STATUS current
    DESCRIPTION
        "Parameter 'magic number' in event PPP.55"
    ::= { pppEventObjects55 2 }

ppp55-dump OBJECT-TYPE
    SYNTAX DisplayString
    MAX-ACCESS accessible-for-notify
    STATUS current
    DESCRIPTION
        "Parameter 'dump' in event PPP.55"
    ::= { pppEventObjects55 3 }

pppEventObjects56 OBJECT-IDENTITY
    STATUS current
    DESCRIPTION
        "Event PPP.56
        Protocol Field Compression option description."
    ::= { pppEventsGroup 56 }

ppp56-link-name OBJECT-TYPE
    SYNTAX DisplayString
    MAX-ACCESS accessible-for-notify
    STATUS current
    DESCRIPTION
        "Parameter 'link name' in event PPP.56"
    ::= { pppEventObjects56 1 }

ppp56-dump OBJECT-TYPE
    SYNTAX DisplayString
    MAX-ACCESS accessible-for-notify
    STATUS current
    DESCRIPTION
        "Parameter 'dump' in event PPP.56"
    ::= { pppEventObjects56 2 }

pppEventObjects57 OBJECT-IDENTITY
    STATUS current
    DESCRIPTION
        "Event PPP.57
        Address/Control Fields Compression option description."
    ::= { pppEventsGroup 57 }

ppp57-link-name OBJECT-TYPE
    SYNTAX DisplayString
    MAX-ACCESS accessible-for-notify
    STATUS current
    DESCRIPTION
        "Parameter 'link name' in event PPP.57"
    ::= { pppEventObjects57 1 }

ppp57-dump OBJECT-TYPE
    SYNTAX DisplayString
    MAX-ACCESS accessible-for-notify
    STATUS current
    DESCRIPTION
        "Parameter 'dump' in event PPP.57"
    ::= { pppEventObjects57 2 }

pppEventObjects58 OBJECT-IDENTITY
    STATUS current
    DESCRIPTION
        "Event PPP.58
        MRRU option description."
    ::= { pppEventsGroup 58 }

ppp58-link-name OBJECT-TYPE
    SYNTAX DisplayString
    MAX-ACCESS accessible-for-notify
    STATUS current
    DESCRIPTION
        "Parameter 'link name' in event PPP.58"
    ::= { pppEventObjects58 1 }

ppp58-mrru OBJECT-TYPE
    SYNTAX Integer32
    MAX-ACCESS accessible-for-notify
    STATUS current
    DESCRIPTION
        "Parameter 'mrru' in event PPP.58"
    ::= { pppEventObjects58 2 }

ppp58-dump OBJECT-TYPE
    SYNTAX DisplayString
    MAX-ACCESS accessible-for-notify
    STATUS current
    DESCRIPTION
        "Parameter 'dump' in event PPP.58"
    ::= { pppEventObjects58 3 }

pppEventObjects59 OBJECT-IDENTITY
    STATUS current
    DESCRIPTION
        "Event PPP.59
        Short Sequence Number header format option description."
    ::= { pppEventsGroup 59 }

ppp59-link-name OBJECT-TYPE
    SYNTAX DisplayString
    MAX-ACCESS accessible-for-notify
    STATUS current
    DESCRIPTION
        "Parameter 'link name' in event PPP.59"
    ::= { pppEventObjects59 1 }

ppp59-dump OBJECT-TYPE
    SYNTAX DisplayString
    MAX-ACCESS accessible-for-notify
    STATUS current
    DESCRIPTION
        "Parameter 'dump' in event PPP.59"
    ::= { pppEventObjects59 2 }

pppEventObjects60 OBJECT-IDENTITY
    STATUS current
    DESCRIPTION
        "Event PPP.60
        End-Point Discriminator option description."
    ::= { pppEventsGroup 60 }

ppp60-link-name OBJECT-TYPE
    SYNTAX DisplayString
    MAX-ACCESS accessible-for-notify
    STATUS current
    DESCRIPTION
        "Parameter 'link name' in event PPP.60"
    ::= { pppEventObjects60 1 }

ppp60-class OBJECT-TYPE
    SYNTAX Integer32
    MAX-ACCESS accessible-for-notify
    STATUS current
    DESCRIPTION
        "Parameter 'class' in event PPP.60"
    ::= { pppEventObjects60 2 }

ppp60-dump OBJECT-TYPE
    SYNTAX DisplayString
    MAX-ACCESS accessible-for-notify
    STATUS current
    DESCRIPTION
        "Parameter 'dump' in event PPP.60"
    ::= { pppEventObjects60 3 }

pppEventObjects61 OBJECT-IDENTITY
    STATUS current
    DESCRIPTION
        "Event PPP.61
        Unknown option description."
    ::= { pppEventsGroup 61 }

ppp61-link-name OBJECT-TYPE
    SYNTAX DisplayString
    MAX-ACCESS accessible-for-notify
    STATUS current
    DESCRIPTION
        "Parameter 'link name' in event PPP.61"
    ::= { pppEventObjects61 1 }

ppp61-dump OBJECT-TYPE
    SYNTAX DisplayString
    MAX-ACCESS accessible-for-notify
    STATUS current
    DESCRIPTION
        "Parameter 'dump' in event PPP.61"
    ::= { pppEventObjects61 2 }

pppEventObjects62 OBJECT-IDENTITY
    STATUS current
    DESCRIPTION
        "Event PPP.62
        Bad format option description."
    ::= { pppEventsGroup 62 }

ppp62-link-name OBJECT-TYPE
    SYNTAX DisplayString
    MAX-ACCESS accessible-for-notify
    STATUS current
    DESCRIPTION
        "Parameter 'link name' in event PPP.62"
    ::= { pppEventObjects62 1 }

ppp62-dump OBJECT-TYPE
    SYNTAX DisplayString
    MAX-ACCESS accessible-for-notify
    STATUS current
    DESCRIPTION
        "Parameter 'dump' in event PPP.62"
    ::= { pppEventObjects62 2 }

pppEventObjects63 OBJECT-IDENTITY
    STATUS current
    DESCRIPTION
        "Event PPP.63
        PAP packet description."
    ::= { pppEventsGroup 63 }

ppp63-link-name OBJECT-TYPE
    SYNTAX DisplayString
    MAX-ACCESS accessible-for-notify
    STATUS current
    DESCRIPTION
        "Parameter 'link name' in event PPP.63"
    ::= { pppEventObjects63 1 }

ppp63-direction OBJECT-TYPE
    SYNTAX DisplayString
    MAX-ACCESS accessible-for-notify
    STATUS current
    DESCRIPTION
        "Parameter 'direction' in event PPP.63"
    ::= { pppEventObjects63 2 }

ppp63-code OBJECT-TYPE
    SYNTAX DisplayString
    MAX-ACCESS accessible-for-notify
    STATUS current
    DESCRIPTION
        "Parameter 'code' in event PPP.63"
    ::= { pppEventObjects63 3 }

ppp63-PAP-state OBJECT-TYPE
    SYNTAX DisplayString
    MAX-ACCESS accessible-for-notify
    STATUS current
    DESCRIPTION
        "Parameter 'PAP state' in event PPP.63"
    ::= { pppEventObjects63 4 }

ppp63-identifier OBJECT-TYPE
    SYNTAX Integer32
    MAX-ACCESS accessible-for-notify
    STATUS current
    DESCRIPTION
        "Parameter 'identifier' in event PPP.63"
    ::= { pppEventObjects63 5 }

ppp63-length OBJECT-TYPE
    SYNTAX Integer32
    MAX-ACCESS accessible-for-notify
    STATUS current
    DESCRIPTION
        "Parameter 'length' in event PPP.63"
    ::= { pppEventObjects63 6 }

pppEventObjects64 OBJECT-IDENTITY
    STATUS current
    DESCRIPTION
        "Event PPP.64
        PAP request peer-id."
    ::= { pppEventsGroup 64 }

ppp64-link-name OBJECT-TYPE
    SYNTAX DisplayString
    MAX-ACCESS accessible-for-notify
    STATUS current
    DESCRIPTION
        "Parameter 'link name' in event PPP.64"
    ::= { pppEventObjects64 1 }

ppp64-peer-id OBJECT-TYPE
    SYNTAX DisplayString
    MAX-ACCESS accessible-for-notify
    STATUS current
    DESCRIPTION
        "Parameter 'peer-id' in event PPP.64"
    ::= { pppEventObjects64 2 }

pppEventObjects65 OBJECT-IDENTITY
    STATUS current
    DESCRIPTION
        "Event PPP.65
        PAP request password."
    ::= { pppEventsGroup 65 }

ppp65-link-name OBJECT-TYPE
    SYNTAX DisplayString
    MAX-ACCESS accessible-for-notify
    STATUS current
    DESCRIPTION
        "Parameter 'link name' in event PPP.65"
    ::= { pppEventObjects65 1 }

ppp65-password OBJECT-TYPE
    SYNTAX DisplayString
    MAX-ACCESS accessible-for-notify
    STATUS current
    DESCRIPTION
        "Parameter 'password' in event PPP.65"
    ::= { pppEventObjects65 2 }

pppEventObjects66 OBJECT-IDENTITY
    STATUS current
    DESCRIPTION
        "Event PPP.66
        PAP reply message."
    ::= { pppEventsGroup 66 }

ppp66-link--name OBJECT-TYPE
    SYNTAX DisplayString
    MAX-ACCESS accessible-for-notify
    STATUS current
    DESCRIPTION
        "Parameter 'link  name' in event PPP.66"
    ::= { pppEventObjects66 1 }

ppp66-message OBJECT-TYPE
    SYNTAX DisplayString
    MAX-ACCESS accessible-for-notify
    STATUS current
    DESCRIPTION
        "Parameter 'message' in event PPP.66"
    ::= { pppEventObjects66 2 }

pppEventObjects67 OBJECT-IDENTITY
    STATUS current
    DESCRIPTION
        "Event PPP.67
        CHAP packet description."
    ::= { pppEventsGroup 67 }

ppp67-link-name OBJECT-TYPE
    SYNTAX DisplayString
    MAX-ACCESS accessible-for-notify
    STATUS current
    DESCRIPTION
        "Parameter 'link name' in event PPP.67"
    ::= { pppEventObjects67 1 }

ppp67-direction OBJECT-TYPE
    SYNTAX DisplayString
    MAX-ACCESS accessible-for-notify
    STATUS current
    DESCRIPTION
        "Parameter 'direction' in event PPP.67"
    ::= { pppEventObjects67 2 }

ppp67-code OBJECT-TYPE
    SYNTAX DisplayString
    MAX-ACCESS accessible-for-notify
    STATUS current
    DESCRIPTION
        "Parameter 'code' in event PPP.67"
    ::= { pppEventObjects67 3 }

ppp67-CHAP-state OBJECT-TYPE
    SYNTAX DisplayString
    MAX-ACCESS accessible-for-notify
    STATUS current
    DESCRIPTION
        "Parameter 'CHAP state' in event PPP.67"
    ::= { pppEventObjects67 4 }

ppp67-identifier OBJECT-TYPE
    SYNTAX Integer32
    MAX-ACCESS accessible-for-notify
    STATUS current
    DESCRIPTION
        "Parameter 'identifier' in event PPP.67"
    ::= { pppEventObjects67 5 }

ppp67-length OBJECT-TYPE
    SYNTAX Integer32
    MAX-ACCESS accessible-for-notify
    STATUS current
    DESCRIPTION
        "Parameter 'length' in event PPP.67"
    ::= { pppEventObjects67 6 }

pppEventObjects68 OBJECT-IDENTITY
    STATUS current
    DESCRIPTION
        "Event PPP.68
        CHAP peer name."
    ::= { pppEventsGroup 68 }

ppp68-link-name OBJECT-TYPE
    SYNTAX DisplayString
    MAX-ACCESS accessible-for-notify
    STATUS current
    DESCRIPTION
        "Parameter 'link name' in event PPP.68"
    ::= { pppEventObjects68 1 }

ppp68-peer-name OBJECT-TYPE
    SYNTAX DisplayString
    MAX-ACCESS accessible-for-notify
    STATUS current
    DESCRIPTION
        "Parameter 'peer name' in event PPP.68"
    ::= { pppEventObjects68 2 }

pppEventObjects69 OBJECT-IDENTITY
    STATUS current
    DESCRIPTION
        "Event PPP.69
        CHAP peer message."
    ::= { pppEventsGroup 69 }

ppp69-link-name OBJECT-TYPE
    SYNTAX DisplayString
    MAX-ACCESS accessible-for-notify
    STATUS current
    DESCRIPTION
        "Parameter 'link name' in event PPP.69"
    ::= { pppEventObjects69 1 }

ppp69-peer-message OBJECT-TYPE
    SYNTAX DisplayString
    MAX-ACCESS accessible-for-notify
    STATUS current
    DESCRIPTION
        "Parameter 'peer message' in event PPP.69"
    ::= { pppEventObjects69 2 }

pppEventObjects70 OBJECT-IDENTITY
    STATUS current
    DESCRIPTION
        "Event PPP.70
        CHAP challenge value."
    ::= { pppEventsGroup 70 }

ppp70-link-name OBJECT-TYPE
    SYNTAX DisplayString
    MAX-ACCESS accessible-for-notify
    STATUS current
    DESCRIPTION
        "Parameter 'link name' in event PPP.70"
    ::= { pppEventObjects70 1 }

ppp70-challenge OBJECT-TYPE
    SYNTAX DisplayString
    MAX-ACCESS accessible-for-notify
    STATUS current
    DESCRIPTION
        "Parameter 'challenge' in event PPP.70"
    ::= { pppEventObjects70 2 }

pppEventObjects71 OBJECT-IDENTITY
    STATUS current
    DESCRIPTION
        "Event PPP.71
        CHAP MD5 value."
    ::= { pppEventsGroup 71 }

ppp71-link-name OBJECT-TYPE
    SYNTAX DisplayString
    MAX-ACCESS accessible-for-notify
    STATUS current
    DESCRIPTION
        "Parameter 'link name' in event PPP.71"
    ::= { pppEventObjects71 1 }

ppp71-md5 OBJECT-TYPE
    SYNTAX DisplayString
    MAX-ACCESS accessible-for-notify
    STATUS current
    DESCRIPTION
        "Parameter 'md5' in event PPP.71"
    ::= { pppEventObjects71 2 }

pppEventObjects72 OBJECT-IDENTITY
    STATUS current
    DESCRIPTION
        "Event PPP.72
        IPCP packet description."
    ::= { pppEventsGroup 72 }

ppp72-link-name OBJECT-TYPE
    SYNTAX DisplayString
    MAX-ACCESS accessible-for-notify
    STATUS current
    DESCRIPTION
        "Parameter 'link name' in event PPP.72"
    ::= { pppEventObjects72 1 }

ppp72-direction OBJECT-TYPE
    SYNTAX DisplayString
    MAX-ACCESS accessible-for-notify
    STATUS current
    DESCRIPTION
        "Parameter 'direction' in event PPP.72"
    ::= { pppEventObjects72 2 }

ppp72-code OBJECT-TYPE
    SYNTAX DisplayString
    MAX-ACCESS accessible-for-notify
    STATUS current
    DESCRIPTION
        "Parameter 'code' in event PPP.72"
    ::= { pppEventObjects72 3 }

ppp72-IPCP-state OBJECT-TYPE
    SYNTAX DisplayString
    MAX-ACCESS accessible-for-notify
    STATUS current
    DESCRIPTION
        "Parameter 'IPCP state' in event PPP.72"
    ::= { pppEventObjects72 4 }

ppp72-identifier OBJECT-TYPE
    SYNTAX Integer32
    MAX-ACCESS accessible-for-notify
    STATUS current
    DESCRIPTION
        "Parameter 'identifier' in event PPP.72"
    ::= { pppEventObjects72 5 }

ppp72-length OBJECT-TYPE
    SYNTAX Integer32
    MAX-ACCESS accessible-for-notify
    STATUS current
    DESCRIPTION
        "Parameter 'length' in event PPP.72"
    ::= { pppEventObjects72 6 }

pppEventObjects73 OBJECT-IDENTITY
    STATUS current
    DESCRIPTION
        "Event PPP.73
        IPCP address option."
    ::= { pppEventsGroup 73 }

ppp73-link-name OBJECT-TYPE
    SYNTAX DisplayString
    MAX-ACCESS accessible-for-notify
    STATUS current
    DESCRIPTION
        "Parameter 'link name' in event PPP.73"
    ::= { pppEventObjects73 1 }

ppp73-address OBJECT-TYPE
    SYNTAX IpAddress
    MAX-ACCESS accessible-for-notify
    STATUS current
    DESCRIPTION
        "Parameter 'address' in event PPP.73"
    ::= { pppEventObjects73 2 }

ppp73-dump OBJECT-TYPE
    SYNTAX DisplayString
    MAX-ACCESS accessible-for-notify
    STATUS current
    DESCRIPTION
        "Parameter 'dump' in event PPP.73"
    ::= { pppEventObjects73 3 }

pppEventObjects74 OBJECT-IDENTITY
    STATUS current
    DESCRIPTION
        "Event PPP.74
        IPCP Van-Jacobson compression protocol."
    ::= { pppEventsGroup 74 }

ppp74-link-name OBJECT-TYPE
    SYNTAX DisplayString
    MAX-ACCESS accessible-for-notify
    STATUS current
    DESCRIPTION
        "Parameter 'link name' in event PPP.74"
    ::= { pppEventObjects74 1 }

ppp74-slots OBJECT-TYPE
    SYNTAX Integer32
    MAX-ACCESS accessible-for-notify
    STATUS current
    DESCRIPTION
        "Parameter 'slots' in event PPP.74"
    ::= { pppEventObjects74 2 }

ppp74-compression-flag OBJECT-TYPE
    SYNTAX DisplayString
    MAX-ACCESS accessible-for-notify
    STATUS current
    DESCRIPTION
        "Parameter 'compression flag' in event PPP.74"
    ::= { pppEventObjects74 3 }

ppp74-dump OBJECT-TYPE
    SYNTAX DisplayString
    MAX-ACCESS accessible-for-notify
    STATUS current
    DESCRIPTION
        "Parameter 'dump' in event PPP.74"
    ::= { pppEventObjects74 4 }

pppEventObjects75 OBJECT-IDENTITY
    STATUS current
    DESCRIPTION
        "Event PPP.75
        IPCP unknown compression protocol."
    ::= { pppEventsGroup 75 }

ppp75-link-name OBJECT-TYPE
    SYNTAX DisplayString
    MAX-ACCESS accessible-for-notify
    STATUS current
    DESCRIPTION
        "Parameter 'link name' in event PPP.75"
    ::= { pppEventObjects75 1 }

ppp75-dump OBJECT-TYPE
    SYNTAX DisplayString
    MAX-ACCESS accessible-for-notify
    STATUS current
    DESCRIPTION
        "Parameter 'dump' in event PPP.75"
    ::= { pppEventObjects75 2 }

pppEventObjects76 OBJECT-IDENTITY
    STATUS current
    DESCRIPTION
        "Event PPP.76
        IPCP unknown option."
    ::= { pppEventsGroup 76 }

ppp76-link-name OBJECT-TYPE
    SYNTAX DisplayString
    MAX-ACCESS accessible-for-notify
    STATUS current
    DESCRIPTION
        "Parameter 'link name' in event PPP.76"
    ::= { pppEventObjects76 1 }

ppp76-dump OBJECT-TYPE
    SYNTAX DisplayString
    MAX-ACCESS accessible-for-notify
    STATUS current
    DESCRIPTION
        "Parameter 'dump' in event PPP.76"
    ::= { pppEventObjects76 2 }

pppEventObjects77 OBJECT-IDENTITY
    STATUS current
    DESCRIPTION
        "Event PPP.77
        CCP packet description."
    ::= { pppEventsGroup 77 }

ppp77-link-name OBJECT-TYPE
    SYNTAX DisplayString
    MAX-ACCESS accessible-for-notify
    STATUS current
    DESCRIPTION
        "Parameter 'link name' in event PPP.77"
    ::= { pppEventObjects77 1 }

ppp77-direction OBJECT-TYPE
    SYNTAX DisplayString
    MAX-ACCESS accessible-for-notify
    STATUS current
    DESCRIPTION
        "Parameter 'direction' in event PPP.77"
    ::= { pppEventObjects77 2 }

ppp77-code OBJECT-TYPE
    SYNTAX DisplayString
    MAX-ACCESS accessible-for-notify
    STATUS current
    DESCRIPTION
        "Parameter 'code' in event PPP.77"
    ::= { pppEventObjects77 3 }

ppp77-CCP-state OBJECT-TYPE
    SYNTAX DisplayString
    MAX-ACCESS accessible-for-notify
    STATUS current
    DESCRIPTION
        "Parameter 'CCP state' in event PPP.77"
    ::= { pppEventObjects77 4 }

ppp77-identifier OBJECT-TYPE
    SYNTAX Integer32
    MAX-ACCESS accessible-for-notify
    STATUS current
    DESCRIPTION
        "Parameter 'identifier' in event PPP.77"
    ::= { pppEventObjects77 5 }

ppp77-length OBJECT-TYPE
    SYNTAX Integer32
    MAX-ACCESS accessible-for-notify
    STATUS current
    DESCRIPTION
        "Parameter 'length' in event PPP.77"
    ::= { pppEventObjects77 6 }

pppEventObjects78 OBJECT-IDENTITY
    STATUS current
    DESCRIPTION
        "Event PPP.78
        LZS-DCP compression option."
    ::= { pppEventsGroup 78 }

ppp78-link-name OBJECT-TYPE
    SYNTAX DisplayString
    MAX-ACCESS accessible-for-notify
    STATUS current
    DESCRIPTION
        "Parameter 'link name' in event PPP.78"
    ::= { pppEventObjects78 1 }

ppp78-dump OBJECT-TYPE
    SYNTAX DisplayString
    MAX-ACCESS accessible-for-notify
    STATUS current
    DESCRIPTION
        "Parameter 'dump' in event PPP.78"
    ::= { pppEventObjects78 2 }

pppEventObjects79 OBJECT-IDENTITY
    STATUS current
    DESCRIPTION
        "Event PPP.79
        Stac LZS compression option."
    ::= { pppEventsGroup 79 }

ppp79-link-name OBJECT-TYPE
    SYNTAX DisplayString
    MAX-ACCESS accessible-for-notify
    STATUS current
    DESCRIPTION
        "Parameter 'link name' in event PPP.79"
    ::= { pppEventObjects79 1 }

ppp79-dump OBJECT-TYPE
    SYNTAX DisplayString
    MAX-ACCESS accessible-for-notify
    STATUS current
    DESCRIPTION
        "Parameter 'dump' in event PPP.79"
    ::= { pppEventObjects79 2 }

pppEventObjects80 OBJECT-IDENTITY
    STATUS current
    DESCRIPTION
        "Event PPP.80
        History number parameter."
    ::= { pppEventsGroup 80 }

ppp80-link-name OBJECT-TYPE
    SYNTAX DisplayString
    MAX-ACCESS accessible-for-notify
    STATUS current
    DESCRIPTION
        "Parameter 'link name' in event PPP.80"
    ::= { pppEventObjects80 1 }

ppp80-histories OBJECT-TYPE
    SYNTAX Integer32
    MAX-ACCESS accessible-for-notify
    STATUS current
    DESCRIPTION
        "Parameter 'histories' in event PPP.80"
    ::= { pppEventObjects80 2 }

pppEventObjects81 OBJECT-IDENTITY
    STATUS current
    DESCRIPTION
        "Event PPP.81
        Check mode parameter."
    ::= { pppEventsGroup 81 }

ppp81-link-name OBJECT-TYPE
    SYNTAX DisplayString
    MAX-ACCESS accessible-for-notify
    STATUS current
    DESCRIPTION
        "Parameter 'link name' in event PPP.81"
    ::= { pppEventObjects81 1 }

ppp81-check-mode OBJECT-TYPE
    SYNTAX DisplayString
    MAX-ACCESS accessible-for-notify
    STATUS current
    DESCRIPTION
        "Parameter 'check mode' in event PPP.81"
    ::= { pppEventObjects81 2 }

pppEventObjects82 OBJECT-IDENTITY
    STATUS current
    DESCRIPTION
        "Event PPP.82
        Process mode parameter."
    ::= { pppEventsGroup 82 }

ppp82-link-name OBJECT-TYPE
    SYNTAX DisplayString
    MAX-ACCESS accessible-for-notify
    STATUS current
    DESCRIPTION
        "Parameter 'link name' in event PPP.82"
    ::= { pppEventObjects82 1 }

ppp82-process-mode OBJECT-TYPE
    SYNTAX DisplayString
    MAX-ACCESS accessible-for-notify
    STATUS current
    DESCRIPTION
        "Parameter 'process mode' in event PPP.82"
    ::= { pppEventObjects82 2 }

pppEventObjects83 OBJECT-IDENTITY
    STATUS current
    DESCRIPTION
        "Event PPP.83
        Unknown compression type."
    ::= { pppEventsGroup 83 }

ppp83-link-name OBJECT-TYPE
    SYNTAX DisplayString
    MAX-ACCESS accessible-for-notify
    STATUS current
    DESCRIPTION
        "Parameter 'link name' in event PPP.83"
    ::= { pppEventObjects83 1 }

ppp83-compression-type OBJECT-TYPE
    SYNTAX Integer32
    MAX-ACCESS accessible-for-notify
    STATUS current
    DESCRIPTION
        "Parameter 'compression type' in event PPP.83"
    ::= { pppEventObjects83 2 }

ppp83-dump OBJECT-TYPE
    SYNTAX DisplayString
    MAX-ACCESS accessible-for-notify
    STATUS current
    DESCRIPTION
        "Parameter 'dump' in event PPP.83"
    ::= { pppEventObjects83 3 }

pppEventObjects84 OBJECT-IDENTITY
    STATUS current
    DESCRIPTION
        "Event PPP.84
        PAP mode description."
    ::= { pppEventsGroup 84 }

ppp84-link-name OBJECT-TYPE
    SYNTAX DisplayString
    MAX-ACCESS accessible-for-notify
    STATUS current
    DESCRIPTION
        "Parameter 'link name' in event PPP.84"
    ::= { pppEventObjects84 1 }

ppp84-mode OBJECT-TYPE
    SYNTAX DisplayString
    MAX-ACCESS accessible-for-notify
    STATUS current
    DESCRIPTION
        "Parameter 'mode' in event PPP.84"
    ::= { pppEventObjects84 2 }

pppEventObjects85 OBJECT-IDENTITY
    STATUS current
    DESCRIPTION
        "Event PPP.85
        CHAP mode description."
    ::= { pppEventsGroup 85 }

ppp85-link-name OBJECT-TYPE
    SYNTAX DisplayString
    MAX-ACCESS accessible-for-notify
    STATUS current
    DESCRIPTION
        "Parameter 'link name' in event PPP.85"
    ::= { pppEventObjects85 1 }

ppp85-mode OBJECT-TYPE
    SYNTAX DisplayString
    MAX-ACCESS accessible-for-notify
    STATUS current
    DESCRIPTION
        "Parameter 'mode' in event PPP.85"
    ::= { pppEventObjects85 2 }

pppEventObjects86 OBJECT-IDENTITY
    STATUS current
    DESCRIPTION
        "Event PPP.86
        LCP bad packet description."
    ::= { pppEventsGroup 86 }

ppp86-link-name OBJECT-TYPE
    SYNTAX DisplayString
    MAX-ACCESS accessible-for-notify
    STATUS current
    DESCRIPTION
        "Parameter 'link name' in event PPP.86"
    ::= { pppEventObjects86 1 }

ppp86-cause OBJECT-TYPE
    SYNTAX DisplayString
    MAX-ACCESS accessible-for-notify
    STATUS current
    DESCRIPTION
        "Parameter 'cause' in event PPP.86"
    ::= { pppEventObjects86 2 }

pppEventObjects87 OBJECT-IDENTITY
    STATUS current
    DESCRIPTION
        "Event PPP.87
        LCP information trace."
    ::= { pppEventsGroup 87 }

ppp87-link-name OBJECT-TYPE
    SYNTAX DisplayString
    MAX-ACCESS accessible-for-notify
    STATUS current
    DESCRIPTION
        "Parameter 'link name' in event PPP.87"
    ::= { pppEventObjects87 1 }

ppp87-information OBJECT-TYPE
    SYNTAX DisplayString
    MAX-ACCESS accessible-for-notify
    STATUS current
    DESCRIPTION
        "Parameter 'information' in event PPP.87"
    ::= { pppEventObjects87 2 }

pppEventObjects88 OBJECT-IDENTITY
    STATUS current
    DESCRIPTION
        "Event PPP.88
        IPCP information trace."
    ::= { pppEventsGroup 88 }

ppp88-link-name OBJECT-TYPE
    SYNTAX DisplayString
    MAX-ACCESS accessible-for-notify
    STATUS current
    DESCRIPTION
        "Parameter 'link name' in event PPP.88"
    ::= { pppEventObjects88 1 }

ppp88-information OBJECT-TYPE
    SYNTAX DisplayString
    MAX-ACCESS accessible-for-notify
    STATUS current
    DESCRIPTION
        "Parameter 'information' in event PPP.88"
    ::= { pppEventObjects88 2 }

pppEventObjects89 OBJECT-IDENTITY
    STATUS current
    DESCRIPTION
        "Event PPP.89
        CCP information trace."
    ::= { pppEventsGroup 89 }

ppp89-link-name OBJECT-TYPE
    SYNTAX DisplayString
    MAX-ACCESS accessible-for-notify
    STATUS current
    DESCRIPTION
        "Parameter 'link name' in event PPP.89"
    ::= { pppEventObjects89 1 }

ppp89-information OBJECT-TYPE
    SYNTAX DisplayString
    MAX-ACCESS accessible-for-notify
    STATUS current
    DESCRIPTION
        "Parameter 'information' in event PPP.89"
    ::= { pppEventObjects89 2 }

pppEventObjects90 OBJECT-IDENTITY
    STATUS current
    DESCRIPTION
        "Event PPP.90
        PPP connection established with the specified negotiation times."
    ::= { pppEventsGroup 90 }

ppp90-serial-number OBJECT-TYPE
    SYNTAX DisplayString
    MAX-ACCESS accessible-for-notify
    STATUS current
    DESCRIPTION
        "Parameter 'serial-number' in event PPP.90"
    ::= { pppEventObjects90 1 }

ppp90-hostname OBJECT-TYPE
    SYNTAX DisplayString
    MAX-ACCESS accessible-for-notify
    STATUS current
    DESCRIPTION
        "Parameter 'hostname' in event PPP.90"
    ::= { pppEventObjects90 2 }

ppp90-network OBJECT-TYPE
    SYNTAX Integer32
    MAX-ACCESS accessible-for-notify
    STATUS current
    DESCRIPTION
        "Parameter 'network' in event PPP.90"
    ::= { pppEventObjects90 3 }

ppp90-local-address OBJECT-TYPE
    SYNTAX IpAddress
    MAX-ACCESS accessible-for-notify
    STATUS current
    DESCRIPTION
        "Parameter 'local-address' in event PPP.90"
    ::= { pppEventObjects90 4 }

ppp90-pppoe-disc-time OBJECT-TYPE
    SYNTAX Integer32
    MAX-ACCESS accessible-for-notify
    STATUS current
    DESCRIPTION
        "Parameter 'pppoe-disc-time' in event PPP.90"
    ::= { pppEventObjects90 5 }

ppp90-lcp-time OBJECT-TYPE
    SYNTAX Integer32
    MAX-ACCESS accessible-for-notify
    STATUS current
    DESCRIPTION
        "Parameter 'lcp-time' in event PPP.90"
    ::= { pppEventObjects90 6 }

ppp90-ipcp-time OBJECT-TYPE
    SYNTAX Integer32
    MAX-ACCESS accessible-for-notify
    STATUS current
    DESCRIPTION
        "Parameter 'ipcp-time' in event PPP.90"
    ::= { pppEventObjects90 7 }

ppp90-authentication-time OBJECT-TYPE
    SYNTAX Integer32
    MAX-ACCESS accessible-for-notify
    STATUS current
    DESCRIPTION
        "Parameter 'authentication-time' in event PPP.90"
    ::= { pppEventObjects90 8 }

ppp90-compression-time OBJECT-TYPE
    SYNTAX Integer32
    MAX-ACCESS accessible-for-notify
    STATUS current
    DESCRIPTION
        "Parameter 'compression-time' in event PPP.90"
    ::= { pppEventObjects90 9 }

ppp90-device-status OBJECT-TYPE
    SYNTAX Integer32
    MAX-ACCESS accessible-for-notify
    STATUS current
    DESCRIPTION
        "Parameter 'device-status' in event PPP.90"
    ::= { pppEventObjects90 10 }

pppEventObjects91 OBJECT-IDENTITY
    STATUS current
    DESCRIPTION
        "Event PPP.91
        An error occurred negotiating the PPP connection."
    ::= { pppEventsGroup 91 }

ppp91-serial-number OBJECT-TYPE
    SYNTAX DisplayString
    MAX-ACCESS accessible-for-notify
    STATUS current
    DESCRIPTION
        "Parameter 'serial-number' in event PPP.91"
    ::= { pppEventObjects91 1 }

ppp91-hostname OBJECT-TYPE
    SYNTAX DisplayString
    MAX-ACCESS accessible-for-notify
    STATUS current
    DESCRIPTION
        "Parameter 'hostname' in event PPP.91"
    ::= { pppEventObjects91 2 }

ppp91-network OBJECT-TYPE
    SYNTAX Integer32
    MAX-ACCESS accessible-for-notify
    STATUS current
    DESCRIPTION
        "Parameter 'network' in event PPP.91"
    ::= { pppEventObjects91 3 }

ppp91-error-identifier OBJECT-TYPE
    SYNTAX Integer32
    MAX-ACCESS accessible-for-notify
    STATUS current
    DESCRIPTION
        "Parameter 'error-identifier' in event PPP.91"
    ::= { pppEventObjects91 4 }

ppp91-date OBJECT-TYPE
    SYNTAX DisplayString
    MAX-ACCESS accessible-for-notify
    STATUS current
    DESCRIPTION
        "Parameter 'date' in event PPP.91"
    ::= { pppEventObjects91 5 }

ppp91-error-code OBJECT-TYPE
    SYNTAX Integer32
    MAX-ACCESS accessible-for-notify
    STATUS current
    DESCRIPTION
        "Parameter 'error-code' in event PPP.91"
    ::= { pppEventObjects91 6 }

pppEventObjects92 OBJECT-IDENTITY
    STATUS current
    DESCRIPTION
        "Event PPP.92
        This messages specifies the protocol which was rejected in
        LCP Protocol Reject frame."
    ::= { pppEventsGroup 92 }

ppp92-link-name OBJECT-TYPE
    SYNTAX DisplayString
    MAX-ACCESS accessible-for-notify
    STATUS current
    DESCRIPTION
        "Parameter 'link name' in event PPP.92"
    ::= { pppEventObjects92 1 }

ppp92-protocol OBJECT-TYPE
    SYNTAX Integer32
    MAX-ACCESS accessible-for-notify
    STATUS current
    DESCRIPTION
        "Parameter 'protocol' in event PPP.92"
    ::= { pppEventObjects92 2 }

ppp92-dump OBJECT-TYPE
    SYNTAX DisplayString
    MAX-ACCESS accessible-for-notify
    STATUS current
    DESCRIPTION
        "Parameter 'dump' in event PPP.92"
    ::= { pppEventObjects92 3 }

pppEventObjects93 OBJECT-IDENTITY
    STATUS current
    DESCRIPTION
        "Event PPP.93
        IPCP generic option."
    ::= { pppEventsGroup 93 }

ppp93-link-name OBJECT-TYPE
    SYNTAX DisplayString
    MAX-ACCESS accessible-for-notify
    STATUS current
    DESCRIPTION
        "Parameter 'link name' in event PPP.93"
    ::= { pppEventObjects93 1 }

ppp93-IPCP-option OBJECT-TYPE
    SYNTAX DisplayString
    MAX-ACCESS accessible-for-notify
    STATUS current
    DESCRIPTION
        "Parameter 'IPCP option' in event PPP.93"
    ::= { pppEventObjects93 2 }

ppp93-dump OBJECT-TYPE
    SYNTAX DisplayString
    MAX-ACCESS accessible-for-notify
    STATUS current
    DESCRIPTION
        "Parameter 'dump' in event PPP.93"
    ::= { pppEventObjects93 3 }

pppEventObjects94 OBJECT-IDENTITY
    STATUS current
    DESCRIPTION
        "Event PPP.94
        IPCP generic parameter (associated to an option)."
    ::= { pppEventsGroup 94 }

ppp94-link-name OBJECT-TYPE
    SYNTAX DisplayString
    MAX-ACCESS accessible-for-notify
    STATUS current
    DESCRIPTION
        "Parameter 'link name' in event PPP.94"
    ::= { pppEventObjects94 1 }

ppp94-IPCP-option-parameter OBJECT-TYPE
    SYNTAX DisplayString
    MAX-ACCESS accessible-for-notify
    STATUS current
    DESCRIPTION
        "Parameter 'IPCP option parameter' in event PPP.94"
    ::= { pppEventObjects94 2 }

pppEventObjects95 OBJECT-IDENTITY
    STATUS current
    DESCRIPTION
        "Event PPP.95
        Generic LLC information trace."
    ::= { pppEventsGroup 95 }

ppp95-link-name OBJECT-TYPE
    SYNTAX DisplayString
    MAX-ACCESS accessible-for-notify
    STATUS current
    DESCRIPTION
        "Parameter 'link name' in event PPP.95"
    ::= { pppEventObjects95 1 }

ppp95-information OBJECT-TYPE
    SYNTAX DisplayString
    MAX-ACCESS accessible-for-notify
    STATUS current
    DESCRIPTION
        "Parameter 'information' in event PPP.95"
    ::= { pppEventObjects95 2 }

pppEventObjects100 OBJECT-IDENTITY
    STATUS current
    DESCRIPTION
        "Event PPP.100
        PPP POS, UDP message control management."
    ::= { pppEventsGroup 100 }

ppp100-message OBJECT-TYPE
    SYNTAX DisplayString
    MAX-ACCESS accessible-for-notify
    STATUS current
    DESCRIPTION
        "Parameter 'message' in event PPP.100"
    ::= { pppEventObjects100 1 }


pppNotification1 NOTIFICATION-TYPE
    OBJECTS { 
              ppp1-interface 
            }
    STATUS current
    DESCRIPTION
        "Notification of Event PPP.1

        Message: 'Interface $1 ready'

        Parameters list:
              $1: ppp1-interface

        Selftest successfully completed."
    ::= { pppNotificationsPrefix 1 }

pppNotification2 NOTIFICATION-TYPE
    OBJECTS { 
              ppp2-interface 
            }
    STATUS current
    DESCRIPTION
        "Notification of Event PPP.2

        Message: 'Interface $1 down'

        Parameters list:
              $1: ppp2-interface

        The selftest indicates that the base interfaces are all down."
    ::= { pppNotificationsPrefix 2 }

pppNotification3 NOTIFICATION-TYPE
    OBJECTS { 
              ppp3-linkPPP, 
              ppp3-size,
              ppp3-MRU 
            }
    STATUS current
    DESCRIPTION
        "Notification of Event PPP.3

        Message: '$1 In frame, MRU exceeded. Size $2, MRU $3'

        Parameters list:
              $1: ppp3-linkPPP
              $2: ppp3-size
              $3: ppp3-MRU

        The MRU has been exceeded in an incoming packet in the indicated link."
    ::= { pppNotificationsPrefix 3 }

pppNotification4 NOTIFICATION-TYPE
    OBJECTS { 
              ppp4-linkPPP, 
              ppp4-action 
            }
    STATUS current
    DESCRIPTION
        "Notification of Event PPP.4

        Message: '$1 MP fragment received out-of-order inside a link [$2]'

        Parameters list:
              $1: ppp4-linkPPP
              $2: ppp4-action

        A multilink PPP fragment has been received out-of-order. Queue is flushed
        or link reordered."
    ::= { pppNotificationsPrefix 4 }

pppNotification5 NOTIFICATION-TYPE
    OBJECTS { 
              ppp5-link-name, 
              ppp5-sequence,
              ppp5-classes,
              ppp5-dump 
            }
    STATUS current
    DESCRIPTION
        "Notification of Event PPP.5

        Message: '$1 LCP   Multilink Header Format: seq $2 classes $3 (0x$4)'

        Parameters list:
              $1: ppp5-link-name
              $2: ppp5-sequence
              $3: ppp5-classes
              $4: ppp5-dump

        Multilink Header Format option description."
    ::= { pppNotificationsPrefix 5 }

pppNotification6 NOTIFICATION-TYPE
    OBJECTS { 
              ppp6-linkPPP 
            }
    STATUS current
    DESCRIPTION
        "Notification of Event PPP.6

        Message: '$1 MP Multiclass Multilink negotiated'

        Parameters list:
              $1: ppp6-linkPPP

        Multiclass Multilink negotiated in the MP bundle."
    ::= { pppNotificationsPrefix 6 }

pppNotification7 NOTIFICATION-TYPE
    OBJECTS { 
              ppp7-linkPPP 
            }
    STATUS current
    DESCRIPTION
        "Notification of Event PPP.7

        Message: '$1 MP Real Time Frame'

        Parameters list:
              $1: ppp7-linkPPP

        MP Real Time Frame."
    ::= { pppNotificationsPrefix 7 }

pppNotification8 NOTIFICATION-TYPE
    STATUS current
    DESCRIPTION
        "Notification of Event PPP.8

        Message: '---'

        Reserved for possible future use."
    ::= { pppNotificationsPrefix 8 }

pppNotification9 NOTIFICATION-TYPE
    STATUS current
    DESCRIPTION
        "Notification of Event PPP.9

        Message: '---'

        Reserved for possible future use."
    ::= { pppNotificationsPrefix 9 }

pppNotification10 NOTIFICATION-TYPE
    STATUS current
    DESCRIPTION
        "Notification of Event PPP.10

        Message: '---'

        Reserved for possible future use."
    ::= { pppNotificationsPrefix 10 }

pppNotification11 NOTIFICATION-TYPE
    OBJECTS { 
              ppp11-linkPPP, 
              ppp11-receivedIn-or-sentOut,
              ppp11-protocol,
              ppp11-size 
            }
    STATUS current
    DESCRIPTION
        "Notification of Event PPP.11

        Message: '$1 $2 frame, protocol type 0x$3, size $4'

        Parameters list:
              $1: ppp11-linkPPP
              $2: ppp11-receivedIn-or-sentOut
              $3: ppp11-protocol
              $4: ppp11-size

        Received/sent frame from the protocol specified by a PPP interface."
    ::= { pppNotificationsPrefix 11 }

pppNotification12 NOTIFICATION-TYPE
    OBJECTS { 
              ppp12-linkPPP, 
              ppp12-receivedIn-or-sentOut,
              ppp12-protocol,
              ppp12-result 
            }
    STATUS current
    DESCRIPTION
        "Notification of Event PPP.12

        Message: '$1 $2 PFC frame, type 0x$3 [result: $4]'

        Parameters list:
              $1: ppp12-linkPPP
              $2: ppp12-receivedIn-or-sentOut
              $3: ppp12-protocol
              $4: ppp12-result

        Frame received with Protocol Field Compression (PFC)."
    ::= { pppNotificationsPrefix 12 }

pppNotification13 NOTIFICATION-TYPE
    OBJECTS { 
              ppp13-linkPPP, 
              ppp13-compressedIn-or-uncompressedOut,
              ppp13-action,
              ppp13-protocol,
              ppp13-result 
            }
    STATUS current
    DESCRIPTION
        "Notification of Event PPP.13

        Message: '$1 $2 $3 VJ frame, type 0x$4 [result: $5]'

        Parameters list:
              $1: ppp13-linkPPP
              $2: ppp13-compressedIn-or-uncompressedOut
              $3: ppp13-action
              $4: ppp13-protocol
              $5: ppp13-result

        A Van Jacobson frame has been compressed/decompressed (indicating
        the result of the operation)."
    ::= { pppNotificationsPrefix 13 }

pppNotification14 NOTIFICATION-TYPE
    OBJECTS { 
              ppp14-linkPPP, 
              ppp14-compressedIn-or-uncompressedOut,
              ppp14-action,
              ppp14-protocol,
              ppp14-result 
            }
    STATUS current
    DESCRIPTION
        "Notification of Event PPP.14

        Message: '$1 $2 $3 IPHC frame, type 0x$4 [result: $5]'

        Parameters list:
              $1: ppp14-linkPPP
              $2: ppp14-compressedIn-or-uncompressedOut
              $3: ppp14-action
              $4: ppp14-protocol
              $5: ppp14-result

        An IPHC frame has been compressed/decompressed (indicating the result
        of the operation)."
    ::= { pppNotificationsPrefix 14 }

pppNotification15 NOTIFICATION-TYPE
    OBJECTS { 
              ppp15-linkPPP, 
              ppp15-compressedIn-or-uncompressedOut,
              ppp15-action,
              ppp15-protocol,
              ppp15-result 
            }
    STATUS current
    DESCRIPTION
        "Notification of Event PPP.15

        Message: '$1 $2 $3 CCP frame, type 0x$4 [result: $5]'

        Parameters list:
              $1: ppp15-linkPPP
              $2: ppp15-compressedIn-or-uncompressedOut
              $3: ppp15-action
              $4: ppp15-protocol
              $5: ppp15-result

        A CCP frame has been compressed/decompressed (indicating the result
        of the operation)."
    ::= { pppNotificationsPrefix 15 }

pppNotification16 NOTIFICATION-TYPE
    OBJECTS { 
              ppp16-linkPPP, 
              ppp16-receivedIn-or-sentOut,
              ppp16-request-ack 
            }
    STATUS current
    DESCRIPTION
        "Notification of Event PPP.16

        Message: '$1 $2 CCP Reset $3'

        Parameters list:
              $1: ppp16-linkPPP
              $2: ppp16-receivedIn-or-sentOut
              $3: ppp16-request-ack

        Se ha enviado/recibido un CCP Reset Request/Ack."
    ::= { pppNotificationsPrefix 16 }

pppNotification17 NOTIFICATION-TYPE
    OBJECTS { 
              ppp17-linkPPP, 
              ppp17-created-or-deleted 
            }
    STATUS current
    DESCRIPTION
        "Notification of Event PPP.17

        Message: '$1 MP $2 bundle'

        Parameters list:
              $1: ppp17-linkPPP
              $2: ppp17-created-or-deleted

        An MP bundle has been created or eliminated."
    ::= { pppNotificationsPrefix 17 }

pppNotification18 NOTIFICATION-TYPE
    OBJECTS { 
              ppp18-linkPPP, 
              ppp18-local-or-remote,
              ppp18-MRRU 
            }
    STATUS current
    DESCRIPTION
        "Notification of Event PPP.18

        Message: '$1 MP $2 MRRU: $3'

        Parameters list:
              $1: ppp18-linkPPP
              $2: ppp18-local-or-remote
              $3: ppp18-MRRU

        MRRU negotiated in the MP bundle."
    ::= { pppNotificationsPrefix 18 }

pppNotification19 NOTIFICATION-TYPE
    OBJECTS { 
              ppp19-linkPPP, 
              ppp19-local-or-remote 
            }
    STATUS current
    DESCRIPTION
        "Notification of Event PPP.19

        Message: '$1 MP $2 SSN header'

        Parameters list:
              $1: ppp19-linkPPP
              $2: ppp19-local-or-remote

        SSN format (Short Sequence Number) negotiated in the MP bundle."
    ::= { pppNotificationsPrefix 19 }

pppNotification20 NOTIFICATION-TYPE
    OBJECTS { 
              ppp20-linkPPP, 
              ppp20-local-or-remote,
              ppp20-Endpoint-class,
              ppp20-Endpoint-value 
            }
    STATUS current
    DESCRIPTION
        "Notification of Event PPP.20

        Message: '$1 MP $2 EndPoint: class $3, value $4'

        Parameters list:
              $1: ppp20-linkPPP
              $2: ppp20-local-or-remote
              $3: ppp20-Endpoint-class
              $4: ppp20-Endpoint-value

        Endpoint Discriminator used in the MP bundle."
    ::= { pppNotificationsPrefix 20 }

pppNotification21 NOTIFICATION-TYPE
    OBJECTS { 
              ppp21-linkPPP, 
              ppp21-added-or-removed 
            }
    STATUS current
    DESCRIPTION
        "Notification of Event PPP.21

        Message: '$1 MP link $2 bundle'

        Parameters list:
              $1: ppp21-linkPPP
              $2: ppp21-added-or-removed

        A PPP link has been added to or removed from an MP bundle."
    ::= { pppNotificationsPrefix 21 }

pppNotification22 NOTIFICATION-TYPE
    OBJECTS { 
              ppp22-linkPPP, 
              ppp22-flags,
              ppp22-received-sequence,
              ppp22-expected-sequence,
              ppp22-action,
              ppp22-size 
            }
    STATUS current
    DESCRIPTION
        "Notification of Event PPP.22

        Message: '$1 In MP frame, flags 0x$2, seq 0x$3 (exp 0x$4)[$5], size $6'

        Parameters list:
              $1: ppp22-linkPPP
              $2: ppp22-flags
              $3: ppp22-received-sequence
              $4: ppp22-expected-sequence
              $5: ppp22-action
              $6: ppp22-size

        A multilink PPP frame has been received with a determined sequence
        number (the expected sequence number is displayed and the corresponding
        action: accept, discard or queue). Includes the flags and
        the frame size."
    ::= { pppNotificationsPrefix 22 }

pppNotification23 NOTIFICATION-TYPE
    OBJECTS { 
              ppp23-linkPPP, 
              ppp23-flags,
              ppp23-transmission-sequence,
              ppp23-size 
            }
    STATUS current
    DESCRIPTION
        "Notification of Event PPP.23

        Message: '$1 Out MP frame, flags 0x$2, seq 0x$3, size $4'

        Parameters list:
              $1: ppp23-linkPPP
              $2: ppp23-flags
              $3: ppp23-transmission-sequence
              $4: ppp23-size

        A multilink PPP frame has been transmitted (the transmission sequence
        number, the flags and the frame size is displayed)."
    ::= { pppNotificationsPrefix 23 }

pppNotification24 NOTIFICATION-TYPE
    OBJECTS { 
              ppp24-linkPPP 
            }
    STATUS current
    DESCRIPTION
        "Notification of Event PPP.24

        Message: '$1 MP Queue exceeds MAX Items'

        Parameters list:
              $1: ppp24-linkPPP

        The maximum number of queued multilink PPP fragments has been exceeded."
    ::= { pppNotificationsPrefix 24 }

pppNotification25 NOTIFICATION-TYPE
    OBJECTS { 
              ppp25-linkPPP, 
              ppp25-sequence 
            }
    STATUS current
    DESCRIPTION
        "Notification of Event PPP.25

        Message: '$1 MP found END fragment: 0x$2'

        Parameters list:
              $1: ppp25-linkPPP
              $2: ppp25-sequence

        A fragment with the MP frame end flag has been found (END) however
        the beginning part of the frame is not available."
    ::= { pppNotificationsPrefix 25 }

pppNotification26 NOTIFICATION-TYPE
    OBJECTS { 
              ppp26-linkPPP, 
              ppp26-compressedIn-or-uncompressedOut,
              ppp26-action,
              ppp26-protocol,
              ppp26-result 
            }
    STATUS current
    DESCRIPTION
        "Notification of Event PPP.26

        Message: '$1 $2 $3 VJ frame, type 0x$4 [result: $5]'

        Parameters list:
              $1: ppp26-linkPPP
              $2: ppp26-compressedIn-or-uncompressedOut
              $3: ppp26-action
              $4: ppp26-protocol
              $5: ppp26-result

        An error has been produced compressing/decompressing
        a Van Jacobson frame."
    ::= { pppNotificationsPrefix 26 }

pppNotification27 NOTIFICATION-TYPE
    OBJECTS { 
              ppp27-linkPPP, 
              ppp27-compressedIn-or-uncompressedOut,
              ppp27-action,
              ppp27-protocol,
              ppp27-result 
            }
    STATUS current
    DESCRIPTION
        "Notification of Event PPP.27

        Message: '$1 $2 $3 IPHC frame, type 0x$4 [result: $5]'

        Parameters list:
              $1: ppp27-linkPPP
              $2: ppp27-compressedIn-or-uncompressedOut
              $3: ppp27-action
              $4: ppp27-protocol
              $5: ppp27-result

        An error has been produced compressing/decompressing a IPHC frame."
    ::= { pppNotificationsPrefix 27 }

pppNotification28 NOTIFICATION-TYPE
    OBJECTS { 
              ppp28-linkPPP, 
              ppp28-compressedIn-or-uncompressedOut,
              ppp28-action,
              ppp28-protocol,
              ppp28-result 
            }
    STATUS current
    DESCRIPTION
        "Notification of Event PPP.28

        Message: '$1 $2 $3 CCP frame, type 0x$4 [result: $5]'

        Parameters list:
              $1: ppp28-linkPPP
              $2: ppp28-compressedIn-or-uncompressedOut
              $3: ppp28-action
              $4: ppp28-protocol
              $5: ppp28-result

        An error has been produced compressing/decompressing a CCP frame."
    ::= { pppNotificationsPrefix 28 }

pppNotification29 NOTIFICATION-TYPE
    OBJECTS { 
              ppp29-link-name, 
              ppp29-user,
              ppp29-action 
            }
    STATUS current
    DESCRIPTION
        "Notification of Event PPP.29

        Message: '$1 L2TP session ($2) $3'

        Parameters list:
              $1: ppp29-link-name
              $2: ppp29-user
              $3: ppp29-action

        Indicates a request/establishment of an L2TP session."
    ::= { pppNotificationsPrefix 29 }

pppNotification30 NOTIFICATION-TYPE
    OBJECTS { 
              ppp30-linkPPP, 
              ppp30-information-message 
            }
    STATUS current
    DESCRIPTION
        "Notification of Event PPP.30

        Message: '$1 MP $2'

        Parameters list:
              $1: ppp30-linkPPP
              $2: ppp30-information-message

        Indicates an unusual situation in Multilink PPP."
    ::= { pppNotificationsPrefix 30 }

pppNotification31 NOTIFICATION-TYPE
    OBJECTS { 
              ppp31-link-name, 
              ppp31-direction,
              ppp31-code,
              ppp31-BCP-state,
              ppp31-identifier,
              ppp31-length 
            }
    STATUS current
    DESCRIPTION
        "Notification of Event PPP.31

        Message: '$1 BCP $2 $3 [$4] id $5 len $6'

        Parameters list:
              $1: ppp31-link-name
              $2: ppp31-direction
              $3: ppp31-code
              $4: ppp31-BCP-state
              $5: ppp31-identifier
              $6: ppp31-length

        BCP packet description."
    ::= { pppNotificationsPrefix 31 }

pppNotification32 NOTIFICATION-TYPE
    OBJECTS { 
              ppp32-link-name, 
              ppp32-id,
              ppp32-dump 
            }
    STATUS current
    DESCRIPTION
        "Notification of Event PPP.32

        Message: '$1 BCP   Bridge ID $2, (0x$3)'

        Parameters list:
              $1: ppp32-link-name
              $2: ppp32-id
              $3: ppp32-dump

        BCP Bridge ID option"
    ::= { pppNotificationsPrefix 32 }

pppNotification33 NOTIFICATION-TYPE
    OBJECTS { 
              ppp33-link-name, 
              ppp33-id,
              ppp33-dump 
            }
    STATUS current
    DESCRIPTION
        "Notification of Event PPP.33

        Message: '$1 BCP   Line ID $2, (0x$3)'

        Parameters list:
              $1: ppp33-link-name
              $2: ppp33-id
              $3: ppp33-dump

        BCP Line ID option."
    ::= { pppNotificationsPrefix 33 }

pppNotification34 NOTIFICATION-TYPE
    OBJECTS { 
              ppp34-link-name, 
              ppp34-maccode,
              ppp34-macname,
              ppp34-dump 
            }
    STATUS current
    DESCRIPTION
        "Notification of Event PPP.34

        Message: '$1 BCP   MAC Support $2 $3, (0x$4)'

        Parameters list:
              $1: ppp34-link-name
              $2: ppp34-maccode
              $3: ppp34-macname
              $4: ppp34-dump

        BCP MAC Support option."
    ::= { pppNotificationsPrefix 34 }

pppNotification35 NOTIFICATION-TYPE
    OBJECTS { 
              ppp35-link-name, 
              ppp35-comp,
              ppp35-dump 
            }
    STATUS current
    DESCRIPTION
        "Notification of Event PPP.35

        Message: '$1 BCP   Tinygram Compression $2, (0x$3)'

        Parameters list:
              $1: ppp35-link-name
              $2: ppp35-comp
              $3: ppp35-dump

        BCP Tinygram compression option."
    ::= { pppNotificationsPrefix 35 }

pppNotification36 NOTIFICATION-TYPE
    OBJECTS { 
              ppp36-link-name, 
              ppp36-lanid,
              ppp36-dump 
            }
    STATUS current
    DESCRIPTION
        "Notification of Event PPP.36

        Message: '$1 BCP   LAN Identification $2, (0x$3)'

        Parameters list:
              $1: ppp36-link-name
              $2: ppp36-lanid
              $3: ppp36-dump

        BCP LAN Identification option."
    ::= { pppNotificationsPrefix 36 }

pppNotification37 NOTIFICATION-TYPE
    OBJECTS { 
              ppp37-link-name, 
              ppp37-macaddr,
              ppp37-dump 
            }
    STATUS current
    DESCRIPTION
        "Notification of Event PPP.37

        Message: '$1 BCP   MAC Address $2, (0x$3)'

        Parameters list:
              $1: ppp37-link-name
              $2: ppp37-macaddr
              $3: ppp37-dump

        BCP MAC Address option."
    ::= { pppNotificationsPrefix 37 }

pppNotification38 NOTIFICATION-TYPE
    OBJECTS { 
              ppp38-link-name, 
              ppp38-oldstp,
              ppp38-dump 
            }
    STATUS current
    DESCRIPTION
        "Notification of Event PPP.38

        Message: '$1 BCP   Old Spanning Tree Protocol $2, (0x$3)'

        Parameters list:
              $1: ppp38-link-name
              $2: ppp38-oldstp
              $3: ppp38-dump

        BCP Old Spanning Tree Protocol option."
    ::= { pppNotificationsPrefix 38 }

pppNotification39 NOTIFICATION-TYPE
    OBJECTS { 
              ppp39-link-name, 
              ppp39-tagged,
              ppp39-dump 
            }
    STATUS current
    DESCRIPTION
        "Notification of Event PPP.39

        Message: '$1 BCP   Tagged Frame $2, (0x$3)'

        Parameters list:
              $1: ppp39-link-name
              $2: ppp39-tagged
              $3: ppp39-dump

        BCP Tagged Frame option."
    ::= { pppNotificationsPrefix 39 }

pppNotification40 NOTIFICATION-TYPE
    OBJECTS { 
              ppp40-link-name, 
              ppp40-dump 
            }
    STATUS current
    DESCRIPTION
        "Notification of Event PPP.40

        Message: '$1 BCP   Management Inline supported, (0x$2)'

        Parameters list:
              $1: ppp40-link-name
              $2: ppp40-dump

        BCP Management Inline support option."
    ::= { pppNotificationsPrefix 40 }

pppNotification41 NOTIFICATION-TYPE
    OBJECTS { 
              ppp41-link-name, 
              ppp41-dump 
            }
    STATUS current
    DESCRIPTION
        "Notification of Event PPP.41

        Message: '$1 BCP   Unknown option (0x$2)'

        Parameters list:
              $1: ppp41-link-name
              $2: ppp41-dump

        BCP unknown option."
    ::= { pppNotificationsPrefix 41 }

pppNotification42 NOTIFICATION-TYPE
    OBJECTS { 
              ppp42-link-name, 
              ppp42-information 
            }
    STATUS current
    DESCRIPTION
        "Notification of Event PPP.42

        Message: '$1 BCP $2'

        Parameters list:
              $1: ppp42-link-name
              $2: ppp42-information

        BCP information trace."
    ::= { pppNotificationsPrefix 42 }

pppNotification43 NOTIFICATION-TYPE
    OBJECTS { 
              ppp43-link-name 
            }
    STATUS current
    DESCRIPTION
        "Notification of Event PPP.43

        Message: '$1 DROP: Bridging not enabled on this interface'

        Parameters list:
              $1: ppp43-link-name

        A frame was received of a bridge type defined in RFC 2878.
        However, since bridging has not been enabled on this circuit, frame
        is being discarded."
    ::= { pppNotificationsPrefix 43 }

pppNotification44 NOTIFICATION-TYPE
    OBJECTS { 
              ppp44-link-name 
            }
    STATUS current
    DESCRIPTION
        "Notification of Event PPP.44

        Message: '$1 DROP: Bridge port not forwarding on this interface'

        Parameters list:
              $1: ppp44-link-name

        A bridge frame is being discarded as a bridge port is not in
        forwarding state."
    ::= { pppNotificationsPrefix 44 }

pppNotification45 NOTIFICATION-TYPE
    OBJECTS { 
              ppp45-link-name, 
              ppp45-source-mac,
              ppp45-dest-mac 
            }
    STATUS current
    DESCRIPTION
        "Notification of Event PPP.45

        Message: '$1 DROP: $2->$3, Frame to bridge port behavior mismatch on this interface'

        Parameters list:
              $1: ppp45-link-name
              $2: ppp45-source-mac
              $3: ppp45-dest-mac

        A bridged frame has been received and is being discarded due to mismatch
        in the frame type versus the bridge port behavior."
    ::= { pppNotificationsPrefix 45 }

pppNotification46 NOTIFICATION-TYPE
    OBJECTS { 
              ppp46-link-name, 
              ppp46-type 
            }
    STATUS current
    DESCRIPTION
        "Notification of Event PPP.46

        Message: '$1 DROP: Unsupported bridge frame type = $2 on this interface'

        Parameters list:
              $1: ppp46-link-name
              $2: ppp46-type

        An unsupported bridge frame type has been encountered."
    ::= { pppNotificationsPrefix 46 }

pppNotification47 NOTIFICATION-TYPE
    STATUS current
    DESCRIPTION
        "Notification of Event PPP.47

        Message: '---'

        Reserved for possible future use."
    ::= { pppNotificationsPrefix 47 }

pppNotification48 NOTIFICATION-TYPE
    STATUS current
    DESCRIPTION
        "Notification of Event PPP.48

        Message: '---'

        Reserved for possible future use."
    ::= { pppNotificationsPrefix 48 }

pppNotification49 NOTIFICATION-TYPE
    OBJECTS { 
              ppp49-link-name, 
              ppp49-option,
              ppp49-dump 
            }
    STATUS current
    DESCRIPTION
        "Notification of Event PPP.49

        Message: '$1 LCP   $2 (0x$3)'

        Parameters list:
              $1: ppp49-link-name
              $2: ppp49-option
              $3: ppp49-dump

        Unsupported LCP option description."
    ::= { pppNotificationsPrefix 49 }

pppNotification50 NOTIFICATION-TYPE
    OBJECTS { 
              ppp50-link-name, 
              ppp50-dump 
            }
    STATUS current
    DESCRIPTION
        "Notification of Event PPP.50

        Message: '$1 LCP   (0x$2)'

        Parameters list:
              $1: ppp50-link-name
              $2: ppp50-dump

        LCP packet data."
    ::= { pppNotificationsPrefix 50 }

pppNotification51 NOTIFICATION-TYPE
    OBJECTS { 
              ppp51-link-name, 
              ppp51-direction,
              ppp51-code,
              ppp51-LCP-state,
              ppp51-identifier,
              ppp51-length 
            }
    STATUS current
    DESCRIPTION
        "Notification of Event PPP.51

        Message: '$1 LCP $2 $3 [$4] id $5 len $6'

        Parameters list:
              $1: ppp51-link-name
              $2: ppp51-direction
              $3: ppp51-code
              $4: ppp51-LCP-state
              $5: ppp51-identifier
              $6: ppp51-length

        LCP packet description."
    ::= { pppNotificationsPrefix 51 }

pppNotification52 NOTIFICATION-TYPE
    OBJECTS { 
              ppp52-link-name, 
              ppp52-mru,
              ppp52-dump 
            }
    STATUS current
    DESCRIPTION
        "Notification of Event PPP.52

        Message: '$1 LCP   MRU $2 (0x$3)'

        Parameters list:
              $1: ppp52-link-name
              $2: ppp52-mru
              $3: ppp52-dump

        MRU option description."
    ::= { pppNotificationsPrefix 52 }

pppNotification53 NOTIFICATION-TYPE
    OBJECTS { 
              ppp53-link-name, 
              ppp53-async-map,
              ppp53-dump 
            }
    STATUS current
    DESCRIPTION
        "Notification of Event PPP.53

        Message: '$1 LCP   AsyncMap $2 (0x$3)'

        Parameters list:
              $1: ppp53-link-name
              $2: ppp53-async-map
              $3: ppp53-dump

        Asynchronous Control Character Map (ACCM) option description."
    ::= { pppNotificationsPrefix 53 }

pppNotification54 NOTIFICATION-TYPE
    OBJECTS { 
              ppp54-link-name, 
              ppp54-auth-protocol,
              ppp54-dump 
            }
    STATUS current
    DESCRIPTION
        "Notification of Event PPP.54

        Message: '$1 LCP   AuthProt $2 (0x$3)'

        Parameters list:
              $1: ppp54-link-name
              $2: ppp54-auth-protocol
              $3: ppp54-dump

        Authentication option description."
    ::= { pppNotificationsPrefix 54 }

pppNotification55 NOTIFICATION-TYPE
    OBJECTS { 
              ppp55-link-name, 
              ppp55-magic-number,
              ppp55-dump 
            }
    STATUS current
    DESCRIPTION
        "Notification of Event PPP.55

        Message: '$1 LCP   MagicNumber $2 (0x$3)'

        Parameters list:
              $1: ppp55-link-name
              $2: ppp55-magic-number
              $3: ppp55-dump

        Magic Number option description."
    ::= { pppNotificationsPrefix 55 }

pppNotification56 NOTIFICATION-TYPE
    OBJECTS { 
              ppp56-link-name, 
              ppp56-dump 
            }
    STATUS current
    DESCRIPTION
        "Notification of Event PPP.56

        Message: '$1 LCP   ProtComp available (0x$2)'

        Parameters list:
              $1: ppp56-link-name
              $2: ppp56-dump

        Protocol Field Compression option description."
    ::= { pppNotificationsPrefix 56 }

pppNotification57 NOTIFICATION-TYPE
    OBJECTS { 
              ppp57-link-name, 
              ppp57-dump 
            }
    STATUS current
    DESCRIPTION
        "Notification of Event PPP.57

        Message: '$1 LCP   AddrCtrlComp available (0x$2)'

        Parameters list:
              $1: ppp57-link-name
              $2: ppp57-dump

        Address/Control Fields Compression option description."
    ::= { pppNotificationsPrefix 57 }

pppNotification58 NOTIFICATION-TYPE
    OBJECTS { 
              ppp58-link-name, 
              ppp58-mrru,
              ppp58-dump 
            }
    STATUS current
    DESCRIPTION
        "Notification of Event PPP.58

        Message: '$1 LCP   MRRU $2 (0x$3)'

        Parameters list:
              $1: ppp58-link-name
              $2: ppp58-mrru
              $3: ppp58-dump

        MRRU option description."
    ::= { pppNotificationsPrefix 58 }

pppNotification59 NOTIFICATION-TYPE
    OBJECTS { 
              ppp59-link-name, 
              ppp59-dump 
            }
    STATUS current
    DESCRIPTION
        "Notification of Event PPP.59

        Message: '$1 LCP   ShortHeader available (0x$2)'

        Parameters list:
              $1: ppp59-link-name
              $2: ppp59-dump

        Short Sequence Number header format option description."
    ::= { pppNotificationsPrefix 59 }

pppNotification60 NOTIFICATION-TYPE
    OBJECTS { 
              ppp60-link-name, 
              ppp60-class,
              ppp60-dump 
            }
    STATUS current
    DESCRIPTION
        "Notification of Event PPP.60

        Message: '$1 LCP   EndPoint class $2 (0x$3)'

        Parameters list:
              $1: ppp60-link-name
              $2: ppp60-class
              $3: ppp60-dump

        End-Point Discriminator option description."
    ::= { pppNotificationsPrefix 60 }

pppNotification61 NOTIFICATION-TYPE
    OBJECTS { 
              ppp61-link-name, 
              ppp61-dump 
            }
    STATUS current
    DESCRIPTION
        "Notification of Event PPP.61

        Message: '$1 LCP   Unknown option (0x$2)'

        Parameters list:
              $1: ppp61-link-name
              $2: ppp61-dump

        Unknown option description."
    ::= { pppNotificationsPrefix 61 }

pppNotification62 NOTIFICATION-TYPE
    OBJECTS { 
              ppp62-link-name, 
              ppp62-dump 
            }
    STATUS current
    DESCRIPTION
        "Notification of Event PPP.62

        Message: '$1 LCP   Bad option (0x$2)'

        Parameters list:
              $1: ppp62-link-name
              $2: ppp62-dump

        Bad format option description."
    ::= { pppNotificationsPrefix 62 }

pppNotification63 NOTIFICATION-TYPE
    OBJECTS { 
              ppp63-link-name, 
              ppp63-direction,
              ppp63-code,
              ppp63-PAP-state,
              ppp63-identifier,
              ppp63-length 
            }
    STATUS current
    DESCRIPTION
        "Notification of Event PPP.63

        Message: '$1 PAP $2 $3 [$4] id $5 len $6'

        Parameters list:
              $1: ppp63-link-name
              $2: ppp63-direction
              $3: ppp63-code
              $4: ppp63-PAP-state
              $5: ppp63-identifier
              $6: ppp63-length

        PAP packet description."
    ::= { pppNotificationsPrefix 63 }

pppNotification64 NOTIFICATION-TYPE
    OBJECTS { 
              ppp64-link-name, 
              ppp64-peer-id 
            }
    STATUS current
    DESCRIPTION
        "Notification of Event PPP.64

        Message: '$1 PAP   Peer-Id $2'

        Parameters list:
              $1: ppp64-link-name
              $2: ppp64-peer-id

        PAP request peer-id."
    ::= { pppNotificationsPrefix 64 }

pppNotification65 NOTIFICATION-TYPE
    OBJECTS { 
              ppp65-link-name, 
              ppp65-password 
            }
    STATUS current
    DESCRIPTION
        "Notification of Event PPP.65

        Message: '$1 PAP   Password $2'

        Parameters list:
              $1: ppp65-link-name
              $2: ppp65-password

        PAP request password."
    ::= { pppNotificationsPrefix 65 }

pppNotification66 NOTIFICATION-TYPE
    OBJECTS { 
              ppp66-link--name, 
              ppp66-message 
            }
    STATUS current
    DESCRIPTION
        "Notification of Event PPP.66

        Message: '$1 PAP   Message: $2'

        Parameters list:
              $1: ppp66-link--name
              $2: ppp66-message

        PAP reply message."
    ::= { pppNotificationsPrefix 66 }

pppNotification67 NOTIFICATION-TYPE
    OBJECTS { 
              ppp67-link-name, 
              ppp67-direction,
              ppp67-code,
              ppp67-CHAP-state,
              ppp67-identifier,
              ppp67-length 
            }
    STATUS current
    DESCRIPTION
        "Notification of Event PPP.67

        Message: '$1 CHAP $2 $3 [$4] id $5 len $6'

        Parameters list:
              $1: ppp67-link-name
              $2: ppp67-direction
              $3: ppp67-code
              $4: ppp67-CHAP-state
              $5: ppp67-identifier
              $6: ppp67-length

        CHAP packet description."
    ::= { pppNotificationsPrefix 67 }

pppNotification68 NOTIFICATION-TYPE
    OBJECTS { 
              ppp68-link-name, 
              ppp68-peer-name 
            }
    STATUS current
    DESCRIPTION
        "Notification of Event PPP.68

        Message: '$1 CHAP   Peer-Name $2'

        Parameters list:
              $1: ppp68-link-name
              $2: ppp68-peer-name

        CHAP peer name."
    ::= { pppNotificationsPrefix 68 }

pppNotification69 NOTIFICATION-TYPE
    OBJECTS { 
              ppp69-link-name, 
              ppp69-peer-message 
            }
    STATUS current
    DESCRIPTION
        "Notification of Event PPP.69

        Message: '$1 CHAP   Message: $2'

        Parameters list:
              $1: ppp69-link-name
              $2: ppp69-peer-message

        CHAP peer message."
    ::= { pppNotificationsPrefix 69 }

pppNotification70 NOTIFICATION-TYPE
    OBJECTS { 
              ppp70-link-name, 
              ppp70-challenge 
            }
    STATUS current
    DESCRIPTION
        "Notification of Event PPP.70

        Message: '$1 CHAP   Challenge $2'

        Parameters list:
              $1: ppp70-link-name
              $2: ppp70-challenge

        CHAP challenge value."
    ::= { pppNotificationsPrefix 70 }

pppNotification71 NOTIFICATION-TYPE
    OBJECTS { 
              ppp71-link-name, 
              ppp71-md5 
            }
    STATUS current
    DESCRIPTION
        "Notification of Event PPP.71

        Message: '$1 CHAP   MD5 $2'

        Parameters list:
              $1: ppp71-link-name
              $2: ppp71-md5

        CHAP MD5 value."
    ::= { pppNotificationsPrefix 71 }

pppNotification72 NOTIFICATION-TYPE
    OBJECTS { 
              ppp72-link-name, 
              ppp72-direction,
              ppp72-code,
              ppp72-IPCP-state,
              ppp72-identifier,
              ppp72-length 
            }
    STATUS current
    DESCRIPTION
        "Notification of Event PPP.72

        Message: '$1 IPCP $2 $3 [$4] id $5 len $6'

        Parameters list:
              $1: ppp72-link-name
              $2: ppp72-direction
              $3: ppp72-code
              $4: ppp72-IPCP-state
              $5: ppp72-identifier
              $6: ppp72-length

        IPCP packet description."
    ::= { pppNotificationsPrefix 72 }

pppNotification73 NOTIFICATION-TYPE
    OBJECTS { 
              ppp73-link-name, 
              ppp73-address,
              ppp73-dump 
            }
    STATUS current
    DESCRIPTION
        "Notification of Event PPP.73

        Message: '$1 IPCP   Address $2 (0x$3)'

        Parameters list:
              $1: ppp73-link-name
              $2: ppp73-address
              $3: ppp73-dump

        IPCP address option."
    ::= { pppNotificationsPrefix 73 }

pppNotification74 NOTIFICATION-TYPE
    OBJECTS { 
              ppp74-link-name, 
              ppp74-slots,
              ppp74-compression-flag,
              ppp74-dump 
            }
    STATUS current
    DESCRIPTION
        "Notification of Event PPP.74

        Message: '$1 IPCP   CompressProt VJ, $2 slots, comp $3 (0x$4)'

        Parameters list:
              $1: ppp74-link-name
              $2: ppp74-slots
              $3: ppp74-compression-flag
              $4: ppp74-dump

        IPCP Van-Jacobson compression protocol."
    ::= { pppNotificationsPrefix 74 }

pppNotification75 NOTIFICATION-TYPE
    OBJECTS { 
              ppp75-link-name, 
              ppp75-dump 
            }
    STATUS current
    DESCRIPTION
        "Notification of Event PPP.75

        Message: '$1 IPCP   Unknown CompressProt (0x$2)'

        Parameters list:
              $1: ppp75-link-name
              $2: ppp75-dump

        IPCP unknown compression protocol."
    ::= { pppNotificationsPrefix 75 }

pppNotification76 NOTIFICATION-TYPE
    OBJECTS { 
              ppp76-link-name, 
              ppp76-dump 
            }
    STATUS current
    DESCRIPTION
        "Notification of Event PPP.76

        Message: '$1 IPCP   Unknown option (0x$2)'

        Parameters list:
              $1: ppp76-link-name
              $2: ppp76-dump

        IPCP unknown option."
    ::= { pppNotificationsPrefix 76 }

pppNotification77 NOTIFICATION-TYPE
    OBJECTS { 
              ppp77-link-name, 
              ppp77-direction,
              ppp77-code,
              ppp77-CCP-state,
              ppp77-identifier,
              ppp77-length 
            }
    STATUS current
    DESCRIPTION
        "Notification of Event PPP.77

        Message: '$1 CCP $2 $3 [$4] id $5 len $6'

        Parameters list:
              $1: ppp77-link-name
              $2: ppp77-direction
              $3: ppp77-code
              $4: ppp77-CCP-state
              $5: ppp77-identifier
              $6: ppp77-length

        CCP packet description."
    ::= { pppNotificationsPrefix 77 }

pppNotification78 NOTIFICATION-TYPE
    OBJECTS { 
              ppp78-link-name, 
              ppp78-dump 
            }
    STATUS current
    DESCRIPTION
        "Notification of Event PPP.78

        Message: '$1 CCP   LZS-DCP Compression (0x$2)'

        Parameters list:
              $1: ppp78-link-name
              $2: ppp78-dump

        LZS-DCP compression option."
    ::= { pppNotificationsPrefix 78 }

pppNotification79 NOTIFICATION-TYPE
    OBJECTS { 
              ppp79-link-name, 
              ppp79-dump 
            }
    STATUS current
    DESCRIPTION
        "Notification of Event PPP.79

        Message: '$1 CCP   Stac LZS Compression (0x$2)'

        Parameters list:
              $1: ppp79-link-name
              $2: ppp79-dump

        Stac LZS compression option."
    ::= { pppNotificationsPrefix 79 }

pppNotification80 NOTIFICATION-TYPE
    OBJECTS { 
              ppp80-link-name, 
              ppp80-histories 
            }
    STATUS current
    DESCRIPTION
        "Notification of Event PPP.80

        Message: '$1 CCP      History number: $2'

        Parameters list:
              $1: ppp80-link-name
              $2: ppp80-histories

        History number parameter."
    ::= { pppNotificationsPrefix 80 }

pppNotification81 NOTIFICATION-TYPE
    OBJECTS { 
              ppp81-link-name, 
              ppp81-check-mode 
            }
    STATUS current
    DESCRIPTION
        "Notification of Event PPP.81

        Message: '$1 CCP      Check mode: $2'

        Parameters list:
              $1: ppp81-link-name
              $2: ppp81-check-mode

        Check mode parameter."
    ::= { pppNotificationsPrefix 81 }

pppNotification82 NOTIFICATION-TYPE
    OBJECTS { 
              ppp82-link-name, 
              ppp82-process-mode 
            }
    STATUS current
    DESCRIPTION
        "Notification of Event PPP.82

        Message: '$1 CCP      Process mode: $2'

        Parameters list:
              $1: ppp82-link-name
              $2: ppp82-process-mode

        Process mode parameter."
    ::= { pppNotificationsPrefix 82 }

pppNotification83 NOTIFICATION-TYPE
    OBJECTS { 
              ppp83-link-name, 
              ppp83-compression-type,
              ppp83-dump 
            }
    STATUS current
    DESCRIPTION
        "Notification of Event PPP.83

        Message: '$1 CCP   Unknown compression type $2 (0x$3)'

        Parameters list:
              $1: ppp83-link-name
              $2: ppp83-compression-type
              $3: ppp83-dump

        Unknown compression type."
    ::= { pppNotificationsPrefix 83 }

pppNotification84 NOTIFICATION-TYPE
    OBJECTS { 
              ppp84-link-name, 
              ppp84-mode 
            }
    STATUS current
    DESCRIPTION
        "Notification of Event PPP.84

        Message: '$1 PAP required by $2'

        Parameters list:
              $1: ppp84-link-name
              $2: ppp84-mode

        PAP mode description."
    ::= { pppNotificationsPrefix 84 }

pppNotification85 NOTIFICATION-TYPE
    OBJECTS { 
              ppp85-link-name, 
              ppp85-mode 
            }
    STATUS current
    DESCRIPTION
        "Notification of Event PPP.85

        Message: '$1 CHAP required by $2'

        Parameters list:
              $1: ppp85-link-name
              $2: ppp85-mode

        CHAP mode description."
    ::= { pppNotificationsPrefix 85 }

pppNotification86 NOTIFICATION-TYPE
    OBJECTS { 
              ppp86-link-name, 
              ppp86-cause 
            }
    STATUS current
    DESCRIPTION
        "Notification of Event PPP.86

        Message: '$1 LCP Invalid packet ($2)'

        Parameters list:
              $1: ppp86-link-name
              $2: ppp86-cause

        LCP bad packet description."
    ::= { pppNotificationsPrefix 86 }

pppNotification87 NOTIFICATION-TYPE
    OBJECTS { 
              ppp87-link-name, 
              ppp87-information 
            }
    STATUS current
    DESCRIPTION
        "Notification of Event PPP.87

        Message: '$1 LCP $2'

        Parameters list:
              $1: ppp87-link-name
              $2: ppp87-information

        LCP information trace."
    ::= { pppNotificationsPrefix 87 }

pppNotification88 NOTIFICATION-TYPE
    OBJECTS { 
              ppp88-link-name, 
              ppp88-information 
            }
    STATUS current
    DESCRIPTION
        "Notification of Event PPP.88

        Message: '$1 IPCP $2'

        Parameters list:
              $1: ppp88-link-name
              $2: ppp88-information

        IPCP information trace."
    ::= { pppNotificationsPrefix 88 }

pppNotification89 NOTIFICATION-TYPE
    OBJECTS { 
              ppp89-link-name, 
              ppp89-information 
            }
    STATUS current
    DESCRIPTION
        "Notification of Event PPP.89

        Message: '$1 CCP $2'

        Parameters list:
              $1: ppp89-link-name
              $2: ppp89-information

        CCP information trace."
    ::= { pppNotificationsPrefix 89 }

pppNotification90 NOTIFICATION-TYPE
    OBJECTS { 
              ppp90-serial-number, 
              ppp90-hostname,
              ppp90-network,
              ppp90-local-address,
              ppp90-pppoe-disc-time,
              ppp90-lcp-time,
              ppp90-ipcp-time,
              ppp90-authentication-time,
              ppp90-compression-time,
              ppp90-device-status 
            }
    STATUS current
    DESCRIPTION
        "Notification of Event PPP.90

        Message: 'est $1 $2 nt $3, local addr: $4, time PPPoED $5 ms, lcp $6 ms, ipcp $7 ms, auth $8 ms, comp $9 ms dev-st=$10'

        Parameters list:
              $1: ppp90-serial-number
              $2: ppp90-hostname
              $3: ppp90-network
              $4: ppp90-local-address
              $5: ppp90-pppoe-disc-time
              $6: ppp90-lcp-time
              $7: ppp90-ipcp-time
              $8: ppp90-authentication-time
              $9: ppp90-compression-time
              $10: ppp90-device-status

        PPP connection established with the specified negotiation times."
    ::= { pppNotificationsPrefix 90 }

pppNotification91 NOTIFICATION-TYPE
    OBJECTS { 
              ppp91-serial-number, 
              ppp91-hostname,
              ppp91-network,
              ppp91-error-identifier,
              ppp91-date,
              ppp91-error-code 
            }
    STATUS current
    DESCRIPTION
        "Notification of Event PPP.91

        Message: 'conn err $1 $2 nt $3 err-id $4 $5 err $6'

        Parameters list:
              $1: ppp91-serial-number
              $2: ppp91-hostname
              $3: ppp91-network
              $4: ppp91-error-identifier
              $5: ppp91-date
              $6: ppp91-error-code

        An error occurred negotiating the PPP connection."
    ::= { pppNotificationsPrefix 91 }

pppNotification92 NOTIFICATION-TYPE
    OBJECTS { 
              ppp92-link-name, 
              ppp92-protocol,
              ppp92-dump 
            }
    STATUS current
    DESCRIPTION
        "Notification of Event PPP.92

        Message: '$1 LCP   Protocol 0x$2 (0x$3)'

        Parameters list:
              $1: ppp92-link-name
              $2: ppp92-protocol
              $3: ppp92-dump

        This messages specifies the protocol which was rejected in
        LCP Protocol Reject frame."
    ::= { pppNotificationsPrefix 92 }

pppNotification93 NOTIFICATION-TYPE
    OBJECTS { 
              ppp93-link-name, 
              ppp93-IPCP-option,
              ppp93-dump 
            }
    STATUS current
    DESCRIPTION
        "Notification of Event PPP.93

        Message: '$1 IPCP   $2 (0x$3)'

        Parameters list:
              $1: ppp93-link-name
              $2: ppp93-IPCP-option
              $3: ppp93-dump

        IPCP generic option."
    ::= { pppNotificationsPrefix 93 }

pppNotification94 NOTIFICATION-TYPE
    OBJECTS { 
              ppp94-link-name, 
              ppp94-IPCP-option-parameter 
            }
    STATUS current
    DESCRIPTION
        "Notification of Event PPP.94

        Message: '$1 IPCP   $2'

        Parameters list:
              $1: ppp94-link-name
              $2: ppp94-IPCP-option-parameter

        IPCP generic parameter (associated to an option)."
    ::= { pppNotificationsPrefix 94 }

pppNotification95 NOTIFICATION-TYPE
    OBJECTS { 
              ppp95-link-name, 
              ppp95-information 
            }
    STATUS current
    DESCRIPTION
        "Notification of Event PPP.95

        Message: '$1 LLC $2'

        Parameters list:
              $1: ppp95-link-name
              $2: ppp95-information

        Generic LLC information trace."
    ::= { pppNotificationsPrefix 95 }

pppNotification96 NOTIFICATION-TYPE
    STATUS current
    DESCRIPTION
        "Notification of Event PPP.96

        Message: '---'

        Reserved for possible future use."
    ::= { pppNotificationsPrefix 96 }

pppNotification97 NOTIFICATION-TYPE
    STATUS current
    DESCRIPTION
        "Notification of Event PPP.97

        Message: '---'

        Reserved for possible future use."
    ::= { pppNotificationsPrefix 97 }

pppNotification98 NOTIFICATION-TYPE
    STATUS current
    DESCRIPTION
        "Notification of Event PPP.98

        Message: '---'

        Reserved for possible future use."
    ::= { pppNotificationsPrefix 98 }

pppNotification99 NOTIFICATION-TYPE
    STATUS current
    DESCRIPTION
        "Notification of Event PPP.99

        Message: '---'

        Reserved for possible future use."
    ::= { pppNotificationsPrefix 99 }

pppNotification100 NOTIFICATION-TYPE
    OBJECTS { 
              ppp100-message 
            }
    STATUS current
    DESCRIPTION
        "Notification of Event PPP.100

        Message: 'POS message: $1'

        Parameters list:
              $1: ppp100-message

        PPP POS, UDP message control management."
    ::= { pppNotificationsPrefix 100 }


END
