-- =================================================================
-- Copyright (C) 2003 by  HUAWEI TECHNOLOGIES. All rights reserved.
--
-- Description: Demonstrates how to maintain SDL ports
-- Reference:   None
-- Version:     V1.0
-- History:
-- liguanrong, 2003-10-28, SDL MIB first define
-- =================================================================

HUAWEI-SDL-MIB DEFINITIONS ::= BEGIN
IMPORTS
    MODULE-IDENTITY, OBJECT-TYPE, Unsigned32
        FROM SNMPv2-SMI
        
        ifIndex
                FROM IF-MIB
    huaweiUtility
                FROM HUAWEI-MIB;

    hwSDL MODULE-IDENTITY
        LAST-UPDATED
                "0310301523Z"
        ORGANIZATION
                "Huawei Technologies co.,Ltd."
        CONTACT-INFO
                "Kefa Road,
                 Fx-Net Dep, Huawei Technologies Co.,Ltd.
                 Science-Based Industrial Park,
                 Nanshan District,Shenzhen  P.R. China
                 http://www.huawei.com
                 Zip:518057"
        DESCRIPTION
            "
            The HUAWEI-SDL-MIB demonstrates how to maintain SDL ports
            "
        ::= { huaweiUtility 35 }

        hwSDLMibObjects     OBJECT IDENTIFIER   ::= { hwSDL             1 }

        sdlBoardTable OBJECT-TYPE
            SYNTAX      SEQUENCE OF SdlBoardEntry
            MAX-ACCESS  not-accessible
            STATUS      current
            DESCRIPTION
                "
                
                "
            ::= { hwSDLMibObjects 1 }

        sdlBoardEntry OBJECT-TYPE
            SYNTAX      SdlBoardEntry
            MAX-ACCESS  not-accessible
            STATUS      current
            DESCRIPTION
                "
                
                "
            INDEX
                {
                ifIndex
                }
            ::= { sdlBoardTable 1 }

        SdlBoardEntry ::=
            SEQUENCE
                {
                hwSdlBoardRunmode
                    INTEGER,
                hwSdlClockSource
                    INTEGER,
                hwSdlHw1TsInfo
                    Unsigned32,
                hwSdlHw2TsInfo
                    Unsigned32,
                hwSdl1E1TsInfo
                    Unsigned32,
                hwSdl2E1TsInfo
                    Unsigned32,
                hwSdl3E1TsInfo
                    Unsigned32,
                hwSdl4E1TsInfo
                    Unsigned32,
                hwSdl1ShdslTsInfo
                    Unsigned32,
                hwSdl2ShdslTsInfo
                    Unsigned32,
                hwSdl3ShdslTsInfo
                    Unsigned32,
                hwSdl4ShdslTsInfo
                    Unsigned32
                }

        hwSdlBoardRunmode OBJECT-TYPE
            SYNTAX      INTEGER
                {
                hwSdlNormal(1),
                hwSdlTransport(2)
                }
            MAX-ACCESS  read-write
            STATUS      current
            DESCRIPTION
                "

                1.Normal
                2.Transport
                "
            ::= { sdlBoardEntry 1 }

        hwSdlClockSource OBJECT-TYPE
            SYNTAX      INTEGER
                {
                hwHWClock(1),
                hwE1PORT1(2),
                hwE1PORT2(3),
                hwE1PORT3(4),
                hwE1PORT4(5),
                hwSHDSLPORT1(6),
                hwSHDSLPORT3(7)
                }
            MAX-ACCESS  read-write
            STATUS      current
            DESCRIPTION
                "
                1. HW clock
                2. First E1 clock
                3. Second E1 clock
                4. Third E1 clock
                5. Fourth E1 clock
                6. First SHDSL clock
                7. Third SHDSL clock

              
                "
            ::= { sdlBoardEntry 2 }

        hwSdlHw1TsInfo OBJECT-TYPE
            SYNTAX      Unsigned32(0..4294967295)
            MAX-ACCESS  read-only
            STATUS      current
            DESCRIPTION
                "
                Each bit figures a channel used or nor, '0' figure not used, '1' figures used

                "
            ::= { sdlBoardEntry 3 }

        hwSdlHw2TsInfo OBJECT-TYPE
            SYNTAX      Unsigned32(0..4294967295)
            MAX-ACCESS  read-only
            STATUS      current
            DESCRIPTION
                "
                Each bit figures a channel used or nor, '0' figure not used, '1' figures used

                "
            ::= { sdlBoardEntry 4 }

        hwSdl1E1TsInfo OBJECT-TYPE
            SYNTAX      Unsigned32(0..4294967295)
            MAX-ACCESS  read-only
            STATUS      current
            DESCRIPTION
                "
                Each bit figures a channel used or nor, '0' figure not used, '1' figures used

                "
            ::= { sdlBoardEntry 5 }

        hwSdl2E1TsInfo OBJECT-TYPE
            SYNTAX      Unsigned32(0..4294967295)
            MAX-ACCESS  read-only
            STATUS      current
            DESCRIPTION
                "
                Each bit figures a channel used or nor, '0' figure not used, '1' figures used

                "
            ::= { sdlBoardEntry 6 }

        hwSdl3E1TsInfo OBJECT-TYPE
            SYNTAX      Unsigned32(0..4294967295)
            MAX-ACCESS  read-only
            STATUS      current
            DESCRIPTION
                "
                Each bit figures a channel used or nor, '0' figure not used, '1' figures used

                "
            ::= { sdlBoardEntry 7 }

        hwSdl4E1TsInfo OBJECT-TYPE
            SYNTAX      Unsigned32(0..4294967295)
            MAX-ACCESS  read-only
            STATUS      current
            DESCRIPTION
                "
                Each bit figures a channel used or nor, '0' figure not used, '1' figures used

               "
            ::= { sdlBoardEntry 8 }

        hwSdl1ShdslTsInfo OBJECT-TYPE
            SYNTAX      Unsigned32(0..4294967295)
            MAX-ACCESS  read-only
            STATUS      current
            DESCRIPTION
                "
                Each bit figures a channel used or nor, '0' figure not used, '1' figures used

                "
            ::= { sdlBoardEntry 9 }

        hwSdl2ShdslTsInfo OBJECT-TYPE
            SYNTAX      Unsigned32(0..4294967295)
            MAX-ACCESS  read-only
            STATUS      current
            DESCRIPTION
                "
                Each bit figures a channel used or nor, '0' figure not used, '1' figures used

                "
            ::= { sdlBoardEntry 10 }

        hwSdl3ShdslTsInfo OBJECT-TYPE
            SYNTAX      Unsigned32(0..4294967295)
            MAX-ACCESS  read-only
            STATUS      current
            DESCRIPTION
                "
                Each bit figures a channel used or nor, '0' figure not used, '1' figures used

                "
            ::= { sdlBoardEntry 11 }

        hwSdl4ShdslTsInfo OBJECT-TYPE
            SYNTAX      Unsigned32(0..4294967295)
            MAX-ACCESS  read-only
            STATUS      current
            DESCRIPTION
                "
                Each bit figures a channel used or nor, '0' figure not used, '1' figures used

                "
            ::= { sdlBoardEntry 12 }

        sdlFE1PortTable OBJECT-TYPE
            SYNTAX      SEQUENCE OF SdlFE1PortEntry
            MAX-ACCESS  not-accessible
            STATUS      current
            DESCRIPTION
              "
              SDL 
              "
            ::= { hwSDLMibObjects 2 }

        sdlFE1PortEntry OBJECT-TYPE
            SYNTAX      SdlFE1PortEntry
            MAX-ACCESS  not-accessible
            STATUS      current
            DESCRIPTION
                "
                SDL 
                "
            INDEX
                {
                    ifIndex
                }
            ::= { sdlFE1PortTable 1 }

        SdlFE1PortEntry ::=
            SEQUENCE
                {
                hwSdlFE1FrameType
                    INTEGER,
                hwSdlFE1UserName
                    OCTET STRING(SIZE(0..10)),
                hwSdlFE1SignalState
                    INTEGER,
                hwSdlFE1LoopState
                    INTEGER,
                hwSdlFE1OprType
                    INTEGER
                }

        hwSdlFE1FrameType OBJECT-TYPE
            SYNTAX      INTEGER
                {
                hwPCM30(1),
                hwPCM30C(2),
                hwPCM31(3),
                hwPCM31C(4),
                hwUNFRAME(5)
                }
            MAX-ACCESS  read-write
            STATUS      current
            DESCRIPTION
                "
                the frame type of the SDL E1 port:
                SDL :
                1. PCM30
                2. PCM30C
                3. PCM31
                4. PCM31C
                5. UNFRRAMED
                "
            ::= { sdlFE1PortEntry 1 }

        hwSdlFE1UserName OBJECT-TYPE
            SYNTAX      OCTET STRING(SIZE(0..10))
            MAX-ACCESS  read-write
            STATUS      current
            DESCRIPTION
                "
                name of SDL FE1 port.

                SDL  (SIZE(0..10))
                "
            ::= { sdlFE1PortEntry 2 }

        hwSdlFE1SignalState OBJECT-TYPE
            SYNTAX      INTEGER
            MAX-ACCESS  read-only
            STATUS      current
            DESCRIPTION
                "
        
                "
            ::= { sdlFE1PortEntry 3 }

        hwSdlFE1LoopState OBJECT-TYPE
            SYNTAX      INTEGER
                {
                hwNoLooping(1),
                hwLocalLooping(2),
                hwRemoteLooping(3)
                }
            MAX-ACCESS  read-only
            STATUS      current
            DESCRIPTION
                "
                1. No Looping
                2. Local Looping
                3. Remote Looping

              
                "
            ::= { sdlFE1PortEntry 4 }

        hwSdlFE1OprType OBJECT-TYPE
            SYNTAX      INTEGER
                {
                hwCancelLoop(1),
                hwLocalLoop(2),
                hwRemoteLoop(3)
                }
            MAX-ACCESS  read-write
            STATUS      current
            DESCRIPTION
                "
                1. Cancel Loop
                2. Local Loop
                3. Remote Loop

               
                "
            ::= { sdlFE1PortEntry 5 }

        sdlShdslPortTable OBJECT-TYPE
            SYNTAX      SEQUENCE OF SdlShdslPortEntry
            MAX-ACCESS  not-accessible
            STATUS      current
            DESCRIPTION
              "
              SDL 
              "
            ::= { hwSDLMibObjects 3 }

        sdlShdslPortEntry OBJECT-TYPE
            SYNTAX      SdlShdslPortEntry
            MAX-ACCESS  not-accessible
            STATUS      current
            DESCRIPTION
                "
                SDL 
                "
            INDEX
                {
                ifIndex
                }
            ::= { sdlShdslPortTable 1 }

        SdlShdslPortEntry ::=
            SEQUENCE
                {
                hwSdlShdslRate
                    INTEGER,
                hwSdlShdslMode
                    INTEGER,
                hwSdlShdslUserName
                    OCTET STRING(SIZE(0..10)),
                hwSdlShdslLoopState
                    INTEGER,
                hwSdlActiveAllow
                    INTEGER,
                hwSdlShdslActiveState
                    INTEGER,
                hwSdlShdslOprType
                    INTEGER,
                hwSdltShdslSet2Or4Line
                    INTEGER
                }

        hwSdlShdslRate OBJECT-TYPE
            SYNTAX      INTEGER(3..32)
            MAX-ACCESS  read-write
            STATUS      current
            DESCRIPTION
                "
                Port rate 3-32x64K bps

                "
            ::= { sdlShdslPortEntry 1 }
            
        hwSdlShdslMode OBJECT-TYPE
            SYNTAX      INTEGER
                {
                hwSdlShdslE1(1),
                hwSdlShdslV35(2)
                }
            MAX-ACCESS  read-write
            STATUS      current
            DESCRIPTION
                "
                1. SHDSL port work in E1 mode
                2. SHDSL port work in V35 mode

                "
            ::= { sdlShdslPortEntry 2 }

         hwSdlShdslUserName OBJECT-TYPE
            SYNTAX      OCTET STRING(SIZE(0..10))
            MAX-ACCESS  read-write
            STATUS      current
            DESCRIPTION
                "
                name of SDL SHDSL port, size in 10 characters.

                "
            ::= { sdlShdslPortEntry 3 }

        hwSdlShdslLoopState OBJECT-TYPE
            SYNTAX      INTEGER
                {
                hwNoLooping(1),
                hwLocalLooping(2),
                hwRemoteLooping(3)
                }
            MAX-ACCESS  read-only
            STATUS      current
            DESCRIPTION
                "
                1. No Looping
                2. Local Looping,
                3. Remote Looping,


                "
            ::= { sdlShdslPortEntry 4 }

        hwSdlActiveAllow OBJECT-TYPE
            SYNTAX      INTEGER
                {
                hwAllow(1),
                hwProhibit(2)
                }
            MAX-ACCESS  read-only
            STATUS      current
            DESCRIPTION
                "
                1. Allow active
                2. Prohibit active

                "
            ::= { sdlShdslPortEntry 5 }

        hwSdlShdslActiveState OBJECT-TYPE
            SYNTAX      INTEGER
                {
                hwActive(1),
                hwDeactive(2)
                }
            MAX-ACCESS  read-only
            STATUS      current
            DESCRIPTION
                "
                1. active
                2. deactive


                "
            ::= { sdlShdslPortEntry 6 }

        hwSdlShdslOprType OBJECT-TYPE
            SYNTAX      INTEGER
                {
                hwCancelLoop(1),
                hwLocalLoop(2),
                hwRemoteLoop(3),
                hwActive(4),
                hwDeactive(5)
                }
            MAX-ACCESS  read-write
            STATUS      current
            DESCRIPTION
                "
                1. Cancel Loop
                2. Local Loop
                3. Remote Loop
                4. Active
                5. Deactive


                "
            ::= { sdlShdslPortEntry 7 }
            
       	hwSdltShdslSet2Or4Line OBJECT-TYPE
       	    SYNTAX      INTEGER
       	        {
       	        hw2line(1),
       	        hw4line(2)
       	        }
       	    MAX-ACCESS  read-write
            STATUS      current
       	    DESCRIPTION
       	    	"
       	    	1.Set 2line mode
       	    	2.Set 4line mode   

       	    	"
            ::={ sdlShdslPortEntry 8 }


END
