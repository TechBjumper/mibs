--
-- 
-- MIB generated by MG-SOFT Visual MIB Builder Version 6.0  Build 88
-- Wednesday, November 21, 2012 at 10:42:55
--

ZTE-AN-SPAN-MIB DEFINITIONS ::= BEGIN
 
    IMPORTS
        ifIndex, InterfaceIndexOrZero                    FROM IF-MIB     
        OBJECT-GROUP, MODULE-COMPLIANCE                  FROM SNMPv2-CONF
        InetAddressType, InetAddress                     FROM INET-ADDRESS-MIB           
        IpAddress, Integer32, OBJECT-TYPE, 
        MODULE-IDENTITY                                  FROM SNMPv2-SMI     
        DisplayString, RowStatus, MacAddress,
        TEXTUAL-CONVENTION                               FROM SNMPv2-TC      
        zxAnSubIfIndex                                   FROM ZTE-AN-IF-MIB      
        zxAnOam                                          FROM ZTE-AN-SMI
        ZxAnSubIfIndex                                   FROM ZTE-AN-TC-MIB;
  
  

    zxAnSpanMib MODULE-IDENTITY 
        LAST-UPDATED    "201212101114Z"    -- December 10, 2012 at 11:14 GMT
        ORGANIZATION    "ZTE Corporation"
        CONTACT-INFO    "Zhang Zhengyi      
                         ZTE Corporation
                         Mail: zhang.zhengyi@zte.com.cn
                         Tel : +86-21-68896470"
        DESCRIPTION     "This MIB defines managed objects of ZTE SPAN."
        REVISION        "201212101114Z"    -- December 10, 2012 at 11:14 GMT
        DESCRIPTION     "Initial version of this MIB module."
        REVISION        "201212061215Z"    -- December 06, 2012 at 12:15 GMT      
        DESCRIPTION     "Add the group: zxAnSpanGroup."
        ::= { zxAnOam 10 }
  
      
--------------------------------------------------------------------------------
-- Following management objects are defined.
-- 1. SPAN Global Objects
-- 2. SPAN Table

-- Following conformance information is defined.
-- 31. zxAnSpanConformance
--------------------------------------------------------------------------------

    zxAnSpanGlobalObjects OBJECT IDENTIFIER ::= { zxAnSpanMib 1 }
    zxAnSpanObjects       OBJECT IDENTIFIER ::= { zxAnSpanMib 2 }
    zxAnSpanNotifications OBJECT IDENTIFIER ::= { zxAnSpanMib 3 } 
    
--------------------------------------------------------------------------------
-- 1. SPAN Global Objects
--------------------------------------------------------------------------------
    
    zxAnSpanCapabilities  OBJECT-TYPE 
        SYNTAX      BITS    {
            spanDstSubIndex(0), 
            spanSpanCpuPktMirror(1),
            spanSrcIfIndex(2),
            spanEncapsulateType(3),
            spanTimeRangeName(4)
        }
        MAX-ACCESS  read-only
        STATUS      current
        DESCRIPTION   
            "The management capabilities of SPAN.          
             spanDstSubIndex(0): value 1 means supporting zxAnSpanDstSubIfIndex.                                      
             spanSpanCpuPktMirror(1): value 1 means NOT supporting
                                      zxAnSpanCpuPktMirrorEnable 
                                      and zxAnSpanCpuPktMirrorDirection.
             spanSrcIfIndex(2): value 1 means supporting
                                zxAnSpanSrcIfIndex1, zxAnSpanSrcSubIfIndex1, 
                                zxAnSpanSrcIfIndex2, zxAnSpanSrcSubIfIndex2,
                                zxAnSpanSrcIfIndex3, zxAnSpanSrcSubIfIndex3,
                                zxAnSpanSrcIfIndex4, zxAnSpanSrcSubIfIndex4
                                and zxAnSpanSrcDirection,
                                not supporting zxAnSpanSrcPortList and
                                zxAnSpanSrcDirectionList. 
             spanEncapsulateType(3): value 1 means supporting 
                                     zxAnSpanEncapsulateType.    
             spanTimeRangeName(4): value 1 means supporting 
                                     zxAnSpanTimeRangeName.               
             NOTE: No recommended to display it in NMS."
        ::= { zxAnSpanGlobalObjects 1 }
        
--------------------------------------------------------------------------------
-- 2. SPAN Table
--------------------------------------------------------------------------------     
        
    zxAnSpanTable    OBJECT-TYPE
        SYNTAX      SEQUENCE OF ZxAnSpanEntry
        MAX-ACCESS  not-accessible
        STATUS      current
        DESCRIPTION
            "This table represents the switched port 
            analyzer related parameters."
        ::= { zxAnSpanObjects 2 }

    
    zxAnSpanEntry    OBJECT-TYPE
        SYNTAX      ZxAnSpanEntry
        MAX-ACCESS  not-accessible
        STATUS      current
        DESCRIPTION
            "An entry in zxAnSpanTable.
        
            The multi-variables binding rule should be complied with when a 
            manager creates an entry. According to this rule, all the related 
            mib variables must be included in one SNMP set operation.
                    
            There are two types of variables: mandatory and optional.
            All of the mandatory variables must be included in one SNMP set 
            operation. Optional variables may be included in one SNMP set 
            operation with the mandatory variables, but must not be used alone. 
                    
            To create an entry of this table, the mandatory and optional 
            variables are as below.
            mandatory: zxAnSpanSessionId       
            optional : the other
                            
            After an entry is created, every variable can be modified.
            "
        INDEX { zxAnSpanSessionId }
        ::= { zxAnSpanTable 1 }

    
    ZxAnSpanEntry ::=
        SEQUENCE { 
            zxAnSpanSessionId                   Integer32,
            zxAnSpanType                        INTEGER,
            zxAnSpanCpuPktMirrorEnable          INTEGER,
            zxAnSpanCpuPktMirrorDirection       INTEGER,
            zxAnSpanSrcPortList                 OBJECT IDENTIFIER,
            zxAnSpanSrcDirectionList            OBJECT IDENTIFIER,
            zxAnSpanSrcIfIndex1                 InterfaceIndexOrZero,
            zxAnSpanSrcSubIfIndex1              ZxAnSubIfIndex,
            zxAnSpanSrcIfIndex2                 InterfaceIndexOrZero,
            zxAnSpanSrcSubIfIndex2              ZxAnSubIfIndex,
            zxAnSpanSrcIfIndex3                 InterfaceIndexOrZero,
            zxAnSpanSrcSubIfIndex3              ZxAnSubIfIndex, 
            zxAnSpanSrcIfIndex4                 InterfaceIndexOrZero,
            zxAnSpanSrcSubIfIndex4              ZxAnSubIfIndex, 
            zxAnSpanSrcDirection                INTEGER,
            zxAnSpanDstPort                     Integer32,
            zxAnSpanVid                         Integer32,
            zxAnSpanCos                         Integer32,
            zxAnSpanTpid                        Integer32,
            zxAnSpanDstIpType                   InetAddressType,
            zxAnSpanDstIpAddr                   InetAddress,
            zxAnSpanSrcIpType                   InetAddressType,
            zxAnSpanSrcIpAddr                   InetAddress,
            zxAnSpanTtl                         Integer32,
            zxAnSpanDscp                        Integer32,
            zxAnSpanDstMac                      MacAddress,
            zxAnSpanSrcMac                      MacAddress,
            zxAnSpanDstSubIfIndex               ZxAnSubIfIndex,
            zxAnSpanEncapsulateType             INTEGER,
            zxAnSpanTimeRangeName               DisplayString,
            zxAnSpanRowStatus                   RowStatus
       }


    zxAnSpanSessionId      OBJECT-TYPE
        SYNTAX      Integer32 (1..16)
        MAX-ACCESS  not-accessible
        STATUS      current
        DESCRIPTION
            "The index of a session."
        ::= { zxAnSpanEntry 1 }

    
    zxAnSpanType     OBJECT-TYPE
        SYNTAX      INTEGER  {
            span(1),
            rspan(2),
            erspan(3),
            unknown(255)
        }
        MAX-ACCESS  read-create
        STATUS      current
        DESCRIPTION
            "The SPAN type of a session.
            span(1)            - Local Switched Port Analyzer. 
            rspan(2)           - Remote SPAN.
            erspan(3)          - Enhanced Remoted SPAN.
            unknown(255)       - Unknown. this value is read-only and 
                                 can not be set to NE."
        DEFVAL { unknown }
        ::= { zxAnSpanEntry 2 }
      
        
    zxAnSpanCpuPktMirrorEnable      OBJECT-TYPE
        SYNTAX      INTEGER  {
            enabled(1),
            disabled(2)
        }       
        MAX-ACCESS  read-create
        STATUS      current
        DESCRIPTION
            "This object indicates whether the packets sent 
             to the CPU are mirrored:
             enabled(1)      - the packets sent to the CPU are mirrored.  
             disabled(2)     - the packets sent to the CPU are not mirrored."             
        DEFVAL {disabled}
        ::= { zxAnSpanEntry 3 }
      
           
    zxAnSpanCpuPktMirrorDirection      OBJECT-TYPE
        SYNTAX      INTEGER  {
            both(1),
            egress(2),
            ingress(3)
        }       
        MAX-ACCESS  read-create
        STATUS      current
        DESCRIPTION
            "The direction of cpu packet."         
        ::= { zxAnSpanEntry 4 }
    
    zxAnSpanSrcPortList      OBJECT-TYPE
        SYNTAX      OBJECT IDENTIFIER
        MAX-ACCESS  read-create
        STATUS      current
        DESCRIPTION
            "It is a sequence of some source ports.                       
             Supports ethernet interface, inner port, smartgroup.
             The format of portlist is like this:
             .ifIndex1.zxAnSubIfIndex1.ifIndex2.zxAnSubIfIndex2...
             |        port1             |        port2          |...

             In case of no zxAnSubIfIndex, the portlist is like this:
             .ifIndex1.0.ifIndex2.0...
             |port1      |port2     |...

             "
        ::= { zxAnSpanEntry 5 }

    

    zxAnSpanSrcDirectionList      OBJECT-TYPE
        SYNTAX      OBJECT IDENTIFIER
        MAX-ACCESS  read-create
        STATUS      current
        DESCRIPTION
            "The traffic direction list of the source port list.
             The format of  direction list is like this:
             .direction1.direction2...
             |port1     |port2    |...

             Each value of the sequence represents a traffic direction.
             The value may be followings:
             both(1),
             egress(2), 
             ingress(3).
            "

        ::= { zxAnSpanEntry 6 }
      
     
    zxAnSpanSrcIfIndex1    OBJECT-TYPE
        SYNTAX      InterfaceIndexOrZero
        MAX-ACCESS  read-create
        STATUS      current
        DESCRIPTION
            "The interface index of the first source port."  
        DEFVAL { 0 }   
        ::= { zxAnSpanEntry 7 }    
  
  
    zxAnSpanSrcSubIfIndex1    OBJECT-TYPE
        SYNTAX      ZxAnSubIfIndex
        MAX-ACCESS  read-create
        STATUS      current
        DESCRIPTION
            "The sub-interface index of the first source port."  
        DEFVAL { 0 }   
        ::= { zxAnSpanEntry 8 }   


    zxAnSpanSrcIfIndex2    OBJECT-TYPE
        SYNTAX      InterfaceIndexOrZero
        MAX-ACCESS  read-create
        STATUS      current
        DESCRIPTION
            "The interface index of the seoond source port."  
        DEFVAL { 0 }   
        ::= { zxAnSpanEntry 9 }    
  
  
    zxAnSpanSrcSubIfIndex2    OBJECT-TYPE
        SYNTAX      ZxAnSubIfIndex
        MAX-ACCESS  read-create
        STATUS      current
        DESCRIPTION
            "The sub-interface index of the second source port."  
        DEFVAL { 0 }   
        ::= { zxAnSpanEntry 10 } 


    zxAnSpanSrcIfIndex3    OBJECT-TYPE
        SYNTAX      InterfaceIndexOrZero
        MAX-ACCESS  read-create
        STATUS      current
        DESCRIPTION
            "The interface index of the third source port."  
        DEFVAL { 0 }   
        ::= { zxAnSpanEntry 11 }    
  
  
    zxAnSpanSrcSubIfIndex3    OBJECT-TYPE
        SYNTAX      ZxAnSubIfIndex
        MAX-ACCESS  read-create
        STATUS      current
        DESCRIPTION
            "The sub-interface index of the third source port."  
        DEFVAL { 0 }   
        ::= { zxAnSpanEntry 12 }   
  
  
    zxAnSpanSrcIfIndex4    OBJECT-TYPE
        SYNTAX      InterfaceIndexOrZero
        MAX-ACCESS  read-create
        STATUS      current
        DESCRIPTION
            "The interface index of the fourth source port."  
        DEFVAL { 0 }   
        ::= { zxAnSpanEntry 13 }    
  
  
    zxAnSpanSrcSubIfIndex4    OBJECT-TYPE
        SYNTAX      ZxAnSubIfIndex
        MAX-ACCESS  read-create
        STATUS      current
        DESCRIPTION
            "The sub-interface index of the fourth source port."  
        DEFVAL { 0 }   
        ::= { zxAnSpanEntry 14 }   
  
  
    zxAnSpanSrcDirection      OBJECT-TYPE
        SYNTAX      INTEGER  {
            both(1),
            egress(2),
            ingress(3)
        }       
        MAX-ACCESS  read-create
        STATUS      current
        DESCRIPTION
            "The traffic direction of the source ports."         
        ::= { zxAnSpanEntry 15 }   
                                
    zxAnSpanDstPort      OBJECT-TYPE
        SYNTAX      Integer32
        MAX-ACCESS  read-create
        STATUS      current
        DESCRIPTION
            "The ifIndex of SPAN and RSPAN destination port.
            Supports ethernet interface and smartgroup."  
        DEFVAL { 0 }   
        ::= { zxAnSpanEntry 20 }      

    
    zxAnSpanVid      OBJECT-TYPE
        SYNTAX      Integer32 (1..4094|65535)
        MAX-ACCESS  read-create
        STATUS      current
        DESCRIPTION
            "The traffic VLAN ID of RSPAN or ERSPAN."
        DEFVAL { 65535 }
        ::= { zxAnSpanEntry 21 }

    
    zxAnSpanCos      OBJECT-TYPE
        SYNTAX      Integer32 (0..7)
        MAX-ACCESS  read-create
        STATUS      current
        DESCRIPTION
            "The traffic CoS of RSPAN or ERSPAN."
        DEFVAL { 0 }
        ::= { zxAnSpanEntry 22 }

    
    zxAnSpanTpid      OBJECT-TYPE
        SYNTAX      Integer32 (0..65535)
        MAX-ACCESS  read-create
        STATUS      current
        DESCRIPTION
            "The traffic TPID of RSPAN or ERSPAN."
        DEFVAL { 33024 }
        ::= { zxAnSpanEntry 23 }

    
     zxAnSpanDstIpType      OBJECT-TYPE
         SYNTAX      InetAddressType
         MAX-ACCESS  read-create
         STATUS      current
         DESCRIPTION
             "The type of IP address about destination IP."
         DEFVAL { ipv4 }
         ::= { zxAnSpanEntry 24 }
        
                
    zxAnSpanDstIpAddr      OBJECT-TYPE
        SYNTAX      InetAddress
        MAX-ACCESS  read-create
        STATUS      current
        DESCRIPTION
            "The destination IP of ERSPAN."
        DEFVAL { '00000000'h }
        ::= { zxAnSpanEntry 25 }

    zxAnSpanSrcIpType      OBJECT-TYPE
        SYNTAX      InetAddressType
        MAX-ACCESS  read-create
        STATUS      current
        DESCRIPTION
            "The type of IP address about source IP."
        DEFVAL { ipv4 }
        ::= { zxAnSpanEntry 26 }
        
        
    zxAnSpanSrcIpAddr      OBJECT-TYPE
        SYNTAX      InetAddress
        MAX-ACCESS  read-create
        STATUS      current
        DESCRIPTION
            "The source IP of ERSPAN."
        DEFVAL { '00000000'h }
        ::= { zxAnSpanEntry 27 }

    
    zxAnSpanTtl      OBJECT-TYPE
        SYNTAX      Integer32 (0..255)
        MAX-ACCESS  read-create
        STATUS      current
        DESCRIPTION
            "The TTL of ERSPAN."
        DEFVAL { 128 }
        ::= { zxAnSpanEntry 28 }

    
    zxAnSpanDscp      OBJECT-TYPE
        SYNTAX      Integer32 (0..63)
        MAX-ACCESS  read-create
        STATUS      current
        DESCRIPTION
             "The DSCP of ERSPAN."
        DEFVAL { 0 }
        ::= { zxAnSpanEntry 29 }

    zxAnSpanDstMac   OBJECT-TYPE
        SYNTAX MacAddress
        MAX-ACCESS read-only
        STATUS current
        DESCRIPTION
            "The destination MAC address of ERSPAN."
        DEFVAL { '000000000000'h }
        ::= { zxAnSpanEntry 30 }
        
    zxAnSpanSrcMac   OBJECT-TYPE
        SYNTAX MacAddress
        MAX-ACCESS read-only
        STATUS current
        DESCRIPTION
            "The source MAC address of ERSPAN."
        DEFVAL { '000000000000'h }
        ::= { zxAnSpanEntry 31 }
        
    zxAnSpanDstSubIfIndex    OBJECT-TYPE
        SYNTAX      ZxAnSubIfIndex
        MAX-ACCESS  read-create
        STATUS      current
        DESCRIPTION
            "The sub-interface index of destination port."  
        DEFVAL { 0 }   
        ::= { zxAnSpanEntry 32 }

    zxAnSpanEncapsulateType     OBJECT-TYPE
        SYNTAX      INTEGER  {
            gre(1),
            udp(2)
        }
        MAX-ACCESS  read-create
        STATUS      current
        DESCRIPTION
            "The encapsulation type of ERSPAN.
             gre(1): Generic routing encapsulation(GRE). 
             udp(2): UDP encapsulation."
        DEFVAL { gre }
        ::= { zxAnSpanEntry 33 }

    zxAnSpanTimeRangeName  OBJECT-TYPE
        SYNTAX      DisplayString(SIZE(0..32))
        MAX-ACCESS  read-create
        STATUS      current
        DESCRIPTION
            "Name of the time range.
             Empty string means all the time the session is valid."
        DEFVAL { "" }
        ::= { zxAnSpanEntry 34 }        

    zxAnSpanRowStatus      OBJECT-TYPE
        SYNTAX      RowStatus
        MAX-ACCESS  read-create
        STATUS      current
        DESCRIPTION
            "The status of this conceptual row.
        
            The supported actions of this conceptual row only include:
            'createAndGo' and 'destroy'.
        
            To create a row in this table, a manager must set this object to 
            createAndGo(4), and must comply with the multi-variables binding 
            rule described in zxAnAclEntry.
        
            To delete a row in this table, a manager must set this object to 
            destroy(6). 
         
            To get this object, the agent always returns active(1)."
        ::= { zxAnSpanEntry 50 }   


--------------------------------------------------------------------------------
-- 31. zxAnSpanConformance
--------------------------------------------------------------------------------    
    zxAnSpanConformance OBJECT IDENTIFIER ::= { zxAnSpanMib 4 }  
    zxAnSpanCompliances OBJECT IDENTIFIER ::= { zxAnSpanConformance 1 }
    

    zxAnSpanCompliance      MODULE-COMPLIANCE
        STATUS      current
        DESCRIPTION 
            "The compliance statement for the ZTE-AN-MONITOR-MIB."
        MODULE -- this module
        MANDATORY-GROUPS { zxAnSpanGroup }
        ::= { zxAnSpanCompliances 1 }

    
    zxAnSpanGroups OBJECT IDENTIFIER ::= { zxAnSpanConformance 2 }

    
    zxAnSpanGroup OBJECT-GROUP
        OBJECTS { zxAnSpanType,
                zxAnSpanCpuPktMirrorEnable, 
                zxAnSpanCpuPktMirrorDirection,         
                zxAnSpanSrcPortList,          
                zxAnSpanSrcDirectionList,
                zxAnSpanDstPort,                          
                zxAnSpanVid,          
                zxAnSpanCos,         
                zxAnSpanTpid,          
                zxAnSpanDstIpType,          
                zxAnSpanDstIpAddr,         
                zxAnSpanSrcIpType,          
                zxAnSpanSrcIpAddr,          
                zxAnSpanTtl,         
                zxAnSpanDscp,          
                zxAnSpanRowStatus
              }
        STATUS current
        DESCRIPTION 
            "A collection of objects providing the access control list 
            configuration information."
        ::= { zxAnSpanGroups 1 }

    
  
  END
