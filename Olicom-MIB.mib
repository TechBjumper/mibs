--  Olicom MIB Object Definitions
--  $Revision: 2.33 $
--  $Date: 1999/04/19 08:14:49 $

-- This MIB module contains definitions of generic MIB objects
-- supported by the various models of Olicom Internetworking Devices.

-- Olicom-MIB   { iso org(3) dod(6) internet(1) private(4)
--                     enterprises(1) olicom(285) }

Olicom-MIB   DEFINITIONS ::= BEGIN

IMPORTS
	TRAP-TYPE FROM RFC-1215
	OBJECT-TYPE
		FROM RFC-1212
	enterprises, TimeTicks, IpAddress
		FROM RFC1155-SMI
	DisplayString
		FROM RFC1213-MIB;


	MacAddress ::= OCTET STRING (SIZE (6))	-- a 6 octet address in
						-- the (non-)"canonical" order
						-- according to the
						-- inetMacAddrForm variable
	IPXAddress ::= OCTET STRING (SIZE (12))	-- a 12 octet address:
                                                -- 4 bytes Net address,
						-- 6 bytes Node address,
						-- 2 bytes Socket address.

--  This MIB Module uses the extended OBJECT-TYPE macro as
--  defined in RFC-1212.

-- TEXTUAL-CONVENTIONS

RowStatus ::= INTEGER {
    active(1),          -- This definition of RowStatus
    notInService(2),    -- corresponds to the definition
    notReady(3),        -- in SNMPv2-TC. We define it
    createAndGo(4),     -- here for use in this MIB in
    createAndWait(5),   -- order to stay within SNMP (v1).
    destroy(6)          -- Usage is as described in
}                       -- RFC 1443.
		-- As defined in RFC 1903. Objects may implement a subset of
		-- the value set.

-- Object definitions

olicom			OBJECT IDENTIFIER ::= { enterprises 285 }

-- Sections
info			OBJECT IDENTIFIER ::= { olicom 1 }
ocmibs			OBJECT IDENTIFIER ::= { olicom 2 }
temporary		OBJECT IDENTIFIER ::= { olicom 3 }
inet			OBJECT IDENTIFIER ::= { olicom 4 }
control			OBJECT IDENTIFIER ::= { olicom 5 }
obm 			OBJECT IDENTIFIER ::= { olicom 6 }
management		OBJECT IDENTIFIER ::= { olicom 7 }
frontpanel		OBJECT IDENTIFIER ::= { olicom 8 }
products		OBJECT IDENTIFIER ::= { olicom 9 }
errorlog		OBJECT IDENTIFIER ::= { olicom 10 }
trconfig		OBJECT IDENTIFIER ::= { olicom 11 }


--- Information section

-- Hardware

infoHardwareProductId OBJECT-TYPE
	SYNTAX  DisplayString
	ACCESS  read-only
	STATUS  mandatory
	DESCRIPTION
		"A string containing the hardware product id."
	::= { info 1 }

infoHardwareVersion OBJECT-TYPE
	SYNTAX  DisplayString
	ACCESS  read-only
	STATUS  mandatory
	DESCRIPTION
		"A string containing the hardware version."
	::= { info 2 }

infoHardwareECOLevel OBJECT-TYPE
	SYNTAX  DisplayString
	ACCESS  read-only
	STATUS  mandatory
	DESCRIPTION
		"A string containing the ECO update level."
	::= { info 3 }

infoHardwareSerialNumber OBJECT-TYPE
	SYNTAX  DisplayString
	ACCESS  read-only
	STATUS  mandatory
	DESCRIPTION
		"A string containing the hardware serial number."
	::= { info 4 }

infoHardwareOptionTable OBJECT-TYPE
	SYNTAX  SEQUENCE OF InfoHardwareOptionTableEntry
	ACCESS  not-accessible
	STATUS  mandatory
	DESCRIPTION
		"A sequence of hardware options, each a string
		describing the appropriate option present."
	::= { info 5 }

infoHardwareOptionTableEntry OBJECT-TYPE
	SYNTAX	InfoHardwareOptionTableEntry
	ACCESS	not-accessible
	STATUS	mandatory
DESCRIPTION ""
	INDEX	{ infoHardwareOptionNo }
	::= { infoHardwareOptionTable 1 }

InfoHardwareOptionTableEntry ::= SEQUENCE {
	infoHardwareOptionNo
		INTEGER,
	infoHardwareOption
		DisplayString
}

infoHardwareOptionNo OBJECT-TYPE
	SYNTAX  INTEGER
	ACCESS  read-only
	STATUS  mandatory
	DESCRIPTION
		"The option number for this option."
	::= { infoHardwareOptionTableEntry 1 }

infoHardwareOption OBJECT-TYPE
	SYNTAX  DisplayString
	ACCESS  read-only
	STATUS  mandatory
	DESCRIPTION
		"A string describing this option."
	::= { infoHardwareOptionTableEntry 2 }

-- Software

infoSoftwareProductId OBJECT-TYPE
	SYNTAX  DisplayString
	ACCESS  read-only
	STATUS  mandatory
	DESCRIPTION
                "A string containing the software product id.
                 Recommended format is as follows: the string consists of
                 fixed and optional part. Fixed part contains device's
                 symbol (eg.'CF8711' for the CrossFire 8711 FE switch).
                 This fixed part cannot contain any whitespace characters.
                 The optional part contains additional description, it must
                 begin with a space character as delimiter."
	::= { info 6 }

infoSoftwareVersion OBJECT-TYPE
	SYNTAX  DisplayString
	ACCESS  read-only
	STATUS  mandatory
	DESCRIPTION
                "A string containing the software version.
                 Recommended format is as follows: the string consists of
                 fixed and optional part. Fixed part contains software
                 version as 4 numbers separated by dot characters (eg.
                 '1.0.0.20'). This fixed part must use only digit and dot
                 characters.
                 The optional part contains additional description, it must
                 begin with a space character as delimiter."
        ::= { info 7 }

infoSoftwareECOLevel OBJECT-TYPE
	SYNTAX  DisplayString
	ACCESS  read-only
	STATUS  mandatory
	DESCRIPTION
		"A string containing the ECO update level."
	::= { info 8 }

infoSoftwareOptionTable OBJECT-TYPE
	SYNTAX  SEQUENCE OF InfoSoftwareOptionTableEntry
	ACCESS  not-accessible
	STATUS  mandatory
	DESCRIPTION
		"A sequence of software options, each a string
		describing the appropriate option present."
	::= { info 9 }

infoSoftwareOptionTableEntry OBJECT-TYPE
	SYNTAX	InfoSoftwareOptionTableEntry
	ACCESS	not-accessible
	STATUS	mandatory
DESCRIPTION ""
	INDEX	{ infoSoftwareOptionNo }
	::= { infoSoftwareOptionTable 1 }

InfoSoftwareOptionTableEntry ::= SEQUENCE {
	infoSoftwareOptionNo
		INTEGER,
	infoSoftwareOption
		DisplayString
}

infoSoftwareOptionNo OBJECT-TYPE
	SYNTAX  INTEGER
	ACCESS  read-only
	STATUS  mandatory
	DESCRIPTION
		"The option number for this option."
	::= { infoSoftwareOptionTableEntry 1 }

infoSoftwareOption OBJECT-TYPE
	SYNTAX  DisplayString
	ACCESS  read-only
	STATUS  mandatory
	DESCRIPTION
		"A string describing this option."
	::= { infoSoftwareOptionTableEntry 2 }

-- MIBs

infoSoftwareMIBsTable OBJECT-TYPE
	SYNTAX  SEQUENCE OF InfoSoftwareMIBsTableEntry
	ACCESS  not-accessible
	STATUS  mandatory
	DESCRIPTION
		"A sequence of MIBs supported by this device."
	::= { info 10 }

infoSoftwareMIBsTableEntry OBJECT-TYPE
	SYNTAX	InfoSoftwareMIBsTableEntry
	ACCESS	not-accessible
	STATUS	mandatory
DESCRIPTION ""
	INDEX	{ infoSoftwareMIBsNo }
	::= { infoSoftwareMIBsTable 1 }

InfoSoftwareMIBsTableEntry ::= SEQUENCE {
	infoSoftwareMIBsNo
		INTEGER,
	infoSoftwareMIBsObjectID
		OBJECT IDENTIFIER,
	infoSoftwareMIBsDescription
		DisplayString
}

infoSoftwareMIBsNo OBJECT-TYPE
	SYNTAX  INTEGER
	ACCESS  read-only
	STATUS  mandatory
	DESCRIPTION
		"The number for this MIB description entry."
	::= { infoSoftwareMIBsTableEntry 1 }

infoSoftwareMIBsObjectID OBJECT-TYPE
	SYNTAX  OBJECT IDENTIFIER
	ACCESS  read-only
	STATUS  mandatory
	DESCRIPTION
		"The unique OBJECT IDENTIFIER for this MIB description entry.
		 Olicom specific MIBs have OBJECT IDENTIFIERs that are
		 defined as { ocmibs N }. (See ocmibs section)."
	::= { infoSoftwareMIBsTableEntry 2 }

infoSoftwareMIBsDescription OBJECT-TYPE
	SYNTAX  DisplayString
	ACCESS  read-only
	STATUS  mandatory
	DESCRIPTION
		"A string describing this MIB description entry."
	::= { infoSoftwareMIBsTableEntry 3 }


-- SW or Microcode Files Product ID

infoXtraSwTable OBJECT-TYPE
        SYNTAX  SEQUENCE OF InfoXtraSwEntry
        ACCESS  not-accessible
        STATUS  optional
        DESCRIPTION
                "This table contains the product IDs and addtional
                 information for the additional files included in a
                 multichunk file."
        ::= { info 11 }

infoXtraSwEntry OBJECT-TYPE
        SYNTAX  InfoXtraSwEntry
        ACCESS  not-accessible
        STATUS  optional
        DESCRIPTION
                "An entry in the infoXtraSwTable."
        INDEX   { infoXtraSwIndex }
        ::= { infoXtraSwTable 1 }

InfoXtraSwEntry ::=
        SEQUENCE {
            infoXtraSwIndex
                INTEGER,
            infoXtraSwFileUse
                INTEGER,
            infoXtraSwProductId
                DisplayString,
            infoXtraSwVersion
                DisplayString,
            infoXtraSwEcoLevel
                DisplayString,
            infoXtraSwSerialNumber
                DisplayString,
            infoXtraSwOptions
                OCTET STRING
        }

infoXtraSwIndex OBJECT-TYPE
        SYNTAX  INTEGER
        ACCESS  read-only
        STATUS  optional
        DESCRIPTION
                "The entry number in the infoXtraSwTable."
        ::= { infoXtraSwEntry 1 }


infoXtraSwFileUse OBJECT-TYPE
        SYNTAX  INTEGER
        ACCESS  read-only
        STATUS  optional
        DESCRIPTION
                "From the file header: The target for the SW image."
        ::= { infoXtraSwEntry 2 }

infoXtraSwProductId OBJECT-TYPE
        SYNTAX  DisplayString
        ACCESS  read-only
        STATUS  optional
        DESCRIPTION
                "From the file header: The SW product ID."
        ::= { infoXtraSwEntry 3 }

infoXtraSwVersion OBJECT-TYPE
        SYNTAX  DisplayString
        ACCESS  read-only
        STATUS  optional
        DESCRIPTION
                "From the file header: The SW version."
        ::= { infoXtraSwEntry 4 }

infoXtraSwEcoLevel OBJECT-TYPE
        SYNTAX  DisplayString
        ACCESS  read-only
        STATUS  optional
        DESCRIPTION
                "From the file header: The SW ECO level."
        ::= { infoXtraSwEntry 5 }

infoXtraSwSerialNumber OBJECT-TYPE
        SYNTAX  DisplayString
        ACCESS  read-only
        STATUS  optional
        DESCRIPTION
                "From the file header: The SW serial number."
        ::= { infoXtraSwEntry 6 }

infoXtraSwOptions OBJECT-TYPE
        SYNTAX  OCTET STRING
        ACCESS  read-only
        STATUS  optional
        DESCRIPTION
                "From the file header: A bitmask of SW options."
        ::= { infoXtraSwEntry 7 }

-- Modules - UEMs and/or switches in a stack.

infoModuleTable OBJECT-TYPE
	SYNTAX  SEQUENCE OF InfoModuleEntry
	ACCESS  not-accessible
	STATUS  mandatory
	DESCRIPTION
		"This table describes all the HW modules in a system with
		 multiple modules."
	::= { info 12 }

infoModuleEntry OBJECT-TYPE
	SYNTAX	InfoModuleEntry
	ACCESS	not-accessible
	STATUS	mandatory
	DESCRIPTION
		"A list of information objects for a HW module."
	INDEX	{ infoModuleIndex }
	::= { infoModuleTable 1 }

InfoModuleEntry ::= SEQUENCE {
	infoModuleIndex            INTEGER,
	infoModuleHwProductId      DisplayString,
	infoModuleHwVersion        DisplayString,
	infoModuleHwSerialNumber   DisplayString,
	infoModuleBootpromVersion  DisplayString
}

infoModuleIndex OBJECT-TYPE
	SYNTAX  INTEGER
	ACCESS  read-only
	STATUS  mandatory
	DESCRIPTION
		"The module index of this module. This is a unique index
		 identifying a hardware module in the switching system.
		 The planar board of a switch box is considered a module.
		 Any expansion boards (slots) are assigned the subsequent
		 moduleIndexes."
	::= { infoModuleEntry 1 }

infoModuleHwProductId OBJECT-TYPE
	SYNTAX  DisplayString
	ACCESS  read-only
	STATUS  mandatory
	DESCRIPTION
		"A string containing the modules product id (eg. from EEPROM)"
	::= { infoModuleEntry 2 }

infoModuleHwVersion OBJECT-TYPE
	SYNTAX  DisplayString
	ACCESS  read-only
	STATUS  mandatory
	DESCRIPTION
		"A string containing the modules version (eg. from EEPROM)"
	::= { infoModuleEntry 3 }

infoModuleHwSerialNumber OBJECT-TYPE
	SYNTAX  DisplayString
	ACCESS  read-only
	STATUS  mandatory
	DESCRIPTION
		"A string containing the modules serial no (eg. from EEPROM)"
	::= { infoModuleEntry 4 }

infoModuleBootpromVersion	OBJECT-TYPE
	SYNTAX  DisplayString
	ACCESS  read-only
	STATUS  mandatory
	DESCRIPTION
		"A string containing the modules bootprom version.
		 An empty string, if no bootprom is present on this module. "
	::= { infoModuleEntry 5 }

-- Multiple SW images

infoSwImageTable OBJECT-TYPE
	SYNTAX  SEQUENCE OF InfoSwImageEntry
	ACCESS  not-accessible
	STATUS  mandatory
	DESCRIPTION
		"This table describes all the SW images in the system."
	::= { info 13 }

infoSwImageEntry OBJECT-TYPE
	SYNTAX	InfoSwImageEntry
	ACCESS	not-accessible
	STATUS	mandatory
	DESCRIPTION
		"A list of information objects for SW image. "
	INDEX	{ infoSwImageModuleIndex, infoSwImageNo }
	::= { infoSwImageTable 1 }

InfoSwImageEntry ::= SEQUENCE {
	infoSwImageModuleIndex     INTEGER,
	infoSwImageNo              INTEGER,
	infoSwImageProductId       DisplayString,
        infoSwImageVersion         DisplayString,
        infoSwImageDownloadTime    INTEGER
}

infoSwImageModuleIndex OBJECT-TYPE
	SYNTAX  INTEGER
	ACCESS  read-only
	STATUS  mandatory
	DESCRIPTION
		"The module index of the module on which the SW image reside."
	::= { infoSwImageEntry 1 }

infoSwImageNo OBJECT-TYPE
	SYNTAX  INTEGER
	ACCESS  read-only
	STATUS  mandatory
	DESCRIPTION
		"The SW image number, relative to the HW module."
	::= { infoSwImageEntry 2 }

infoSwImageProductId OBJECT-TYPE
	SYNTAX  DisplayString
	ACCESS  read-only
	STATUS  mandatory
	DESCRIPTION
		"A string containing the SW images product id.
		 An empty string, if this image is not present or corrupted."
	::= { infoSwImageEntry 3 }

infoSwImageVersion OBJECT-TYPE
	SYNTAX  DisplayString
	ACCESS  read-only
	STATUS  mandatory
	DESCRIPTION
		"A string containing the SW images version.
		 An empty string, if this image is not present or corrupted."
	::= { infoSwImageEntry 4 }

infoSwImageDownloadTime OBJECT-TYPE
        SYNTAX  INTEGER
        ACCESS  read-only
        STATUS  mandatory
        DESCRIPTION
                "The time when the software image was downloaded to the device.
                 This is measured in seconds since 00:00:00 on 1 January 1970 (i.e. UNIX
                 standard time)."
        ::= { infoSwImageEntry 5 }

-- OCMIB section
-- Each product has its own specific set of MIBs from this list :

ocmibsBridgeMIB	OBJECT IDENTIFIER ::= { ocmibs 1 }
		-- file ocbridge.mib

ocmibsCauMIB	OBJECT IDENTIFIER ::= { ocmibs 2 }
		-- file occau.mib

ocmibsCamMIB	OBJECT IDENTIFIER ::= { ocmibs 3 }
		-- file occam.mib

ocmibsEhubMIB	OBJECT IDENTIFIER ::= { ocmibs 4 }
		-- file ocehub.mib

ocmibsOc8100MIB	OBJECT IDENTIFIER ::= { ocmibs 5 }
		-- file oc8100.mib

ocmibsCrossfireAtmMIB OBJECT IDENTIFIER ::= { ocmibs 6 }
                -- file oc9100.mib

ocmibsOc8200MIB	OBJECT IDENTIFIER ::= { ocmibs 7 }
		-- file oc8200.mib

ocmibsOc8600MIB	OBJECT IDENTIFIER ::= { ocmibs 8 }
		-- file oc8600.mib

ocmibsOc84x0MIB	OBJECT IDENTIFIER ::= { ocmibs 9 }
		-- file oc84x0.mib

ocmibsLanSwitchMIB      OBJECT IDENTIFIER ::= { ocmibs 10 }
		-- file oclansw.mib

ocmibsVlanMIB           OBJECT IDENTIFIER ::=  { ocmibs 11 }
		-- file ocvlan.mib

ocmibsSmartStatusMIB    OBJECT IDENTIFIER ::= { ocmibs 12 }


ocmibsCf871xMIB OBJECT IDENTIFIER ::= { ocmibs 13 }
		-- file cf871x.mib

atmUplinkMIB OBJECT IDENTIFIER ::= { ocmibs 14 }
                -- ATM uplink MIB


-- Temporary section

lmpMib				OBJECT IDENTIFIER ::= { temporary 1 }
				-- file lmp.mib

--- Inet section

inetMacAddrForm OBJECT-TYPE
	SYNTAX	INTEGER {
			canonical(1),
			non-canonical(2)
		}
	ACCESS  read-write
	STATUS  mandatory
	DESCRIPTION
		"This variable controls in which form MAC addresses will
		be represented. The default is canonical form for ethernet
		products and non-cannonical for tokenring products.
	        Setting this variable controls the representation for
		syntax's:
		PhysAddress, MacAddress and MacAddressString.
		Setting this variable will enforce a reboot."
	::= { inet 1 }

inetEnableRwho OBJECT-TYPE
	SYNTAX  INTEGER
		{
			enabled(1),
			disabled(2)		-- default
		}
	ACCESS  read-write
	STATUS  mandatory
	DESCRIPTION
		"This variable controls whether the device will send
		rhwo packets on UDP port 513. The packets include information
		about pseudo-users logged in. For the Olicom Bridge products,
		these are: Olicom Bridge Manager (user: obrimg) or the (IBM)
		Lan Network Manager	(users: control, altern, observ).
	    	The tty information describes the management link.
		If this object it disabled, it overrides the value of
		inetIPAddressEnableRwho."
	::= { inet 2 }

inetEnableRIP OBJECT-TYPE
	SYNTAX  INTEGER
		{
			enabled(1),
			disabled(2)		-- default
		}
	ACCESS  read-write
	STATUS  mandatory
	DESCRIPTION
		"This variable control whether the device will process
		RIP (Routing Information Protocol) packets on UDP port 520
		to update the IP routing table. The device will not announce
		any routes, it will only participate as a passive host.
		Refer to Unix documentation of either routed or gated
		daemons, or Internet RFC document 1058.
		If this object it disabled, it overrides the value of
		inetIPAddressEnableRIP."
	::= { inet 3 }

-- SNMP community config

-- The admin community table contains entries for each
-- community which is authorized to access the agent.

inetCommunityMaxEntries OBJECT-TYPE
	SYNTAX	INTEGER
	ACCESS	read-only
	STATUS	mandatory
	DESCRIPTION
		"The maximum number of community entries
		allowed in inetCommunityTable."
	::= { inet 4 }

inetCommunityTable OBJECT-TYPE
	SYNTAX  SEQUENCE OF InetCommunityTableEntry
	ACCESS  not-accessible
	STATUS  mandatory
	DESCRIPTION
		"A list of entries for each community which is
		authorized to access the agent.  The maximum number of
		entries is given by inetCommunityMaxEntries."
	::= { inet 5 }

inetCommunityTableEntry OBJECT-TYPE
	SYNTAX  InetCommunityTableEntry
	ACCESS  not-accessible
	STATUS  mandatory
	DESCRIPTION
		"A community entry containing objects pertaining to a
		network manager which is authorized to access the agent."
	INDEX   { inetCommunityNo }
	::= { inetCommunityTable 1 }

InetCommunityTableEntry ::= SEQUENCE {
	inetCommunityNo
		INTEGER,
	inetCommunityName
                DisplayString,
	inetCommunityIPAddress
		IpAddress,
	inetCommunityAccess
		INTEGER,
	inetCommunityDelete
		INTEGER,
	inetCommunityIPXAddress
		IPXAddress,
	inetCommunityTransportProtocols
		INTEGER,
        inetCommunityMACAddress
                MacAddress
}

inetCommunityNo OBJECT-TYPE
	SYNTAX	INTEGER
	ACCESS	read-only
	STATUS	mandatory
	DESCRIPTION
		"The entry number in the community table for this community."
	::= { inetCommunityTableEntry 1 }

inetCommunityName OBJECT-TYPE
        SYNTAX  DisplayString
	ACCESS  write-only
	STATUS  mandatory
	DESCRIPTION
		"The community name used by the management station to
		 access the agent. An empty community name means that any
		 request regardless of it's community name will be accepted."
	::= { inetCommunityTableEntry 2 }

inetCommunityIPAddress OBJECT-TYPE
	SYNTAX  IpAddress
	ACCESS  write-only
	STATUS  mandatory
	DESCRIPTION
		"The IP address of the management station authorized
		to access the agent.  A value of 0.0.0.0 allows every
		IP node to use the community name."
	::= { inetCommunityTableEntry 3 }

inetCommunityAccess OBJECT-TYPE
	SYNTAX	INTEGER {
			readOnly(1),		-- default
			readWrite(2)
		}
	ACCESS  write-only
	STATUS	mandatory
	DESCRIPTION
		"Controls the access rights of the management station."
	::= { inetCommunityTableEntry 4 }

inetCommunityDelete OBJECT-TYPE
	SYNTAX  INTEGER
	ACCESS  write-only
	STATUS  mandatory
	DESCRIPTION
        	"Setting this object to a non zero value, deletes the
		 entry for this community entry."
	::= { inetCommunityTableEntry 5 }

inetCommunityIPXAddress OBJECT-TYPE
	SYNTAX  IPXAddress
	ACCESS  write-only
	STATUS  mandatory
	DESCRIPTION
		"The IPX address of the management station authorized
		to access the agent.  A value of all zeroes allows every
		IPX node to use the community name."
	::= { inetCommunityTableEntry 6 }

inetCommunityTransportProtocols OBJECT-TYPE
        SYNTAX  INTEGER
	ACCESS  write-only
	STATUS  mandatory
	DESCRIPTION
		"This variable defines which transport protocols should be
		 expected to deliver requests for this community.
		 If the bit-value 0x01 is set, UDP/IP is used and the
		 inetCommunityIPAddress variable contains the source
		 address.
                 If the bit-value 0x02 is set, IPX is used and
		 the inetCommunityIPXAddress variable will be used.
                 If the bit-value 0x04 is set, MAC is used and
                 the inetCommunityMACAddress varial will be used.
		 All three bit-values can be set, in which case all source
		 addresses will be allowed."
	::= { inetCommunityTableEntry 7 }

inetCommunityMACAddress OBJECT-TYPE
	SYNTAX  MacAddress
	ACCESS  write-only
	STATUS  mandatory
	DESCRIPTION
		"The MAC address of the management station authorized
		to access the agent.  A value of 000000000000 allows every
		MAC node to use the community name."
	::= { inetCommunityTableEntry 8 }

-- SNMP Trap config

-- The admin trap table contains entries for each network
-- manager which receives traps from the agent.

inetTrapMaxEntries OBJECT-TYPE
	SYNTAX	INTEGER
	ACCESS	read-only
	STATUS	mandatory
	DESCRIPTION
		"The maximum number of network manager entries
		allowed in inetTrapTable."
	::= { inet 6 }

inetTrapTable OBJECT-TYPE
	SYNTAX  SEQUENCE OF InetTrapTableEntry
	ACCESS  not-accessible
	STATUS  mandatory
	DESCRIPTION
		"A list of trap entries for each network manager
		which receives traps from the agent.  The maximum
		number of entries is given by trapMaxEntries."
	::= { inet 7 }

inetTrapTableEntry OBJECT-TYPE
	SYNTAX  InetTrapTableEntry
	ACCESS  not-accessible
	STATUS  mandatory
	DESCRIPTION
		"A trap entry containing objects pertaining to a
		network manager which receives traps from the
		agent."
	INDEX   { inetTrapIndex }
	::= { inetTrapTable 1 }

InetTrapTableEntry ::= SEQUENCE {
	inetTrapCommunity
		OCTET STRING,
	inetTrapDestIPAddress
		IpAddress,
	inetTrapEventDisableMask
		OCTET STRING,
	inetTrapDelete
		INTEGER,
	inetTrapDestUDPPort
		INTEGER,
	inetTrapIndex
		INTEGER,
	inetTrapDestIPXAddress
		IPXAddress,
	inetTrapTransportProtocols
		INTEGER,
	inetTrapIPEncapsulation
		INTEGER,
	inetTrapIPXEncapsulation
		INTEGER
}

inetTrapCommunity OBJECT-TYPE
	SYNTAX  DisplayString
	ACCESS  read-write
	STATUS  mandatory
	DESCRIPTION
		"The community name used in traps sent to the
		management station."
	::= { inetTrapTableEntry 1 }

inetTrapDestIPAddress OBJECT-TYPE
	SYNTAX  IpAddress
	ACCESS  read-write
	STATUS  mandatory
	DESCRIPTION
		"The IP address of the management station to receive traps.
       Note a value of zero or resetting inetTrapTransportProtocols
       bit value 0x01 disables IP based traps from the entry
		 However inetTrapDelete should be used to delete entries as it
	   resets all parameters to default settings."
	::= { inetTrapTableEntry 2 }

inetTrapEventDisableMask OBJECT-TYPE
	SYNTAX	OCTET STRING			-- default zero
	ACCESS  read-write
	STATUS	deprecated
	DESCRIPTION
		"NOTE: This field has been replaced by the controlTrapTable.
		 Bitmask of disabled traps from product-specific network
		 management agents.  Each octet within the value of
		 this object specifies a set of eight traps, with the
		 first octet specifying traps 1 through 8, the second
		 octet specifying traps 9 through 16, etc.  Within each
		 octet, the least significant bit represents the lowest
		 numbered trap, and the most significant bit represents
		 the highest numbered trap.  Thus, each trap of the
		 device is represented by a single bit within the value
		 of this object.  If that bit has a value of `0' then
		 that trap is included in the set of traps; the trap is
		 not included if its bit has a value of `1'.
		 The bits corresponds to the TRAP numbers found in the
		 the product specific MIBs."
	REFERENCE "Olicom Bridge MIB, trap section.
		   Olicom Remote Bridge with CAM MIB, trap section.
		   Olicom Multiport Bridge MIB, trap section.
		   Olicom EHUB MIB, trap section.
		   Olicom CAM MIB, trap section.
		   Olicom CAU MIB, trap section."
	::= { inetTrapTableEntry 3 }

inetTrapDelete OBJECT-TYPE
	SYNTAX  INTEGER
	ACCESS  write-only
	STATUS  mandatory
	DESCRIPTION
        	"Setting this object to a non-zero value, deletes the
		 entry for the trap destination."
    ::= { inetTrapTableEntry 4 }

inetTrapDestUDPPort OBJECT-TYPE
	SYNTAX  INTEGER (1..65536)
	ACCESS  read-write
	STATUS  mandatory
	DESCRIPTION
		"The UDP port on the management station to receive traps.
		 If set to 0 (zero) the default value 162 is used."
	::= { inetTrapTableEntry 5 }

inetTrapIndex OBJECT-TYPE
	SYNTAX  INTEGER
	ACCESS  read-only
	STATUS  mandatory
	DESCRIPTION
		"All entries in the inetTrapTable have a unique index,
		 denoted by this variable."
	::= { inetTrapTableEntry 6 }

inetTrapDestIPXAddress OBJECT-TYPE
	SYNTAX  IPXAddress
	ACCESS  read-write
	STATUS  mandatory
	DESCRIPTION
		"The IPX address of the management station to receive traps.
                Note a value of zero or resetting inetTrapTransportProtocols
                bit value 0x02 disables IPX based traps from the entry
		However inetTrapDelete should be used to delete entries as it
		resets all parameters to default settings."
	::= { inetTrapTableEntry 7 }

inetTrapTransportProtocols OBJECT-TYPE
	SYNTAX  INTEGER
	ACCESS  read-write
	STATUS  mandatory
	DESCRIPTION
		"This variable defines which transport protocols should be
		 used to deliver TRAPs for this trap destination.
		 If the bit-value 0x01 is set, UDP/IP is use and the
		 inetTrapDestIPAddress variable contains the destination
		 address (together with the inetTrapDestUDPPort variable),
		 and if the bit-value 0x02 is set, IPX is used and the
		 inetTrapDestIPXAddress variable will be used.
		 Both bit-values can be set, in which case the traps will be
		 set to both destinations."
	::= { inetTrapTableEntry 8 }

inetTrapIPEncapsulation OBJECT-TYPE
	SYNTAX	INTEGER
		{
			ethernet(1),
			ieee8022(2),
			snap(3)		-- Default value
		}
	ACCESS	read-write
	STATUS	mandatory
	DESCRIPTION
		"This variable controls the encapsulation method used when
		 delivering TRAPs via the UDP/IP protocol.
		 NOTE: On TokenRing devices only snap(3) works.
		       ON EtherNet devices only ethernet(1) and snap(3)
		       works."
	::= { inetTrapTableEntry 9 }

inetTrapIPXEncapsulation OBJECT-TYPE
	SYNTAX	INTEGER
		{
			ethernet(1),
			ieee8022(2),	-- Default value
			snap(3)
		}
	ACCESS	read-write
	STATUS	mandatory
	DESCRIPTION
		"This variable controls the encapsulation method used when
		 delivering TRAPs via the IPX protocol.
		 NOTE: On TokenRing devices only ieee8022(2) and snap(3)
		 works."
	::= { inetTrapTableEntry 10 }

inetDefaultIPEncapsulation OBJECT-TYPE
	SYNTAX	INTEGER
		{
			ethernet(1),
			ieee8022(2),
			snap(3)		-- Default value
		}
	ACCESS	read-write
	STATUS	mandatory
	DESCRIPTION
		"This variable controls the default encapsulation method
		 used by this device, when transmitting via the UDP/IP
		 protocol.
		 This default encapsulation method is only used when there
		 is no other way to know which encapsulation method the
		 receiving host understands.
		 NOTE: On TokenRing devices only snap(3) works.
		       ON EtherNet devices only ethernet(1) and snap(3)
		       works."
	::= { inet 8 }

inetDefaultIPXEncapsulation OBJECT-TYPE
	SYNTAX	INTEGER
		{
			ethernet(1),
			ieee8022(2),	-- Default value
			snap(3)
		}
	ACCESS	read-write
	STATUS	mandatory
	DESCRIPTION
		"This variable controls the default encapsulation method
		 used by this device, when transmitting via the IPX protocol.
		 This default encapsulation method is only used when there
		 is no other way to know which encapsulation method the
		 receiving host understands.
		 NOTE: On TokenRing devices only ieee8022(2) and snap(3)
		 works."
	::= { inet 9 }

inetIPAddressTable OBJECT-TYPE
	SYNTAX	SEQUENCE OF InetIPAddressEntry
	ACCESS  not-accessible
	STATUS	mandatory
	DESCRIPTION
		"This table contains IP addressing information for each
		interface."
	::= { inet 10 }

inetIPAddressEntry OBJECT-TYPE
	SYNTAX	InetIPAddressEntry
	ACCESS  not-accessible
	STATUS	mandatory
DESCRIPTION ""
	INDEX   { inetIPAddressIfNumber }
	::= { inetIPAddressTable 1 }

InetIPAddressEntry ::= SEQUENCE {
	inetIPAddressIfNumber
		INTEGER,
	inetIPAddressIPAddress
		IpAddress,
	inetIPAddressNetmask
		IpAddress,
	inetIPAddressDefaultGateway
		IpAddress,
	inetIPAddressEnableRwho
		INTEGER,
	inetIPAddressEnableRIP
		INTEGER,
	inetIPAddressIPEncapsulation
		INTEGER
}

inetIPAddressIfNumber OBJECT-TYPE
	SYNTAX	INTEGER
	ACCESS  read-only
	STATUS	mandatory
	DESCRIPTION
		"This number corresponds to the interface number, ifIndex,
		in ifTable from MIB-II."
	::= { inetIPAddressEntry 1 }

inetIPAddressIPAddress OBJECT-TYPE
	SYNTAX  IpAddress
	ACCESS  read-write
	STATUS	mandatory
	DESCRIPTION
		"This is the IP address associated with the interface."
	::= { inetIPAddressEntry 2 }

inetIPAddressNetmask OBJECT-TYPE
	SYNTAX  IpAddress
	ACCESS  read-write
	STATUS	mandatory
	DESCRIPTION
		"This is the IP netmask associated with the interface.
		Note: Setting the netmask for one interface may change
		the netmask for other interfaces."
	::= { inetIPAddressEntry 3 }

inetIPAddressDefaultGateway OBJECT-TYPE
	SYNTAX  IpAddress
	ACCESS  read-write
	STATUS	mandatory
	DESCRIPTION
		"This is the IP default gateway associated with the
		interface.
		Note: Setting the default gateway for one interface
		may change the default gateway for other interfaces."
	::= { inetIPAddressEntry 4 }

inetIPAddressEnableRwho OBJECT-TYPE
	SYNTAX  INTEGER
		{
			enabled(1),		-- default
			disabled(2)
		}
	ACCESS  read-write
	STATUS  optional
	DESCRIPTION
		"This variable controls whether the device will send
		rhwo packets on UDP port 513 on the specified
		interface. The packets include information about
		pseudo-users logged in.
		This object has effect only if inetEnableRwho has the
		value 'enabled'."
	::= { inetIPAddressEntry 5 }

inetIPAddressEnableRIP OBJECT-TYPE
	SYNTAX  INTEGER
		{
			enabled(1),		-- default
			disabled(2)
		}
	ACCESS  read-write
	STATUS  optional
	DESCRIPTION
		"This variable control whether the device will process
		RIP (Routing Information Protocol) packets on UDP port
		520 on the specified interface to update the IP
		routing table. The device will not announce any
		routes, it will only participate as a passive host.
		Refer to Unix documentation of either routed or gated
		daemons, or Internet RFC document 1058.
		This object has effect only if inetEnableRIP has the
		value 'enabled'."
	::= { inetIPAddressEntry 6 }

inetIPAddressIPEncapsulation OBJECT-TYPE
	SYNTAX	INTEGER
		{
			ethernet(1),
			snap(3),
			media-default(4)	-- default
		}
	ACCESS	read-write
	STATUS	mandatory
	DESCRIPTION
		"This variable controls the IP encapsulation
		 method used on the specified interface.
		 Choosing media-default(4) selects SNAP encapsulation
		 on TokenRing interfaces and Ethernet encapsulation
		 on Ethernet interfaces.
		 NOTE: On TokenRing interfaces only snap(3) and
               media-default(4) works."
	::= { inetIPAddressEntry 7 }


-- SLIP Configuration

inetSlipBaudrate OBJECT-TYPE
        SYNTAX  INTEGER {
                        b1200(1),
                        b2400(2),
                        b4800(3),
                        b9600(4),
                        b19200(5),
                        b38400(6)
                }
        ACCESS  read-write
        STATUS  optional
        DESCRIPTION
                "The baud rate used by a SLIP connection."
        ::= { inet 11 }

inetSlipParity OBJECT-TYPE
        SYNTAX  INTEGER {
                        none(1),
                        even(2),
                        odd(3)
                }
        ACCESS  read-write
        STATUS  optional
        DESCRIPTION
                "The transmission parity used by a SLIP connection."
        ::= { inet 12 }

inetSlipStopbits OBJECT-TYPE
        SYNTAX  INTEGER {
                        one(1),
                        two(2)
                }
        ACCESS  read-write
        STATUS  optional
        DESCRIPTION
                "The number of stop bits used by a SLIP connection."
        ::= { inet 13 }

inetSlipModemInit OBJECT-TYPE
        SYNTAX  DisplayString (SIZE (0..20))
        ACCESS  read-write
        STATUS  optional
        DESCRIPTION
                "A string sent to the modem to initialize it prior to
                 establishing a SLIP connection."
        ::= { inet 14 }

inetSlipHeaderCompressionEnabled OBJECT-TYPE
        SYNTAX  INTEGER { yes(1), no(2) }
        ACCESS  read-write
        STATUS  optional
        DESCRIPTION
                 "Enable or disable compression of the SLIP headers."
        ::= { inet 15 }

inetSlipMaxMtuSize OBJECT-TYPE
        SYNTAX  INTEGER
        ACCESS  read-write
        STATUS  optional
        DESCRIPTION
                "Maximum Transmit Unit size, that is, the maximum size
                 of a PDU transmitted on a SLIP connection."
        ::= { inet 16 }

inetSlipMaxMruSize OBJECT-TYPE
        SYNTAX  INTEGER
        ACCESS  read-write
        STATUS  optional
        DESCRIPTION
                "Maximum Receive Unit size, that is, the maximum acceptable
                 size of a PDU received on a SLIP connection."
        ::= { inet 17 }

sCallbackEnable OBJECT-TYPE
        SYNTAX  INTEGER {
                        disabled(1),            -- default
                        enabled(2)
                }
        ACCESS  read-write
        STATUS  deprecated
        DESCRIPTION
                "This object controls whether the Olicom Out-Of-Band
                Management Callback sub-system should be active (enabled)
                or not."
        ::= { inet 18 }

sCallbackPhoneNumber OBJECT-TYPE
        SYNTAX  DisplayString (SIZE (0..30))
        ACCESS  read-write
        STATUS  deprecated
        DESCRIPTION
                "A string containing the telephone number to be used by the
                callback sub-system. This string will be sent `as is' to
                the modem connected to the OBM communication port."
        ::= { inet 19 }

sCalloutEnable OBJECT-TYPE
        SYNTAX  INTEGER {
                        disabled(1),            -- default
                        enabled(2)
                }
        ACCESS  read-write
        STATUS  deprecated
        DESCRIPTION
                "This object controls whether the Olicom Out-Of-Band
                Management Callout sub-system should be active (enabled)
                or not."
        ::= { inet 20 }

sCalloutPhoneNumber OBJECT-TYPE
        SYNTAX  DisplayString (SIZE (0..30))
        ACCESS  read-write
        STATUS  deprecated
        DESCRIPTION
                "A string containing the telephone number to be used by the
                callout sub-system. This string will be sent `as is' to
                the modem connected to the OBM communication port."
        ::= { inet 21 }

-- Control section

controlRestart OBJECT-TYPE
	SYNTAX	INTEGER
	ACCESS	write-only
	STATUS	mandatory
	DESCRIPTION
		"Writing any value other than zero to this variable
		causes the device program to restart."
	::= { control 1 }

controlConfigChangeCounter OBJECT-TYPE
	SYNTAX	INTEGER
	ACCESS	read-write
	STATUS	mandatory
	DESCRIPTION
		"This variable contains the number of times, any part of
		 the configuration has been changed by any of the management
		 systems controlling this device. See the managementTable."
	::= { control 2 }

controlTrapTable OBJECT-TYPE
	SYNTAX  SEQUENCE OF ControlTrapTableEntry
	ACCESS  not-accessible
	STATUS  mandatory
	DESCRIPTION
		"This table contains an entry for each enterprise-specific
		 TRAP this device is capable of sending.
		 The only writable field in the table is the
		 controlTrapGeneration field, which controls the generation
		 is that particular TRAP. All other fields are used as
		 indices."
	::= { control 3 }

controlTrapTableEntry OBJECT-TYPE
	SYNTAX  ControlTrapTableEntry
	ACCESS  not-accessible
	STATUS  mandatory
	DESCRIPTION
		"A controlTrapTableEntry entry contains objects pertaining to
		 one particular enterprise-specific TRAP."
	INDEX   { controlTrapIndex,
		  controlTrapMIBIndex,
		  controlTrapNumber }
	::= { controlTrapTable 1 }

ControlTrapTableEntry ::= SEQUENCE {
	controlTrapIndex
		INTEGER,
	controlTrapMIBIndex
		INTEGER,
	controlTrapNumber
		INTEGER,
	controlTrapDescription
		DisplayString,
	controlTrapGeneration
		INTEGER
}

controlTrapIndex OBJECT-TYPE
	SYNTAX	INTEGER
	ACCESS	read-only
	STATUS	mandatory
	DESCRIPTION
		"This variable corresponds to the inetTrapIndex variable in
		 the inetTrapTable."
	::= { controlTrapTableEntry 1 }

controlTrapMIBIndex OBJECT-TYPE
	SYNTAX	INTEGER
	ACCESS	read-only
	STATUS	mandatory
	DESCRIPTION
		"This variable identifies the MIB in which this TRAP
		 is defined. The variable is the index of the entry in
		 infoSoftwareMIBsTable that defines the MIB in question."
	::= { controlTrapTableEntry 2 }

controlTrapNumber OBJECT-TYPE
	SYNTAX	INTEGER
	ACCESS	read-only
	STATUS	mandatory
	DESCRIPTION
		"This variable describes in which TRAP in the MIB subtree
		 this TRAP is."
	::= { controlTrapTableEntry 3 }

controlTrapDescription OBJECT-TYPE
	SYNTAX	DisplayString
	ACCESS	read-only
	STATUS	mandatory
	DESCRIPTION
		"This variable describes the TRAP. This corresponds to the
		 description field in the MIB text for this TRAP."
	::= { controlTrapTableEntry 4 }

controlTrapGeneration OBJECT-TYPE
	SYNTAX	INTEGER
		{
			never(1),
			always(2)
		}
	ACCESS	read-write
	STATUS	mandatory
	DESCRIPTION
		"This variable controls whether this TRAP never(1) is
		 generated or is always(2) generated."
	::= { controlTrapTableEntry 5 }

controlLoadProtocol OBJECT-TYPE
	SYNTAX	INTEGER
		{
			ibm-rpl(1),
			ibm-hlm(2),
			bootp-tftp(3),
			olicom-rpl(4),
			olicom-remote-software-update(5)
		}
	ACCESS	read-write
	STATUS	mandatory
	DESCRIPTION
		"This variable defines which protocol should be used for
		downloading configuration and program code.
		Notice that a specific Olicom product will typically support
		only one or two of the listed protocols."
	::= { control 4 }

controlLoadFilename OBJECT-TYPE
        SYNTAX  DisplayString (SIZE (0..255))
	ACCESS	read-write
	STATUS	mandatory
	DESCRIPTION
		"In the Load protocols where it is relevant this variable
		 contains the name of the file to be downloaded."
	::= { control 5 }

controlLoadServerMACAddress OBJECT-TYPE
        SYNTAX      MacAddress
        ACCESS      read-write
        STATUS      optional
        DESCRIPTION
		"This object specifies the MAC address of the Load server
		 used for download. Only used if the Load protocol defined
		 by the controlLoadProtocol variable needs the MAC address
		 of the an Load server."
	::= { control 6 }

controlLoadServerIPAddress OBJECT-TYPE
        SYNTAX      IpAddress
        ACCESS      read-write
        STATUS      optional
        DESCRIPTION
		"This object specifies the IP address of the Load server
		 used for download. Only used if the Load protocol defined
		 by the controlLoadProtocol variable needs the IP address
		 of the an Load server."
	::= { control 7 }

controlLoadServerIPXAddress OBJECT-TYPE
        SYNTAX      IPXAddress
        ACCESS      read-write
        STATUS      optional
        DESCRIPTION
		"This object specifies the IPX address of the Load server
		 used for download. Only used if the Load protocol defined
		 by the controlLoadProtocol variable needs the IPX address
		 of the an Load server."
	::= { control 8 }

controlLoadStart OBJECT-TYPE
	SYNTAX	INTEGER
                {
                    notInitiated(1),    --no transfer since last reboot
                    starting(2),
                    inProgress(3),
                    finishing(4),
                    completed(5),       --last transfer was completed successfully
                    protocolFailure(6), --transmission failed e.g. TFTP error
                    flashFailure(7),    --writing to the flash failed
                    badFile(8)          --the file transmitted was corrupted
                }
        ACCESS  read-write
	STATUS	mandatory
	DESCRIPTION
		"Writing any value other than zero to this variable
                 causes a download to start.
                 While reading, it returns the current status of transmission
                 or last transmission result."
	::= { control 9 }

controlTime OBJECT-TYPE
	SYNTAX	INTEGER
	ACCESS	read-write
	STATUS	mandatory
	DESCRIPTION
		"The internal clock in the device. This is measured in
		 seconds since 00:00:00 on 1 January 1970 (i.e. UNIX
		 standard time)."
	::= { control 10 }

controlEnableRmon OBJECT-TYPE
        SYNTAX  INTEGER
                {
                        enabled(1),
                        disabled(2)             -- default
                }
        ACCESS  read-write
        STATUS  optional
        DESCRIPTION
                "This object specifies whether RMON probe is enabled or
                 disabled. If the device does not support RMON only disabled
		 is allowed. Setting this variable resets the CAU."
	::= { control 11 }

controlAutoRestart OBJECT-TYPE
        SYNTAX  INTEGER
                {
                        enabled(1),             -- default
                        disabled(2)
                }
        ACCESS  read-write
        STATUS  optional
        DESCRIPTION
                "This object specifies whether changes to certain fundamental
		 configuration parameters (as specified for the corresponding
		 MIB variables) shall cause the device to restart automatically.
		 The auto restart functionality is always enabled after
		 restarting the bridge.

		 NOTICE:
		 In general, disabling this functionality is not recommended,
		 since some changes may cause the device to behave erratically
		 (which may be the reason why the device has to restart).
		 However, for the initial configuration of the device (i.e.
		 before it is operational, it is usually safe to postpone
		 restarting the device until all configuration changes
		 have been made."
	::= { control 12 }

controlSwAdminStatus OBJECT-TYPE
        SYNTAX  INTEGER
        ACCESS  read-write
        STATUS  optional
        DESCRIPTION
                "This object controls the state of the SW images in systems
                 where more than one image is present.

                 In the OC-9100 the state of each image may be:
                        empty(1) - no image is present,
                        future1(2) - the image may be used later,
                        futureTest(3) - the image will be used once on the next restart,
                        future2(4) - the image may be used later,
                        current1(5) - the image is in use now,
                        past(6) - the image was previously used,
                        current2(7) - the image is in use now,
                        checksumError(8) - the image is faulty,
                        erased(9) - the image has been erased.
                 Because this information is stored in flash each state cannot be
                 used arbitrarily. For example, the future state can only be
                 used twice, namely as state future1 and future2. Normally,
                 the state of a SW image progresses through numerically
                 increasing states.

                 In the OC-8500 and OC-8700 series the status word is stored in
                 BBS RAM. This releases the constraints to the sequence of
                 states, thus only a subset of the above is needed:
                        empty(1) - no image is present,
                        future1(2) - the image may be used later,
                        futureTest(3) - the image will be used once on the next restart,
                        current1(5) - the image is in use now,
                        past(6) - the image was previously used,
                        checksumError(8) - the image is faulty,
                        erased(9) - the image has been erased.

                 The value actually stored in this object is state1*256+state2,
                 where state1 and state2 are the values of the two SW image
                 states. Note that a number of combinations are illegal. For
                 example, the value 6*256+6 (indicating two 'past' images) may
                 not be written."
        ::= { control 13 }

-- { control 14 } has been deleted

controlFlashConfigSize OBJECT-TYPE
        SYNTAX  INTEGER
        ACCESS  read-only
        STATUS  optional
        DESCRIPTION
                "The total number of bytes in the configuration FLASH, or
                 rather, in one of the two alternating sections."
        ::= { control 15 }

controlFlashConfigFree OBJECT-TYPE
        SYNTAX  INTEGER
        ACCESS  read-only
        STATUS  optional
        DESCRIPTION
                "The number of free bytes in the configuration FLASH."
        ::= { control 16 }

controlFlashConfigState OBJECT-TYPE
        SYNTAX  INTEGER { normal(1),
                          default(2),
                          corrupted(3),
                          temporary(4),
                          testTemporary(5),
                          acceptTemporary(6),
                          rejectTemporary(7),
                          rewrite(8) }
        ACCESS  read-write
        STATUS  optional
        DESCRIPTION
                "Controls the state of the FLASH configuration. The states
                 are as follows:
                     normal
                     default - The DEFAULT button has been activated.
                     corrupted - The FLASH configuration has been corrupted,
                                 default configuration is used.
                     temporary - A temporary update to the configuration has
                                 been initiated.
                     testTemporary - A restart has been performed after a
                                     'temporary' update.
                     acceptTemporary - Setting this value in state 'temporary'
                                       or 'testTemporary' will force the state
                                       to 'normal' and will cause the
                                       configuration to be accepted.
                     rejectTemporary - Setting this value in state 'temporary'
                                       or 'testTemporary' will cause the
                                       temporary configuration update to be
                                       aborted.
                     rewrite - Setting this value will cause the FLASH to be
                               rewritten, resulting in maximum free FLASH."
        ::= { control 17 }

controlDelayedRestart OBJECT-TYPE
	SYNTAX	INTEGER
        ACCESS  read-write
	STATUS	mandatory
	DESCRIPTION
		"Writing value n to this variable will cause device to restart
                after n seconds.
                Writing zero cancels the reboot.
                Writing new value when the reboot is already scheduled
                cancels previously scheduled action and schedules new reboot.
                While reading this variable shows time remaining to the reboot
                (0 if reboot is not scheduled)."
        ::= { control 18 }

controlLoadProggress OBJECT-TYPE
	SYNTAX	INTEGER
        ACCESS  read-only
	STATUS	mandatory
	DESCRIPTION
                "Number of bytes transmitted so far.
                 0 if no transmission is currently in progress."
        ::= { control 19 }

controlLoadFileSize OBJECT-TYPE
	SYNTAX	INTEGER
        ACCESS  read-only
	STATUS	mandatory
	DESCRIPTION
                "Length of the file being transmitted.
                 0 if no transmission is currently in progress or if
                 the size is unknown."
        ::= { control 20 }

controlTftpClient  OBJECT IDENTIFIER ::= { control 21 }

controlTftpMaxSessions OBJECT-TYPE
        SYNTAX  INTEGER
        ACCESS  read-only
        STATUS  optional
        DESCRIPTION
                "The maximum number of simultaneous sessions this device is
                 able to handle."
        ::= { controlTftpClient 1 }

controlTftpNextSessionIndex OBJECT-TYPE
        SYNTAX  INTEGER
        ACCESS  read-only
        STATUS  optional
        DESCRIPTION
                "The unique identifier of the next free TFTP session.
                 This index should be used for manipulating rows in
                 controlTftpSessionTable."
        ::= { controlTftpClient 2 }

controlTftpSessionTable OBJECT-TYPE
        SYNTAX  SEQUENCE OF ControlTftpSessionEntry
        ACCESS  not-accessible
        STATUS  optional
        DESCRIPTION
                "This table makes it possible to control TFTP sessions performed
                 by the built-in device TFTP client."
        ::= { controlTftpClient 3 }

controlTftpSessionEntry OBJECT-TYPE
        SYNTAX  ControlTftpSessionEntry
        ACCESS  not-accessible
        STATUS  mandatory
        DESCRIPTION
                "A list of configuration objects for the TFTP session."
        INDEX   {  controlTftpSessionIndex  }
        ::=  { controlTftpSessionTable 1 }

ControlTftpSessionEntry  ::=  SEQUENCE {
        controlTftpSessionIndex
                INTEGER,
        controlTftpSessionRowStatus
                RowStatus,
        controlTftpSessionDirection
                INTEGER,
        controlTftpSessionServerAddress
                IpAddress,
        controlTftpSessionServerFile
                DisplayString,
        controlTftpSessionLocalFile
                DisplayString,
        controlTftpSessionStatus
                INTEGER,
        controlTftpSessionProgress
                INTEGER,
        controlTftpSessionFileSize
                INTEGER
}

controlTftpSessionIndex OBJECT-TYPE
        SYNTAX  INTEGER
        ACCESS  read-only
        STATUS  mandatory
        DESCRIPTION
                "The TFTP session index."
        ::=  {  controlTftpSessionEntry 1  }

controlTftpSessionRowStatus OBJECT-TYPE
        SYNTAX  RowStatus
        ACCESS  read-write
        STATUS  mandatory
        DESCRIPTION
                "The status of this TFTP session entry.
                 The following values are possible:
                 'active' - TFTP operation is in progress. Setting this
                 object to this value starts the transmission.
                 'notInService' - The row is created but there is no TFTP
                 transfer in progress.
                 'createAndWait' - the only way to create the session.
                 If the operation is successful the status of the row
                 should be 'notInService'.
                 'destroy' - destroys the row and frees the resources. This
                 operation will fail when the row is 'active'.
                 'createAndGo' is illegal. Setting this object to this
                 value will fail.
                 'notReady' is not used for this variable."
        ::=  {  controlTftpSessionEntry 2  }

controlTftpSessionDirection OBJECT-TYPE
        SYNTAX  INTEGER
        {
            download(1), --to the device
            upload(2)   --from the device
        }
        ACCESS  read-write
        STATUS  mandatory
        DESCRIPTION
                "The direction of this session's transfer."
        ::=  {  controlTftpSessionEntry 3  }

controlTftpSessionServerAddress OBJECT-TYPE
        SYNTAX      IpAddress
        ACCESS      read-write
        STATUS      mandatory
        DESCRIPTION
                "The IP address of the TFTP server used for the transmission."
        ::= { controlTftpSessionEntry 4 }

controlTftpSessionServerFile OBJECT-TYPE
        SYNTAX      DisplayString
        ACCESS      read-write
        STATUS      mandatory
        DESCRIPTION
                "The name of the transferred file on the server side."
        ::= { controlTftpSessionEntry 5 }

controlTftpSessionLocalFile OBJECT-TYPE
        SYNTAX      DisplayString
        ACCESS      read-write
        STATUS      mandatory
        DESCRIPTION
                "The name of the transferred file on the switch side.
                 In case of upload switch may ignore this variable."
        ::= { controlTftpSessionEntry 6 }

controlTftpSessionStatus OBJECT-TYPE
        SYNTAX  INTEGER
                {
                    notInitiated(1),
                    starting(2),
                    inProgress(3),
                    finishing(4),
                    completed(5),
                    protocolFailure(6),
                    flashFailure(7),
                    badFile(8)
                }
        ACCESS  read-only
        STATUS  mandatory
        DESCRIPTION
                "The status of the session or transmission result when
                 the session was completed.
                 The following values are possible:
                    notInitiated(1)     no transfer since this row creation
                    starting(2)
                    inProgress(3)
                    finishing(4)
                    completed(5)        last transfer was completed successfully
                    protocolFailure(6)  transmission failed (e.g. TFTP error)
                    flashFailure(7)     writing to the flash failed
                    badFile(8)          the file transmitted was corrupted
                 The download/upload cycle doesn't have to go through all of
                 the states listed above.
                "
        ::= { controlTftpSessionEntry 7 }

controlTftpSessionProgress OBJECT-TYPE
        SYNTAX  INTEGER
        ACCESS  read-only
        STATUS  mandatory
        DESCRIPTION
                "Number of bytes transmitted so far.
                 0 if no transmission is currently in progress."
        ::= { controlTftpSessionEntry 8 }

controlTftpSessionFileSize OBJECT-TYPE
        SYNTAX  INTEGER
        ACCESS  read-only
        STATUS  mandatory
        DESCRIPTION
                "Length of the file being transmitted.
                 0 if no transmission is currently in progress or if
                 the size is unknown."
        ::= { controlTftpSessionEntry 9 }

controlRestartType OBJECT-TYPE
        SYNTAX  INTEGER
                {
                    soft(1),
                    default(2)
                }
        ACCESS  read-write
        STATUS  mandatory
        DESCRIPTION
                "The type of restart that will be performed after next reboot
                request. After any kind of reboot the value of this object should
                be soft(1) regardles of the previous value."
        DEFVAL { soft }
        ::= { control 22 }


-- OBM section

obmEnable OBJECT-TYPE
        SYNTAX  INTEGER {
                        disabled(1),
                        enabled(2)            -- default
                }
        ACCESS  read-write
        STATUS  mandatory
        DESCRIPTION
                "This object controls whether the Olicom Out-Of-Band
                Management system should be active (enabled) or not."
        ::= { obm 1 }

obmPassword OBJECT-TYPE
        SYNTAX  DisplayString (SIZE (0..7))
        ACCESS  read-write
        STATUS  mandatory
        DESCRIPTION
                "A string containing the password needed to access the
                device through the OBM communication port.
                NOTE: Reading the password will return the string
                `********' - an attempt to set the password to that
                value will not modify the password."
        ::= { obm 2 }

obmBaudrate OBJECT-TYPE
        SYNTAX  INTEGER {
                        b1200(1),
                        b2400(2),
                        b4800(3),
                        b9600(4),               -- default
                        b19200(5),
                        b38400(6),
                        b57600(7),
                        b115200(8),
                        b230400(9),
                        b460800(10),
                        b921600(11),
                        auto(12)
                }
        ACCESS  read-write
        STATUS  mandatory
        DESCRIPTION
                "This object controls the baudrate of the communication
                port used by the Out-of-Band Management system. The 'auto'
                means automatic UART speed sensing."
        ::= { obm 3 }

obmParity OBJECT-TYPE
        SYNTAX  INTEGER {
                        none(1),                -- default
                        even(2),
                        odd(3)
                }
        ACCESS  read-write
        STATUS  mandatory
        DESCRIPTION
                "This object controls the parity of the communication
                port used by the Out-of-Band Management system."
        ::= { obm 4 }

obmStopbits OBJECT-TYPE
        SYNTAX  INTEGER {
                        one(1),                 -- default
                        two(2)
                }
        ACCESS  read-write
        STATUS  mandatory
        DESCRIPTION
                "This object controls the number of stopbits of the
                communication port used by the Out-of-Band Management
                system."
        ::= { obm 5 }

obmModemInit OBJECT-TYPE
        SYNTAX  DisplayString (SIZE (0..20))
        ACCESS  read-write
        STATUS  mandatory
        DESCRIPTION
                "A string containing the initialization string used to
                initialize the modem connected to the OBM communication
                port. This string will be sent `as is'."
        ::= { obm 6 }

obmCallbackEnable OBJECT-TYPE
        SYNTAX  INTEGER {
                        disabled(1),            -- default
                        enabled(2)
                }
        ACCESS  read-write
        STATUS  mandatory
        DESCRIPTION
                "This object controls whether the Olicom Out-Of-Band
                Management Callback sub-system should be active (enabled)
                or not."
        ::= { obm 7 }

obmCallbackPhoneNumber OBJECT-TYPE
        SYNTAX  DisplayString (SIZE (0..30))
        ACCESS  read-write
        STATUS  mandatory
        DESCRIPTION
                "A string containing the default phone number to be used by the
                callback sub-system. This string will be sent `as is' to
                the modem connected to the OBM communication port."
        ::= { obm 8 }

obmCalloutEnable OBJECT-TYPE
        SYNTAX  INTEGER {
                        disabled(1),            -- default
                        enabled(2)
                }
        ACCESS  read-write
        STATUS  mandatory
        DESCRIPTION
                "This object controls whether the Olicom Out-Of-Band
                Management Callout sub-system should be active (enabled)
                or not."
        ::= { obm 9 }

obmCalloutPhoneNumber OBJECT-TYPE
        SYNTAX  DisplayString (SIZE (0..30))
        ACCESS  read-write
        STATUS  mandatory
        DESCRIPTION
                "A string containing the telephone number to be used by the
                callout sub-system. This string will be sent `as is' to
                the modem connected to the OBM communication port."
        ::= { obm 10 }

obmCalloutTriggerEvent OBJECT-TYPE
        SYNTAX  OCTET STRING                    -- default zero
        ACCESS  read-write
        STATUS  mandatory
        DESCRIPTION
                "This object controls which events will trigger the
                callout sub-system to try to establish a connection using
                the obmCalloutPhoneNumber. The value is a bitmask,
                representing the following possibilities:
                  0x01 : Fatal Error.                  (CAU/CAM/BRIDGE)
                  0x02 : Adapter Failure.              (CAU)
                  0x02 : Start-up Failure.             (BRIDGE)
                  0x04 : Fan Failure.                  (SWI)
                  0x04 : LAM Failure.                  (CAU/CAM)
                  0x08 : Main ring Wrap due to beacon. (CAU)
                  0x10 : HLM Connection Lost.          (CAU/CAM)
                  0x10 : Temperature warning           (SWI)
                  0x20 : Power System Failure          (CAU)
                  0x40 : WAN link failure              (BRIDGE)
                  0x40 : Port auto disabled            (SWI)"
        ::= { obm 11 }

obmCalloutRetries OBJECT-TYPE
        SYNTAX  INTEGER (0..255)
        ACCESS  read-write
        STATUS  mandatory
        DESCRIPTION
                "This value denotes the number of times the callout
                sub-system will try to establish a connection using the
                obmCallbackPhoneNumber string. Used also for call-back."
        ::= { obm 12 }

obmCalloutRetryTimer OBJECT-TYPE
        SYNTAX  INTEGER (0..255)
        ACCESS  read-write
        STATUS  mandatory
        DESCRIPTION
                "This value denotes the number of minutes between
                unsuccesful attempts to establish a connection using the
                obmCalloutPhoneNumber string. Used also for call-back."
        ::= { obm 13 }

obmDelayedRecovery OBJECT-TYPE
        SYNTAX  INTEGER {
                        disabled(1),            -- default
                        enabled(2)
                }
        ACCESS  read-write
        STATUS  mandatory
        DESCRIPTION
                "This object controls whether the Olicom Out-Of-Band
                Management delayed Recovery sub-system should be active
                (enabled) or not.  On a bridge this is controlled by
                the configRestartOnError variable."
        ::= { obm 14 }

obmEnableTelnet OBJECT-TYPE
        SYNTAX  INTEGER {
                        disabled(1),
                        enabled(2)
                }
        ACCESS  read-write
        STATUS  optional
        DESCRIPTION
                "This object controls whether the Olicom Out-Of-Band
                Management can be accessed from telnet."
        ::= { obm 15 }

obmConnectTimeout OBJECT-TYPE
        SYNTAX  INTEGER (0..255)
        ACCESS  read-write
        STATUS  optional
        DESCRIPTION
                "This value denotes the number of seconds the user must
                wait after 3 unsuccesfull attempts to enter the correct
                password.
                The default value is 60 sec."
        ::= { obm 16 }

obmDefaultOperationalMode OBJECT-TYPE
        SYNTAX  INTEGER {
                        autoSense(1),
                        serialConsole(2),      -- default
                        asyncPPP (3)
                }
        ACCESS  read-write
        STATUS  optional
        DESCRIPTION
                "This object controls whether the Olicom Out-Of-Band
                Management can be accessed via serial console or
                async PPP/SLIP or selected dynamically
                (serial or async PPP/SLIP) based on the incoming data type."
        ::= { obm 17 }

obmInactivityTimeout OBJECT-TYPE
        SYNTAX  INTEGER (0..255)
        ACCESS  read-write
        STATUS  mandatory
        DESCRIPTION
                "This object controls value of inactivity timeout [min]
                which will be used to disconnect an idle user from
                the Out-of-Band Management system.
                The default value is 3 min.
                Value 0 disables this feature (infinite timeout)"
        ::= { obm 18 }

obmDialType OBJECT-TYPE
        SYNTAX  INTEGER {
                        pulse(1),
                        tone(2)              -- default
                }
        ACCESS  read-write
        STATUS  mandatory
        DESCRIPTION
                "This object controls if ATDP or ATDT will be sent
                to a modem while dialing from the Out-of-Band Management
                system."
        ::= { obm 19 }

obmPasswordRead OBJECT-TYPE
        SYNTAX  DisplayString (SIZE (0..7))
        ACCESS  read-write
        STATUS  mandatory
        DESCRIPTION
                "A string containing the password needed to read-access the
                device through the OBM communication port.
                NOTE: Reading the password will return the string
                `********' - an attempt to set the password to that
                value will not modify the password."
        ::= { obm 20 }

obmXonXoffHandshake OBJECT-TYPE
        SYNTAX  INTEGER {
                        enabled(1),
                        disabled(2)
                }
        ACCESS  read-write
        STATUS  mandatory
        DESCRIPTION
                "The status of Xon/Xoff flow control."
        ::= { obm 21 }

obmRtsCtsHandshake OBJECT-TYPE
        SYNTAX  INTEGER {
                        enabled(1),
                        disabled(2)
                }
        ACCESS  read-write
        STATUS  mandatory
        DESCRIPTION
                "The status of RTS/CTS handshake."
        ::= { obm 22 }

obmDatabits OBJECT-TYPE
        SYNTAX  INTEGER
        ACCESS  read-only
        STATUS  mandatory
        DESCRIPTION
                "Number of databits to be used by serial interface."
        ::= { obm 23 }


-- Management section

managementTable OBJECT-TYPE
        SYNTAX  SEQUENCE OF ManagementTableEntry
        ACCESS  not-accessible
        STATUS  mandatory
        DESCRIPTION
                "A list of entries for each management system the device
                 supports.
                 NOTE: The SNMP management system is always the first entry
                 in the table."
        ::= { management 1 }

managementTableEntry OBJECT-TYPE
        SYNTAX  ManagementTableEntry
        ACCESS  not-accessible
        STATUS  mandatory
        DESCRIPTION
                "A management entry contains objects pertaining to a
                 network management system which is supported by this
                 device."
        INDEX   { managementNo }
        ::= { managementTable 1 }

ManagementTableEntry ::= SEQUENCE {
        managementNo
                INTEGER,
        managementDescription
                DisplayString,
        managementAssociationState
                INTEGER,
        managementPriority
                INTEGER
}

managementNo OBJECT-TYPE
        SYNTAX  INTEGER
        ACCESS  read-only
        STATUS  mandatory
        DESCRIPTION
                "The entry number in the management table for this management
                 system."
        ::= { managementTableEntry 1 }

managementDescription OBJECT-TYPE
        SYNTAX  DisplayString
        ACCESS  read-only
        STATUS  mandatory
        DESCRIPTION
                "A descriptive text for this management system (protocol)."
        ::= { managementTableEntry 2 }

managementAssociationState OBJECT-TYPE
        SYNTAX  INTEGER
                {
                        associated(1),          -- Someone logged in
                        not-associated(2),      -- Nobody logged in
                        na-association(3)       -- Association not applicable
                }
        ACCESS  read-only
        STATUS  mandatory
        DESCRIPTION
                "This variable describes the current association between this
                 device and this management system. Some systems are
                 association oriented (e.g. CMIP) and can therefore have
                 state associated(1) or not-associated(2), while other
                 management systems are request/reply oriented (e.g. SNMP)
                 and therefore  always have the state na-association(3)."
        ::= { managementTableEntry 3 }

managementPriority OBJECT-TYPE
        SYNTAX  INTEGER
        ACCESS  read-only
        STATUS  mandatory
        DESCRIPTION
                "This variable describes the relative priority of the
                 management systems supported by this device. The associated
                 management system with the highest managementPriority value
                 (numerically) will be the ONLY system with write access to
                 all management variables."

        ::= { managementTableEntry 4 }


managementSnmpAccessLogTable OBJECT-TYPE
        SYNTAX  SEQUENCE OF ManagementSnmpAccessLogEntry
        ACCESS  not-accessible
        STATUS  optional
        DESCRIPTION
                "This table contains the history log for the last 10
                 SNMP managers which have accessed this device."
        ::= { management 2 }

managementSnmpAccessLogEntry OBJECT-TYPE
        SYNTAX  ManagementSnmpAccessLogEntry
        ACCESS  not-accessible
        STATUS  optional
        DESCRIPTION
                "An entry in the managementSnmpAccessLogTable."
        INDEX   { managementSnmpAccessLogIndex }
        ::= { managementSnmpAccessLogTable 1 }

ManagementSnmpAccessLogEntry ::=
        SEQUENCE {
            managementSnmpAccessLogIndex
                INTEGER,
            managementSnmpAccessLogTimeStamp
                TimeTicks,
            managementSnmpAccessLogIpAddress
                IpAddress,
            managementSnmpAccessLogAccessRights
                INTEGER,
            managementSnmpAccessLogCount
                INTEGER
        }

managementSnmpAccessLogIndex OBJECT-TYPE
        SYNTAX  INTEGER (1..10)
        ACCESS  read-only
        STATUS  optional
        DESCRIPTION
                "The number of this entry in the
                 managementSnmpAccessLogTable."
        ::= { managementSnmpAccessLogEntry 1 }

managementSnmpAccessLogTimeStamp OBJECT-TYPE
        SYNTAX  TimeTicks
        ACCESS  read-only
        STATUS  optional
        DESCRIPTION
                "The time at which the SNMP manager last accessed
                 this device."
        ::= { managementSnmpAccessLogEntry 2 }

managementSnmpAccessLogIpAddress OBJECT-TYPE
        SYNTAX  IpAddress
        ACCESS  read-only
        STATUS  optional
        DESCRIPTION
                "The IP Address of the SNMP manager."
        ::= { managementSnmpAccessLogEntry 3 }

managementSnmpAccessLogAccessRights OBJECT-TYPE
        SYNTAX  INTEGER {
			readOnly(1),
			readWrite(2)
		}
        ACCESS  read-only
        STATUS  optional
        DESCRIPTION
                "Specifies the access rights of the SNMP manager."
        ::= { managementSnmpAccessLogEntry 4 }

managementSnmpAccessLogCount OBJECT-TYPE
        SYNTAX  INTEGER
        ACCESS  read-only
        STATUS  optional
        DESCRIPTION
                "Specifies the number of times the SNMP manager
                 has accessed this device."
        ::= { managementSnmpAccessLogEntry 5 }


managementSnmpLastErrorReason OBJECT-TYPE
        SYNTAX  DisplayString
        ACCESS  read-only
        STATUS  mandatory
        DESCRIPTION
                "A detailed explanation of why the last SNMP operation
                 failed. It is used by the management station when
                 the SNMP error-status in the response does not fully
                 explain the reason for the failure. For example,
                 'badValue' can be returned if the user has entered
                 an improper value or if there are insufficient system
                 resources to perform a requested action. The SNMP agent
                 should return the failure explanation only if it is
                 requested by the station that caused it. If no failure
                 has occurred, the SNMP agent should return an empty string
                 when a request for this object."
        ::= { management 3 }


-- Frontpanel section

frontpanelDisplay OBJECT-TYPE
        SYNTAX  DisplayString
        ACCESS  read-write
        STATUS  optional
        DESCRIPTION
                "This variable contains the text that is displayed in the
                 device's frontpanel display."
        ::= { frontpanel 1 }

frontpanelKeyboardAccess OBJECT-TYPE
        SYNTAX  INTEGER
                {
                        enabled(1),
                        status-only(2),
                        disabled(3)
                }
        ACCESS  read-write
        STATUS  optional
        DESCRIPTION
                "This variable controls whether the keyboard on the device's
                 frontpanel will work. The value enabled(1) means all actions
                 are permitted, status-only(2) means that all keyboard
                 actions that change the device's configuration is denied,
                 while disabled(3) means that all access is denied."
        ::= { frontpanel 2 }

frontpanelErrorcode OBJECT-TYPE
        SYNTAX  INTEGER
        ACCESS  read-write
        STATUS  optional
        DESCRIPTION
                "This variable contains the errorcode that is displayed in the
                 device's frontpanel display."
        ::= { frontpanel 3 }

frontpanelErrorLED OBJECT-TYPE
        SYNTAX  INTEGER
                {
                        led-unknown(1),
                        led-off(2),
                        led-on-steady(3),
                        led-flashing(4)
                }
        ACCESS  read-write
        STATUS  optional
        DESCRIPTION
                "This variable contains the state of the error LED on this
                 device's frontpanel."
        ::= { frontpanel 4 }

frontpanelDefaultDisplay OBJECT-TYPE
        SYNTAX  INTEGER
        ACCESS  read-write
        STATUS  optional
        DESCRIPTION
                "The display of the device is capable of showing different
                 status displays with different counters.
                 This variable determines which counter-display should be
                 shown, when no other error-messages need to be displayed.
                 The device may choose to ignore this value. The value
                 0 (zero) means default display of the device's choice."
        ::= { frontpanel 5 }

frontpanelKeyPress OBJECT-TYPE
        SYNTAX  INTEGER
                {
			key-enter(400),
                        key-up(401),
                        key-down(402),
                        key-left(403),
                        key-right(404)
                }
        ACCESS  write-only
        STATUS  optional
        DESCRIPTION
                "Some devices have a front-panel keyboard.
		 This variable may be used to remotely operate the
		 front-panel keyboard."
        ::= { frontpanel 6 }

frontpanelDisplayLogTable OBJECT-TYPE
        SYNTAX  SEQUENCE OF FrontpanelDisplayLogEntry
        ACCESS  not-accessible
        STATUS  optional
        DESCRIPTION
                "This table is used to store history logs in the form of
                 a number of display texts, including a corresponding
                 time stamp."
        ::= { frontpanel 7 }

frontpanelDisplayLogEntry OBJECT-TYPE
        SYNTAX  FrontpanelDisplayLogEntry
        ACCESS  not-accessible
        STATUS  optional
        DESCRIPTION
                "This is an entry in the frontpanelDisplayLogTable."
        INDEX   { frontpanelDisplayLogIndex }
        ::= { frontpanelDisplayLogTable 1 }

FrontpanelDisplayLogEntry ::=
        SEQUENCE {
            frontpanelDisplayLogIndex
                INTEGER,
            frontpanelDisplayLogTimeStamp
                TimeTicks,
            frontpanelDisplayLogDisplayText
                DisplayString
        }

frontpanelDisplayLogIndex OBJECT-TYPE
        SYNTAX  INTEGER
        ACCESS  read-only
        STATUS  optional
        DESCRIPTION
                "The entry number in the frontpanelDisplayLogTable. In
                order to ensure that an SNMP GET-NEXT operation
                produces consistent results, it is recommended that
                entries be added to this table starting with a high
                index value; subsequent addtions to the table should
                happen with decreasing index values."
        ::= { frontpanelDisplayLogEntry 1 }

frontpanelDisplayLogTimeStamp OBJECT-TYPE
        SYNTAX  TimeTicks
        ACCESS  read-only
        STATUS  optional
        DESCRIPTION
                "The time at which the entry was made."
        ::= { frontpanelDisplayLogEntry 2 }

frontpanelDisplayLogDisplayText OBJECT-TYPE
        SYNTAX  DisplayString
        ACCESS  read-only
        STATUS  optional
        DESCRIPTION
                "The text string from the front panel display."
        ::= { frontpanelDisplayLogEntry 3 }



--- Products section
tokenRingBridgeSR               OBJECT IDENTIFIER ::= { products 1 }
                                -- OC-3401

controlledAccessUnit            OBJECT IDENTIFIER ::= { products 2 }
                                -- OC-3610

controlledAttachmentModule      OBJECT IDENTIFIER ::= { products 3 }
                                -- OC-3671

etherNetAttachmentHUB           OBJECT IDENTIFIER ::= { products 4 }
                                -- OC-2611

tokenRingRemoteBridgeAndCAM     OBJECT IDENTIFIER ::= { products 5 }
                                -- OC-3445

tokenRingMultiPortBridge        OBJECT IDENTIFIER ::= { products 6 }
                                -- OC-3450

desktopManagementAgent          OBJECT IDENTIFIER ::= { products 7 }
                                -- OC-5010

localPCBridge                   OBJECT IDENTIFIER ::= { products 8 }
                                -- OC-3150, OC-3152

remoteDOSPCBridge               OBJECT IDENTIFIER ::= { products 9 }
                                -- OC-3146, OC-3151

remoteOS2PCBridge               OBJECT IDENTIFIER ::= { products 10 }
                                -- OC-3146, OC-3151

tokenRingSwitchOc8100           OBJECT IDENTIFIER ::= { products 11 }
                                -- OC-8100

crossfireAtmSwitch              OBJECT IDENTIFIER ::= { products 12 }
                                -- OC-9100

ethernetSwitchOc8200            OBJECT IDENTIFIER ::= { products 13 }
                                -- OC-8200

tokenRingSwitchOc8600           OBJECT IDENTIFIER ::= { products 14 }
                                -- OC-8600

tokenRingSwitchOc8007           OBJECT IDENTIFIER ::= { products 15 }
                                -- OC-8007 (XLTRS)

crossfireAtmSwitchOc8008        OBJECT IDENTIFIER ::= { products 16 }
                                -- OC-8008 (XLX)

fastEthernetSwitchOc8400        OBJECT IDENTIFIER ::= { products 17 }
                                -- OC-8400 8-port Fast Ethernet Switch

fastEthernetSwitchOc8420        OBJECT IDENTIFIER ::= { products 18 }
                                -- OC-8420 24-port Fast Ethernet Switch

lanscoutOc5020                  OBJECT IDENTIFIER ::= { products 19 }
                                -- OC-5020 LANscout Desktop Agent

crossfireAtmSwitchCf9200        OBJECT IDENTIFIER ::= { products 20 }
                                -- CF9200

crossfireRouterCf7100           OBJECT IDENTIFIER ::= { products 21 }
                                -- CF7100 branch office router

tokenRingSwitchCf8500           OBJECT IDENTIFIER ::= { products 22 }
                                -- CF8500 HSTR switch

ethernetSwitchCf8711            OBJECT IDENTIFIER ::= { products 23 }
                                -- CF8711 fast Ethernet switch

ethernetSwitchCf8720            OBJECT IDENTIFIER ::= { products 24 }
                                -- CF8720 fast Ethernet switch

ethernetSwitchCf8810            OBJECT IDENTIFIER ::= { products 25 }
                                -- CF8810 gigabit Ethernet switch

--- Errorlog section

errorlogTable OBJECT-TYPE
        SYNTAX  SEQUENCE OF ErrorlogEntry
        ACCESS  not-accessible
        STATUS  optional
        DESCRIPTION
                "This table contains a number of error log entries
                 from the managed device."
        ::= { errorlog 1 }

errorlogEntry OBJECT-TYPE
        SYNTAX  ErrorlogEntry
        ACCESS  not-accessible
        STATUS  optional
DESCRIPTION ""
        INDEX   { errorlogNumber }
        ::= { errorlogTable 1 }

ErrorlogEntry ::= SEQUENCE {
        errorlogNumber
                INTEGER,
        errorlogTimeStamp
                TimeTicks,
        errorlogErrorDescription
                DisplayString,
        errorlogErrorData
                OCTET STRING,
        errorlogTime
                INTEGER,
        errorlogTimeRemoved
                INTEGER,
        errorlogCategory
                INTEGER,
        errorlogSeverity
                INTEGER,
        errorlogPhysicalIf
                INTEGER,
        errorlogVirtualIf
                INTEGER
}

errorlogNumber OBJECT-TYPE
        SYNTAX  INTEGER
        ACCESS  read-only
        STATUS  optional
        DESCRIPTION
                "The number of the entry."
        ::= { errorlogEntry 1 }

errorlogTimeStamp OBJECT-TYPE
        SYNTAX  TimeTicks
        ACCESS  read-only
        STATUS  optional
        DESCRIPTION
                "This variable describes the device's perception of the
                 time when the error occurred."
        ::= { errorlogEntry 2 }

errorlogErrorDescription OBJECT-TYPE
        SYNTAX  DisplayString
        ACCESS  read-only
        STATUS  optional
        DESCRIPTION
                "This variable contains a description of the error
                 that occurred in this device."
        ::= { errorlogEntry 3 }

errorlogErrorData OBJECT-TYPE
        SYNTAX  OCTET STRING
        ACCESS  read-only
        STATUS  optional
        DESCRIPTION
                "This variable contains additional information about
                 the error."
        ::= { errorlogEntry 4 }

errorlogTime OBJECT-TYPE
        SYNTAX  INTEGER
        ACCESS  read-only
        STATUS  optional
        DESCRIPTION
                "This variable describes the device's conception of the
		 calendar time when the error occurred. This is measured in
		 seconds since 00:00:00 on 1 January 1970 (i.e. UNIX
		 standard time)."
	::= { errorlogEntry 5 }

errorlogTimeRemoved OBJECT-TYPE
       SYNTAX INTEGER
       ACCESS read-only
       STATUS optional
       DESCRIPTION
             "This variable describes the device's conception of the
             calendar time when the error condition disappeared.
             This is measured in seconds since 00:00:00 on 1 January
             1970 (i.e. UNIX standard time). A value of 0 (zero)
             indicates that the error condition has not disappeared."
       ::= { errorlogEntry 6 }

errorlogCategory OBJECT-TYPE
       SYNTAX INTEGER {
                bootload(1),
                startup(2),
                operational(3)
	     }
       ACCESS read-only
       STATUS optional
       DESCRIPTION
             "This variable contains the category of the error log"
       ::= { errorlogEntry 7 }

errorlogSeverity OBJECT-TYPE
       SYNTAX INTEGER {
                information(1),
                notice(2),
                warning(3),
                error(4),
                critical(5),
                alert(6),
                panic(7),
                debug(8),
                fatal(9)
           }
       ACCESS read-only
       STATUS optional
       DESCRIPTION
             "This variable contains the severity of the error log"
	::= { errorlogEntry 8 }

errorlogPhysicalIf OBJECT-TYPE
       SYNTAX INTEGER
       ACCESS read-only
       STATUS optional
       DESCRIPTION
             "This variable contains the physical interface number of
              the error log, if the log is related to a certain physical
              interface. Otherwise it will have the value 0"
       ::= { errorlogEntry 9 }

errorlogVirtualIf OBJECT-TYPE
       SYNTAX INTEGER
       ACCESS read-only
       STATUS optional
       DESCRIPTION
             "This variable contains the virtual interface number of
              the error log, if the log is related to a certain virtual
              interface. Otherwise it will have the value 0"
       ::= { errorlogEntry 10 }


errorlogTraceControl OBJECT-TYPE
        SYNTAX  INTEGER {
			log-empty(1),
			log-present(2),
			save-log(3),
			erase-log(4)
		}
        ACCESS  read-write
        STATUS  optional
        DESCRIPTION
                "The current state of device's trace log area."
        ::= { errorlog 2 }

errorlogTraceMaskCurrent OBJECT-TYPE
        SYNTAX  OCTET STRING
        ACCESS  read-write
        STATUS  optional
        DESCRIPTION
                "The current trace log mask. The interpretation of
		this variable is device specific."
        ::= { errorlog 3 }

errorlogTraceMaskInitial OBJECT-TYPE
        SYNTAX  OCTET STRING
        ACCESS  read-write
        STATUS  optional
        DESCRIPTION
                "The current trace log mask. The interpretation of
		this variable is device specific."
        ::= { errorlog 4 }

errorlogTraceMaskOperational OBJECT-TYPE
        SYNTAX  OCTET STRING
        ACCESS  read-write
        STATUS  optional
        DESCRIPTION
                "The current trace log mask. The interpretation of
		this variable is device specific."
        ::= { errorlog 5 }

errorlogTraceLogSize OBJECT-TYPE
        SYNTAX  INTEGER
        ACCESS  read-write
        STATUS  optional
        DESCRIPTION
                "The size of the trace log area (in bytes)."
        ::= { errorlog 6 }

errorlogTraceSliceTable OBJECT-TYPE
        SYNTAX  SEQUENCE OF ErrorlogTraceSliceTableEntry
        ACCESS  not-accessible
        STATUS  optional
        DESCRIPTION
                "This table provides access to the device's trace log."
        ::= { errorlog 7 }

errorlogTraceSliceTableEntry OBJECT-TYPE
        SYNTAX  ErrorlogTraceSliceTableEntry
        ACCESS  not-accessible
        STATUS  optional
DESCRIPTION ""
        INDEX   { errorlogTraceSliceNumber, errorlogTraceSliceSize }
        ::= { errorlogTraceSliceTable 1 }

ErrorlogTraceSliceTableEntry ::= SEQUENCE {
        errorlogTraceSliceNumber
                INTEGER,
        errorlogTraceSliceSize
                INTEGER,
        errorlogTraceSliceData
                OCTET STRING
}

errorlogTraceSliceNumber OBJECT-TYPE
        SYNTAX  INTEGER
        ACCESS  read-only
        STATUS  optional
        DESCRIPTION
                "The number of this trace log area slice (each of
		size `errorlogTraceSliceSize')."
        ::= { errorlogTraceSliceTableEntry 1 }

errorlogTraceSliceSize OBJECT-TYPE
        SYNTAX  INTEGER (1 .. 2048)
        ACCESS  read-only
        STATUS  optional
        DESCRIPTION
                "The size of this slice of the trace log area."
        ::= { errorlogTraceSliceTableEntry 2 }

errorlogTraceSliceData OBJECT-TYPE
        SYNTAX  OCTET STRING
        ACCESS  read-only
        STATUS  optional
        DESCRIPTION
                "The data in this slice of the trace log area."
        ::= { errorlogTraceSliceTableEntry 3 }

errorlogStoredSeverityLevel OBJECT-TYPE
       SYNTAX INTEGER
       ACCESS read-write
       STATUS optional
       DESCRIPTION
             "This variable contains the severity level determining
              which error logs will be written to permanent storage.
              Any error log with severity higher than or equal to this
              severity level will be stored for retrieval, even after a reset"
       ::= { errorlog 8 }


--- Token Ring Config section

trconfigTable OBJECT-TYPE
        SYNTAX  SEQUENCE OF TrconfigEntry
        ACCESS  not-accessible
        STATUS  optional
        DESCRIPTION
                "This table contains Token Ring configuration information
                for each interface."
        ::= { trconfig 1 }

trconfigEntry OBJECT-TYPE
        SYNTAX  TrconfigEntry
        ACCESS  not-accessible
        STATUS  optional
DESCRIPTION ""
        INDEX   { trconfigIfNumber }
        ::= { trconfigTable 1 }

TrconfigEntry ::= SEQUENCE {
        trconfigIfNumber
                INTEGER,
        trconfigBurntInAddress
                MacAddress,
        trconfigLocalAddress
                MacAddress,
        trconfigEarlyTokenRelease
                INTEGER
}

trconfigIfNumber OBJECT-TYPE
        SYNTAX  INTEGER
        ACCESS  read-only
        STATUS  optional
        DESCRIPTION
                "This number corresponds to the interface number, ifIndex,
                in ifTable from MIB-II."
        ::= { trconfigEntry 1 }

trconfigBurntInAddress OBJECT-TYPE
        SYNTAX  MacAddress
        ACCESS  read-only
        STATUS  optional
        DESCRIPTION
                "The burnt-in MAC address for this interface."
        ::= { trconfigEntry 2 }

trconfigLocalAddress OBJECT-TYPE
        SYNTAX  MacAddress
        ACCESS  read-write
        STATUS  optional
        DESCRIPTION
                "The locally administered MAC address for this interface.
                If locally address MAC addresses are not used, this entry
                is all zeroes."
        ::= { trconfigEntry 3 }

trconfigEarlyTokenRelease OBJECT-TYPE
        SYNTAX  INTEGER
                {
                        enabled(1),
                        disabled(2)
                }
        ACCESS  read-write
        STATUS  optional
        DESCRIPTION
                "Indicates if early token release is used on the interface."
        ::= { trconfigEntry 4 }


-- Trap section

obmCallback TRAP-TYPE
        ENTERPRISE  olicom
        VARIABLES   { obmCallbackPhoneNumber }
        DESCRIPTION
                "This trap is sent when the device tries to
                place a OBM callback phonecall to phone number
                obmCallbackPhoneNumber.  Even though the call might be
                repeated several times before a connection is
                established, only one trap is sent."

--Novell NMS trap annotation
--#TYPE      "OBM call-back trap received"
--#SUMMARY   "Call-back phone no.: %s"
--#ARGUMENTS {0}
--#SEVERITY  INFORMATIONAL
--#HELP      "OC-2611.HLP"
--#HELPTAG   100
--#STATE     OPERATIONAL

        ::= 1

obmCallout TRAP-TYPE
        ENTERPRISE  olicom
        VARIABLES   { obmCalloutPhoneNumber, obmCalloutTriggerEvent }
        DESCRIPTION
                "This trap is sent when the device tries to
                place a OBM callout phonecall to phone number
                obmCalloutPhoneNumber because it was triggered by the
                event(s) obmCalloutTriggerEvent.  Even though the call
                might be repeated several times before a connection is
                established, only one trap is sent."


--Novell NMS trap annotation
--#TYPE      "OBM call-out trap received"
--#SUMMARY   "Call-out phone no.: %s. Trigger event: %xh"
--#ARGUMENTS {0, 1}
--#SEVERITY  MINOR
--#HELP      "OC-2611.HLP"
--#HELPTAG   100
--#STATE     OPERATIONAL

        ::= 2

        END
