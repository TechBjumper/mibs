DTABLE-MIB2 DEFINITIONS ::= BEGIN

IMPORTS
    enterprises, MODULE-IDENTITY, IpAddress, Integer32
        FROM SNMPv2-SMI;

dtable MODULE-IDENTITY
    LAST-UPDATED "0609201255Z"
    ORGANIZATION "Sun Microsystems Inc."
    CONTACT-INFO
        "        Sun Microsystems Inc.
       Customer Support
            Postal: 901 San Antonio Road 
       Palo Alto, CA-94303-4900
    USA
                         Tel: 650-960-1300
                E-mail: service@sun.com"
    DESCRIPTION
        ""
    ::= { modules 15 }
modules	OBJECT IDENTIFIER ::= { agent 2 }

agent	OBJECT IDENTIFIER ::= { sunsymon 2 }

sunsymon	OBJECT IDENTIFIER ::= { prod 12 }

prod	OBJECT IDENTIFIER ::= { sun 2 }

sun	OBJECT IDENTIFIER ::= { enterprises 42 }


discovery	OBJECT IDENTIFIER ::= { dtable 1 }

DisplayString ::= TEXTUAL-CONVENTION
    DISPLAY-HINT "255a"
    STATUS       current
    DESCRIPTION
            "Represents textual information taken from the NVT ASCII
            character set, as defined in pages 4, 10-11 of RFC 854.

            To summarize RFC 854, the NVT ASCII repertoire specifies:

              - the use of character codes 0-127 (decimal)

              - the graphics characters (32-126) are interpreted as
                US ASCII

              - NUL, LF, CR, BEL, BS, HT, VT and FF have the special
                meanings specified in RFC 854

              - the other 25 codes have no standard interpretation

              - the sequence 'CR LF' means newline

              - the sequence 'CR NUL' means carriage-return

              - an 'LF' not preceded by a 'CR' means moving to the
                same column on the next line.

              - the sequence 'CR x' for any x other than LF or NUL is
                illegal.  (Note that this also means that a string may
                end with either 'CR LF' or 'CR NUL', but not with CR.)

            Any object defined using this syntax may not exceed 255
            characters in length."
    SYNTAX       OCTET STRING (SIZE (0..255))

magicnumber OBJECT-TYPE
    SYNTAX      DisplayString
    MAX-ACCESS  read-only
    STATUS      current
    DESCRIPTION
                "Character string value"
    ::= { discovery 1 }

discoveryTable OBJECT-TYPE
    SYNTAX      SEQUENCE OF DiscoveryTableEntry
    MAX-ACCESS  not-accessible
    STATUS      current
    DESCRIPTION
                "MIB tree branch"
    ::= { discovery 2 }

discoveryTableEntry OBJECT-TYPE
    SYNTAX      DiscoveryTableEntry
    MAX-ACCESS  not-accessible
    STATUS      current
    DESCRIPTION
                "MIB tree branch"
    INDEX  { entry }
    ::= { discoveryTable 1 }

DiscoveryTableEntry ::=
    SEQUENCE {
        entry
            DisplayString,
        discoveryipaddr
            IpAddress,
        discoveryport
            Integer32,
        discoveryOID
            OBJECT IDENTIFIER,
        discoverymethodid
            DisplayString,
        discoveryversion
            Integer32,
        discoveryobjectfamily
            DisplayString,
        discoveryobjectname
            DisplayString
    }

entry OBJECT-TYPE
    SYNTAX      DisplayString
    MAX-ACCESS  read-only
    STATUS      current
    DESCRIPTION
                "Character string value"
    ::= { discoveryTableEntry 1 }

discoveryipaddr OBJECT-TYPE
    SYNTAX      IpAddress
    MAX-ACCESS  read-only
    STATUS      current
    DESCRIPTION
                "IP Address value"
    ::= { discoveryTableEntry 2 }

discoveryport OBJECT-TYPE
    SYNTAX      Integer32 (-2147483648..2147483647)
    MAX-ACCESS  read-only
    STATUS      current
    DESCRIPTION
                "Integer value"
    ::= { discoveryTableEntry 3 }

discoveryOID OBJECT-TYPE
    SYNTAX      OBJECT IDENTIFIER
    MAX-ACCESS  read-only
    STATUS      current
    DESCRIPTION
                "ASN.1 object identifier"
    ::= { discoveryTableEntry 4 }

discoverymethodid OBJECT-TYPE
    SYNTAX      DisplayString
    MAX-ACCESS  read-only
    STATUS      current
    DESCRIPTION
                "Character string value"
    ::= { discoveryTableEntry 5 }

discoveryversion OBJECT-TYPE
    SYNTAX      Integer32 (-2147483648..2147483647)
    MAX-ACCESS  read-only
    STATUS      current
    DESCRIPTION
                "Integer value"
    ::= { discoveryTableEntry 6 }

discoveryobjectfamily OBJECT-TYPE
    SYNTAX      DisplayString
    MAX-ACCESS  read-only
    STATUS      current
    DESCRIPTION
                "Character string value"
    ::= { discoveryTableEntry 7 }

discoveryobjectname OBJECT-TYPE
    SYNTAX      DisplayString
    MAX-ACCESS  read-only
    STATUS      current
    DESCRIPTION
                "Character string value"
    ::= { discoveryTableEntry 8 }
END
