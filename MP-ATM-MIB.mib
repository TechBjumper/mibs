-- ************************************************************************************************
-- FileName    :mpAtmCallCtl.my
-- Description :MultiMedia Platform private MIB
-- Revision History     :
--   Ver.     mark   date     
--   04.00    @011  11/15/2000
--
-- ************************************************************************************************
--


MP-ATM-MIB DEFINITIONS ::= BEGIN

   IMPORTS
      mgmt, NetworkAddress, IpAddress, Counter, Gauge, TimeTicks
      FROM RFC1155-SMI

      ifIndex
      FROM RFC1213-MIB

      OBJECT-TYPE
      FROM RFC-1212

--      DisplayString
--      FROM RFC1155-SMI

      TRAP-TYPE
      FROM RFC-1215
		
		AtmTrafficDescrParamIndex FROM ATM-MIB;

   RowStatus   ::= INTEGER { active(1), notInService(2), notReady(3),
                       createAndGo(4), createAndWait(5), destroy(6) }

   NetPrefix ::= OCTET STRING (SIZE (13))

   DisplayString ::= OCTET STRING

-- The following definition was gotten from rfc1514
   DateAndTime ::= OCTET STRING (SIZE (8 | 11))
-- in OpenView , DateAndTime must be comment   98/12/15 YI
   --        A date-time specification for the local time of day.
   --        This data type is intended to provide a consistent
   --        method of reporting date information.
   --
   --            field  octets  contents                  range
   --            _____  ______  ________                  _____
   --              1      1-2   year                      0..65536
   --                           (in network byte order)
   --              2       3    month                     1..12
   --              3       4    day                       1..31
   --              4       5    hour                      0..23
   --              5       6    minutes                   0..59
   --              6       7    seconds                   0..60
   --                           (use 60 for leap-second)
   --              7       8    deci-seconds              0..9
   --              8       9    direction from UTC        "+" / "-"
   --                           (in ascii notation)
   --              9      10    hours from UTC            0..11
   --             10      11    minutes from UTC          0..59
   --
   --            Note that if only local time is known, then
   --            timezone information (fields 8-10) is not present.

-- The following definition was cadged from the Bridge MIB
      MacAddress ::= OCTET STRING (SIZE (6))
                                                -- a 6 octet address
                                                -- in the
                                                -- "canonical"
                                                -- order
      -- defined by IEEE 802.1a, i.e., as if it were transmitted
      -- least significant bit first, even though 802.5 (in
      -- contrast to other n802.x protocols) requires MAC
      -- addresses to be transmitted most significant bit first.
      --
      -- 16-bit addresses, if needed, are represented by setting
      -- their upper 4 octets to all 0's, i.e., AAFF would be
      -- represented as 00000000AAFF.

-- The following definition is privately defined for Sanfran Private MIB
      PhysAddress ::= OCTET STRING (SIZE (6))


--   nec               OBJECT IDENTIFIER ::= { enterprises 119}

--   necProduct        OBJECT IDENTIFIER ::= { nec 1 }
--   nec-mib           OBJECT IDENTIFIER ::= { nec 2 }
--   necExperimental   OBJECT IDENTIFIER ::= { nec 3 }

--   datax             OBJECT IDENTIFIER ::= { necProduct 3 }
--   ether-sw          OBJECT IDENTIFIER ::= { datax 10 }
--   sf                OBJECT IDENTIFIER ::= { ether-sw 3 }

--   necCommon         OBJECT IDENTIFIER ::= { nec-mib 1 }
--   necFunction       OBJECT IDENTIFIER ::= { nec-mib 2 }
--   necProductDepend  OBJECT IDENTIFIER ::= { nec-mib 3 }

--   datax-mib         OBJECT IDENTIFIER ::= { necProductDepend 3 }
--   ether-sw-mib      OBJECT IDENTIFIER ::= { datax-mib 10 }
--   ether-sw          OBJECT IDENTIFIER ::= { datax 10 }




  org         OBJECT IDENTIFIER     ::= { iso 3 }
  dod         OBJECT IDENTIFIER     ::= { org 6 }
  internet    OBJECT IDENTIFIER     ::= { dod 1 }
  private     OBJECT IDENTIFIER     ::= { internet 4 }
  enterprises OBJECT IDENTIFIER     ::= { private 1 }
  nec               OBJECT IDENTIFIER ::= { enterprises 119}


-- 98/12/15 YI mmpf => mmpf-mib CHG start
-- sysObjectID
   necProduct        OBJECT IDENTIFIER ::= { nec 1 }
   datax             OBJECT IDENTIFIER ::= { necProduct 3 }
   mmpf              OBJECT IDENTIFIER ::= { datax 13 }
   mmn9110           OBJECT IDENTIFIER ::= { mmpf 1 }
   mmn9120           OBJECT IDENTIFIER ::= { mmpf 2 }
-- [sysObjectID]  MM-Node9110/MM-Node9120
--  mmn9110           OBJECT IDENTIFIER ::= { nec necProduct(1) datax(3) mmpf(13) mmn9110(1) }
--  mmn9120           OBJECT IDENTIFIER ::= { nec necProduct(1) datax(3) mmpf(13) mmn9110(2) }


   nec-mib           OBJECT IDENTIFIER ::= { nec 2 }
   necProductDepend  OBJECT IDENTIFIER ::= { nec-mib 3 }
   datax-mib         OBJECT IDENTIFIER ::= { necProductDepend 3 }
   mmpf-mib          OBJECT IDENTIFIER ::= { datax-mib 13 }

   mpSystem                 OBJECT IDENTIFIER ::= { mmpf-mib 1 }
   mpIfCard                 OBJECT IDENTIFIER ::= { mmpf-mib 2 }
   mpEtherPort              OBJECT IDENTIFIER ::= { mmpf-mib 3 }
   mpVlan                   OBJECT IDENTIFIER ::= { mmpf-mib 4 }
   mpBridge                 OBJECT IDENTIFIER ::= { mmpf-mib 5 }
   mpDbAccess               OBJECT IDENTIFIER ::= { mmpf-mib 6 }
   mpEventLog               OBJECT IDENTIFIER ::= { mmpf-mib 7 }
   mpUiSession              OBJECT IDENTIFIER ::= { mmpf-mib 8 }
   mpFtp                    OBJECT IDENTIFIER ::= { mmpf-mib 9 }
   mpDhcp                   OBJECT IDENTIFIER ::= { mmpf-mib 10 }
   mpIp                     OBJECT IDENTIFIER ::= { mmpf-mib 11 }
   mpRip                    OBJECT IDENTIFIER ::= { mmpf-mib 12 }
   mpSnmp                   OBJECT IDENTIFIER ::= { mmpf-mib 13 }
   mpStats                  OBJECT IDENTIFIER ::= { mmpf-mib 14 }
   mpCli                    OBJECT IDENTIFIER ::= { mmpf-mib 15 }
   mpAtm                    OBJECT IDENTIFIER ::= { mmpf-mib 16 }
   mpLis                    OBJECT IDENTIFIER ::= { mmpf-mib 17 }
   mpDns                    OBJECT IDENTIFIER ::= { mmpf-mib 18 }
   mpLec                    OBJECT IDENTIFIER ::= { mmpf-mib 19 }
   mpMpc                    OBJECT IDENTIFIER ::= { mmpf-mib 20 }
   mpStp                    OBJECT IDENTIFIER ::= { mmpf-mib 21 }
   mpLlc                    OBJECT IDENTIFIER ::= { mmpf-mib 22 }
   mpOspf                   OBJECT IDENTIFIER ::= { mmpf-mib 23 }

   mpObsCtl                 OBJECT IDENTIFIER ::= { mmpf-mib 101 }
   mpCardInfo               OBJECT IDENTIFIER ::= { mmpf-mib 102 }
   mpInterface              OBJECT IDENTIFIER ::= { mmpf-mib 103 }
   mpPvoice                 OBJECT IDENTIFIER ::= { mmpf-mib 104 }
-- 98/12/15 YI mmpf => mmpf-mib CHG end

   mpAtmCallCtl             OBJECT IDENTIFIER ::= { mmpf-mib 110 }
   mpCes                    OBJECT IDENTIFIER ::= { mmpf-mib 111 }
   mpIpsw                   OBJECT IDENTIFIER ::= { mmpf-mib 112 }
   mpInsCtl                 OBJECT IDENTIFIER ::= { mmpf-mib 113 }
   mpFfr                    OBJECT IDENTIFIER ::= { mmpf-mib 114 }



AtmAddr ::= OCTET STRING (SIZE(0|8|20))


MpAtmCCCladType ::= INTEGER{ com(1),
                             mux(2),
                             atm-uni(3),
                             atm-trunk(4),
                             atm-uni-vmc(5),
                             lvc(6),
                             ffr(7),
                             odt(8),
                             ces(9),
                             ins(10),
                             sel(11),
                             eth(12),
                             atm-trunk-cdm(13)
                           }



--
--

        mpAtmCCBaseGroup      OBJECT IDENTIFIER ::= { mpAtmCallCtl 1 }

        mpAtmCCNextTrafficDescrIndex  OBJECT-TYPE
                SYNTAX  AtmTrafficDescrParamIndex
                ACCESS  read-only
                STATUS  mandatory
                DESCRIPTION
                     "A unique value to identify ATM Traffic Descriptor."
                ::= { mpAtmCCBaseGroup 1 }

        mpAtmCCNextNodeVci    OBJECT-TYPE
                SYNTAX  INTEGER
                ACCESS  read-only
                STATUS  mandatory
                DESCRIPTION
                     "A unique value to identify Node VCI."
                ::= { mpAtmCCBaseGroup 2 }


--
--

        mpAtmCCStaticPVPC     OBJECT IDENTIFIER ::= { mpAtmCallCtl 2 }

--
--

        mpAtmCCStaticPvpTable OBJECT-TYPE
                SYNTAX  SEQUENCE OF MpAtmCCStaticPvpEntry
                ACCESS  not-accessible
                STATUS  mandatory
                DESCRIPTION
                        "Static-PVP Table"
                ::= { mpAtmCCStaticPVPC 1 }

        mpAtmCCStaticPvpEntry OBJECT-TYPE
                SYNTAX  MpAtmCCStaticPvpEntry
                ACCESS  not-accessible
                STATUS  mandatory
                DESCRIPTION
                        "Static-PVP Entry"
                INDEX { mpAtmCCStaticPvpIndex,
                        mpAtmCCStaticPvpLowIfIndex,
                        mpAtmCCStaticPvpLowVpi,
                        mpAtmCCStaticPvpHighIfIndex,
                        mpAtmCCStaticPvpHighVpi }
                ::= { mpAtmCCStaticPvpTable 1 }

        MpAtmCCStaticPvpEntry ::=
                SEQUENCE {
                        mpAtmCCStaticPvpIndex         INTEGER,
                        mpAtmCCStaticPvpLowIfIndex    INTEGER,
                        mpAtmCCStaticPvpLowVpi        INTEGER,
                        mpAtmCCStaticPvpHighIfIndex   INTEGER,
                        mpAtmCCStaticPvpHighVpi       INTEGER,
                        mpAtmCCStaticPvpLowReceiveTrafficDescrIndex
                                                AtmTrafficDescrParamIndex,
                        mpAtmCCStaticPvpLowTransmitTrafficDescrIndex
                                                AtmTrafficDescrParamIndex,
                        mpAtmCCStaticPvpHighReceiveTrafficDescrIndex
                                                AtmTrafficDescrParamIndex,
                        mpAtmCCStaticPvpHighTransmitTrafficDescrIndex
                                                AtmTrafficDescrParamIndex,
                        mpAtmCCStaticPvpPriority      INTEGER,
                        mpAtmCCStaticPvpLowCladType   MpAtmCCCladType,
                        mpAtmCCStaticPvpHighCladType  MpAtmCCCladType,
                        mpAtmCCStaticPvpAdminStatus   INTEGER,
                        mpAtmCCStaticPvpOperStatus    INTEGER,
                        mpAtmCCStaticPvpPvpId         INTEGER,
                        mpAtmCCStaticPvpSeqNo         INTEGER,
                        mpAtmCCStaticPvpPgcRequest    INTEGER,    -- @007
                        mpAtmCCStaticPvpCfgStatus     INTEGER,
                        mpAtmCCStaticPvpErrInfo       INTEGER
                        }

        mpAtmCCStaticPvpIndex OBJECT-TYPE
                SYNTAX  INTEGER(1..2147483647)                    -- @001
--              SYNTAX  INTEGER(1)
                ACCESS  not-accessible
                STATUS  mandatory
                DESCRIPTION
                        "A unique value to identify this Static-PVP.
                        The value is used only 1 (p2p)."
                ::= { mpAtmCCStaticPvpEntry 1 }

        mpAtmCCStaticPvpLowIfIndex    OBJECT-TYPE
                SYNTAX  INTEGER
                ACCESS  not-accessible
                STATUS  mandatory
                DESCRIPTION
                     "The value of this object is equal to MIB II's
                      ifIndex value of the ATM interface port for this
                      Static-PVP."
                ::= { mpAtmCCStaticPvpEntry 2 }

        mpAtmCCStaticPvpLowVpi        OBJECT-TYPE
                SYNTAX  INTEGER(0..4095)
                ACCESS  not-accessible
                STATUS  mandatory
                DESCRIPTION
                     "The value of this object is equal to the VPI
                      value at the ATM interface associated with
                      the Static-PVP that is identified by
                      mpAtmCCStaticPvcLowIfIndex.
                      The VPI value cannot exceed the number
                      supported by the atmInterfaceMaxVpiBits
                      at the low ATM interface port."
                ::= { mpAtmCCStaticPvpEntry 3 }

        mpAtmCCStaticPvpHighIfIndex   OBJECT-TYPE
                SYNTAX  INTEGER
                ACCESS  not-accessible
                STATUS  mandatory
                DESCRIPTION
                     "The value of this object is equal to MIB II's
                      ifIndex value for the ATM interface port for
                      this static-PVP."
                ::= { mpAtmCCStaticPvpEntry 4 }

        mpAtmCCStaticPvpHighVpi       OBJECT-TYPE
                SYNTAX  INTEGER(0..4095)
                ACCESS  not-accessible
                STATUS  mandatory
                DESCRIPTION
                     "The value of this object is equal to the VPI
                      value at the ATM interface
                      associated with the Static-PVP that is
                      identified by mpAtmCCStaticPvcHighIfIndex.
                      The VPI value cannot exceed
                      the number supported by the atmInterfaceMaxVpiBits
                      at the high ATM interface port."
                ::= { mpAtmCCStaticPvpEntry 5 }

        mpAtmCCStaticPvpLowReceiveTrafficDescrIndex   OBJECT-TYPE
                SYNTAX  AtmTrafficDescrParamIndex
                ACCESS  read-write
                STATUS  mandatory
                DESCRIPTION
                     "The value of this object identifies
                      in the ATM Traffic Descriptor Table which
                      applies to the receive direction of this Static-PVP."
                ::= { mpAtmCCStaticPvpEntry 6 }

        mpAtmCCStaticPvpLowTransmitTrafficDescrIndex  OBJECT-TYPE
                SYNTAX  AtmTrafficDescrParamIndex
                ACCESS  read-write
                STATUS  mandatory
                DESCRIPTION
                     "The value of this object identifies
                      in the ATM Traffic Descriptor Table which
                      applies to the transmit direction of this Static-PVP."
                ::= { mpAtmCCStaticPvpEntry 7 }

        mpAtmCCStaticPvpHighReceiveTrafficDescrIndex  OBJECT-TYPE
                SYNTAX  AtmTrafficDescrParamIndex
                ACCESS  read-write
                STATUS  mandatory
                DESCRIPTION
                     "The value of this object identifies
                      in the ATM Traffic Descriptor Table which
                      applies to the receive direction of this Static-PVP."
                ::= { mpAtmCCStaticPvpEntry 8 }

        mpAtmCCStaticPvpHighTransmitTrafficDescrIndex OBJECT-TYPE
                SYNTAX  AtmTrafficDescrParamIndex
                ACCESS  read-write
                STATUS  mandatory
                DESCRIPTION
                     "The value of this object identifies
                      in the ATM Traffic Descriptor Table which
                      applies to the transmit direction of this Static-PVP."
                ::= { mpAtmCCStaticPvpEntry 9 }

        mpAtmCCStaticPvpPriority      OBJECT-TYPE
                SYNTAX  INTEGER(1..3)                               -- @001
                ACCESS  read-write
                STATUS  mandatory
                DESCRIPTION
                     "Connection priority"
                DEFVAL { 1 }                                        -- @001
                ::= { mpAtmCCStaticPvpEntry 10 }

        mpAtmCCStaticPvpLowCladType      OBJECT-TYPE
                SYNTAX  MpAtmCCCladType
                ACCESS  read-only
                STATUS  mandatory
                DESCRIPTION
                     "CLAD Type"
                ::= { mpAtmCCStaticPvpEntry 11 }

        mpAtmCCStaticPvpHighCladType      OBJECT-TYPE
                SYNTAX  MpAtmCCCladType
                ACCESS  read-only
                STATUS  mandatory
                DESCRIPTION
                     "CLAD Type"
                ::= { mpAtmCCStaticPvpEntry 12 }

        mpAtmCCStaticPvpAdminStatus   OBJECT-TYPE
                SYNTAX  INTEGER {
                                up(1),
                                down(2)
                                }
                ACCESS  read-write
                STATUS  mandatory
                DESCRIPTION
                     "The value of this object identifies the desired
                      administrative status of this Static-PVP.
                      The up and down states indicate that the traffic
                      flow is enabled and disabled respectively on this
                      Static-PVP."
                DEFVAL { down }
                ::= { mpAtmCCStaticPvpEntry 13 }

        mpAtmCCStaticPvpOperStatus    OBJECT-TYPE
                SYNTAX  INTEGER
                ACCESS  read-only
                STATUS  mandatory
                DESCRIPTION
                     "The value of this object identifies the desired
                      operational status of this Static-PVP."
                ::= { mpAtmCCStaticPvpEntry 14 }

        mpAtmCCStaticPvpPvpId      OBJECT-TYPE
                SYNTAX  INTEGER
                ACCESS  read-write
                STATUS  mandatory
                DESCRIPTION
                     "The value of this object identifies the desired
                      cross connection."
--              DEFVAL { 0 }
                ::= { mpAtmCCStaticPvpEntry 15 }

        mpAtmCCStaticPvpSeqNo      OBJECT-TYPE
                SYNTAX  INTEGER
                ACCESS  read-write
                STATUS  mandatory
                DESCRIPTION
                     "Order information in the cross connection."
--              DEFVAL { 0 }
                ::= { mpAtmCCStaticPvpEntry 16 }


        mpAtmCCStaticPvpPgcRequest      OBJECT-TYPE             -- @007
                SYNTAX  INTEGER
                ACCESS  read-only
                STATUS  mandatory
                DESCRIPTION
                     "Indicates whether this PVP was configureated from
                      the PVC-Group-Cutover function.
                      The value of '0' indicates that this PVP was normal.
                      The value of '!=0' indicates that this PVP was
                      configrated form PVC-Group-Cutover function.
                       In this case, the value was indicated the PVC-Group Number"
                ::= { mpAtmCCStaticPvpEntry 17 }


        mpAtmCCStaticPvpCfgStatus  OBJECT-TYPE
                SYNTAX  INTEGER {
                                enable(1),
                                cancel(2),
                                delete(3),
                                unknown(4)
                                }
                ACCESS  read-write
                STATUS  mandatory
                DESCRIPTION
                        "Configuration setting start object. If this object is
                         set the setting of the configuration is started."
                DEFVAL { unknown }
                ::= { mpAtmCCStaticPvpEntry 98 }

        mpAtmCCStaticPvpErrInfo    OBJECT-TYPE
                SYNTAX  INTEGER
                ACCESS  read-only
                STATUS  mandatory
                DESCRIPTION
                        "Object that the configuration setting result is set up."
                ::= { mpAtmCCStaticPvpEntry 99 }


--
--

        mpAtmCCStaticPvcTable OBJECT-TYPE
                SYNTAX  SEQUENCE OF MpAtmCCStaticPvcEntry
                ACCESS  not-accessible
                STATUS  mandatory
                DESCRIPTION
                        "Static-PVC Table"
                ::= { mpAtmCCStaticPVPC 2 }

        mpAtmCCStaticPvcEntry OBJECT-TYPE
                SYNTAX  MpAtmCCStaticPvcEntry
                ACCESS  not-accessible
                STATUS  mandatory
                DESCRIPTION
                        "Static-PVC Entry"
                INDEX { mpAtmCCStaticPvcIndex,
                        mpAtmCCStaticPvcLowIfIndex,
                        mpAtmCCStaticPvcLowVpi,
                        mpAtmCCStaticPvcLowVci,
                        mpAtmCCStaticPvcHighIfIndex,
                        mpAtmCCStaticPvcHighVpi,
                        mpAtmCCStaticPvcHighVci }
                ::= { mpAtmCCStaticPvcTable 1 }

        MpAtmCCStaticPvcEntry ::=
                SEQUENCE {
                        mpAtmCCStaticPvcIndex         INTEGER,
                        mpAtmCCStaticPvcLowIfIndex    INTEGER,
                        mpAtmCCStaticPvcLowVpi        INTEGER,
                        mpAtmCCStaticPvcLowVci        INTEGER,
                        mpAtmCCStaticPvcHighIfIndex   INTEGER,
                        mpAtmCCStaticPvcHighVpi       INTEGER,
                        mpAtmCCStaticPvcHighVci       INTEGER,
                        mpAtmCCStaticPvcLowReceiveTrafficDescrIndex
                                                AtmTrafficDescrParamIndex,
                        mpAtmCCStaticPvcLowTransmitTrafficDescrIndex
                                                AtmTrafficDescrParamIndex,
                        mpAtmCCStaticPvcHighReceiveTrafficDescrIndex
                                                AtmTrafficDescrParamIndex,
                        mpAtmCCStaticPvcHighTransmitTrafficDescrIndex
                                                AtmTrafficDescrParamIndex,
                        mpAtmCCStaticPvcPriority      INTEGER,
                        mpAtmCCStaticPvcLowCladType   MpAtmCCCladType,
                        mpAtmCCStaticPvcHighCladType  MpAtmCCCladType,
                        mpAtmCCStaticPvcAdminStatus   INTEGER,
                        mpAtmCCStaticPvcOperStatus    INTEGER,
                        mpAtmCCStaticPvcPvcId         INTEGER,
                        mpAtmCCStaticPvcSeqNo         INTEGER,
                        mpAtmCCStaticPvcPgcRequest    INTEGER,      -- @007
                        mpAtmCCStaticPvcCfgStatus     INTEGER,
                        mpAtmCCStaticPvcErrInfo       INTEGER
                        }

        mpAtmCCStaticPvcIndex OBJECT-TYPE
                SYNTAX  INTEGER(1..2147483647)                      -- @001
--              SYNTAX  INTEGER(1)                                     @001
                ACCESS  not-accessible
                STATUS  mandatory
                DESCRIPTION
                        "A unique value to identify this Static-PVC.
                        The value is used only 1 (p2p)."
                ::= { mpAtmCCStaticPvcEntry 1 }

        mpAtmCCStaticPvcLowIfIndex    OBJECT-TYPE
                SYNTAX  INTEGER
                ACCESS  not-accessible
                STATUS  mandatory
                DESCRIPTION
                     "The value of this object is equal to MIB II's
                      ifIndex value of the ATM interface port for this
                      Static-PVC."
                ::= { mpAtmCCStaticPvcEntry 2 }

        mpAtmCCStaticPvcLowVpi        OBJECT-TYPE
                SYNTAX  INTEGER(0..4095)
                ACCESS  not-accessible
                STATUS  mandatory
                DESCRIPTION
                     "The value of this object is equal to the VPI
                      value at the ATM interface associated with
                      the Static-PVC that is identified by
                      mpAtmCCStaticPvcLowIfIndex.
                      The VPI value cannot exceed the number
                      supported by the atmInterfaceMaxVpiBits
                      at the low ATM interface port."
                ::= { mpAtmCCStaticPvcEntry 3 }

        mpAtmCCStaticPvcLowVci        OBJECT-TYPE
                SYNTAX  INTEGER(0..65535)
                ACCESS  not-accessible
                STATUS  mandatory
                DESCRIPTION
                     "The value of this object is equal to the VCI
                      value at the ATM interface
                      associated with this Static-PVC that is
                      identified by mpAtmCCStaticPvcLowIfIndex.
                      The VCI value cannot exceed the number
                      supported by the atmInterfaceMaxVciBits
                      at the low ATM interface port."
                ::= { mpAtmCCStaticPvcEntry 4 }

        mpAtmCCStaticPvcHighIfIndex   OBJECT-TYPE
                SYNTAX  INTEGER
                ACCESS  not-accessible
                STATUS  mandatory
                DESCRIPTION
                     "The value of this object is equal to MIB II's
                      ifIndex value for the ATM interface port for
                      this static-PVC."
                ::= { mpAtmCCStaticPvcEntry 5 }

        mpAtmCCStaticPvcHighVpi       OBJECT-TYPE
                SYNTAX  INTEGER(0..4095)
                ACCESS  not-accessible
                STATUS  mandatory
                DESCRIPTION
                     "The value of this object is equal to the VPI
                      value at the ATM interface
                      associated with the Static-PVC that is
                      identified by mpAtmCCStaticPvcHighIfIndex.
                      The VPI value cannot exceed
                      the number supported by the atmInterfaceMaxVpiBits
                      at the high ATM interface port."
                ::= { mpAtmCCStaticPvcEntry 6 }

        mpAtmCCStaticPvcHighVci       OBJECT-TYPE
                SYNTAX  INTEGER(0..65535)
                ACCESS  not-accessible
                STATUS  mandatory
                DESCRIPTION
                     "The value of this object is equal to the VCI
                      value at the ATM interface
                      associated with the static-PVC that is
                      identified by mpAtmCCStaticPvcHighIfIndex.
                      The VCI value cannot exceed
                      the number supported by the atmInterfaceMaxVciBits
                      at the high ATM interface port."
                ::= { mpAtmCCStaticPvcEntry 7 }

        mpAtmCCStaticPvcLowReceiveTrafficDescrIndex   OBJECT-TYPE
                SYNTAX  AtmTrafficDescrParamIndex
                ACCESS  read-write
                STATUS  mandatory
                DESCRIPTION
                     "The value of this object identifies
                      in the ATM Traffic Descriptor Table which
                      applies to the receive direction of this Static-PVC."
                ::= { mpAtmCCStaticPvcEntry 8 }

        mpAtmCCStaticPvcLowTransmitTrafficDescrIndex  OBJECT-TYPE
                SYNTAX  AtmTrafficDescrParamIndex
                ACCESS  read-write
                STATUS  mandatory
                DESCRIPTION
                     "The value of this object identifies
                      in the ATM Traffic Descriptor Table which
                      applies to the transmit direction of this Static-PVC."
                ::= { mpAtmCCStaticPvcEntry 9 }

        mpAtmCCStaticPvcHighReceiveTrafficDescrIndex  OBJECT-TYPE
                SYNTAX  AtmTrafficDescrParamIndex
                ACCESS  read-write
                STATUS  mandatory
                DESCRIPTION
                     "The value of this object identifies
                      in the ATM Traffic Descriptor Table which
                      applies to the receive direction of this Static-PVC."
                ::= { mpAtmCCStaticPvcEntry 10 }

        mpAtmCCStaticPvcHighTransmitTrafficDescrIndex OBJECT-TYPE
                SYNTAX  AtmTrafficDescrParamIndex
                ACCESS  read-write
                STATUS  mandatory
                DESCRIPTION
                     "The value of this object identifies
                      in the ATM Traffic Descriptor Table which
                      applies to the transmit direction of this Static-PVC."
                ::= { mpAtmCCStaticPvcEntry 11 }

        mpAtmCCStaticPvcPriority      OBJECT-TYPE
                SYNTAX  INTEGER(1..3)                               -- @001
                ACCESS  read-write
                STATUS  mandatory
                DESCRIPTION
                     "Connection priority"
                DEFVAL { 1 }                                        -- @001
                ::= { mpAtmCCStaticPvcEntry 12 }

        mpAtmCCStaticPvcLowCladType      OBJECT-TYPE
                SYNTAX  MpAtmCCCladType
                ACCESS  read-only
                STATUS  mandatory
                DESCRIPTION
                     "CLAD Type"
                ::= { mpAtmCCStaticPvcEntry 13 }

        mpAtmCCStaticPvcHighCladType      OBJECT-TYPE
                SYNTAX  MpAtmCCCladType
                ACCESS  read-only
                STATUS  mandatory
                DESCRIPTION
                     "CLAD Type"
                ::= { mpAtmCCStaticPvcEntry 14 }

        mpAtmCCStaticPvcAdminStatus   OBJECT-TYPE
                SYNTAX  INTEGER {
                                up(1),
                                down(2)
                                }
                ACCESS  read-write
                STATUS  mandatory
                DESCRIPTION
                     "The value of this object identifies the desired
                      administrative status of this Static-PVC.
                      The up and down states indicate that the traffic
                      flow is enabled and disabled respectively on this
                      Static-PVC."
                DEFVAL { down }
                ::= { mpAtmCCStaticPvcEntry 15 }

        mpAtmCCStaticPvcOperStatus    OBJECT-TYPE
                SYNTAX  INTEGER
                ACCESS  read-only
                STATUS  mandatory
                DESCRIPTION
                     "The value of this object identifies the desired
                      operational status of this Static-PVC."
                ::= { mpAtmCCStaticPvcEntry 16 }

        mpAtmCCStaticPvcPvcId      OBJECT-TYPE
                SYNTAX  INTEGER
                ACCESS  read-write
                STATUS  mandatory
                DESCRIPTION
                     "The value of this object identifies the desired
                      cross connection."
--              DEFVAL { 0 }
                ::= { mpAtmCCStaticPvcEntry 17 }

        mpAtmCCStaticPvcSeqNo      OBJECT-TYPE
                SYNTAX  INTEGER
                ACCESS  read-write
                STATUS  mandatory
                DESCRIPTION
                     "Order information in the cross connection."
--              DEFVAL { 0 }
                ::= { mpAtmCCStaticPvcEntry 18 }


        mpAtmCCStaticPvcPgcRequest      OBJECT-TYPE             -- @007
                SYNTAX  INTEGER
                ACCESS  read-only
                STATUS  mandatory
                DESCRIPTION
                     "Indicates whether this PVP was configureated from
                      the PVC-Group-Cutover function.
                      The value of '0' indicates that this PVP was normal.
                      The value of '!=0' indicates that this PVP was
                      configrated form PVC-Group-Cutover function.
                       In this case, the value was indicated the PVC-Group Number"
                ::= { mpAtmCCStaticPvcEntry 19 }


        mpAtmCCStaticPvcCfgStatus  OBJECT-TYPE
                SYNTAX  INTEGER {
                                enable(1),
                                cancel(2),
                                delete(3),
                                unknown(4)
                                }
                ACCESS  read-write
                STATUS  mandatory
                DESCRIPTION
                        "Configuration setting start object. If this object is
                         set the setting of the configuration is started."
                DEFVAL { unknown }
                ::= { mpAtmCCStaticPvcEntry 98 }

        mpAtmCCStaticPvcErrInfo        OBJECT-TYPE
                SYNTAX  INTEGER
                ACCESS  read-only
                STATUS  mandatory
                DESCRIPTION
                        "Object that the configuration setting result is set up."
                ::= { mpAtmCCStaticPvcEntry 99 }




--
--

        mpAtmCCSoftPVPC       OBJECT IDENTIFIER ::= { mpAtmCallCtl 3 }

--
--

--
--

        mpAtmCCSoftPvpTable   OBJECT-TYPE
                SYNTAX  SEQUENCE OF MpAtmCCSoftPvpEntry
                ACCESS  not-accessible
                STATUS  mandatory
                DESCRIPTION
                        "Soft-PVP(Calling) Table"
                ::= { mpAtmCCSoftPVPC 1 }

        mpAtmCCSoftPvpEntry   OBJECT-TYPE
                SYNTAX  MpAtmCCSoftPvpEntry
                ACCESS  not-accessible
                STATUS  mandatory
                DESCRIPTION
                        "Soft-PVP(Calling) Entry"
                INDEX { mpAtmCCSoftPvpLeafReference,
                        mpAtmCCSoftPvpIfIndex,
                        mpAtmCCSoftPvpVpi
                }
                ::= { mpAtmCCSoftPvpTable 1 }

        MpAtmCCSoftPvpEntry ::=
                SEQUENCE {
                        mpAtmCCSoftPvpLeafReference   INTEGER,
                        mpAtmCCSoftPvpIfIndex         INTEGER,
                        mpAtmCCSoftPvpVpi             INTEGER,
                        mpAtmCCSoftPvpReceiveTrafficDescrIndex
                                                AtmTrafficDescrParamIndex,
                        mpAtmCCSoftPvpTransmitTrafficDescrIndex
                                                AtmTrafficDescrParamIndex,
                        mpAtmCCSoftPvpTargetAddress   AtmAddr,
                        mpAtmCCSoftPvpTargetVpi       INTEGER,
                        mpAtmCCSoftPvpLastReleaseCause INTEGER,
                        mpAtmCCSoftPvpLastReleaseDiagnostic
                                                OCTET STRING,
                        mpAtmCCSoftPvpPriority        INTEGER,
                        mpAtmCCSoftPvpCladType        MpAtmCCCladType,
                        mpAtmCCSoftPvpOriginalAddress AtmAddr,
                        mpAtmCCSoftPvpAdminStatus     INTEGER,
                        mpAtmCCSoftPvpOperStatus      INTEGER,
                        mpAtmCCSoftPvpPgcRequest      INTEGER,      -- @007 
                        mpAtmCCSoftPvpCfgStatus       INTEGER,
                        mpAtmCCSoftPvpErrInfo         INTEGER
                        }

        mpAtmCCSoftPvpLeafReference   OBJECT-TYPE
                SYNTAX  INTEGER(1..65535)                           -- @001 
--              SYNTAX  INTEGER(1)                                     @001 
                ACCESS  not-accessible
                STATUS  mandatory
                DESCRIPTION
                        "A unique value to identify this Soft-PVP.
                        The value is used only 1 (p2p)."
                ::= { mpAtmCCSoftPvpEntry 1 }

        mpAtmCCSoftPvpIfIndex OBJECT-TYPE
                SYNTAX  INTEGER
                ACCESS  not-accessible
                STATUS  mandatory
                DESCRIPTION
                     "The value of this object is equal to MIB II's
                      ifIndex value of the ATM interface port for this
                      Soft-PVP."
                ::= { mpAtmCCSoftPvpEntry 2 }

        mpAtmCCSoftPvpVpi     OBJECT-TYPE
                SYNTAX  INTEGER
                ACCESS  not-accessible
                STATUS  mandatory
                DESCRIPTION
                     "The value of this object is equal to the VPI
                      value at the ATM interface associated with
                      the Soft-PVP that is identified by
                      mpAtmCCSoftPvpIfIndex.
                      The VPI value cannot exceed the number
                      supported by the atmInterfaceMaxVpiBits
                      at the ATM interface port."
                ::= { mpAtmCCSoftPvpEntry 3 }

        mpAtmCCSoftPvpReceiveTrafficDescrIndex        OBJECT-TYPE
                SYNTAX  AtmTrafficDescrParamIndex
                ACCESS  read-write
                STATUS  mandatory
                DESCRIPTION
                     "The value of this object identifies
                      in the ATM Traffic Descriptor Table which
                      applies to the receive direction of this Soft-PVP."
                ::= { mpAtmCCSoftPvpEntry 4 }

        mpAtmCCSoftPvpTransmitTrafficDescrIndex       OBJECT-TYPE
                SYNTAX  AtmTrafficDescrParamIndex
                ACCESS  read-write
                STATUS  mandatory
                DESCRIPTION
                     "The value of this object identifies
                      in the ATM Traffic Descriptor Table which
                      applies to the transmit direction of this Soft-PVP."
                ::= { mpAtmCCSoftPvpEntry 5 }

        mpAtmCCSoftPvpTargetAddress   OBJECT-TYPE
                SYNTAX  AtmAddr
                ACCESS  read-write
                STATUS  mandatory
                DESCRIPTION
                        "The target ATM Address of this Soft-PVP.  If no
                        address is supplied, no attempts to establish the
                        Soft-PVP are initiated."
                ::= { mpAtmCCSoftPvpEntry 6 }

        mpAtmCCSoftPvpTargetVpi       OBJECT-TYPE
                SYNTAX  INTEGER (0..4095)
                ACCESS  read-write
                STATUS  mandatory
                DESCRIPTION
                        "The VPI value of the VCL used at the target interface."
                DEFVAL { 0 }
                ::= { mpAtmCCSoftPvpEntry 7 }

        mpAtmCCSoftPvpLastReleaseCause        OBJECT-TYPE
                SYNTAX  INTEGER(1..127)
                ACCESS  read-only
                STATUS  mandatory
                DESCRIPTION
                        "Value of the Cause field of the Cause
                        Information Element in the last RELEASE
                        signalling message received for this Soft-PVP.
                        Indicates the reason for the Release."
                ::= { mpAtmCCSoftPvpEntry 8 }

        mpAtmCCSoftPvpLastReleaseDiagnostic   OBJECT-TYPE
                SYNTAX  OCTET STRING (SIZE(0..8))
                ACCESS  read-only
                STATUS  mandatory
                DESCRIPTION
                        "Value of the first 8 bytes of diagnostic information
                        from the Cause field of the Cause Information Element
                        in the last RELEASE signalling message received for
                        this Soft-PVP."
                ::= { mpAtmCCSoftPvpEntry 9 }

        mpAtmCCSoftPvpPriority        OBJECT-TYPE
                SYNTAX  INTEGER(1..3)                               -- @001 
                ACCESS  read-write
                STATUS  mandatory
                DESCRIPTION
                     "Connection priority"
                DEFVAL { 1 }                                        -- @001 
                ::= { mpAtmCCSoftPvpEntry 10 }

        mpAtmCCSoftPvpCladType        OBJECT-TYPE
                SYNTAX  MpAtmCCCladType
                ACCESS  read-only
                STATUS  mandatory
                DESCRIPTION
                     "CLAD Type"
                ::= { mpAtmCCSoftPvpEntry 11 }

        mpAtmCCSoftPvpOriginalAddress   OBJECT-TYPE
                SYNTAX  AtmAddr
                ACCESS  read-only
                STATUS  mandatory
                DESCRIPTION
                        "The original ATM Address of this Soft-PVP.  If no
                        address is supplied, no attempts to establish the
                        Soft-PVP are initiated."
                ::= { mpAtmCCSoftPvpEntry 12 }

        mpAtmCCSoftPvpAdminStatus     OBJECT-TYPE
                SYNTAX  INTEGER {
                                up(1),
                                down(2)
                                }
                ACCESS  read-write
                STATUS  mandatory
                DESCRIPTION
                     "The value of this object identifies the desired
                      administrative status of this Soft-PVP.
                      The up and down states indicate that the traffic
                      flow is enabled and disabled respectively on this
                      Soft-PVP."
                DEFVAL { down }
                ::= { mpAtmCCSoftPvpEntry 13 }

        mpAtmCCSoftPvpOperStatus      OBJECT-TYPE
                SYNTAX  INTEGER
                ACCESS  read-only
                STATUS  mandatory
                DESCRIPTION
                     "Soft-PVP Oper Status up/down = enable/disable"
                ::= { mpAtmCCSoftPvpEntry 14 }

        mpAtmCCSoftPvpPgcRequest      OBJECT-TYPE             -- @007
                SYNTAX  INTEGER
                ACCESS  read-only
                STATUS  mandatory
                DESCRIPTION
                     "Indicates whether this PVP was configureated from
                      the PVC-Group-Cutover function.
                      The value of '0' indicates that this PVP was normal.
                      The value of '!=0' indicates that this PVP was
                      configrated form PVC-Group-Cutover function.
                       In this case, the value was indicated the PVC-Group Number"
                ::= { mpAtmCCSoftPvpEntry 15 }

        mpAtmCCSoftPvpCfgStatus    OBJECT-TYPE
                SYNTAX  INTEGER {
                                enable(1),
                                cancel(2),
                                delete(3),
                                unknown(4)
                                }
                ACCESS  read-write
                STATUS  mandatory
                DESCRIPTION
                        "Configuration setting start object. If this object is
                         set the setting of the configuration is started."
                DEFVAL { unknown }
                ::= { mpAtmCCSoftPvpEntry 98 }

        mpAtmCCSoftPvpErrInfo          OBJECT-TYPE
                SYNTAX  INTEGER
                ACCESS  read-only
                STATUS  mandatory
                DESCRIPTION
                        "Object that the configuration setting result is set up."
                ::= { mpAtmCCSoftPvpEntry 99 }


--
--

        mpAtmCCSoftPvcTable   OBJECT-TYPE
                SYNTAX  SEQUENCE OF MpAtmCCSoftPvcEntry
                ACCESS  not-accessible
                STATUS  mandatory
                DESCRIPTION
                        "Soft-PVC(Calling) Table"
                ::= { mpAtmCCSoftPVPC 2 }

        mpAtmCCSoftPvcEntry   OBJECT-TYPE
                SYNTAX  MpAtmCCSoftPvcEntry
                ACCESS  not-accessible
                STATUS  mandatory
                DESCRIPTION
                        "Soft-PVC(Calling) Entry"
                INDEX { mpAtmCCSoftPvcLeafReference,
                        mpAtmCCSoftPvcIfIndex,
                        mpAtmCCSoftPvcVpi,
                        mpAtmCCSoftPvcVci
                }
                ::= { mpAtmCCSoftPvcTable 1 }

        MpAtmCCSoftPvcEntry ::=
                SEQUENCE {
                        mpAtmCCSoftPvcLeafReference   INTEGER,
                        mpAtmCCSoftPvcIfIndex         INTEGER,
                        mpAtmCCSoftPvcVpi             INTEGER,
                        mpAtmCCSoftPvcVci             INTEGER,
                        mpAtmCCSoftPvcReceiveTrafficDescrIndex
                                                AtmTrafficDescrParamIndex,
                        mpAtmCCSoftPvcTransmitTrafficDescrIndex
                                                AtmTrafficDescrParamIndex,
                        mpAtmCCSoftPvcTargetAddress   AtmAddr,
                        mpAtmCCSoftPvcTargetVpi       INTEGER,
                        mpAtmCCSoftPvcTargetVci       INTEGER,
                        mpAtmCCSoftPvcLastReleaseCause INTEGER,
                        mpAtmCCSoftPvcLastReleaseDiagnostic
                                                OCTET STRING,
                        mpAtmCCSoftPvcPriority        INTEGER,
                        mpAtmCCSoftPvcCladType        MpAtmCCCladType,
                        mpAtmCCSoftPvcOriginalAddress AtmAddr,
                        mpAtmCCSoftPvcAdminStatus     INTEGER,
                        mpAtmCCSoftPvcOperStatus      INTEGER,
                        mpAtmCCSoftPvcPgcRequest      INTEGER,      -- @007 
                        mpAtmCCSoftPvcCfgStatus       INTEGER,
                        mpAtmCCSoftPvcErrInfo         INTEGER
                        }

        mpAtmCCSoftPvcLeafReference   OBJECT-TYPE
                SYNTAX  INTEGER(1..65535)                           -- @001 
--              SYNTAX  INTEGER(1)                                     @001 
                ACCESS  not-accessible
                STATUS  mandatory
                DESCRIPTION
                        "A unique value to identify this Soft-PVC.
                        The value is used only 1 (p2p)."
                ::= { mpAtmCCSoftPvcEntry 1 }

        mpAtmCCSoftPvcIfIndex OBJECT-TYPE
                SYNTAX  INTEGER
                ACCESS  not-accessible
                STATUS  mandatory
                DESCRIPTION
                     "The value of this object is equal to MIB II's
                      ifIndex value of the ATM interface port for this
                      Soft-PVC."
                ::= { mpAtmCCSoftPvcEntry 2 }

        mpAtmCCSoftPvcVpi     OBJECT-TYPE
                SYNTAX  INTEGER
                ACCESS  not-accessible
                STATUS  mandatory
                DESCRIPTION
                     "The value of this object is equal to the VPI
                      value at the ATM interface associated with
                      the Soft-PVC that is identified by
                      mpAtmCCSoftPvcIfIndex.
                      The VPI value cannot exceed the number
                      supported by the atmInterfaceMaxVpiBits
                      at the ATM interface port."
                ::= { mpAtmCCSoftPvcEntry 3 }

        mpAtmCCSoftPvcVci     OBJECT-TYPE
                SYNTAX  INTEGER
                ACCESS  not-accessible
                STATUS  mandatory
                DESCRIPTION
                     "The value of this object is equal to the VCI
                      value at the ATM interface associated with
                      the Soft-PVC that is identified by
                      mpAtmCCSoftPvcIfIndex.
                      The VPI value cannot exceed the number
                      supported by the atmInterfaceMaxVciBits
                      at the ATM interface port."
                ::= { mpAtmCCSoftPvcEntry 4 }

        mpAtmCCSoftPvcReceiveTrafficDescrIndex        OBJECT-TYPE
                SYNTAX  AtmTrafficDescrParamIndex
                ACCESS  read-write
                STATUS  mandatory
                DESCRIPTION
                     "The value of this object identifies
                      in the ATM Traffic Descriptor Table which
                      applies to the receive direction of this Soft-PVC."
                ::= { mpAtmCCSoftPvcEntry 5 }

        mpAtmCCSoftPvcTransmitTrafficDescrIndex       OBJECT-TYPE
                SYNTAX  AtmTrafficDescrParamIndex
                ACCESS  read-write
                STATUS  mandatory
                DESCRIPTION
                     "The value of this object identifies
                      in the ATM Traffic Descriptor Table which
                      applies to the transmit direction of this Soft-PVC."
                ::= { mpAtmCCSoftPvcEntry 6 }

        mpAtmCCSoftPvcTargetAddress   OBJECT-TYPE
                SYNTAX  AtmAddr
                ACCESS  read-write
                STATUS  mandatory
                DESCRIPTION
                        "The target ATM Address of this Soft PVCC.  If no
                        address is supplied, no attempts to establish the
                        Soft PVCC are initiated."
                ::= { mpAtmCCSoftPvcEntry 7 }

        mpAtmCCSoftPvcTargetVpi       OBJECT-TYPE
                SYNTAX  INTEGER (0..4095)
                ACCESS  read-write
                STATUS  mandatory
                DESCRIPTION
                        "The VPI value of the VCL used at the target interface."
                DEFVAL { 0 }
                ::= { mpAtmCCSoftPvcEntry 8 }

        mpAtmCCSoftPvcTargetVci       OBJECT-TYPE
                SYNTAX  INTEGER (0..65535)
                ACCESS  read-write
                STATUS  mandatory
                DESCRIPTION
                        "The VCI value of the VCL used at the target interface."
                ::= { mpAtmCCSoftPvcEntry 9 }

        mpAtmCCSoftPvcLastReleaseCause        OBJECT-TYPE
                SYNTAX  INTEGER(1..127)
                ACCESS  read-only
                STATUS  mandatory
                DESCRIPTION
                        "Value of the Cause field of the Cause
                        Information Element in the last RELEASE
                        signalling message received for this Soft PVCC.
                        Indicates the reason for the Release."
                ::= { mpAtmCCSoftPvcEntry 10 }

        mpAtmCCSoftPvcLastReleaseDiagnostic   OBJECT-TYPE
                SYNTAX  OCTET STRING (SIZE(0..8))
                ACCESS  read-only
                STATUS  mandatory
                DESCRIPTION
                        "Value of the first 8 bytes of diagnostic information
                        from the Cause field of the Cause Information Element
                        in the last RELEASE signalling message received for
                        this Soft-PVC."
                ::= { mpAtmCCSoftPvcEntry 11 }

        mpAtmCCSoftPvcPriority        OBJECT-TYPE
                SYNTAX  INTEGER(1..3)                               -- @001 
                ACCESS  read-write
                STATUS  mandatory
                DESCRIPTION
                     "Connection priority"
                DEFVAL { 1 }                                        -- @001 
                ::= { mpAtmCCSoftPvcEntry 12 }

        mpAtmCCSoftPvcCladType        OBJECT-TYPE
                SYNTAX  MpAtmCCCladType
                ACCESS  read-only
                STATUS  mandatory
                DESCRIPTION
                     "CLAD Type"
                ::= { mpAtmCCSoftPvcEntry 13 }

        mpAtmCCSoftPvcOriginalAddress   OBJECT-TYPE
                SYNTAX  AtmAddr
                ACCESS  read-only
                STATUS  mandatory
                DESCRIPTION
                        "The origjnal ATM Address of this Soft PVCC.  If no
                        address is supplied, no attempts to establish the
                        Soft PVCC are initiated."
                ::= { mpAtmCCSoftPvcEntry 14 }

        mpAtmCCSoftPvcAdminStatus     OBJECT-TYPE
                SYNTAX  INTEGER {
                                up(1),
                                down(2)
                                }
                ACCESS  read-write
                STATUS  mandatory
                DESCRIPTION
                     "The value of this object identifies the desired
                      administrative status of this Soft-PVC.
                      The up and down states indicate that the traffic
                      flow is enabled and disabled respectively on this
                      Soft-PVC."
                DEFVAL { down }
                ::= { mpAtmCCSoftPvcEntry 15 }

        mpAtmCCSoftPvcOperStatus      OBJECT-TYPE
                SYNTAX  INTEGER
                ACCESS  read-only
                STATUS  mandatory
                DESCRIPTION
                     "The value of this object identifies the desired
                      operational status of this Soft-PVC."
                ::= { mpAtmCCSoftPvcEntry 16 }

        mpAtmCCSoftPvcPgcRequest      OBJECT-TYPE             -- @007
                SYNTAX  INTEGER
                ACCESS  read-only
                STATUS  mandatory
                DESCRIPTION
                     "Indicates whether this PVP was configureated from
                      the PVC-Group-Cutover function.
                      The value of '0' indicates that this PVP was normal.
                      The value of '!=0' indicates that this PVP was
                      configrated form PVC-Group-Cutover function.
                       In this case, the value was indicated the PVC-Group Number"
                ::= { mpAtmCCSoftPvcEntry 17 }


        mpAtmCCSoftPvcCfgStatus    OBJECT-TYPE
                SYNTAX  INTEGER {
                                enable(1),
                                cancel(2),
                                delete(3),
                                unknown(4)
                                }
                ACCESS  read-write
                STATUS  mandatory
                DESCRIPTION
                        "Configuration setting start object. If this object is
                         set the setting of the configuration is started."
                DEFVAL { unknown }
                ::= { mpAtmCCSoftPvcEntry 98 }

        mpAtmCCSoftPvcErrInfo          OBJECT-TYPE
                SYNTAX  INTEGER
                ACCESS  read-only
                STATUS  mandatory
                DESCRIPTION
                        "Object that the configuration setting result is set up."
                ::= { mpAtmCCSoftPvcEntry 99 }


--
--

--
--

        mpAtmCCSoftPvpCalledTable     OBJECT-TYPE
                SYNTAX  SEQUENCE OF MpAtmCCSoftPvpCalledEntry
                ACCESS  not-accessible
                STATUS  mandatory
                DESCRIPTION
                        "Soft-PVP(Called) Table"
                ::= { mpAtmCCSoftPVPC 3 }

        mpAtmCCSoftPvpCalledEntry     OBJECT-TYPE
                SYNTAX  MpAtmCCSoftPvpCalledEntry
                ACCESS  not-accessible
                STATUS  mandatory
                DESCRIPTION
                        "Soft-PVP(Called) Entry"
                INDEX { mpAtmCCSoftPvpCalledLeafReference,
                        mpAtmCCSoftPvpCalledIfIndex,
                        mpAtmCCSoftPvpCalledVpi
                }
                ::= { mpAtmCCSoftPvpCalledTable 1 }

        MpAtmCCSoftPvpCalledEntry ::=
                SEQUENCE {
                        mpAtmCCSoftPvpCalledLeafReference     INTEGER,
                        mpAtmCCSoftPvpCalledIfIndex           INTEGER,
                        mpAtmCCSoftPvpCalledVpi               INTEGER,
                        mpAtmCCSoftPvpCalledReceiveTrafficDescrIndex
                                                AtmTrafficDescrParamIndex,
                        mpAtmCCSoftPvpCalledTransmitTrafficDescrIndex
                                                AtmTrafficDescrParamIndex,
                        mpAtmCCSoftPvpCalledTargetAddress     AtmAddr,
                        mpAtmCCSoftPvpCalledTargetVpi         INTEGER,
                        mpAtmCCSoftPvpCalledLastReleaseCause  INTEGER,
                        mpAtmCCSoftPvpCalledLastReleaseDiagnostic
                                                        OCTET STRING,
                        mpAtmCCSoftPvpCalledPriority          INTEGER,
                        mpAtmCCSoftPvpCalledCladType          MpAtmCCCladType,
                        mpAtmCCSoftPvpCalledOriginalAddress   AtmAddr,
                        mpAtmCCSoftPvpCalledAdminStatus       INTEGER,
                        mpAtmCCSoftPvpCalledOperStatus        INTEGER,
                        mpAtmCCSoftPvpCalledPgcRequest        INTEGER,  -- @010 
                        mpAtmCCSoftPvpCalledCfgStatus         INTEGER,
                        mpAtmCCSoftPvpCalledErrInfo           INTEGER
                        }

        mpAtmCCSoftPvpCalledLeafReference     OBJECT-TYPE
                SYNTAX  INTEGER(1..65535)                           -- @001 
--              SYNTAX  INTEGER(1)                                     @001 
                ACCESS  not-accessible
                STATUS  mandatory
                DESCRIPTION
                        "A unique value to identify this Soft-PVP.
                        The value is used only 1 (p2p)."
                ::= { mpAtmCCSoftPvpCalledEntry 1 }

        mpAtmCCSoftPvpCalledIfIndex   OBJECT-TYPE
                SYNTAX  INTEGER
                ACCESS  not-accessible
                STATUS  mandatory
                DESCRIPTION
                     "The value of this object is equal to MIB II's
                      ifIndex value of the ATM interface port for this
                      Soft-PVP."
                ::= { mpAtmCCSoftPvpCalledEntry 2 }

        mpAtmCCSoftPvpCalledVpi       OBJECT-TYPE
                SYNTAX  INTEGER
                ACCESS  not-accessible
                STATUS  mandatory
                DESCRIPTION
                     "The value of this object is equal to the VPI
                      value at the ATM interface associated with
                      the Soft-PVP that is identified by
                      mpAtmCCSoftPvpCalledIfIndex.
                      The VPI value cannot exceed the number
                      supported by the atmInterfaceMaxVpiBits
                      at the ATM interface port."
                ::= { mpAtmCCSoftPvpCalledEntry 3 }

        mpAtmCCSoftPvpCalledReceiveTrafficDescrIndex  OBJECT-TYPE
                SYNTAX  AtmTrafficDescrParamIndex
                ACCESS  read-write
                STATUS  mandatory
                DESCRIPTION
                     "The value of this object identifies
                      in the ATM Traffic Descriptor Table which
                      applies to the receive direction of this Soft-PVP."
                ::= { mpAtmCCSoftPvpCalledEntry 4 }

        mpAtmCCSoftPvpCalledTransmitTrafficDescrIndex OBJECT-TYPE
                SYNTAX  AtmTrafficDescrParamIndex
                ACCESS  read-write
                STATUS  mandatory
                DESCRIPTION
                     "The value of this object identifies
                      in the ATM Traffic Descriptor Table which
                      applies to the transmit direction of this Soft-PVP."
                ::= { mpAtmCCSoftPvpCalledEntry 5 }

        mpAtmCCSoftPvpCalledTargetAddress     OBJECT-TYPE
                SYNTAX  AtmAddr
                ACCESS  read-write
                STATUS  mandatory
                DESCRIPTION
                        "The target ATM Address of this Soft-PVP.  If no
                        address is supplied, no attempts to establish the
                        Soft-PVP are initiated."
                ::= { mpAtmCCSoftPvpCalledEntry 6 }

        mpAtmCCSoftPvpCalledTargetVpi OBJECT-TYPE
                SYNTAX  INTEGER (0..4095)
                ACCESS  read-write
                STATUS  mandatory
                DESCRIPTION
                        "The VPI value of the VCL used at the target interface."
                DEFVAL { 0 }
                ::= { mpAtmCCSoftPvpCalledEntry 7 }

        mpAtmCCSoftPvpCalledLastReleaseCause  OBJECT-TYPE
                SYNTAX  INTEGER(1..127)
                ACCESS  read-only
                STATUS  mandatory
                DESCRIPTION
                        "Value of the Cause field of the Cause
                        Information Element in the last RELEASE
                        signalling message received for this Soft-PVP.
                        Indicates the reason for the Release."
                ::= { mpAtmCCSoftPvpCalledEntry 8 }

        mpAtmCCSoftPvpCalledLastReleaseDiagnostic     OBJECT-TYPE
                SYNTAX  OCTET STRING (SIZE(0..8))
                ACCESS  read-only
                STATUS  mandatory
                DESCRIPTION
                        "Value of the first 8 bytes of diagnostic information
                        from the Cause field of the Cause Information Element
                        in the last RELEASE signalling message received for
                        this Soft-PVP."
                ::= { mpAtmCCSoftPvpCalledEntry 9 }

        mpAtmCCSoftPvpCalledPriority  OBJECT-TYPE
                SYNTAX  INTEGER(1..3)                               -- @001 
                ACCESS  read-write
                STATUS  mandatory
                DESCRIPTION
                     "Connection priority"
                DEFVAL { 1 }                                        -- @001 
                ::= { mpAtmCCSoftPvpCalledEntry 10 }

        mpAtmCCSoftPvpCalledCladType  OBJECT-TYPE
                SYNTAX  MpAtmCCCladType
                ACCESS  read-only
                STATUS  mandatory
                DESCRIPTION
                     "CLAD Type"
                ::= { mpAtmCCSoftPvpCalledEntry 11 }

        mpAtmCCSoftPvpCalledOriginalAddress     OBJECT-TYPE
                SYNTAX  AtmAddr
                ACCESS  read-only
                STATUS  mandatory
                DESCRIPTION
                        "The original ATM Address of this Soft-PVP.  If no
                        address is supplied, no attempts to establish the
                        Soft-PVP are initiated."
                ::= { mpAtmCCSoftPvpCalledEntry 12 }

        mpAtmCCSoftPvpCalledAdminStatus       OBJECT-TYPE
                SYNTAX  INTEGER {
                                up(1),
                                down(2)
                                }
                ACCESS  read-write
                STATUS  mandatory
                DESCRIPTION
                     "The value of this object identifies the desired
                      administrative status of this Soft-PVP.
                      The up and down states indicate that the traffic
                      flow is enabled and disabled respectively on this
                      Soft-PVP."
                DEFVAL { down }
                ::= { mpAtmCCSoftPvpCalledEntry 13 }

        mpAtmCCSoftPvpCalledOperStatus        OBJECT-TYPE
                SYNTAX  INTEGER
                ACCESS  read-only
                STATUS  mandatory
                DESCRIPTION
                     "The value of this object identifies the desired
                      operational status of this Soft-PVP."
                ::= { mpAtmCCSoftPvpCalledEntry 14 }

        mpAtmCCSoftPvpCalledPgcRequest     OBJECT-TYPE    -- @010 
                SYNTAX  INTEGER
                ACCESS  read-only
                STATUS  mandatory
                DESCRIPTION
                     "Indicates whether this PVP was configureated from
                      the PVC-Group-Cutover function.
                      The value of '0' indicates that this PVP was normal.
                      The value of '!=0' indicates that this PVP was
                      configrated form PVC-Group-Cutover function.
                       In this case, the value was indicated the PVC-Group Number"
                ::= { mpAtmCCSoftPvpCalledEntry 15 }

        mpAtmCCSoftPvpCalledCfgStatus      OBJECT-TYPE
                SYNTAX  INTEGER {
                                enable(1),
                                cancel(2),
                                delete(3),
                                unknown(4)
                                }
                ACCESS  read-write
                STATUS  mandatory
                DESCRIPTION
                        "Configuration setting start object. If this object is
                         set the setting of the configuration is started."
                DEFVAL { unknown }
                ::= { mpAtmCCSoftPvpCalledEntry 98 }

        mpAtmCCSoftPvpCalledErrInfo    OBJECT-TYPE
                SYNTAX  INTEGER
                ACCESS  read-only
                STATUS  mandatory
                DESCRIPTION
                        "Object that the configuration setting result is set up."
                ::= { mpAtmCCSoftPvpCalledEntry 99 }


--
-- 
--

        mpAtmCCSoftPvcCalledTable     OBJECT-TYPE
                SYNTAX  SEQUENCE OF MpAtmCCSoftPvcCalledEntry
                ACCESS  not-accessible
                STATUS  mandatory
                DESCRIPTION
                        "Soft-PVC(Called) Table"
                ::= { mpAtmCCSoftPVPC 4 }

        mpAtmCCSoftPvcCalledEntry     OBJECT-TYPE
                SYNTAX  MpAtmCCSoftPvcCalledEntry
                ACCESS  not-accessible
                STATUS  mandatory
                DESCRIPTION
                        "Soft-PVC(Called) Entry"
                INDEX { mpAtmCCSoftPvcCalledLeafReference,
                        mpAtmCCSoftPvcCalledIfIndex,
                        mpAtmCCSoftPvcCalledVpi,
                        mpAtmCCSoftPvcCalledVci
                }
                ::= { mpAtmCCSoftPvcCalledTable 1 }

        MpAtmCCSoftPvcCalledEntry ::=
                SEQUENCE {
                        mpAtmCCSoftPvcCalledLeafReference     INTEGER,
                        mpAtmCCSoftPvcCalledIfIndex           INTEGER,
                        mpAtmCCSoftPvcCalledVpi               INTEGER,
                        mpAtmCCSoftPvcCalledVci               INTEGER,
                        mpAtmCCSoftPvcCalledReceiveTrafficDescrIndex
                                                AtmTrafficDescrParamIndex,
                        mpAtmCCSoftPvcCalledTransmitTrafficDescrIndex
                                                AtmTrafficDescrParamIndex,
                        mpAtmCCSoftPvcCalledTargetAddress     AtmAddr,
                        mpAtmCCSoftPvcCalledTargetVpi         INTEGER,
                        mpAtmCCSoftPvcCalledTargetVci         INTEGER,
                        mpAtmCCSoftPvcCalledLastReleaseCause  INTEGER,
                        mpAtmCCSoftPvcCalledLastReleaseDiagnostic
                                                        OCTET STRING,
                        mpAtmCCSoftPvcCalledPriority          INTEGER,
                        mpAtmCCSoftPvcCalledCladType          MpAtmCCCladType,
                        mpAtmCCSoftPvcCalledOriginalAddress   AtmAddr,
                        mpAtmCCSoftPvcCalledAdminStatus       INTEGER,
                        mpAtmCCSoftPvcCalledOperStatus        INTEGER,
                        mpAtmCCSoftPvcCalledPgcRequest        INTEGER,  -- @010 
                        mpAtmCCSoftPvcCalledCfgStatus         INTEGER,
                        mpAtmCCSoftPvcCalledErrInfo           INTEGER
                        }

        mpAtmCCSoftPvcCalledLeafReference     OBJECT-TYPE
                SYNTAX  INTEGER(1..65535)                           -- @001 
--              SYNTAX  INTEGER(1)                                     @001 
                ACCESS  not-accessible
                STATUS  mandatory
                DESCRIPTION
                        "A unique value to identify this Soft-PVC.
                        The value is used only 1 (p2p)."
                ::= { mpAtmCCSoftPvcCalledEntry 1 }

        mpAtmCCSoftPvcCalledIfIndex   OBJECT-TYPE
                SYNTAX  INTEGER
                ACCESS  not-accessible
                STATUS  mandatory
                DESCRIPTION
                     "The value of this object is equal to MIB II's
                      ifIndex value of the ATM interface port for this
                      Soft-PVC."
                ::= { mpAtmCCSoftPvcCalledEntry 2 }

        mpAtmCCSoftPvcCalledVpi       OBJECT-TYPE
                SYNTAX  INTEGER
                ACCESS  not-accessible
                STATUS  mandatory
                DESCRIPTION
                     "The value of this object is equal to the VPI
                      value at the ATM interface associated with
                      the Soft-PVC that is identified by
                      mpAtmCCSoftPvcCalledIfIndex.
                      The VPI value cannot exceed the number
                      supported by the atmInterfaceMaxVpiBits
                      at the ATM interface port."

                ::= { mpAtmCCSoftPvcCalledEntry 3 }

        mpAtmCCSoftPvcCalledVci       OBJECT-TYPE
                SYNTAX  INTEGER
                ACCESS  not-accessible
                STATUS  mandatory
                DESCRIPTION
                     "The value of this object is equal to the VCI
                      value at the ATM interface associated with
                      the Soft-PVC that is identified by
                      mpAtmCCSoftPvcCalledIfIndex.
                      The VPI value cannot exceed the number
                      supported by the atmInterfaceMaxVciBits
                      at the ATM interface port."
                ::= { mpAtmCCSoftPvcCalledEntry 4 }

        mpAtmCCSoftPvcCalledReceiveTrafficDescrIndex  OBJECT-TYPE
                SYNTAX  AtmTrafficDescrParamIndex
                ACCESS  read-write
                STATUS  mandatory
                DESCRIPTION
                     "The value of this object identifies
                      in the ATM Traffic Descriptor Table which
                      applies to the receive direction of this Soft-PVC."
                ::= { mpAtmCCSoftPvcCalledEntry 5 }

        mpAtmCCSoftPvcCalledTransmitTrafficDescrIndex OBJECT-TYPE
                SYNTAX  AtmTrafficDescrParamIndex
                ACCESS  read-write
                STATUS  mandatory
                DESCRIPTION
                     "The value of this object identifies
                      in the ATM Traffic Descriptor Table which
                      applies to the transmit direction of this Soft-PVC."
                ::= { mpAtmCCSoftPvcCalledEntry 6 }

        mpAtmCCSoftPvcCalledTargetAddress     OBJECT-TYPE
                SYNTAX  AtmAddr
                ACCESS  read-write
                STATUS  mandatory
                DESCRIPTION
                        "The target ATM Address of this Soft PVCC.  If no
                        address is supplied, no attempts to establish the
                        Soft PVCC are initiated."
                ::= { mpAtmCCSoftPvcCalledEntry 7 }

        mpAtmCCSoftPvcCalledTargetVpi OBJECT-TYPE
                SYNTAX  INTEGER (0..4095)
                ACCESS  read-write
                STATUS  mandatory
                DESCRIPTION
                        "The VPI value of the VCL used at the target interface."
                DEFVAL { 0 }
                ::= { mpAtmCCSoftPvcCalledEntry 8 }

        mpAtmCCSoftPvcCalledTargetVci OBJECT-TYPE
                SYNTAX  INTEGER (0..65535)
                ACCESS  read-write
                STATUS  mandatory
                DESCRIPTION
                        "The VCI value of the VCL used at the target interface."
                ::= { mpAtmCCSoftPvcCalledEntry 9 }

        mpAtmCCSoftPvcCalledLastReleaseCause  OBJECT-TYPE
                SYNTAX  INTEGER(1..127)
                ACCESS  read-only
                STATUS  mandatory
                DESCRIPTION
                        "Value of the Cause field of the Cause
                        Information Element in the last RELEASE
                        signalling message received for this Soft PVCC.
                        Indicates the reason for the Release."
                ::= { mpAtmCCSoftPvcCalledEntry 10 }

        mpAtmCCSoftPvcCalledLastReleaseDiagnostic     OBJECT-TYPE
                SYNTAX  OCTET STRING (SIZE(0..8))
                ACCESS  read-only
                STATUS  mandatory
                DESCRIPTION
                        "Value of the first 8 bytes of diagnostic information
                        from the Cause field of the Cause Information Element
                        in the last RELEASE signalling message received for
                        this Soft-PVC."
                ::= { mpAtmCCSoftPvcCalledEntry 11 }

        mpAtmCCSoftPvcCalledPriority  OBJECT-TYPE
                SYNTAX  INTEGER(1..3)                               -- @001 
                ACCESS  read-write
                STATUS  mandatory
                DESCRIPTION
                     "Connection priority"
                DEFVAL { 1 }                                        -- @001 
                ::= { mpAtmCCSoftPvcCalledEntry 12 }

        mpAtmCCSoftPvcCalledCladType  OBJECT-TYPE
                SYNTAX  MpAtmCCCladType
                ACCESS  read-only
                STATUS  mandatory
                DESCRIPTION
                     "CLAD Type"
                ::= { mpAtmCCSoftPvcCalledEntry 13 }

        mpAtmCCSoftPvcCalledOriginalAddress     OBJECT-TYPE
                SYNTAX  AtmAddr
                ACCESS  read-only
                STATUS  mandatory
                DESCRIPTION
                        "The original ATM Address of this Soft PVCC.  If no
                        address is supplied, no attempts to establish the
                        Soft PVCC are initiated."
                ::= { mpAtmCCSoftPvcCalledEntry 14 }

        mpAtmCCSoftPvcCalledAdminStatus       OBJECT-TYPE
                SYNTAX  INTEGER {
                                up(1),
                                down(2)
                                }
                ACCESS  read-write
                STATUS  mandatory
                DESCRIPTION
                     "The value of this object identifies the desired
                      administrative status of this Soft-PVC.
                      The up and down states indicate that the traffic
                      flow is enabled and disabled respectively on this
                      Soft-PVC."
                DEFVAL { down }
                ::= { mpAtmCCSoftPvcCalledEntry 15 }

        mpAtmCCSoftPvcCalledOperStatus        OBJECT-TYPE
                SYNTAX  INTEGER
                ACCESS  read-only
                STATUS  mandatory
                DESCRIPTION
                     "The value of this object identifies the desired
                      operational status of this Soft-PVC."
                ::= { mpAtmCCSoftPvcCalledEntry 16 }

        mpAtmCCSoftPvcCalledPgcRequest        OBJECT-TYPE    -- @010 
                SYNTAX  INTEGER
                ACCESS  read-only
                STATUS  mandatory
                DESCRIPTION
                     "Indicates whether this PVC was configureated from
                      the PVC-Group-Cutover function.
                      The value of '0' indicates that this PVC was normal.
                      The value of '!=0' indicates that this PVC was
                      configrated form PVC-Group-Cutover function.
                       In this case, the value was indicated the PVC-Group Number"
                ::= { mpAtmCCSoftPvcCalledEntry 17 }

        mpAtmCCSoftPvcCalledCfgStatus      OBJECT-TYPE
                SYNTAX  INTEGER {
                                enable(1),
                                cancel(2),
                                delete(3),
                                unknown(4)
                                }
                ACCESS  read-write
                STATUS  mandatory
                DESCRIPTION
                        "Configuration setting start object. If this object is
                         set the setting of the configuration is started."
                DEFVAL { unknown }
                ::= { mpAtmCCSoftPvcCalledEntry 98 }

        mpAtmCCSoftPvcCalledErrInfo    OBJECT-TYPE
                SYNTAX  INTEGER
                ACCESS  read-only
                STATUS  mandatory
                DESCRIPTION
                        "Object that the configuration setting result is set up."
                ::= { mpAtmCCSoftPvcCalledEntry 99 }


--
--    
--

        mpAtmCCStatistics      OBJECT IDENTIFIER ::= { mpAtmCallCtl 4 }

--
--

mpAtmCCVpStatisticsTable OBJECT-TYPE
        SYNTAX  SEQUENCE OF MpAtmCCVpStatisticsEntry
        ACCESS  not-accessible
        STATUS  mandatory
        DESCRIPTION
                " Indicate traffic counter information per connection."
        ::= { mpAtmCCStatistics 1 }

mpAtmCCVpStatisticsEntry OBJECT-TYPE
        SYNTAX  MpAtmCCVpStatisticsEntry
        ACCESS  not-accessible
        STATUS  mandatory
        DESCRIPTION
                " Entry of traffic per connection."
        INDEX{ ifIndex, mpAtmCCVpStatVpi }
        ::= { mpAtmCCVpStatisticsTable 1 }

MpAtmCCVpStatisticsEntry ::=
        SEQUENCE {
                mpAtmCCVpStatVpi
                        INTEGER,
                mpAtmCCVpStatInCells
                        OCTET STRING,
                mpAtmCCVpStatInCellsCounters
                        Counter,
                mpAtmCCVpStatOutCells
                        OCTET STRING,
                mpAtmCCVpStatOutCellsCounters
                        Counter,
                mpAtmCCVpStatInDropCells
                        OCTET STRING,
                mpAtmCCVpStatInDropCellsCounters
                        Counter
        }

mpAtmCCVpStatVpi       OBJECT-TYPE
        SYNTAX  INTEGER
        ACCESS  not-accessible
        STATUS  mandatory
        DESCRIPTION
                "Indicate value for the specific VPI "
        ::= { mpAtmCCVpStatisticsEntry 1 }

mpAtmCCVpStatInCells       OBJECT-TYPE
        SYNTAX  OCTET STRING
        ACCESS  read-only
        STATUS  mandatory
        DESCRIPTION
                " The number of receive cells  64 bit counter"
        ::= { mpAtmCCVpStatisticsEntry 2 }

mpAtmCCVpStatInCellsCounters       OBJECT-TYPE
        SYNTAX  Counter
        ACCESS  read-only
        STATUS  mandatory
        DESCRIPTION
                " The number of receive cells  32 bit counter"
        ::= { mpAtmCCVpStatisticsEntry 3 }

mpAtmCCVpStatOutCells      OBJECT-TYPE
        SYNTAX  OCTET STRING
        ACCESS  read-only
        STATUS  mandatory
        DESCRIPTION
                " The number of transmit cells  64 bit counter"
        ::= { mpAtmCCVpStatisticsEntry 4 }

mpAtmCCVpStatOutCellsCounters      OBJECT-TYPE
        SYNTAX  Counter
        ACCESS  read-only
        STATUS  mandatory
        DESCRIPTION
                " The number of transmit cells  32 bit counter"
        ::= { mpAtmCCVpStatisticsEntry 5 }

mpAtmCCVpStatInDropCells   OBJECT-TYPE
        SYNTAX  OCTET STRING
        ACCESS  read-only
        STATUS  mandatory
        DESCRIPTION
                " The number of receive drop cells  64 bit counter "
        ::= { mpAtmCCVpStatisticsEntry 6 }

mpAtmCCVpStatInDropCellsCounters   OBJECT-TYPE
        SYNTAX  Counter
        ACCESS  read-only
        STATUS  mandatory
        DESCRIPTION
                " The number of receive drop cells  32 bit counter"
        ::= { mpAtmCCVpStatisticsEntry 7 }

--
--

mpAtmCCVcStatisticsTable OBJECT-TYPE
        SYNTAX  SEQUENCE OF MpAtmCCVcStatisticsEntry
        ACCESS  not-accessible
        STATUS  mandatory
        DESCRIPTION
                " Indicate traffic counter information per connection."
        ::= { mpAtmCCStatistics 2 }

mpAtmCCVcStatisticsEntry OBJECT-TYPE
        SYNTAX  MpAtmCCVcStatisticsEntry
        ACCESS  not-accessible
        STATUS  mandatory
        DESCRIPTION
                " Entry of traffic per connection."
        INDEX{ ifIndex, mpAtmCCVcStatVpi, mpAtmCCVcStatVci }
        ::= { mpAtmCCVcStatisticsTable 1 }

MpAtmCCVcStatisticsEntry ::=
        SEQUENCE {
                mpAtmCCVcStatVpi
                        INTEGER,
                mpAtmCCVcStatVci
                        INTEGER,
                mpAtmCCVcStatInCells
                        OCTET STRING,
                mpAtmCCVcStatInCellsCounters
                        Counter,
                mpAtmCCVcStatOutCells
                        OCTET STRING,
                mpAtmCCVcStatOutCellsCounters
                        Counter,
                mpAtmCCVcStatInDropCells
                        OCTET STRING,
                mpAtmCCVcStatInDropCellsCounters
                        Counter
        }

mpAtmCCVcStatVpi       OBJECT-TYPE
        SYNTAX  INTEGER
        ACCESS  not-accessible
        STATUS  mandatory
        DESCRIPTION
                "Indicate value for the specific VPI "
        ::= { mpAtmCCVcStatisticsEntry 1 }

mpAtmCCVcStatVci       OBJECT-TYPE
        SYNTAX  INTEGER
        ACCESS  not-accessible
        STATUS  mandatory
        DESCRIPTION
                "Indicate value for the specific VCI "
        ::= { mpAtmCCVcStatisticsEntry 2 }

mpAtmCCVcStatInCells       OBJECT-TYPE
        SYNTAX  OCTET STRING
        ACCESS  read-only
        STATUS  mandatory
        DESCRIPTION
                " The number of receive cells  64 bit counter"
        ::= { mpAtmCCVcStatisticsEntry 3 }

mpAtmCCVcStatInCellsCounters       OBJECT-TYPE
        SYNTAX  Counter
        ACCESS  read-only
        STATUS  mandatory
        DESCRIPTION
                " The number of receive cells  32 bit counter"
        ::= { mpAtmCCVcStatisticsEntry 4 }

mpAtmCCVcStatOutCells      OBJECT-TYPE
        SYNTAX  OCTET STRING
        ACCESS  read-only
        STATUS  mandatory
        DESCRIPTION
                " The number of transmit cells  64 bit counter"
        ::= { mpAtmCCVcStatisticsEntry 5 }

mpAtmCCVcStatOutCellsCounters      OBJECT-TYPE
        SYNTAX  Counter
        ACCESS  read-only
        STATUS  mandatory
        DESCRIPTION
                " The number of transmit cells  32 bit counter"
        ::= { mpAtmCCVcStatisticsEntry 6 }

mpAtmCCVcStatInDropCells   OBJECT-TYPE
        SYNTAX  OCTET STRING
        ACCESS  read-only
        STATUS  mandatory
        DESCRIPTION
                " The number of receive drop cells  64 bit counter "
        ::= { mpAtmCCVcStatisticsEntry 7 }

mpAtmCCVcStatInDropCellsCounters   OBJECT-TYPE
        SYNTAX  Counter
        ACCESS  read-only
        STATUS  mandatory
        DESCRIPTION
                " The number of receive drop cells  32 bit counter"
        ::= { mpAtmCCVcStatisticsEntry 8 }


--

mpAtmCCOuspStatisticsTable OBJECT-TYPE
        SYNTAX  SEQUENCE OF MpAtmCCOuspStatisticsEntry
        ACCESS  not-accessible
        STATUS  mandatory
        DESCRIPTION
                "Quality information by the unit of card.
                 All entrys are detected by the OUS-P."
        ::= { mpAtmCCStatistics 3 }

mpAtmCCOuspStatisticsEntry OBJECT-TYPE
        SYNTAX  MpAtmCCOuspStatisticsEntry
        ACCESS  not-accessible
        STATUS  mandatory
        DESCRIPTION
                " An entry of mpAtmCCOuspStatisticsTable."
        INDEX{ mpAtmCCOuspStatIndex }
        ::= { mpAtmCCOuspStatisticsTable 1 }

MpAtmCCOuspStatisticsEntry ::=
        SEQUENCE {
                mpAtmCCOuspStatIndex
                        INTEGER,
                mpAtmCCOuspStatRcvCrcErrCellsCounters
                        Counter,
                mpAtmCCOuspStatSendOfifoFullCounters
                        Counter,
                mpAtmCCOuspStatRcvBufOverCounters
                        Counter,
                mpAtmCCOuspStatRcvUnknownCellsCounters        --@006
                        Counter,
                mpAtmCCOuspStatRcvInvalidCellsCounters
                        Counter,
                mpAtmCCOuspStatSendScheduleErrorCounters
                        Counter,
                mpAtmCCOuspStatRcvScheduleErrorCounters
                        Counter,
                mpAtmCCOuspStatSendInvalidCdvCounters
                        Counter
        }

mpAtmCCOuspStatIndex       OBJECT-TYPE
        SYNTAX  INTEGER
        ACCESS  not-accessible
        STATUS  mandatory
        DESCRIPTION
                "The index value at this table. It consist of card number."
        ::= { mpAtmCCOuspStatisticsEntry 1 }

mpAtmCCOuspStatRcvCrcErrCellsCounters       OBJECT-TYPE
        SYNTAX  Counter
        ACCESS  read-only
        STATUS  mandatory
        DESCRIPTION
                "The number of OAM cells received by the port with CRC errors."
        ::= { mpAtmCCOuspStatisticsEntry 2 }

mpAtmCCOuspStatSendOfifoFullCounters       OBJECT-TYPE
        SYNTAX  Counter
        ACCESS  read-only
        STATUS  mandatory
        DESCRIPTION
                "The number of cells discarded due to Out-FIFO overflow."
        ::= { mpAtmCCOuspStatisticsEntry 3 }

mpAtmCCOuspStatRcvBufOverCounters       OBJECT-TYPE
        SYNTAX  Counter
        ACCESS  read-only
        STATUS  mandatory
        DESCRIPTION
                "The number of overflow cells at the reveive buffer."
        ::= { mpAtmCCOuspStatisticsEntry 4 }

mpAtmCCOuspStatRcvUnknownCellsCounters       OBJECT-TYPE         --@006
        SYNTAX  Counter
        ACCESS  read-only
        STATUS  mandatory
        DESCRIPTION
                "The number of cells received by the port with unknown cells."
        ::= { mpAtmCCOuspStatisticsEntry 5 }

mpAtmCCOuspStatRcvInvalidCellsCounters       OBJECT-TYPE
        SYNTAX  Counter
        ACCESS  read-only
        STATUS  mandatory
        DESCRIPTION
                "The number of cells received by the port with invalid cells."
        ::= { mpAtmCCOuspStatisticsEntry 6 }

mpAtmCCOuspStatSendScheduleErrorCounters       OBJECT-TYPE
        SYNTAX  Counter
        ACCESS  read-only
        STATUS  mandatory
        DESCRIPTION
                "The number of transmission cells discaded due to fail
                 the scheduling"
        ::= { mpAtmCCOuspStatisticsEntry 7 }

mpAtmCCOuspStatRcvScheduleErrorCounters       OBJECT-TYPE
        SYNTAX  Counter
        ACCESS  read-only
        STATUS  mandatory
        DESCRIPTION
                "The number of received cells discaded due to fail
                 the scheduling"
        ::= { mpAtmCCOuspStatisticsEntry 8 }

mpAtmCCOuspStatSendInvalidCdvCounters       OBJECT-TYPE
        SYNTAX  Counter
        ACCESS  read-only
        STATUS  mandatory
        DESCRIPTION
                "The number of un-scheduling cells due to invalid CDV."
        ::= { mpAtmCCOuspStatisticsEntry 9 }


--
--

mpAtmCCPhyStatisticsTable OBJECT-TYPE
        SYNTAX  SEQUENCE OF MpAtmCCPhyStatisticsEntry
        ACCESS  not-accessible
        STATUS  mandatory
        DESCRIPTION
                "Quality information by the unit of port.
                 All entrys are detected by the PHY.
                 This table are supports for ATM CARDs
                 NOTE:ATM CARD
                      ATM-S155, ATM-M155, 2TRK-45, 2TRK6.3I,
                      ATRK-1.5I, ATRK-192K, 2UNI-VMC, 4ATM-25"
        ::= { mpAtmCCStatistics 4 }

mpAtmCCPhyStatisticsEntry OBJECT-TYPE
        SYNTAX  MpAtmCCPhyStatisticsEntry
        ACCESS  not-accessible
        STATUS  mandatory
        DESCRIPTION
                " An entry of mpAtmCCPhyStatisticsTable."
        INDEX{ ifIndex }
        ::= { mpAtmCCPhyStatisticsTable 1 }

MpAtmCCPhyStatisticsEntry ::=
        SEQUENCE {
                mpAtmCCPhyStatTmtCellsCounters
                        Counter,
                mpAtmCCPhyStatRcvCellsCounters
                        Counter,
                mpAtmCCPhyStatCorrectHecErrCounters
                        Counter,
                mpAtmCCPhyStatUncorrectHecErrCounters
                        Counter,
                mpAtmCCPhyStatB1ErrCounters
                        Counter,
                mpAtmCCPhyStatB2ErrCounters
                        Counter,
                mpAtmCCPhyStatB3ErrCounters
                        Counter,
                mpAtmCCPhyStatFebeCounters
                        Counter,
                mpAtmCCPhyStatSymbolErrCounters
                        Counter,
                mpAtmCCPhyStatParityErrCounters
                        Counter
        }

mpAtmCCPhyStatTmtCellsCounters       OBJECT-TYPE
        SYNTAX  Counter
        ACCESS  read-only
        STATUS  mandatory
        DESCRIPTION
                "The number of cells transmitted regardless of error status."
        ::= { mpAtmCCPhyStatisticsEntry 1 }

mpAtmCCPhyStatRcvCellsCounters       OBJECT-TYPE
        SYNTAX  Counter
        ACCESS  read-only
        STATUS  mandatory
        DESCRIPTION
                "The number of cells received regardless of error status"
        ::= { mpAtmCCPhyStatisticsEntry 2 }

mpAtmCCPhyStatCorrectHecErrCounters       OBJECT-TYPE
        SYNTAX  Counter
        ACCESS  read-only
        STATUS  mandatory
        DESCRIPTION
                "The number of cells reveived by the port with correctable
                 HEC error.
                 NOTE: At the 4ATM-25 card, this object incudeing the
                       mpAtmCCPhyUncountCorrectHecErrCounters."
        ::= { mpAtmCCPhyStatisticsEntry 3 }

mpAtmCCPhyStatUncorrectHecErrCounters       OBJECT-TYPE
        SYNTAX  Counter
        ACCESS  read-only
        STATUS  mandatory
        DESCRIPTION
                "The number of cells reveived by the port with un-correctable
                 HEC error.
                   NOTE: At the 4ATM-25 card, this object is always ZERO."
        ::= { mpAtmCCPhyStatisticsEntry 4 }

mpAtmCCPhyStatB1ErrCounters       OBJECT-TYPE
        SYNTAX  Counter
        ACCESS  read-only
        STATUS  mandatory
        DESCRIPTION
                "The number of cells with B1 error.
                   NOTE: At the 4ATM-25 card, this object is always ZERO."
        ::= { mpAtmCCPhyStatisticsEntry 5 }

mpAtmCCPhyStatB2ErrCounters       OBJECT-TYPE
        SYNTAX  Counter
        ACCESS  read-only
        STATUS  mandatory
        DESCRIPTION
                "The number of cells with B2 error.
                 NOTE: This object is ATM-S155 and ATM-M155 only.
                       Other cards are always ZERO."
        ::= { mpAtmCCPhyStatisticsEntry 6 }

mpAtmCCPhyStatB3ErrCounters       OBJECT-TYPE
        SYNTAX  Counter
        ACCESS  read-only
        STATUS  mandatory
        DESCRIPTION
                "The number of cells with B3 error
                 NOTE: This object is ATM-S155 and ATM-M155 only.
                       Other cards are always ZERO."
        ::= { mpAtmCCPhyStatisticsEntry 7 }


mpAtmCCPhyStatFebeCounters       OBJECT-TYPE
        SYNTAX  Counter
        ACCESS  read-only
        STATUS  mandatory
        DESCRIPTION
                "The number of cells with FEBE error.
                   NOTE: At the 4ATM-25 card, this object is always ZERO."
        ::= { mpAtmCCPhyStatisticsEntry 8 }

mpAtmCCPhyStatSymbolErrCounters       OBJECT-TYPE
        SYNTAX  Counter
        ACCESS  read-only
        STATUS  mandatory
        DESCRIPTION
                "The number of cells with symbol error.
                 NOTE: This object is 4ATM-25 only.
                       Other cards are always ZERO."
        ::= { mpAtmCCPhyStatisticsEntry 9 }

mpAtmCCPhyStatParityErrCounters       OBJECT-TYPE
        SYNTAX  Counter
        ACCESS  read-only
        STATUS  mandatory
        DESCRIPTION
                "The number of cells with parity error.
                   NOTE: At the 4ATM-25 card, this object is always ZERO."
        ::= { mpAtmCCPhyStatisticsEntry 10 }


--
--

mpAtmCCPortAlarmStatisticsTable OBJECT-TYPE
        SYNTAX  SEQUENCE OF MpAtmCCPortAlarmStatisticsEntry
        ACCESS  not-accessible
        STATUS  mandatory
        DESCRIPTION
                "Table of port alarm infomation."
        ::= { mpAtmCCStatistics 5 }

mpAtmCCPortAlarmStatisticsEntry OBJECT-TYPE
        SYNTAX  MpAtmCCPortAlarmStatisticsEntry
        ACCESS  not-accessible
        STATUS  mandatory
        DESCRIPTION
                " An entry of mpAtmCCPortAlarmStatisticsTable."
        INDEX{ ifIndex }
        ::= { mpAtmCCPortAlarmStatisticsTable 1 }

MpAtmCCPortAlarmStatisticsEntry ::=
        SEQUENCE {
                mpAtmCCPortAlarmStatRedLosCounters
                        Counter,
                mpAtmCCPortAlarmStatRedLofCounters
                        Counter,
                mpAtmCCPortAlarmStatRedMsAisCounters
                        Counter,
                mpAtmCCPortAlarmStatRedLopCounters
                        Counter,
                mpAtmCCPortAlarmStatRedPAisCounters
                        Counter,
                mpAtmCCPortAlarmStatRedLocCounters
                        Counter,
                mpAtmCCPortAlarmStatRedResetCounters
                        Counter,
                mpAtmCCPortAlarmStatRedCcRedCounters
                        Counter,
                mpAtmCCPortAlarmStatRedOofCounters
                        Counter,
                mpAtmCCPortAlarmStatRedAisCounters
                        Counter,
                mpAtmCCPortAlarmStatRedPOofCounters
                        Counter,
                mpAtmCCPortAlarmStatRedBadSigCounters
                        Counter,
                mpAtmCCPortAlarmStatRedLcdCounters
                        Counter,
                mpAtmCCPortAlarmStatRedLinkAisCounters
                        Counter,
                mpAtmCCPortAlarmStatRedInfo0Counters
                        Counter,
                mpAtmCCPortAlarmStatYelMsRdiCounters
                        Counter,
                mpAtmCCPortAlarmStatYelPRdiCounters
                        Counter,
                mpAtmCCPortAlarmStatYelCcYelCounters
                        Counter,
                mpAtmCCPortAlarmStatYelRaiCounters
                        Counter,
                mpAtmCCPortAlarmStatYelPRaiCounters
                        Counter,
                mpAtmCCPortAlarmStatYelInfo2Counters
                        Counter
        }

mpAtmCCPortAlarmStatRedLosCounters       OBJECT-TYPE
        SYNTAX  Counter
        ACCESS  read-only
        STATUS  mandatory
        DESCRIPTION
                "Total number of LOS alarm detected by HW.
                 NOTE: This object is
                          ATM-S155, ATM-M155, 2ATM-45,
                          2UNI-VMC, 2TRK-6.3I, 4TRK-1.5I
                       only.   Other cards are always ZERO."
        ::= { mpAtmCCPortAlarmStatisticsEntry 1 }

mpAtmCCPortAlarmStatRedLofCounters       OBJECT-TYPE
        SYNTAX  Counter
        ACCESS  read-only
        STATUS  mandatory
        DESCRIPTION
                "Total number of LOF alarm detected by HW.
                 NOTE: This object is
                          ATM-S155, ATM-M155, 2TRK-6.3I, 4TRK-1.5I
                       only.   Other cards are always ZERO."
        ::= { mpAtmCCPortAlarmStatisticsEntry 2 }

mpAtmCCPortAlarmStatRedMsAisCounters       OBJECT-TYPE
        SYNTAX  Counter
        ACCESS  read-only
        STATUS  mandatory
        DESCRIPTION
                "Total number of MS-AIS alarm detected by HW.
                 NOTE: This object is
                          ATM-S155, ATM-M155
                       only.   Other cards are always ZERO."
        ::= { mpAtmCCPortAlarmStatisticsEntry 3 }

mpAtmCCPortAlarmStatRedLopCounters       OBJECT-TYPE
        SYNTAX  Counter
        ACCESS  read-only
        STATUS  mandatory
        DESCRIPTION
                "Total number of LOP alarm detected by HW.
                 NOTE: This object is
                          ATM-S155, ATM-M155
                       only.   Other cards are always ZERO."
        ::= { mpAtmCCPortAlarmStatisticsEntry 4 }

mpAtmCCPortAlarmStatRedPAisCounters       OBJECT-TYPE
        SYNTAX  Counter
        ACCESS  read-only
        STATUS  mandatory
        DESCRIPTION
                "Total number of P-AIS alarm detected by HW.
                 NOTE: This object is
                          ATM-S155, ATM-M155
                       only.   Other cards are always ZERO."
        ::= { mpAtmCCPortAlarmStatisticsEntry 5 }

mpAtmCCPortAlarmStatRedLocCounters       OBJECT-TYPE
        SYNTAX  Counter
        ACCESS  read-only
        STATUS  mandatory
        DESCRIPTION
                "Total number of LOC alarm detected by HW.
                 NOTE: This object is
                          ATM-S155, ATM-M155
                       only.   Other cards are always ZERO."
        ::= { mpAtmCCPortAlarmStatisticsEntry 6 }

mpAtmCCPortAlarmStatRedResetCounters       OBJECT-TYPE
        SYNTAX  Counter
        ACCESS  read-only
        STATUS  mandatory
        DESCRIPTION
                "Total number of Reset alarm detected by HW.
                 NOTE: This object is
                          ATM-S155, ATM-M155
                       only.   Other cards are always ZERO."
        ::= { mpAtmCCPortAlarmStatisticsEntry 7 }

mpAtmCCPortAlarmStatRedCcRedCounters       OBJECT-TYPE
        SYNTAX  Counter
        ACCESS  read-only
        STATUS  mandatory
        DESCRIPTION
                "Total number of CC-RED alarm detected by HW.
                 NOTE: This object is ATM CARDs only."
        ::= { mpAtmCCPortAlarmStatisticsEntry 8 }

mpAtmCCPortAlarmStatRedOofCounters       OBJECT-TYPE
        SYNTAX  Counter
        ACCESS  read-only
        STATUS  mandatory
        DESCRIPTION
                "Total number of OOF alarm detected by HW.
                 NOTE: This object is 2ATM-45 only.
                       Other cards are always ZERO."
        ::= { mpAtmCCPortAlarmStatisticsEntry 9 }

mpAtmCCPortAlarmStatRedAisCounters       OBJECT-TYPE
        SYNTAX  Counter
        ACCESS  read-only
        STATUS  mandatory
        DESCRIPTION
                "Total number of AIS alarm detected by HW.
                 NOTE: This object is
                          2ATM-45, 2TRK-6.3I, 4TRK-1.5I
                       only.   Other cards are always ZERO."
        ::= { mpAtmCCPortAlarmStatisticsEntry 10 }

mpAtmCCPortAlarmStatRedPOofCounters       OBJECT-TYPE
        SYNTAX  Counter
        ACCESS  read-only
        STATUS  mandatory
        DESCRIPTION
                "Total number of P-OOF alarm detected by HW.
                 NOTE: This object is 2ATM-45, 2TRK-6.3I, 4TRK-1.5I
                       only.   Other cards are always ZERO."
        ::= { mpAtmCCPortAlarmStatisticsEntry 11 }

mpAtmCCPortAlarmStatRedBadSigCounters       OBJECT-TYPE
        SYNTAX  Counter
        ACCESS  read-only
        STATUS  mandatory
        DESCRIPTION
                "Total number of Bad-sig alarm detected by HW.
                 NOTE: This object is 4ATM-45 only.
                       Other cards are always ZERO."
        ::= { mpAtmCCPortAlarmStatisticsEntry 12 }

mpAtmCCPortAlarmStatRedLcdCounters       OBJECT-TYPE
        SYNTAX  Counter
        ACCESS  read-only
        STATUS  mandatory
        DESCRIPTION
                "Total number of LCD alarm detected by HW.
                 NOTE: This object is
                          2UNI-VMC, 2TRK-6.3I, 4TRK-1.5I, 2TRK-192K
                       only.   Other cards are always ZERO."
        ::= { mpAtmCCPortAlarmStatisticsEntry 13 }

mpAtmCCPortAlarmStatRedLinkAisCounters       OBJECT-TYPE
        SYNTAX  Counter
        ACCESS  read-only
        STATUS  mandatory
        DESCRIPTION
                "Total number of LINK-AIS alarm detected by HW.
                 NOTE: This object is
                          2TRK-6.3I, 4TRK-1.5I, 2TRK-192K
                       only.   Other cards are always ZERO."
        ::= { mpAtmCCPortAlarmStatisticsEntry 14 }

mpAtmCCPortAlarmStatRedInfo0Counters       OBJECT-TYPE
        SYNTAX  Counter
        ACCESS  read-only
        STATUS  mandatory
        DESCRIPTION
                "Total number of INDO0 alarm detected by HW.
                 NOTE: This object is 2TRK-192KI only.
                       Other cards are always ZERO."
        ::= { mpAtmCCPortAlarmStatisticsEntry 15 }

mpAtmCCPortAlarmStatYelMsRdiCounters       OBJECT-TYPE
        SYNTAX  Counter
        ACCESS  read-only
        STATUS  mandatory
        DESCRIPTION
                "Total number of MS-RDI alarm detected by HW.
                 NOTE: This object is
                          ATM-S155, ATM-M155
                       only.   Other cards are always ZERO."
        ::= { mpAtmCCPortAlarmStatisticsEntry 16 }

mpAtmCCPortAlarmStatYelPRdiCounters       OBJECT-TYPE
        SYNTAX  Counter
        ACCESS  read-only
        STATUS  mandatory
        DESCRIPTION
                "Total number of P-RDI alarm detected by HW.
                 NOTE: This object is
                          ATM-S155, ATM-M155
                       only.   Other cards are always ZERO."
        ::= { mpAtmCCPortAlarmStatisticsEntry 17 }

mpAtmCCPortAlarmStatYelCcYelCounters       OBJECT-TYPE
        SYNTAX  Counter
        ACCESS  read-only
        STATUS  mandatory
        DESCRIPTION
                "Total number of CC-YEL alarm detected by HW.
                 NOTE: This object is ATM CARDs only."
        ::= { mpAtmCCPortAlarmStatisticsEntry 18 }

mpAtmCCPortAlarmStatYelRaiCounters       OBJECT-TYPE
        SYNTAX  Counter
        ACCESS  read-only
        STATUS  mandatory
        DESCRIPTION
                "Total number of RAI alarm detected by HW.
                 NOTE: This object is
                          2ATM-45, 2TRK-6.3I, 4TRK-1.5I
                       only.   Other cards are always ZERO."
        ::= { mpAtmCCPortAlarmStatisticsEntry 19 }

mpAtmCCPortAlarmStatYelPRaiCounters       OBJECT-TYPE
        SYNTAX  Counter
        ACCESS  read-only
        STATUS  mandatory
        DESCRIPTION
                "Total number of P-RAI alarm detected by HW.
                 NOTE: This object is 2ATM-45 only.
                       Other cards are always ZERO."
        ::= { mpAtmCCPortAlarmStatisticsEntry 20 }

mpAtmCCPortAlarmStatYelInfo2Counters       OBJECT-TYPE
        SYNTAX  Counter
        ACCESS  read-only
        STATUS  mandatory
        DESCRIPTION
                "Total number of INFO2 alarm detected by HW.
                 NOTE: This object is 2TRK-192KI only.
                       Other cards are always ZERO."
        ::= { mpAtmCCPortAlarmStatisticsEntry 21 }


--
--

mpAtmCCVpTunnellingStatisticsTable OBJECT-TYPE
        SYNTAX  SEQUENCE OF MpAtmCCVpTunnellingStatisticsEntry
        ACCESS  not-accessible
        STATUS  mandatory
        DESCRIPTION
                "This table indicate traffic counter information
                 per VP-tunnelling."
        ::= { mpAtmCCStatistics 6 }

mpAtmCCVpTunnellingStatisticsEntry OBJECT-TYPE
        SYNTAX  MpAtmCCVpTunnellingStatisticsEntry
        ACCESS  not-accessible
        STATUS  mandatory
        DESCRIPTION
                " An entry of mpAtmCCVpTunnellingStatisticsTable."
        INDEX{ ifIndex }
        ::= { mpAtmCCVpTunnellingStatisticsTable 1 }

MpAtmCCVpTunnellingStatisticsEntry ::=
        SEQUENCE {
                mpAtmCCVpTunStatTmtCellsCounters
                        Counter,
                mpAtmCCVpTunStatRcvCellsCounters
                        Counter
        }

mpAtmCCVpTunStatTmtCellsCounters       OBJECT-TYPE
        SYNTAX  Counter
        ACCESS  read-only
        STATUS  mandatory
        DESCRIPTION
                "The number of cells transmitted regardless of error status."
        ::= { mpAtmCCVpTunnellingStatisticsEntry 1 }

mpAtmCCVpTunStatRcvCellsCounters       OBJECT-TYPE
        SYNTAX  Counter
        ACCESS  read-only
        STATUS  mandatory
        DESCRIPTION
                "The number of cells received regardless of error status"
        ::= { mpAtmCCVpTunnellingStatisticsEntry 2 }


--
--

mpAtmCCVccStatisticsRegTable OBJECT-TYPE
        SYNTAX  SEQUENCE OF MpAtmCCVccStatisticsRegEntry
        ACCESS  not-accessible
        STATUS  mandatory
        DESCRIPTION
                " Indicate traffic counter information per connection."
        ::= { mpAtmCCStatistics 7 }

mpAtmCCVccStatisticsRegEntry OBJECT-TYPE
        SYNTAX  MpAtmCCVccStatisticsRegEntry
        ACCESS  not-accessible
        STATUS  mandatory
        DESCRIPTION
                " Entry of traffic per connection."
        INDEX{ ifIndex, mpAtmCCVccStatRegVpi, mpAtmCCVccStatRegVci }
        ::= { mpAtmCCVccStatisticsRegTable 1 }

MpAtmCCVccStatisticsRegEntry ::=
        SEQUENCE {
                mpAtmCCVccStatRegVpi
                        INTEGER,
                mpAtmCCVccStatRegVci
                        INTEGER,
                mpAtmCCVccStatRegInCellsCounters
                        Counter,
                mpAtmCCVccStatRegOutCellsCounters
                        Counter,
                mpAtmCCVccStatRegStatus
                        INTEGER,
                mpAtmCCVccStatRegErrInfo
                        INTEGER
        }

mpAtmCCVccStatRegVpi       OBJECT-TYPE
        SYNTAX  INTEGER
        ACCESS  not-accessible
        STATUS  mandatory
        DESCRIPTION
                "Indicate value for the specific VPI "
        ::= { mpAtmCCVccStatisticsRegEntry 1 }

mpAtmCCVccStatRegVci       OBJECT-TYPE
        SYNTAX  INTEGER
        ACCESS  not-accessible
        STATUS  mandatory
        DESCRIPTION
                "Indicate value for the specific VCI "
        ::= { mpAtmCCVccStatisticsRegEntry 2 }

mpAtmCCVccStatRegInCellsCounters       OBJECT-TYPE
        SYNTAX  Counter
        ACCESS  read-only
        STATUS  mandatory
        DESCRIPTION
                " The number of receive cells"
        ::= { mpAtmCCVccStatisticsRegEntry 3 }

mpAtmCCVccStatRegOutCellsCounters      OBJECT-TYPE
        SYNTAX  Counter
        ACCESS  read-only
        STATUS  mandatory
        DESCRIPTION
                " The number of transmit cells"
        ::= { mpAtmCCVccStatisticsRegEntry 4 }

mpAtmCCVccStatRegStatus    OBJECT-TYPE
        SYNTAX  INTEGER{
                        start(1),
                        stop(2)
                       }
        ACCESS  read-write
        STATUS  mandatory
        DESCRIPTION
                "This variable indicates the registratoin status.
                 - 'start', which indicates that start and collecting the
                    taffic information.
                 - 'stop', which indicates that stopn and delete the traffic
                   information."
        ::= { mpAtmCCVccStatisticsRegEntry 5 }

mpAtmCCVccStatRegErrInfo    OBJECT-TYPE
        SYNTAX  INTEGER
        ACCESS  read-only
        STATUS  mandatory
        DESCRIPTION
            "Indicats the result of setting to the
             mpAtmCCVccStatRegStatus."
        ::= { mpAtmCCVccStatisticsRegEntry 99 }



--
--

        mpAtmCCResourceControl      OBJECT IDENTIFIER ::= { mpAtmCallCtl 5 }

--
--

mpAtmCCPortResourceInfomationTable OBJECT-TYPE
        SYNTAX  SEQUENCE OF MpAtmCCPortResourceInfomationEntry
        ACCESS  not-accessible
        STATUS  mandatory
        DESCRIPTION
                "This table indicate the resource infomation at the
                 ATM port.
                 NOTE:
                   This table is supported the physical port only."
        ::= { mpAtmCCResourceControl 1 }

mpAtmCCPortResourceInfomationEntry OBJECT-TYPE
        SYNTAX  MpAtmCCPortResourceInfomationEntry
        ACCESS  not-accessible
        STATUS  mandatory
        DESCRIPTION
                " Entry of mpAtmCCPortResourceInfomationTable."
        INDEX{ ifIndex }
        ::= { mpAtmCCPortResourceInfomationTable 1 }

MpAtmCCPortResourceInfomationEntry ::=
        SEQUENCE {
                mpAtmCCPortResInfoPortSpeed
                        Gauge,
                mpAtmCCPortResInfoMaxVpiBits
                        INTEGER,
                mpAtmCCPortResInfoMaxVciBits
                        INTEGER,
                mpAtmCCPortResInfoMaxVPC
                        INTEGER,
                mpAtmCCPortResInfoMaxVCC
                        INTEGER,
                mpAtmCCPortResInfoMaxSvpcVpi
                        INTEGER,
                mpAtmCCPortResInfoMaxSvccVpi
                        INTEGER,
                mpAtmCCPortResInfoMinSvccVci
                        INTEGER,
                mpAtmCCPortResInfoShaperKind
                        INTEGER,
                mpAtmCCPortResInfoVpTunnellingConfig
                        INTEGER,
                mpAtmCCPortResInfoSvccVciHuntWay
                        INTEGER,
                mpAtmCCPortResInfoVpiCounters
                        Counter,
                mpAtmCCPortResInfoVpcCounters
                        Counter,
                mpAtmCCPortResInfoVccCounters
                        Counter
        }

mpAtmCCPortResInfoPortSpeed       OBJECT-TYPE
        SYNTAX  Gauge
        ACCESS  read-only
        STATUS  mandatory
        DESCRIPTION
                "The port's bandwidth in bit per second at this ATM port."
        ::= { mpAtmCCPortResourceInfomationEntry 1 }

mpAtmCCPortResInfoMaxVpiBits       OBJECT-TYPE
        SYNTAX  INTEGER
        ACCESS  read-only
        STATUS  mandatory
        DESCRIPTION
                "The number of VPI bits at this ATM port."
        ::= { mpAtmCCPortResourceInfomationEntry 2 }

mpAtmCCPortResInfoMaxVciBits       OBJECT-TYPE
        SYNTAX  INTEGER
        ACCESS  read-only
        STATUS  mandatory
        DESCRIPTION
                "The number of VCI bits at this ATM port."
        ::= { mpAtmCCPortResourceInfomationEntry 3 }

mpAtmCCPortResInfoMaxVPC       OBJECT-TYPE
        SYNTAX  INTEGER
        ACCESS  read-only
        STATUS  mandatory
        DESCRIPTION
                "The maximum number of VPCs ( PVPs and SVPs )
                 supported at this port."
        ::= { mpAtmCCPortResourceInfomationEntry 4 }

mpAtmCCPortResInfoMaxVCC       OBJECT-TYPE
        SYNTAX  INTEGER
        ACCESS  read-only
        STATUS  mandatory
        DESCRIPTION
                "The maximum number of VCCs ( PVCs and SVCs )
                 supported at this port."
        ::= { mpAtmCCPortResourceInfomationEntry 5 }

mpAtmCCPortResInfoMaxSvpcVpi       OBJECT-TYPE
        SYNTAX  INTEGER
        ACCESS  read-only
        STATUS  mandatory
        DESCRIPTION
                "The maximum VPI that the signaling stack on
                 the ATM interface is configured to support for
                 allocation to switched virtual path connections."
        ::= { mpAtmCCPortResourceInfomationEntry 6 }

mpAtmCCPortResInfoMaxSvccVpi       OBJECT-TYPE
        SYNTAX  INTEGER
        ACCESS  read-only
        STATUS  mandatory
        DESCRIPTION
                "The maximum VPI that the signaling stack on
                 the ATM interface is configured to support for
                 allocation to switched virtual channel connections."
        ::= { mpAtmCCPortResourceInfomationEntry 7 }

mpAtmCCPortResInfoMinSvccVci       OBJECT-TYPE
        SYNTAX  INTEGER
        ACCESS  read-only
        STATUS  mandatory
        DESCRIPTION
                "The minimum VPI that the signalling stack is
                 configured to support for allocation to switched
                 virtual channel connections."
        ::= { mpAtmCCPortResourceInfomationEntry 8 }

mpAtmCCPortResInfoShaperKind       OBJECT-TYPE
        SYNTAX  INTEGER{
                    none(1),     -- 
                    vp(2),       -- 
                    vc(3),       -- 
                    vpAndVc(4)   -- 
                }
        ACCESS  read-only
        STATUS  mandatory
        DESCRIPTION
                "The kind of shaper at this port."
        ::= { mpAtmCCPortResourceInfomationEntry 9 }

mpAtmCCPortResInfoVpTunnellingConfig       OBJECT-TYPE
        SYNTAX  INTEGER{
                    notConfigured(1),  -- 
                    configured(2)      -- 
                }
        ACCESS  read-only
        STATUS  mandatory
        DESCRIPTION
                "Indicates whether the vp-tunnelling is configered
                 at this port."
        --
        ::= { mpAtmCCPortResourceInfomationEntry 10 }


mpAtmCCPortResInfoSvccVciHuntWay       OBJECT-TYPE
        SYNTAX  INTEGER{
                    low2high(1),  --
                    high2low(2)   --
                }
        ACCESS  read-only
        STATUS  mandatory
        DESCRIPTION
                "This value indicates the way of VCI use at the SVCs.
                 The value low2high indicates that hunt the lowest not-used
                 VCI when received the SETUP message.
                 The value low2high indicates that hunt the highest not-used
                 VCI when received the SETUP message."
        --
        ::= { mpAtmCCPortResourceInfomationEntry 11 }

mpAtmCCPortResInfoVpiCounters       OBJECT-TYPE
        SYNTAX  Counter
        ACCESS  read-only
        STATUS  mandatory
        DESCRIPTION
                "The number of using VPIs at this port."
        --
        ::= { mpAtmCCPortResourceInfomationEntry 12 }

mpAtmCCPortResInfoVpcCounters       OBJECT-TYPE
        SYNTAX  Counter
        ACCESS  read-only
        STATUS  mandatory
        DESCRIPTION
                "The number of VPCs ( PVPs and SVPs )
                 established at this port."
        --
        ::= { mpAtmCCPortResourceInfomationEntry 13 }

mpAtmCCPortResInfoVccCounters       OBJECT-TYPE
        SYNTAX  Counter
        ACCESS  read-only
        STATUS  mandatory
        DESCRIPTION
                "The number of VCCs ( PVCs and SVCs )
                 established at this port."
        --
        ::= { mpAtmCCPortResourceInfomationEntry 14 }


--
--                  @001
--

mpAtmCCPortBandwidthInfomationTable OBJECT-TYPE
        SYNTAX  SEQUENCE OF MpAtmCCPortBandwidthInfomationEntry
        ACCESS  not-accessible
        STATUS  mandatory
        DESCRIPTION
                "This table indicate that infom the bandwidth at
                 the ATM port."
        --
        ::= { mpAtmCCResourceControl 2 }

mpAtmCCPortBandwidthInfomationEntry OBJECT-TYPE
        SYNTAX  MpAtmCCPortBandwidthInfomationEntry
        ACCESS  not-accessible
        STATUS  mandatory
        DESCRIPTION
                " Entry of mpAtmCCPortBandwidthInfomationTable."
        --
        INDEX{ ifIndex, mpAtmCCPortBwInfoVpi }                   --
        ::= { mpAtmCCPortBandwidthInfomationTable 1 }

MpAtmCCPortBandwidthInfomationEntry ::=
        SEQUENCE {
                mpAtmCCPortBwInfoVpi                             --
                        INTEGER,                                 --
                mpAtmCCPortBwInfoRawBandwidthBps
                        INTEGER,
                mpAtmCCPortBwInfoRawBandwidthCps
                        INTEGER,
                mpAtmCCPortBwInfoTmitUsedBwCps
                        INTEGER,
                mpAtmCCPortBwInfoRcvUsedBwCps
                        INTEGER,
                mpAtmCCPortBwInfoVciCounters
                        Counter
        }

mpAtmCCPortBwInfoVpi    OBJECT-TYPE                       --
        SYNTAX  INTEGER
        ACCESS  not-accessible
        STATUS  mandatory
        DESCRIPTION
                "A index value at this table."
        --
        ::= { mpAtmCCPortBandwidthInfomationEntry 1 }

mpAtmCCPortBwInfoRawBandwidthBps       OBJECT-TYPE
        SYNTAX  INTEGER
        ACCESS  read-only
        STATUS  mandatory
        DESCRIPTION
                "Adminsitratively desired bandwidth size
                 in kilo bit per second for this ATM port."
        --
        ::= { mpAtmCCPortBandwidthInfomationEntry 2 }   --

mpAtmCCPortBwInfoRawBandwidthCps       OBJECT-TYPE
        SYNTAX  INTEGER
        ACCESS  read-only
        STATUS  mandatory
        DESCRIPTION
                "Adminsitratively desired bandwidth size
                 in cell per second for this ATM port."
        --
        ::= { mpAtmCCPortBandwidthInfomationEntry 3 }   --

mpAtmCCPortBwInfoTmitUsedBwCps       OBJECT-TYPE
        SYNTAX  INTEGER
        ACCESS  read-only
        STATUS  mandatory
        DESCRIPTION
                "The current using transmission bandwidth value ( total of
                 assigned bandwidth for each connections ) in cell per
                 second for this ATM port."
        --
        ::= { mpAtmCCPortBandwidthInfomationEntry 4 }   --

mpAtmCCPortBwInfoRcvUsedBwCps       OBJECT-TYPE
        SYNTAX  INTEGER
        ACCESS  read-only
        STATUS  mandatory
        DESCRIPTION
                "The current using receved bandwidth value ( total of
                 assigned bandwidth for each connections ) in cell per
                 second for this ATM port."
        --
        ::= { mpAtmCCPortBandwidthInfomationEntry 5 }   --

mpAtmCCPortBwInfoVciCounters       OBJECT-TYPE
        SYNTAX  INTEGER
        ACCESS  read-only
        STATUS  mandatory
        DESCRIPTION
                "The number of using VCIs at this port."
        --
        ::= { mpAtmCCPortBandwidthInfomationEntry 6 }   --


--
--
--

mpAtmCCBwInfoPortTable OBJECT-TYPE
        SYNTAX  SEQUENCE OF MpAtmCCBwInfoPortEntry
        ACCESS  not-accessible
        STATUS  mandatory
        DESCRIPTION
                "This table indicate the resource infomation at the
                 ATM port and vp-tunneling port"
        --
        ::= { mpAtmCCResourceControl 3 }

mpAtmCCBwInfoPortEntry OBJECT-TYPE
        SYNTAX  MpAtmCCBwInfoPortEntry
        ACCESS  not-accessible
        STATUS  mandatory
        DESCRIPTION
                " Entry of mpAtmCCBwInfoPortTable."
        --
        INDEX{ ifIndex }
        ::= { mpAtmCCBwInfoPortTable 1 }

MpAtmCCBwInfoPortEntry ::=
        SEQUENCE {
                mpAtmCCBwInfoPortRawBandwidthBps
                        INTEGER,
                mpAtmCCBwInfoPortRawBandwidthCps
                        INTEGER,
                mpAtmCCBwInfoPortTmitUsedBwCps
                        INTEGER,
                mpAtmCCBwInfoPortRcvUsedBwCps
                        INTEGER,
                mpAtmCCBwInfoPortTmitRemainBwCps
                        INTEGER,
                mpAtmCCBwInfoPortRcvRemainBwCps
                        INTEGER,
                mpAtmCCBwInfoPortVpTunneling
                        INTEGER
        }

mpAtmCCBwInfoPortRawBandwidthBps    OBJECT-TYPE
        SYNTAX  INTEGER
        ACCESS  read-only
        STATUS  mandatory
        DESCRIPTION
                "Adminsitratively desired bandwidth size
                 in kilo bit per second for this ATM port."
        --
        ::= { mpAtmCCBwInfoPortEntry 1 }

mpAtmCCBwInfoPortRawBandwidthCps    OBJECT-TYPE
        SYNTAX  INTEGER
        ACCESS  read-only
        STATUS  mandatory
        DESCRIPTION
                "Adminsitratively desired bandwidth size
                 in cell per second for this ATM port."
        --
        ::= { mpAtmCCBwInfoPortEntry 2 }

mpAtmCCBwInfoPortTmitUsedBwCps    OBJECT-TYPE
        SYNTAX  INTEGER
        ACCESS  read-only
        STATUS  mandatory
        DESCRIPTION
                "The current using transmission bandwidth value ( total of
                 assigned bandwidth for each connections ) in cell per
                 second for this ATM port."
        --
        ::= { mpAtmCCBwInfoPortEntry 3 }

mpAtmCCBwInfoPortRcvUsedBwCps    OBJECT-TYPE
        SYNTAX  INTEGER
        ACCESS  read-only
        STATUS  mandatory
        DESCRIPTION
                "The current using receved bandwidth value ( total of
                 assigned bandwidth for each connections ) in cell per
                 second for this ATM port."
        --
        ::= { mpAtmCCBwInfoPortEntry 4 }

mpAtmCCBwInfoPortTmitRemainBwCps    OBJECT-TYPE
        SYNTAX  INTEGER
        ACCESS  read-only
        STATUS  mandatory
        DESCRIPTION
                "The current remaining transmission bandwidth value (
                 total of assigned bandwidth for each connections ) in
                 cell per second for this ATM port."
        --
        ::= { mpAtmCCBwInfoPortEntry 5 }

mpAtmCCBwInfoPortRcvRemainBwCps    OBJECT-TYPE
        SYNTAX  INTEGER
        ACCESS  read-only
        STATUS  mandatory
        DESCRIPTION
                "The current remaining receved bandwidth value ( total
                 of assigned bandwidth for each connections ) in cell
                 per second for this ATM port."
        --
        ::= { mpAtmCCBwInfoPortEntry 6 }

mpAtmCCBwInfoPortVpTunneling       OBJECT-TYPE
        SYNTAX  INTEGER(1..2)
        ACCESS  read-only
        STATUS  mandatory
        DESCRIPTION
                "VP-Tunneling indication.
                   1:VP-Tunneling
                   2:Not VP-Tunneling"
        --
        --
        --
        ::= { mpAtmCCBwInfoPortEntry 7 }



--
--
--

        mpAtmCCProtocol     OBJECT IDENTIFIER ::= { mpAtmCallCtl 6 }

--
--
--

mpAtmCCSscopTable OBJECT-TYPE
        SYNTAX  SEQUENCE OF MpAtmCCSscopEntry
        ACCESS  not-accessible
        STATUS  mandatory
        DESCRIPTION
                "SSCOP parameter Table"
        ::= { mpAtmCCProtocol 1 }

mpAtmCCSscopEntry OBJECT-TYPE
        SYNTAX  MpAtmCCSscopEntry
        ACCESS  not-accessible
        STATUS  mandatory
        DESCRIPTION
                "Entry of mpATMCCSscopTable."
        INDEX { ifIndex }
        ::= { mpAtmCCSscopTable 1 }

MpAtmCCSscopEntry ::=
        SEQUENCE {
                mpAtmCCSscopTimerPoll
                        INTEGER,
                mpAtmCCSscopTimerNoResponce
                        INTEGER,
                mpAtmCCSscopTimerKeepAlive
                        INTEGER,
                mpAtmCCSscopTimerIdle
                        INTEGER,
                mpAtmCCSscopTimerCc
                        INTEGER,
                mpAtmCCSscopMaxCc
                        INTEGER,
                mpAtmCCSscopMaxPd
                        INTEGER,
                mpAtmCCSscopMaxStat
                        INTEGER,
                mpAtmCCSscopClearBuffs
                        INTEGER,
                mpAtmCCSscopCredit
                        INTEGER
        }

mpAtmCCSscopTimerPoll       OBJECT-TYPE
        SYNTAX  INTEGER
        ACCESS  read-write
        STATUS  mandatory
        DESCRIPTION
                "Expert variable: timer in milliseconds
                 (default is 750 msecs for Uni 3.1)."
        REFERENCE
                "ATM Forum User-Network Interface Specification,
                 Version 3.1"
        --
        DEFVAL { 750 }
        ::= { mpAtmCCSscopEntry 1 }

mpAtmCCSscopTimerNoResponce       OBJECT-TYPE
        SYNTAX  INTEGER
        ACCESS  read-write
        STATUS  mandatory
        DESCRIPTION
                "Expert variable: timer in milliseconds
                 (default is 7000 msecs for Uni 3.1)."
        REFERENCE
                "ATM Forum User-Network Interface Specification,
                 Version 3.1"
        --
        DEFVAL { 7000 }
        ::= { mpAtmCCSscopEntry 2 }

mpAtmCCSscopTimerKeepAlive       OBJECT-TYPE
        SYNTAX  INTEGER
        ACCESS  read-write
        STATUS  mandatory
        DESCRIPTION
                "Expert variable: timer in milliseconds
                 (default is 2000 msecs for Uni 3.1)."
        REFERENCE
                "ATM Forum User-Network Interface Specification,
                 Version 3.1"
        --
        DEFVAL { 2000 }
        ::= { mpAtmCCSscopEntry 3 }

mpAtmCCSscopTimerIdle       OBJECT-TYPE
        SYNTAX  INTEGER
        ACCESS  read-write
        STATUS  mandatory
        DESCRIPTION
                "Expert variable: timer in milliseconds
                 (default is 1500 msecs for Uni 3.1)."
        REFERENCE
                "ATM Forum User-Network Interface Specification,
                 Version 3.1"
        --
        DEFVAL { 15000 }
        ::= { mpAtmCCSscopEntry 4 }

mpAtmCCSscopTimerCc       OBJECT-TYPE
        SYNTAX  INTEGER
        ACCESS  read-write
        STATUS  mandatory
        DESCRIPTION
                "Expert variable: timer in milliseconds
                  (default is 1000 msecs for Uni 3.1)."
        REFERENCE
                "ATM Forum User-Network Interface Specification,
                 Version 3.1"
        --
        DEFVAL { 1000 }
        ::= { mpAtmCCSscopEntry 5 }

mpAtmCCSscopMaxCc       OBJECT-TYPE
        SYNTAX  INTEGER
        ACCESS  read-write
        STATUS  mandatory
        DESCRIPTION
                "Expert variable
                  (default is 4 for Uni 3.1)."
        --
        REFERENCE
                "ATM Forum User-Network Interface Specification,
                 Version 3.1"
        DEFVAL { 4 }
        ::= { mpAtmCCSscopEntry 6 }

mpAtmCCSscopMaxPd       OBJECT-TYPE
        SYNTAX  INTEGER
        ACCESS  read-write
        STATUS  mandatory
        DESCRIPTION
                "Expert variable
                  (default is 25 for Uni 3.1)."
        --
        REFERENCE
                "ATM Forum User-Network Interface Specification,
                 Version 3.1"
        DEFVAL { 25 }
        ::= { mpAtmCCSscopEntry 7 }

mpAtmCCSscopMaxStat       OBJECT-TYPE
        SYNTAX  INTEGER
        ACCESS  read-write
        STATUS  mandatory
        DESCRIPTION
                "Expert variable
                  (default is 67 for Uni 3.1)."
        --
        REFERENCE
                "ATM Forum User-Network Interface Specification,
                 Version 3.1"
        DEFVAL { 67 }
        ::= { mpAtmCCSscopEntry 8 }

mpAtmCCSscopClearBuffs       OBJECT-TYPE
        SYNTAX  INTEGER{
                    yes(1),
                    no(2)
                }
        ACCESS  read-only
        STATUS  mandatory
        DESCRIPTION
                "Expert variable."
        --
        REFERENCE
                "ATM Forum User-Network Interface Specification,
                 Version 3.1"
        ::= { mpAtmCCSscopEntry 9 }

mpAtmCCSscopCredit       OBJECT-TYPE
        SYNTAX  INTEGER{
                    yes(1),
                    no(2)
                }
        ACCESS  read-only
        STATUS  mandatory
        DESCRIPTION
                "Expert variable."
        --
        REFERENCE
                "ATM Forum User-Network Interface Specification,
                 Version 3.1"
        ::= { mpAtmCCSscopEntry 10 }



--
--
--

mpAtmCCIlmiTable OBJECT-TYPE
        SYNTAX  SEQUENCE OF MpAtmCCIlmiEntry
        ACCESS  not-accessible
        STATUS  mandatory
        DESCRIPTION
                "ILMI parameter Table"
        ::= { mpAtmCCProtocol 2 }

mpAtmCCIlmiEntry OBJECT-TYPE
        SYNTAX  MpAtmCCIlmiEntry
        ACCESS  not-accessible
        STATUS  mandatory
        DESCRIPTION
                "Entry of mpATMCCIlmiTable."
        INDEX { ifIndex }
        ::= { mpAtmCCIlmiTable 1 }

MpAtmCCIlmiEntry ::=
        SEQUENCE {
                mpAtmCCIlmiConfigStatus
                        INTEGER,
                mpAtmCClmiMaxTransmissions
                        INTEGER,
                mpAtmCCIlmiRetransmitInterval
                        INTEGER
         }

mpAtmCCIlmiConfigStatus OBJECT-TYPE
         SYNTAX  INTEGER {
                         enabled(1),
                         disabled(2)
                 }
         ACCESS  read-write
         STATUS  mandatory
         DESCRIPTION
                 "Indicates whether ilmi is currently enabled at
                  this interface."
         --
         DEFVAL  { enabled }
         ::= { mpAtmCCIlmiEntry 1 }

mpAtmCClmiMaxTransmissions OBJECT-TYPE
         SYNTAX  INTEGER
         ACCESS  read-write
         STATUS  mandatory
         DESCRIPTION
                 "In a situation where a request is not receiving
                  a response within
                  mpAtmCCLimiRetransmitInterval, the number of
                  consecutive transmissions/non-responses that will
                  cause the UME to declare a loss of ILMI
                  connectivity
                  This variable is intended to promote
                  interoperability, so no range restriction is
                  given."
         --
         DEFVAL { 4 }
         ::= { mpAtmCCIlmiEntry 2 }

mpAtmCCIlmiRetransmitInterval OBJECT-TYPE
         SYNTAX  INTEGER
         ACCESS  read-write
         STATUS  mandatory
         DESCRIPTION
                 "The time in seconds between retransmissions of
                  ILMI requests
                  This variable is intended to promote
                  interoperability, so no range restriction is
                  given."
         --
         DEFVAL { 5 }
         ::= { mpAtmCCIlmiEntry 3 }


--
--
--

mpAtmCCSignallingTable OBJECT-TYPE
        SYNTAX  SEQUENCE OF MpAtmCCSignallingEntry
        ACCESS  not-accessible
        STATUS  mandatory
        DESCRIPTION
                "ILMI parameter Table"
        ::= { mpAtmCCProtocol 3 }

mpAtmCCSignallingEntry OBJECT-TYPE
        SYNTAX  MpAtmCCSignallingEntry
        ACCESS  not-accessible
        STATUS  mandatory
        DESCRIPTION
                "Entry of mpATMCCSignallingTable."
        INDEX { ifIndex }
        ::= { mpAtmCCSignallingTable 1 }

MpAtmCCSignallingEntry ::=
        SEQUENCE {
                mpAtmCCSignallingT301
                        INTEGER,
                mpAtmCCSignallingT303
                        INTEGER,
                mpAtmCCSignallingT308
                        INTEGER,
                mpAtmCCSignallingT309
                        INTEGER,
                mpAtmCCSignallingT310
                        INTEGER,
                mpAtmCCSignallingT313
                        INTEGER,
                mpAtmCCSignallingT316
                        INTEGER,
                mpAtmCCSignallingT317
                        INTEGER,
                mpAtmCCSignallingT322
                        INTEGER,
                mpAtmCCSignallingT331
                        INTEGER,
                mpAtmCCSignallingT397
                        INTEGER,
                mpAtmCCSignallingT398
                        INTEGER,
                mpAtmCCSignallingT399
                        INTEGER
        }

mpAtmCCSignallingT301 OBJECT-TYPE
         SYNTAX  INTEGER
         ACCESS  read-write
         STATUS  mandatory
         DESCRIPTION
                 "Expert variable: timer in seconds"
         --
         REFERENCE
                 "ATM Forum User-Network Interface Specification,
                  Version 3.1"
         DEFVAL  { 180 }
         ::= { mpAtmCCSignallingEntry 1 }

mpAtmCCSignallingT303 OBJECT-TYPE
         SYNTAX  INTEGER
         ACCESS  read-write
         STATUS  mandatory
         DESCRIPTION
                 "Expert variable: timer in seconds"
         --
         REFERENCE
                 "ATM Forum User-Network Interface Specification,
                  Version 3.1"
         DEFVAL  { 4 }
         ::= { mpAtmCCSignallingEntry 2 }

mpAtmCCSignallingT308 OBJECT-TYPE
         SYNTAX  INTEGER
         ACCESS  read-write
         STATUS  mandatory
         DESCRIPTION
                 "Expert variable: timer in seconds"
         --
         REFERENCE
                 "ATM Forum User-Network Interface Specification,
                  Version 3.1"
         DEFVAL  { 30 }
         ::= { mpAtmCCSignallingEntry 3 }

mpAtmCCSignallingT309 OBJECT-TYPE
         SYNTAX  INTEGER
         ACCESS  read-write
         STATUS  mandatory
         DESCRIPTION
                 "Expert variable: timer in seconds"
         --
         REFERENCE
                 "ATM Forum User-Network Interface Specification,
                  Version 3.1"
         DEFVAL  { 10 }
         ::= { mpAtmCCSignallingEntry 4 }

mpAtmCCSignallingT310 OBJECT-TYPE
         SYNTAX  INTEGER
         ACCESS  read-write
         STATUS  mandatory
         DESCRIPTION
                 "Expert variable: timer in seconds"
         --
         REFERENCE
                 "ATM Forum User-Network Interface Specification,
                  Version 3.1"
         DEFVAL  { 30 }
         ::= { mpAtmCCSignallingEntry 5 }

mpAtmCCSignallingT313 OBJECT-TYPE
         SYNTAX  INTEGER
         ACCESS  read-write
         STATUS  mandatory
         DESCRIPTION
                 "Expert variable: timer in seconds"
         --
         REFERENCE
                 "ATM Forum User-Network Interface Specification,
                  Version 3.1"
         DEFVAL  { 4 }
         ::= { mpAtmCCSignallingEntry 6 }

mpAtmCCSignallingT316 OBJECT-TYPE
         SYNTAX  INTEGER
         ACCESS  read-write
         STATUS  mandatory
         DESCRIPTION
                 "Expert variable: timer in seconds"
         --
         REFERENCE
                 "ATM Forum User-Network Interface Specification,
                  Version 3.1"
         DEFVAL  { 120 }
         ::= { mpAtmCCSignallingEntry 7 }

mpAtmCCSignallingT317 OBJECT-TYPE
         SYNTAX  INTEGER
         ACCESS  read-write
         STATUS  mandatory
         DESCRIPTION
                 "Expert variable: timer in seconds"
         --
         REFERENCE
                 "ATM Forum User-Network Interface Specification,
                  Version 3.1"
         DEFVAL  { 180 }
         ::= { mpAtmCCSignallingEntry 8 }

mpAtmCCSignallingT322 OBJECT-TYPE
         SYNTAX  INTEGER
         ACCESS  read-write
         STATUS  mandatory
         DESCRIPTION
                 "Expert variable: timer in seconds"
         --
         REFERENCE
                 "ATM Forum User-Network Interface Specification,
                  Version 3.1"
         DEFVAL  { 4 }
         ::= { mpAtmCCSignallingEntry 9 }

mpAtmCCSignallingT331 OBJECT-TYPE
         SYNTAX  INTEGER
         ACCESS  read-write
         STATUS  mandatory
         DESCRIPTION
                 "Expert variable: timer in seconds"
         --
         REFERENCE
                 "ATM Forum User-Network Interface Specification,
                  Version 3.1"
         DEFVAL  { 60 }
         ::= { mpAtmCCSignallingEntry 10 }

mpAtmCCSignallingT397 OBJECT-TYPE
         SYNTAX  INTEGER
         ACCESS  read-write
         STATUS  mandatory
         DESCRIPTION
                 "Expert variable: timer in seconds"
         --
         REFERENCE
                 "ATM Forum User-Network Interface Specification,
                  Version 3.1"
         DEFVAL  { 180 }
         ::= { mpAtmCCSignallingEntry 11 }

mpAtmCCSignallingT398 OBJECT-TYPE
         SYNTAX  INTEGER
         ACCESS  read-write
         STATUS  mandatory
         DESCRIPTION
                 "Expert variable: timer in seconds"
         --
         REFERENCE
                 "ATM Forum User-Network Interface Specification,
                  Version 3.1"
         DEFVAL  { 4 }
         ::= { mpAtmCCSignallingEntry 12 }

mpAtmCCSignallingT399 OBJECT-TYPE
         SYNTAX  INTEGER
         ACCESS  read-write
         STATUS  mandatory
         DESCRIPTION
                 "Expert variable: timer in seconds"
         --
         REFERENCE
                 "ATM Forum User-Network Interface Specification,
                  Version 3.1"
         DEFVAL  { 34 }
         ::= { mpAtmCCSignallingEntry 13 }


--
--
--

mpAtmCCProtocolTrapInfoTable OBJECT-TYPE
        SYNTAX  SEQUENCE OF MpAtmCCProtocolTrapInfoEntry
        ACCESS  not-accessible
        STATUS  mandatory
        DESCRIPTION
                "ATM Protocol Control Trap Infomation tabale"
        ::= { mpAtmCCProtocol 4 }

mpAtmCCProtocolTrapInfoEntry OBJECT-TYPE
        SYNTAX  MpAtmCCProtocolTrapInfoEntry
        ACCESS  not-accessible
        STATUS  mandatory
        DESCRIPTION
                "Entry of mpATMCCProtocolTrapInfoTable."
        INDEX { mpAtmCCProtocolTrapInfoIndex }
        ::= { mpAtmCCProtocolTrapInfoTable 1 }

MpAtmCCProtocolTrapInfoEntry ::=
        SEQUENCE {
                mpAtmCCProtocolTrapInfoIndex
                        INTEGER,
                mpAtmCCProtocolTrapInfoCause
                        INTEGER
                 }

mpAtmCCProtocolTrapInfoIndex OBJECT-TYPE
         SYNTAX  INTEGER
         ACCESS  read-only
         STATUS  mandatory
         DESCRIPTION
                 "The index value at this table"
         --
         ::= { mpAtmCCProtocolTrapInfoEntry 1 }

mpAtmCCProtocolTrapInfoCause OBJECT-TYPE
         SYNTAX  INTEGER
         ACCESS  read-only
         STATUS  mandatory
         DESCRIPTION
                 "Indicates why this trap send "
         --
         ::= { mpAtmCCProtocolTrapInfoEntry 2 }


--
--
--

        mpAtmCCPathTrace      OBJECT IDENTIFIER ::= { mpAtmCallCtl 7 }

--
--
--

mpAtmCCVccStatusTable OBJECT-TYPE
        SYNTAX  SEQUENCE OF MpAtmCCVccStatusEntry
        ACCESS  not-accessible
        STATUS  mandatory
        DESCRIPTION
                "This table indicate the vcc status infomation at the
                 ATM port."
        --
        ::= { mpAtmCCPathTrace 1 }

mpAtmCCVccStatusEntry OBJECT-TYPE
        SYNTAX  MpAtmCCVccStatusEntry
        ACCESS  not-accessible
        STATUS  mandatory
        DESCRIPTION
                " Entry of mpAtmCCVccStatusTable."
        --
        INDEX{ mpAtmCCVccStatusOrgPort,
               mpAtmCCVccStatusOrgVpi,
               mpAtmCCVccStatusOrgVci
             }
        ::= { mpAtmCCVccStatusTable 1 }

MpAtmCCVccStatusEntry ::=
        SEQUENCE {
               mpAtmCCVccStatusOrgPort
                        INTEGER,
               mpAtmCCVccStatusOrgVpi
                        INTEGER,
               mpAtmCCVccStatusOrgVci
                        INTEGER,
               mpAtmCCVccStatusDestPort
                        INTEGER,
               mpAtmCCVccStatusDestVpi
                        INTEGER,
               mpAtmCCVccStatusDestVci
                        INTEGER,
               mpAtmCCVccStatusPathKind
                        INTEGER,
               mpAtmCCVccStatusOrgCallKind
                        INTEGER,
               mpAtmCCVccStatusDestCallKind
                        INTEGER,
               mpAtmCCVccStatusAdminStatus
                        INTEGER,
               mpAtmCCVccStatusOperStatus
                        INTEGER,
               mpAtmCCVccStatusInsStatus
                        INTEGER,
               mpAtmCCVccStatusOrgPortVpTunneling    --
                        INTEGER,
               mpAtmCCVccStatusDestPortVpTunneling   --
                        INTEGER,
               mpAtmCCVccStatusConnCastType          --
                        INTEGER
        }

mpAtmCCVccStatusOrgPort       OBJECT-TYPE
        SYNTAX  INTEGER
        ACCESS  not-accessible
        STATUS  mandatory
        DESCRIPTION
                "Specified PORT number."
        --
        ::= { mpAtmCCVccStatusEntry 1 }

mpAtmCCVccStatusOrgVpi       OBJECT-TYPE
        SYNTAX  INTEGER
        ACCESS  not-accessible
        STATUS  mandatory
        DESCRIPTION
                "Specified VPI number."
        --
        ::= { mpAtmCCVccStatusEntry 2 }

mpAtmCCVccStatusOrgVci       OBJECT-TYPE
        SYNTAX  INTEGER
        ACCESS  not-accessible
        STATUS  mandatory
        DESCRIPTION
                "Specified VCI number."
        --
        ::= { mpAtmCCVccStatusEntry 3 }

mpAtmCCVccStatusDestPort       OBJECT-TYPE
        SYNTAX  INTEGER
        ACCESS  read-only
        STATUS  mandatory
        DESCRIPTION
                "Destination PORT number."
        --
        ::= { mpAtmCCVccStatusEntry 4 }

mpAtmCCVccStatusDestVpi       OBJECT-TYPE
        SYNTAX  INTEGER
        ACCESS  read-only
        STATUS  mandatory
        DESCRIPTION
                "Destination VPI number."
        --
        ::= { mpAtmCCVccStatusEntry 5 }

mpAtmCCVccStatusDestVci       OBJECT-TYPE
        SYNTAX  INTEGER
        ACCESS  read-only
        STATUS  mandatory
        DESCRIPTION
                "Destination VCI number."
        --
        ::= { mpAtmCCVccStatusEntry 6 }

mpAtmCCVccStatusPathKind       OBJECT-TYPE
        SYNTAX  INTEGER{
                        pvc(1),
                        softpvc(2),
                        insPvc(3),            --
                        pvp(4),               --
                        softpvp(5)            --
                       }
        ACCESS  read-only
        STATUS  mandatory
        DESCRIPTION
                "Path classification."
        --
        ::= { mpAtmCCVccStatusEntry 7 }

mpAtmCCVccStatusOrgCallKind       OBJECT-TYPE
        SYNTAX  INTEGER{
                        calling(1),      --
                        outgoing(2),     --
                        incoming(3),     --
                        called(4)        --
                       }
        ACCESS  read-only
        STATUS  mandatory
        DESCRIPTION
                "Port classification for specified an edge point."
        --
        ::= { mpAtmCCVccStatusEntry 8 }

mpAtmCCVccStatusDestCallKind       OBJECT-TYPE
        SYNTAX  INTEGER{
                        calling(1),      --
                        outgoing(2),     --
                        incoming(3),     --
                        called(4)        --
                       }
        ACCESS  read-only
        STATUS  mandatory
        DESCRIPTION
                "Port classification for destination an edge point."
        --
        ::= { mpAtmCCVccStatusEntry 9 }

mpAtmCCVccStatusAdminStatus       OBJECT-TYPE
        SYNTAX  INTEGER{
                       up(1),
                       down(2)
                       }
        ACCESS  read-only
        STATUS  mandatory
        DESCRIPTION
                "Control status."
        --
        ::= { mpAtmCCVccStatusEntry 10 }

mpAtmCCVccStatusOperStatus       OBJECT-TYPE
        SYNTAX  INTEGER{
                       up(1),
                       down(2)
                       }
        ACCESS  read-only
        STATUS  mandatory
        DESCRIPTION
                "Connection status."
        --
        ::= { mpAtmCCVccStatusEntry 11 }

mpAtmCCVccStatusInsStatus       OBJECT-TYPE
        SYNTAX  INTEGER{
                        trunkPort(1),  --
                        insPort(2)     --
                        }
        ACCESS  read-only
        STATUS  mandatory
        DESCRIPTION
                "INS detour indication."
        --
        ::= { mpAtmCCVccStatusEntry 12 }


mpAtmCCVccStatusOrgPortVpTunneling       OBJECT-TYPE
        SYNTAX  INTEGER(1..2)
        ACCESS  read-only
        STATUS  mandatory
        DESCRIPTION
                "Original port VP-Tunneling indication.
                   1:VP-Tunneling
                   2:Not VP-Tunneling"
        --
        --
        --
        ::= { mpAtmCCVccStatusEntry 13 }


mpAtmCCVccStatusDestPortVpTunneling       OBJECT-TYPE
        SYNTAX  INTEGER(1..2)
        ACCESS  read-only
        STATUS  mandatory
        DESCRIPTION
                "Destination port VP-Tunneling indication.
                   1:VP-Tunneling
                   2:Not VP-Tunneling"
        --
        --
        --
        ::= { mpAtmCCVccStatusEntry 14 }

mpAtmCCVccStatusConnCastType       OBJECT-TYPE              --
        SYNTAX  INTEGER{
                        p2p(1),
                        p2mpRoot(2),
                        p2mpLeaf(3)
                       }
        ACCESS  read-only
        STATUS  mandatory
        DESCRIPTION
              "The type of topology of a connection (point-
              to-point, point-to-multipoint)."
        --
        ::= { mpAtmCCVccStatusEntry 15 }



--
--
--

mpAtmCCPvcTraceControlTable OBJECT-TYPE
        SYNTAX  SEQUENCE OF MpAtmCCPvcTraceCtlEntry
        ACCESS  not-accessible
        STATUS  mandatory
        DESCRIPTION
                "This is the table type object of the
                 PVC PathTrace registration."
        --
        ::= { mpAtmCCPathTrace 2 }

mpAtmCCPvcTraceCtlEntry OBJECT-TYPE
        SYNTAX  MpAtmCCPvcTraceCtlEntry
        ACCESS  not-accessible
        STATUS  mandatory
        DESCRIPTION
                " Entry of mpAtmCCPvcTraceInfoTable."
        --
        INDEX{ mpAtmCCPvcTraceIndex }
        ::= { mpAtmCCPvcTraceControlTable 1 }

MpAtmCCPvcTraceCtlEntry ::=
        SEQUENCE {
               mpAtmCCPvcTraceIndex
                        INTEGER,
               mpAtmCCPvcTraceCtlPathKind
                        INTEGER,
               mpAtmCCPvcTraceCtlIfIndex
                        INTEGER,
               mpAtmCCPvcTraceCtlVpi
                        INTEGER,
               mpAtmCCPvcTraceCtlVci
                        INTEGER,
               mpAtmCCPvcTraceCtlStatus
                        INTEGER
        }

mpAtmCCPvcTraceIndex    OBJECT-TYPE
        SYNTAX  INTEGER(1..10)
        ACCESS  read-only
        STATUS  mandatory
        DESCRIPTION
                "The value of this object identifies the
                 PVC PathTrace collection number."
--
        ::= { mpAtmCCPvcTraceCtlEntry 1 }

mpAtmCCPvcTraceCtlPathKind    OBJECT-TYPE
        SYNTAX  INTEGER{
                  vcc(1),
                  vpc(2)
                }
        ACCESS  read-write
        STATUS  mandatory
        DESCRIPTION
                "The value of this object identifies the
                 path kind."
--
        ::= { mpAtmCCPvcTraceCtlEntry 2 }

mpAtmCCPvcTraceCtlIfIndex    OBJECT-TYPE
        SYNTAX  INTEGER
        ACCESS  read-write
        STATUS  mandatory
        DESCRIPTION
                "The value of this object identifies the
                 interface number."
--
        ::= { mpAtmCCPvcTraceCtlEntry 3 }

mpAtmCCPvcTraceCtlVpi    OBJECT-TYPE
        SYNTAX  INTEGER
        ACCESS  read-write
        STATUS  mandatory
        DESCRIPTION
                "The value of this object identifies the
                 VPI number."
--
        ::= { mpAtmCCPvcTraceCtlEntry 4 }

mpAtmCCPvcTraceCtlVci    OBJECT-TYPE
        SYNTAX  INTEGER
        ACCESS  read-write
        STATUS  mandatory
        DESCRIPTION
                "The value of this object identifies the
                 VCI number."
--
        ::= { mpAtmCCPvcTraceCtlEntry 5 }

mpAtmCCPvcTraceCtlStatus    OBJECT-TYPE
        SYNTAX  INTEGER{
                    idle(1),        -- read-only
                    start(2),       -- write-only
                    collecting(3),  -- read-only
                    done(4),        -- read-only
                    cancel(5),      -- write-only
                    unknown(6)      -- read-ony
                }
        ACCESS  read-write
        STATUS  mandatory
        DESCRIPTION
                "The value of this object identifies the
                 PVC PathTrace condition."
--
        ::= { mpAtmCCPvcTraceCtlEntry 6 }


--
--
--


mpAtmCCPvcTraceInfoTable OBJECT-TYPE
        SYNTAX  SEQUENCE OF MpAtmCCPvcTraceInfoEntry
        ACCESS  not-accessible
        STATUS  mandatory
        DESCRIPTION
                "This is the table type object of the
                 PVC PathTrace information."
        --
        ::= { mpAtmCCPathTrace 3 }

mpAtmCCPvcTraceInfoEntry OBJECT-TYPE
--        SYNTAX  MpAtmCCPvcTraceControlEntry
        SYNTAX  MpAtmCCPvcTraceInfoEntry
        ACCESS  not-accessible
        STATUS  mandatory
        DESCRIPTION
                " Entry of mpAtmCCPvcTraceInfoTable."
        --
        INDEX{ mpAtmCCPvcTraceIndex, mpAtmCCPvcTraceEntryIndex }
        ::= { mpAtmCCPvcTraceInfoTable 1 }

MpAtmCCPvcTraceInfoEntry ::=
        SEQUENCE {
               mpAtmCCPvcTraceEntryIndex
                        INTEGER,
               mpAtmCCPvcTraceInfoSysName
                        DisplayString,
               mpAtmCCPvcTraceInfoIfIndex
                        INTEGER,
               mpAtmCCPvcTraceInfoVpi
                        INTEGER,
               mpAtmCCPvcTraceInfoVci
                        INTEGER,
               mpAtmCCPvcTraceInfoPathKind
                        INTEGER,
               mpAtmCCPvcTraceInfoCallKind
                        INTEGER,
               mpAtmCCPvcTraceInfoLastSegment
                        INTEGER
        }

mpAtmCCPvcTraceEntryIndex    OBJECT-TYPE
        SYNTAX  INTEGER(1..20)
        ACCESS  not-accessible
        STATUS  mandatory
        DESCRIPTION
                "The value of this object identifies the
                 inside index of PVC PathTrace information."
--
        ::= { mpAtmCCPvcTraceInfoEntry 1 }

mpAtmCCPvcTraceInfoSysName    OBJECT-TYPE
        SYNTAX  DisplayString(SIZE(0..255))
        ACCESS  read-only
        STATUS  mandatory
        DESCRIPTION
                "The value of this object identifies the
                 node name."
--
        ::= { mpAtmCCPvcTraceInfoEntry 2 }

mpAtmCCPvcTraceInfoIfIndex    OBJECT-TYPE
        SYNTAX  INTEGER
        ACCESS  read-only
        STATUS  mandatory
        DESCRIPTION
                "The value of this object identifies the
                 interface number."
--
        ::= { mpAtmCCPvcTraceInfoEntry 3 }

mpAtmCCPvcTraceInfoVpi    OBJECT-TYPE
        SYNTAX  INTEGER
        ACCESS  read-only
        STATUS  mandatory
        DESCRIPTION
                "The value of this object identifies the
                 VPI number."
--              VPI
        ::= { mpAtmCCPvcTraceInfoEntry 4 }

mpAtmCCPvcTraceInfoVci    OBJECT-TYPE
        SYNTAX  INTEGER
        ACCESS  read-only
        STATUS  mandatory
        DESCRIPTION
                "The value of this object identifies the
                 VCI number."
--              VCI
        ::= { mpAtmCCPvcTraceInfoEntry 5 }

mpAtmCCPvcTraceInfoPathKind    OBJECT-TYPE
        SYNTAX  INTEGER{
                    pvc(1),
                    softpvc(2),
                    inspvc(3),
                    pvp(4),
                    softpvp(5)
                }
        ACCESS  read-only
        STATUS  mandatory
        DESCRIPTION
                "The value of this object identifies the
                 path kind."
--
        ::= { mpAtmCCPvcTraceInfoEntry 6 }

mpAtmCCPvcTraceInfoCallKind    OBJECT-TYPE
        SYNTAX  INTEGER{
                    calling(1),
                    outgoing(2),
                    incoming(3),
                    called(4)
                }
        ACCESS  read-only
        STATUS  mandatory
        DESCRIPTION
                "The value of this object identifies the
                 connection type."
--
        ::= { mpAtmCCPvcTraceInfoEntry 7 }

mpAtmCCPvcTraceInfoLastSegment    OBJECT-TYPE
        SYNTAX  INTEGER{
                    notlast(1),
                    last(2)
                }
        ACCESS  read-only
        STATUS  mandatory
        DESCRIPTION
                "The value of this object identifies the
                 last segment."
--
        ::= { mpAtmCCPvcTraceInfoEntry 8 }



--
--
--

        mpAtmCCMuxMib      OBJECT IDENTIFIER ::= { mpAtmCallCtl 8 }

--
--
--

        mpAtmCCMuxStatistics    OBJECT IDENTIFIER ::= { mpAtmCCMuxMib 1 }


mpAtmCCMuxStatReceiveCellsCounters      OBJECT-TYPE
        SYNTAX  Counter
        ACCESS  read-only
        STATUS  mandatory
        DESCRIPTION
                "Counter of MUX receive cells."
        --
        ::= { mpAtmCCMuxStatistics 1 }

mpAtmCCMuxStatReceiveCellsCntOvfCounters      OBJECT-TYPE
        SYNTAX  Counter
        ACCESS  read-only
        STATUS  mandatory
        DESCRIPTION
                "Overflow counter of MUX receive cells counter."
        --
        ::= { mpAtmCCMuxStatistics 2 }

mpAtmCCMuxStatDiscardCellsBufOvfCounters      OBJECT-TYPE
        SYNTAX  Counter
        ACCESS  read-only
        STATUS  mandatory
        DESCRIPTION
                "Discard cell counter on buffer overflow."
        --
        ::= { mpAtmCCMuxStatistics 3 }

mpAtmCCMuxStatDiscardCellsBufOvfCntOvfCounters      OBJECT-TYPE
        SYNTAX  Counter
        ACCESS  read-only
        STATUS  mandatory
        DESCRIPTION
                "Overflow counter of discard cell counter on buffer overflow."
        --
        ::= { mpAtmCCMuxStatistics 4 }


mpAtmCCMuxStatDiscardCellsHTErrCounters      OBJECT-TYPE
        SYNTAX  Counter
        ACCESS  read-only
        STATUS  mandatory
        DESCRIPTION
                "Discard cell counter on header transration error."
        --
        ::= { mpAtmCCMuxStatistics 5 }

mpAtmCCMuxStatDiscardCellsHTErrCntOvfCounters      OBJECT-TYPE
        SYNTAX  Counter
        ACCESS  read-only
        STATUS  mandatory
        DESCRIPTION
                "Overflow counter of discard cell counter on header transration error."
        --
        ::= { mpAtmCCMuxStatistics 6 }


mpAtmCCMuxStatDiscardCellsThresholdOvfCounters      OBJECT-TYPE
        SYNTAX  Counter
        ACCESS  read-only
        STATUS  mandatory
        DESCRIPTION
                "Discard cell counter on threshold overflow."
        --
        ::= { mpAtmCCMuxStatistics 7 }

mpAtmCCMuxStatDiscardCellsThresholdOvfCntOvfCounters      OBJECT-TYPE
        SYNTAX  Counter
        ACCESS  read-only
        STATUS  mandatory
        DESCRIPTION
                "Overflow counter of discard cell counter on threshold overflow."
        --
        ::= { mpAtmCCMuxStatistics 8 }


--
--
--

        mpAtmCCVpTunneling      OBJECT IDENTIFIER ::= { mpAtmCallCtl 9 }

--
--
--

mpAtmCCVpTunnelingTable OBJECT-TYPE
        SYNTAX  SEQUENCE OF MpAtmCCVpTunnelingEntry
        ACCESS  not-accessible
        STATUS  mandatory
        DESCRIPTION
                "VP-Tunneling parameter Table"
        --
        ::= { mpAtmCCVpTunneling 1 }

mpAtmCCVpTunnelingEntry OBJECT-TYPE
        SYNTAX  MpAtmCCVpTunnelingEntry
        ACCESS  not-accessible
        STATUS  mandatory
        DESCRIPTION
                " Entry of mpAtmCCVpTunnelingTable."
        --
        INDEX{ ifIndex, mpAtmCCVpTunnelingVpi }
        ::= { mpAtmCCVpTunnelingTable 1 }

MpAtmCCVpTunnelingEntry ::=
        SEQUENCE {
               mpAtmCCVpTunnelingVpi
                        INTEGER,
               mpAtmCCVpTunnelingAdminStatus
                        INTEGER,
               mpAtmCCVpTunnelingOperStatus
                        INTEGER,
               mpAtmCCVpTunnelingSpeed
                        INTEGER,
               mpAtmCCVpTunnelingNeighborInfo
                        INTEGER,
               mpAtmCCVpTunnelingPnniVer
                        INTEGER,
               mpAtmCCVpTunnelingContinuityCheck
                        INTEGER,
               mpAtmCCVpTunnelingTrapState
                        INTEGER,
               mpAtmCCVpTunnelingSeverity
                        INTEGER,
               mpAtmCCVpTunnelingCfgStatus
                        INTEGER,
               mpAtmCCVpTunnelingErrInfo
                        INTEGER
        }

mpAtmCCVpTunnelingVpi       OBJECT-TYPE
        SYNTAX  INTEGER
        ACCESS  not-accessible
        STATUS  mandatory
        DESCRIPTION
                "Specified VPI number."
        --
        ::= { mpAtmCCVpTunnelingEntry 1 }

mpAtmCCVpTunnelingAdminStatus       OBJECT-TYPE
        SYNTAX  INTEGER{
                       up(1),
                       down(2)
                       }
        ACCESS  read-write
        STATUS  mandatory
        DESCRIPTION
                "Control status."
        --
        ::= { mpAtmCCVpTunnelingEntry 2 }

mpAtmCCVpTunnelingOperStatus       OBJECT-TYPE
        SYNTAX  INTEGER{
                       up(1),
                       down(2)
                       }
        ACCESS  read-only
        STATUS  mandatory
        DESCRIPTION
                "Connection status."
        --
        ::= { mpAtmCCVpTunnelingEntry 3 }

mpAtmCCVpTunnelingSpeed       OBJECT-TYPE
        SYNTAX  INTEGER
        ACCESS  read-only
        STATUS  mandatory
        DESCRIPTION
                "VP bandwidth(kbps)."
        --
        ::= { mpAtmCCVpTunnelingEntry 4 }

mpAtmCCVpTunnelingNeighborInfo       OBJECT-TYPE
        SYNTAX  INTEGER
        ACCESS  read-only
        STATUS  mandatory
        DESCRIPTION
                "Neighbor Info(ifIndex)."
        --
        ::= { mpAtmCCVpTunnelingEntry 5 }

mpAtmCCVpTunnelingPnniVer       OBJECT-TYPE
        SYNTAX  INTEGER
        ACCESS  read-only
        STATUS  mandatory
        DESCRIPTION
                "PNNI Signaling version."
        --
        ::= { mpAtmCCVpTunnelingEntry 6 }

mpAtmCCVpTunnelingContinuityCheck       OBJECT-TYPE
        SYNTAX  INTEGER{
                       off(1),
                       on(2)
                       }
        ACCESS  read-only
        STATUS  mandatory
        DESCRIPTION
                "Continuity Check."
        --
        ::= { mpAtmCCVpTunnelingEntry 7 }

mpAtmCCVpTunnelingTrapState       OBJECT-TYPE
        SYNTAX  INTEGER{
                       off(1),
                       on(2)
                       }
        ACCESS  read-only
        STATUS  mandatory
        DESCRIPTION
                "Trap State."
        --
        ::= { mpAtmCCVpTunnelingEntry 8 }

mpAtmCCVpTunnelingSeverity       OBJECT-TYPE
        SYNTAX  INTEGER{
                       critical(1),
                       major(2),
                       minor(3),
                       warning(4),
                       informational(5)
                       }
        ACCESS  read-only
        STATUS  mandatory
        DESCRIPTION
                "Severity."
        --
        ::= { mpAtmCCVpTunnelingEntry 9 }

mpAtmCCVpTunnelingCfgStatus      OBJECT-TYPE
        SYNTAX  INTEGER {
                        enable(1),
                        cancel(2),
                        delete(3),
                        unknown(4)
                        }
        ACCESS  read-write
        STATUS  mandatory
        DESCRIPTION
                "Configuration setting start object. If this object is
                 set the setting of the configuration is started."
--
        DEFVAL { unknown }
        ::= { mpAtmCCVpTunnelingEntry 98 }

mpAtmCCVpTunnelingErrInfo    OBJECT-TYPE
        SYNTAX  INTEGER
        ACCESS  read-only
        STATUS  mandatory
        DESCRIPTION
                "Object that the configuration setting result is set up."
--
        ::= { mpAtmCCVpTunnelingEntry 99 }



--
--
--

        mpAtmCCPathTest      OBJECT IDENTIFIER ::= { mpAtmCallCtl 10 }

--
--
--

mpAtmCCPathTestTable OBJECT-TYPE
        SYNTAX  SEQUENCE OF MpAtmCCPathTestEntry
        ACCESS  not-accessible
        STATUS  mandatory
        DESCRIPTION
                "This Table is control for the PATH TEST(F5 OAM CELL)
                 function"
        --
        ::= { mpAtmCCPathTest 1 }

mpAtmCCPathTestEntry OBJECT-TYPE
        SYNTAX  MpAtmCCPathTestEntry
        ACCESS  not-accessible
        STATUS  mandatory
        DESCRIPTION
                " Entry of mpAtmCCPathTestTable."
        --
        INDEX{ ifIndex, mpAtmCCPathTestVpi, mpAtmCCPathTestVci }
        ::= { mpAtmCCPathTestTable 1 }

MpAtmCCPathTestEntry ::=
        SEQUENCE {
               mpAtmCCPathTestVpi
                        INTEGER,
               mpAtmCCPathTestVci
                        INTEGER,
               mpAtmCCPathTestStatus
                        INTEGER,
               mpAtmCCPathTestSendDirection         --
                        INTEGER,                    --
               mpAtmCCPathTestSendTime
                        INTEGER,
               mpAtmCCPathTestSendCellsCounters
                        Counter,
               mpAtmCCPathTestRcvCellsCounters
                        Counter,
               mpAtmCCPathTestErrInfo
                        INTEGER
        }

mpAtmCCPathTestVpi    OBJECT-TYPE
        SYNTAX  INTEGER
        ACCESS  read-only                           --
        STATUS  mandatory
        DESCRIPTION
                "Index value for the specific VPI"
--
        ::= { mpAtmCCPathTestEntry 1 }

mpAtmCCPathTestVci    OBJECT-TYPE
        SYNTAX  INTEGER
        ACCESS  read-only                           --
        STATUS  mandatory
        DESCRIPTION
                "Index value for the specific VCI"
--
        ::= { mpAtmCCPathTestEntry 2 }

mpAtmCCPathTestStatus    OBJECT-TYPE
        SYNTAX  INTEGER{                                          --
                    testReq(1),       -- test point registration (read-only)
                    sendStart(2),     -- start sending F5OAM-cell
                    sendStop(3),      -- stop sending F5OAM-cell
                    loopSet(4),       -- loop point registration
                    loopRelease(5),   -- loop point deletion (read-only)
                    delete(6),        -- delete send or loop point (write-only)
                    unknown(7)        -- unknown status(read-only)  --
                }
        ACCESS  read-write
        STATUS  mandatory
        DESCRIPTION
                "The value of this object identifies the desired status of this table."
--
        DEFVAL{ unknown }                               --
        ::= { mpAtmCCPathTestEntry 3 }

mpAtmCCPathTestSendDirection    OBJECT-TYPE             --
        SYNTAX  INTEGER{
                    port(1),      -- to port
                    mux(2)        -- to mux
                       }
        ACCESS  read-write
        STATUS  mandatory
        DESCRIPTION
                "Indicate the direction which send the F5 OAM cells."
--
--
        DEFVAL{ port }
        ::= { mpAtmCCPathTestEntry 4 }

mpAtmCCPathTestSendTime    OBJECT-TYPE
        SYNTAX  INTEGER(1..68400)                       --
        ACCESS  read-write
        STATUS  mandatory
        DESCRIPTION
                "The amount of time this path will send the F5 OAM cells."
--
--
        DEFVAL{ 5 }
        ::= { mpAtmCCPathTestEntry 5 }                  --

mpAtmCCPathTestSendCellsCounters    OBJECT-TYPE
        SYNTAX  Counter
        ACCESS  read-only
        STATUS  mandatory
        DESCRIPTION
                "A amount of the number of F5 OAM cells sending."
--
        ::= { mpAtmCCPathTestEntry 6 }                  --

mpAtmCCPathTestRcvCellsCounters    OBJECT-TYPE
        SYNTAX  Counter
        ACCESS  read-only
        STATUS  mandatory
        DESCRIPTION
                "A aomut of the number of F5 OAN cells received."
--
        ::= { mpAtmCCPathTestEntry 7 }                  --

mpAtmCCPathTestErrInfo    OBJECT-TYPE
        SYNTAX  INTEGER
        ACCESS  read-only
        STATUS  mandatory
        DESCRIPTION
                "A additonal infomation for the error-response."
--
        ::= { mpAtmCCPathTestEntry 99 }



--
--
--

        mpAtmCCPvcGroupCutover      OBJECT IDENTIFIER ::= { mpAtmCallCtl 11 }


--
--
--

       mpAtmCCPvcGroupCutoverBaseInfo   OBJECT IDENTIFIER ::= { mpAtmCCPvcGroupCutover 1 }


mpAtmCCPvcGroupCutoverEnable    OBJECT-TYPE
        SYNTAX  INTEGER{
                    ture(1),   --
                    false(2)   --
                }
        ACCESS  read-only
        STATUS  mandatory
        DESCRIPTION
                "Specifies whether the node is currently operating the
                 PVC-Group-CutOver functions. If the value is 'false', then it
                 can not support the PVC-Group-CutOver service. This attribute
                 reflects the node configration data in the PVC-Group-CutOver
                 Service Request State and functiins condition.
                 It can change only Command Line Interface(CLI).
                 (Node reboot is indispensable chage to the PVC-Group-CutOver
                  Service Request Status )"
--
--
--
--
        ::= { mpAtmCCPvcGroupCutoverBaseInfo 1 }

mpAtmCCPvcGroupCutoverStatus    OBJECT-TYPE                       --
        SYNTAX  INTEGER{
                           null(1),
                           underAvtivate(2),
                           underDeactivate(3)
                       }
        ACCESS  read-only
        STATUS  mandatory
        DESCRIPTION
                "The current status of PVC-Group-Cutover function status."
--
        ::= { mpAtmCCPvcGroupCutoverBaseInfo 2 }



--
--
--

       mpAtmCCUnitePvcGroup   OBJECT IDENTIFIER ::= { mpAtmCCPvcGroupCutover 2 }


--
--
--

       mpAtmCCUpgcBaseInfo   OBJECT IDENTIFIER ::= { mpAtmCCUnitePvcGroup 1 }


mpAtmCCUpgcTotalGroupNumber    OBJECT-TYPE
        SYNTAX  INTEGER
        ACCESS  read-only
        STATUS  mandatory
        DESCRIPTION
                "The total number of registerd to Unite Pvc Group in this node."
--
        ::= { mpAtmCCUpgcBaseInfo 1 }

mpAtmCCUpgcBaseActiveGroupNumber    OBJECT-TYPE
        SYNTAX  INTEGER
        ACCESS  read-only
        STATUS  mandatory
        DESCRIPTION
                "The number of active Unite Pvc Group."
--
        ::= { mpAtmCCUpgcBaseInfo 2 }


--
--
--


--

--
--
--
--
--
--
--
--
--

--
--
--

--
--
--
--
--
--
--
--
--
--


mpAtmCCUnitePvcGroupControlTable OBJECT-TYPE
        SYNTAX  SEQUENCE OF MpAtmCCUpgcCtlEntry
        ACCESS  not-accessible
        STATUS  mandatory
        DESCRIPTION
                "This table contains the control of the Unite Pvc Group objects"
        --
        ::= { mpAtmCCUnitePvcGroup 2 }

mpAtmCCUpgcCtlEntry OBJECT-TYPE
        SYNTAX  MpAtmCCUpgcCtlEntry
        ACCESS  not-accessible
        STATUS  mandatory
        DESCRIPTION
                "An entry in the mpAtmCCUpgcCtlTable."
        --
        INDEX{ mpAtmCCUpgcIndex }
        ::= { mpAtmCCUnitePvcGroupControlTable 1 }

MpAtmCCUpgcCtlEntry ::=
        SEQUENCE {
               mpAtmCCUpgcIndex
                   INTEGER,
               mpAtmCCUpgcCtlStatus
                   INTEGER,
               mpAtmCCUpgcCtlCountPgc
                   INTEGER,
               mpAtmCCUpgcCtlResult
                   INTEGER
        }

mpAtmCCUpgcIndex    OBJECT-TYPE
        SYNTAX  INTEGER(1..64)
        ACCESS  read-only
        STATUS  mandatory
        DESCRIPTION
                "The Unite Pvc Group identifier for this node.
                 A value assigned to a node in this node that uniquely
                 identifies in the MIB."
--
        ::= { mpAtmCCUpgcCtlEntry 1 }

mpAtmCCUpgcCtlStatus    OBJECT-TYPE
        SYNTAX  INTEGER{
                    register(1),        -- write-only
                    active(2),          -- read-write
                    inactive(3),        -- read-write
                    delete(4),          -- write-only
                    stsInactive(5),     -- write-only
                    underEstablish(6),  -- read-only
                    underDeactivate(7)  -- read-only
                }
        ACCESS  read-write
        STATUS  mandatory
        DESCRIPTION
                "This variable indicates the Control Status of this Unite
                 Pvc Group.
                  - 'register', which indicates that request to careate a
                    new instance (Unite PVC Group) in the node.
                  - 'active', which indicates that the Unite Pvc Group is
                    connected.
                  - 'inactive', which indicates that the Unite Pvc Group is
                    disconnected.
                  - 'delete', which indicates that request to delete the Unite
                    Pvc Group.
                  - 'stsInactive', which indicates that request to only the
                    status is change to 'inactive'. This request is not
                    disconnect the connecting PVC's.
                  - 'underEstablish', which indicates that the under the
                    connecting progress in the Unite Pvc Group.
                  - 'underDeactivate', which indicates that the under the
                    disconnecting progress in the Unite Pvc Group.
                  "
--
--
--
--
--
--
--
--
--
--
--
--
        ::= { mpAtmCCUpgcCtlEntry 2 }

mpAtmCCUpgcCtlCountPgc    OBJECT-TYPE
        SYNTAX  INTEGER
        ACCESS  read-only
        STATUS  mandatory
        DESCRIPTION
                "The total number of registered Pvc Group in the Unite Pvc Group."
--
        ::= { mpAtmCCUpgcCtlEntry 3 }

mpAtmCCUpgcCtlResult    OBJECT-TYPE
        SYNTAX  INTEGER
        ACCESS  read-only
        STATUS  mandatory
        DESCRIPTION
                "Indicate the result at which process the Unite Pvc Group
                 CutOver."
--
        ::= { mpAtmCCUpgcCtlEntry 4 }



--
--
--

mpAtmCCUnitePvcGroupRegisterTable OBJECT-TYPE
        SYNTAX  SEQUENCE OF MpAtmCCUpgcRegiEntry
        ACCESS  not-accessible
        STATUS  mandatory
        DESCRIPTION
                "This table uesd that register the Pvc Group for the Unite Pvc
                 Group."
        --
        ::= { mpAtmCCUnitePvcGroup 3 }

mpAtmCCUpgcRegiEntry OBJECT-TYPE
        SYNTAX  MpAtmCCUpgcRegiEntry
        ACCESS  not-accessible
        STATUS  mandatory
        DESCRIPTION
                "An entry in the mpAtmCCUpgcRegiTable."
        --
        INDEX{ mpAtmCCUpgcIndex, mpAtmCCUpgcPgcIndex }
        ::= { mpAtmCCUnitePvcGroupRegisterTable 1 }

MpAtmCCUpgcRegiEntry ::=
        SEQUENCE {
               mpAtmCCUpgcPgcIndex
                   INTEGER,
               mpAtmCCUpgcRegiStatus
                   INTEGER
        }


mpAtmCCUpgcPgcIndex    OBJECT-TYPE
        SYNTAX  INTEGER(1..256)
        ACCESS  read-only
        STATUS  mandatory
        DESCRIPTION
                "The Index value for specified the Pvc Group that
                 to add (or delete) from Unite Pvc Group."
--
        ::= { mpAtmCCUpgcRegiEntry 1 }

mpAtmCCUpgcRegiStatus    OBJECT-TYPE
        SYNTAX  INTEGER{
                    add(1),      -- write-only
                    delete(2),   -- write-only
                    enable(3)    -- read-only
                }
        ACCESS  read-write                             --
        STATUS  mandatory
        DESCRIPTION
                "This variable indicates the ragistratoin Status the PVC
                 Groupe to specified the Unite Pvc Group.
                 - 'add', which indicates that add the Pvc group to Unite
                   Pvc Group.
                 - 'delete', which indicates that delete the Pvc group to
                   Unite Pvc Group.
                 - 'enable', which indicates that ragisterd the Pvc group
                   in the Unite Pvc Group."
--
--
--
--
--
--
--
        ::= { mpAtmCCUpgcRegiEntry 2 }



--
--
--

       mpAtmCCPvcGroup   OBJECT IDENTIFIER ::= { mpAtmCCPvcGroupCutover 3 }


--
--
--

       mpAtmCCPgcBaseInfo   OBJECT IDENTIFIER ::= { mpAtmCCPvcGroup 1 }


mpAtmCCPgcTotalGroupNumber    OBJECT-TYPE
        SYNTAX  INTEGER
        ACCESS  read-only
        STATUS  mandatory
        DESCRIPTION
                "The total number of registerd to Pvc Group in this node."
--
        ::= { mpAtmCCPgcBaseInfo 1 }


--

--
--
--
--
--
--
--

--
--
--
--
--
--
--
--
--
--
--
-- 
--
--
--
--
--
--
--
--

--
--
--
--
--
--
--

--
--
--
--
--
--
--
--


--
--
--

mpAtmCCPvcGroupControlTable OBJECT-TYPE
        SYNTAX  SEQUENCE OF MpAtmCCPgcCtlEntry
        ACCESS  not-accessible
        STATUS  mandatory
        DESCRIPTION
                "This table contains the control of the Pvc Group objects"
        --
        ::= { mpAtmCCPvcGroup 2 }

mpAtmCCPgcCtlEntry OBJECT-TYPE
        SYNTAX  MpAtmCCPgcCtlEntry
        ACCESS  not-accessible
        STATUS  mandatory
        DESCRIPTION
                "An entry in the mpAtmCCPgcCtlTable."
        --
        INDEX{ mpAtmCCPgcIndex }
        ::= { mpAtmCCPvcGroupControlTable 1 }

MpAtmCCPgcCtlEntry ::=
        SEQUENCE {
               mpAtmCCPgcIndex
                   INTEGER,
               mpAtmCCPgcCtlStatus
                   INTEGER,
               mpAtmCCPgcCtlCountPvc
                   INTEGER,
               mpAtmCCPgcCtlResult
                   INTEGER
        }

mpAtmCCPgcIndex    OBJECT-TYPE
        SYNTAX  INTEGER(1..4096)
        ACCESS  read-only
        STATUS  mandatory
        DESCRIPTION
                "The Pvc Group identifier for this node. A value assigned
                 to a node in this node that uniquely identifies in the MIB."
--
        ::= { mpAtmCCPgcCtlEntry 1 }

mpAtmCCPgcCtlStatus    OBJECT-TYPE
        SYNTAX  INTEGER{
                    register(1),        -- write-only
                    active(2),          -- read-write
                    inactive(3),        -- read-write
                    delete(4),          -- write-only
                    stsInactive(5),     -- write-only
                    underEstablish(6),  -- read-only
                    underDeactivate(7)  -- read-only
                }
        ACCESS  read-write
        STATUS  mandatory
        DESCRIPTION
                "This variable indicates the Control Status of this Pvc
                 Group.
                  - 'register', which indicates that request to careate a
                    new instance (PVC Group) in the node.
                  - 'active', which indicates that the Pvc Group is connected.
                  - 'inactive', which indicates that the Pvc Group is
                    disconnected.
                  - 'delete', which indicates that request to delete the Pvc
                    Group.
                  - 'stsInactive', which indicates that request to only the
                    status is change to 'inactive'. This request is not
                    disconnect the connecting PVC's.
                  - 'underEstablish', which indicates that the under the
                    connecting progress in the Pvc Group.
                  - 'underDeactivate', which indicates that the under the
                    disconnecting progress in the Pvc Group.
                  "
--
--
--
--
--
--
--
--
--
--
--
        ::= { mpAtmCCPgcCtlEntry 2 }

mpAtmCCPgcCtlCountPvc    OBJECT-TYPE
        SYNTAX  INTEGER
        ACCESS  read-only
        STATUS  mandatory
        DESCRIPTION
                "The total number of registered Pvc in the Pvc Group."
--
        ::= { mpAtmCCPgcCtlEntry 3 }

mpAtmCCPgcCtlResult    OBJECT-TYPE
        SYNTAX  INTEGER
        ACCESS  read-only
        STATUS  mandatory
        DESCRIPTION
                "Indicate the result at which process the Pvc Group CutOver."
--
        ::= { mpAtmCCPgcCtlEntry 4 }



--
--
--

mpAtmCCPvcGroupRegisterTable OBJECT-TYPE
        SYNTAX  SEQUENCE OF MpAtmCCPgcRegiEntry
        ACCESS  not-accessible
        STATUS  mandatory
        DESCRIPTION
                "This table uesd that register the Pvc for the Pvc Group."
        --
        ::= { mpAtmCCPvcGroup 3 }

mpAtmCCPgcRegiEntry OBJECT-TYPE
        SYNTAX  MpAtmCCPgcRegiEntry
        ACCESS  not-accessible
        STATUS  mandatory
        DESCRIPTION
                "An entry in the mpAtmCCPgcRegiTable."
        --
        INDEX{ mpAtmCCPgcIndex,
               mpAtmCCPgcPvcIfIndex,
               mpAtmCCPgcPvcVpi,
               mpAtmCCPgcPvcVci }
        ::= { mpAtmCCPvcGroupRegisterTable 1 }

MpAtmCCPgcRegiEntry ::=
        SEQUENCE {
               mpAtmCCPgcPvcIfIndex
                   INTEGER,
               mpAtmCCPgcPvcVpi
                   INTEGER,
               mpAtmCCPgcPvcVci
                   INTEGER,
               mpAtmCCPgcPvcKind
                   INTEGER,
               mpAtmCCPgcStaticPvcDestIfIndex
                   INTEGER,
               mpAtmCCPgcSoftPvcDestAtmAddress
                   AtmAddr,
               mpAtmCCPgcPvcDestVpi
                   INTEGER,
               mpAtmCCPgcPvcDestVci
                   INTEGER,
               mpAtmCCPgcPvcReceiveTrafficDescrIndex
                   AtmTrafficDescrParamIndex,
               mpAtmCCPgcPvcTransmitTrafficDescrIndex
                   AtmTrafficDescrParamIndex,
               mpAtmCCPgcPvcPriority
                   INTEGER,
               mpAtmCCPgcStaticPvcId
                   INTEGER,
               mpAtmCCPgcStaticPvcSeqNo
                   INTEGER,
               mpAtmCCPgcSoftPvcCallKind
                   INTEGER,
               mpAtmCCPgcRegiAdminStatus
                   INTEGER,
               mpAtmCCPgcRegiCfgStatus
                   INTEGER,
               mpAtmCCPgcRegiErrInfo
                   INTEGER
        }

mpAtmCCPgcPvcIfIndex    OBJECT-TYPE
        SYNTAX  INTEGER
        ACCESS  not-accessible
        STATUS  mandatory
        DESCRIPTION
                "The value of this object is equal to MIB II's ifIndex value
                 of the ATM interface port for this pvc in PVC Group."
--
        ::= { mpAtmCCPgcRegiEntry 1 }

mpAtmCCPgcPvcVpi    OBJECT-TYPE
        SYNTAX  INTEGER
        ACCESS  not-accessible
        STATUS  mandatory
        DESCRIPTION
                "The VPI value of the pvc in PVC Group."
--
        ::= { mpAtmCCPgcRegiEntry 2 }

mpAtmCCPgcPvcVci    OBJECT-TYPE
        SYNTAX  INTEGER
        ACCESS  not-accessible
        STATUS  mandatory
        DESCRIPTION
                "The VCI value of the pvc in PVC Group.
                 The value of 0 can used with PVP."
--
--
        ::= { mpAtmCCPgcRegiEntry 3 }

mpAtmCCPgcPvcKind    OBJECT-TYPE
        SYNTAX  INTEGER{
                    staticPvc(1),
                    softPvc(2)
                }
        ACCESS  read-write
        STATUS  mandatory
        DESCRIPTION
                "This object is indicates the kind of pvc."
--
        ::= { mpAtmCCPgcRegiEntry 4 }

mpAtmCCPgcStaticPvcDestIfIndex    OBJECT-TYPE
        SYNTAX  INTEGER
        ACCESS  read-write
        STATUS  mandatory
        DESCRIPTION
                "The value of this object is equal to MIB II's ifIndex value
                 of the distination ATM interface port.
                 This value is not relevant when the value of mpAtmCCPgcPvcKind
                 is 'softPvc'."
--
        ::= { mpAtmCCPgcRegiEntry 5 }

mpAtmCCPgcSoftPvcDestAtmAddress    OBJECT-TYPE
--        SYNTAX  INTEGER                      @008 change
        SYNTAX  AtmAddr                     -- @008 change
        ACCESS  read-write
        STATUS  mandatory
        DESCRIPTION
                "The distinaniton ATM address of this pvc in the PVC Group.
                 This value is not relevant when the value of mpAtmCCPgcPvcKind
                 is 'staticPvc'."
--
        ::= { mpAtmCCPgcRegiEntry 6 }

mpAtmCCPgcPvcDestVpi    OBJECT-TYPE
        SYNTAX  INTEGER
        ACCESS  read-write
        STATUS  mandatory
        DESCRIPTION
                "The VPI value of the distination pvc."
--
        ::= { mpAtmCCPgcRegiEntry 7 }

mpAtmCCPgcPvcDestVci    OBJECT-TYPE
        SYNTAX  INTEGER
        ACCESS  read-write
        STATUS  mandatory
        DESCRIPTION
                "The VCI value of the distination pvc.
                 When the value of mpAtmCCPgcPvcVci is 0, the value of
                 this object is accept 0 only."
--
        ::= { mpAtmCCPgcRegiEntry 8 }

mpAtmCCPgcPvcReceiveTrafficDescrIndex    OBJECT-TYPE
        SYNTAX  AtmTrafficDescrParamIndex
        ACCESS  read-write
        STATUS  mandatory
        DESCRIPTION
                "The value of this ofject identifies the row of the ATM
                 Traffic Descriptor Table which applies to the receive
                 direction of this pvc in PVC Group."
--
        ::= { mpAtmCCPgcRegiEntry 9 }

mpAtmCCPgcPvcTransmitTrafficDescrIndex    OBJECT-TYPE
        SYNTAX  AtmTrafficDescrParamIndex
        ACCESS  read-write
        STATUS  mandatory
        DESCRIPTION
                "The value of this ofject identifies the row of the ATM
                 Traffic Descriptor Table which applies to the transmit
                 direction of this pvc in PVC Group."
--
        ::= { mpAtmCCPgcRegiEntry 10 }

mpAtmCCPgcPvcPriority    OBJECT-TYPE
        SYNTAX  INTEGER(1..3)
        ACCESS  read-write
        STATUS  mandatory
        DESCRIPTION
                "The value of this ofject identifies the connect priority
                 of the pvc in the PVC Group"
--
        ::= { mpAtmCCPgcRegiEntry 11 }

mpAtmCCPgcStaticPvcId    OBJECT-TYPE
        SYNTAX  INTEGER
        ACCESS  read-write
        STATUS  mandatory
        DESCRIPTION
                "The value of this object identifies the Static-PVC IDENTIFY
                 the pvc in the PVC Group.
                 This value is not relevant when the value of mpAtmCCPgcPvcKind
                 is 'softPvc'."
--
        ::= { mpAtmCCPgcRegiEntry 12 }

mpAtmCCPgcStaticPvcSeqNo    OBJECT-TYPE
        SYNTAX  INTEGER
        ACCESS  read-write
        STATUS  mandatory
        DESCRIPTION
                "The value of this object identifies the Sequence Number of
                 the static-pvc in the PvcGroup.
                 This value is not relevant when the value of mpAtmCCPgcPvcKind
                 is 'softPvc'."
--
        ::= { mpAtmCCPgcRegiEntry 13 }

mpAtmCCPgcSoftPvcCallKind    OBJECT-TYPE
        SYNTAX  INTEGER{
                    calling(1),  --
                    called(2)    --
                }
        ACCESS  read-write
        STATUS  mandatory
        DESCRIPTION
                "The value of this object identifies the call kind of the
                 soft-pvc in the PvcGroup.
                 This value is not relevant when the value of mpAtmCCPgcPvcKind
                 is 'staticPvc'."
--
        ::= { mpAtmCCPgcRegiEntry 14 }

mpAtmCCPgcRegiAdminStatus    OBJECT-TYPE
        SYNTAX  INTEGER{
                    inactive(1),      -- read-write
                    active(2),        -- read-write
                    stsInactive(3),   -- write-only
                    connectWait(4),   -- read-only
                    disconnectWait(5) -- read-only
                }
        ACCESS  read-write
        STATUS  mandatory
        DESCRIPTION
                "The value of this object identifies the desired administrative
                 status of this pvc in the PVC Group.
                  - 'inactive', which indicates that request to disconnect the
                     pvc.
                  - 'active', which indicates that request to connect the pvc.
                  - 'stsInactive', which indicates that request to only a
                     status is change, not disconnect the pvc.
                  - 'connectWait', which indicates that connecting progress at
                    this pvc.
                  - 'disconnectWait', which indicates that disconnecting
                    progress at this pvc.
                 "
--
--
--
--
--
--
--
--
        ::= { mpAtmCCPgcRegiEntry 15 }

mpAtmCCPgcRegiCfgStatus    OBJECT-TYPE
        SYNTAX  INTEGER{
                    enable(1),
                    cancel(2),
                    delete(3),
                    unknown(4)
                }
        ACCESS  read-write
        STATUS  mandatory
        DESCRIPTION
                "The value of this object identifies the desired configration
                 status of this pvc in the PVC Group.
                  - 'enable', which indicates that set to the configration
                  - 'cancel', which indicates that request to clear the
                    procedure
                  - 'delete', which indicates that deleted form the configration
                  - 'unkown',
                "
--
        ::= { mpAtmCCPgcRegiEntry 16 }

mpAtmCCPgcRegiErrInfo    OBJECT-TYPE
        SYNTAX  INTEGER
        ACCESS  read-only
        STATUS  mandatory
        DESCRIPTION
                "The value of this object indicate the result of set request."
--
        ::= { mpAtmCCPgcRegiEntry 17 }


--
--
--

mpAtmCCPvcGroupActiveInfoTable OBJECT-TYPE
        SYNTAX  SEQUENCE OF MpAtmCCPgcActInfoEntry
        ACCESS  not-accessible
        STATUS  mandatory
        DESCRIPTION
                "Confirm to the PVC Group that status is active."
        --
        ::= { mpAtmCCPvcGroup 4 }

mpAtmCCPgcActInfoEntry OBJECT-TYPE
        SYNTAX  MpAtmCCPgcActInfoEntry
        ACCESS  not-accessible
        STATUS  mandatory
        DESCRIPTION
                "The entry of mpAtmCCPvcGroupActiveInfoTable."
        --
        INDEX{ mpAtmCCPgcActGrpNum }
        ::= { mpAtmCCPvcGroupActiveInfoTable 1 }

MpAtmCCPgcActInfoEntry ::=
        SEQUENCE {
               mpAtmCCPgcActGrpNum
                       INTEGER
               }

mpAtmCCPgcActGrpNum    OBJECT-TYPE
        SYNTAX  INTEGER
        ACCESS  read-only
        STATUS  mandatory
        DESCRIPTION
                "The number of the PVC Group that status is active."
--
        ::= { mpAtmCCPgcActInfoEntry 1 }



--
--
--

        mpAtmCCAtmMulticast      OBJECT IDENTIFIER ::= { mpAtmCallCtl 12 }


--
--
--

mpAtmCCAtmMulticastRegistration  OBJECT IDENTIFIER ::= { mpAtmCCAtmMulticast 1 }

mpAtmCCAtmMultiRootIfIndex    OBJECT-TYPE
        SYNTAX  INTEGER
        ACCESS  read-write
        STATUS  mandatory
        DESCRIPTION
                "The value of this object is equal to MIB II's ifIndex value
                 of the ATM interface port."
--
        ::= { mpAtmCCAtmMulticastRegistration 1 }

mpAtmCCAtmMultiRootVpi    OBJECT-TYPE
        SYNTAX  INTEGER
        ACCESS  read-write
        STATUS  mandatory
        DESCRIPTION
                "The VPI value of the Multicast-Root-PVC."
--
        ::= { mpAtmCCAtmMulticastRegistration 2 }

mpAtmCCAtmMultiRootVci    OBJECT-TYPE
        SYNTAX  INTEGER
        ACCESS  read-write
        STATUS  mandatory
        DESCRIPTION
                "The VCI value of the Multicast-Root-PVC."
--
        ::= { mpAtmCCAtmMulticastRegistration 3 }

mpAtmCCAtmMultiLeafIfIndex    OBJECT-TYPE
        SYNTAX  INTEGER
        ACCESS  read-write
        STATUS  mandatory
        DESCRIPTION
                "The value of this object is equal to MIB II's ifIndex value
                 of the ATM interface port."
--
        ::= { mpAtmCCAtmMulticastRegistration 4 }

mpAtmCCAtmMultiLeafVpi    OBJECT-TYPE
        SYNTAX  INTEGER
        ACCESS  read-write
        STATUS  mandatory
        DESCRIPTION
                "The VPI value of the Multicast-Leaf-PVC."
--
        ::= { mpAtmCCAtmMulticastRegistration 5 }

mpAtmCCAtmMultiLeafVci    OBJECT-TYPE
        SYNTAX  INTEGER
        ACCESS  read-write
        STATUS  mandatory
        DESCRIPTION
                "The VCI value of the Multicast-Leaf-PVC."
--
        ::= { mpAtmCCAtmMulticastRegistration 6 }

mpAtmCCAtmMultiTrafficDescrIndex    OBJECT-TYPE
        SYNTAX  AtmTrafficDescrParamIndex
        ACCESS  read-write
        STATUS  mandatory
        DESCRIPTION
                "The value of this object identifies in the ATM
                 Traffic Descriptor Table which applies to this
                 multicast PVC."
--
        ::= { mpAtmCCAtmMulticastRegistration 7 }

mpAtmCCAtmMultiSlotNumber    OBJECT-TYPE
        SYNTAX  INTEGER
        ACCESS  read-write
        STATUS  mandatory
        DESCRIPTION
                "Specified the slot number which used the Multicast Card."
--
        ::= { mpAtmCCAtmMulticastRegistration 8 }

mpAtmCCAtmMultiVcRdiResponse    OBJECT-TYPE
        SYNTAX  INTEGER{
                        ture(1),
                        false(2)   -- default
                       }
        ACCESS  read-write
        STATUS  mandatory
        DESCRIPTION
                "Specified responds to the VC-AIS or not when the VC-RDI
                 received."
--
        ::= { mpAtmCCAtmMulticastRegistration 9 }

mpAtmCCAtmMultiPvcId    OBJECT-TYPE
        SYNTAX  INTEGER
        ACCESS  read-write
        STATUS  mandatory
        DESCRIPTION
                "The value of this object identifies the desired
                 this connection."
--
--      DEFVAL { 0 }
        ::= { mpAtmCCAtmMulticastRegistration 10 }

mpAtmCCAtmMultiSeqNo    OBJECT-TYPE
        SYNTAX  INTEGER
        ACCESS  read-write
        STATUS  mandatory
        DESCRIPTION
                "Order information in this connection."
--
--      DEFVAL { 0 }
        ::= { mpAtmCCAtmMulticastRegistration 11 }

mpAtmCCAtmMultiCfgStatus    OBJECT-TYPE
        SYNTAX  INTEGER {
                         enable(1),   -- write-only
                         cancel(2),   -- write-only
                         delete(3),   -- write-only
                         unknown(4)   -- read-only
                        }
        ACCESS  read-write
        STATUS  mandatory
        DESCRIPTION
                "The value of this object identifies configration
                 status for this table."
--
        DEFVAL { unknown }
        ::= { mpAtmCCAtmMulticastRegistration 98 }

mpAtmCCAtmMultiRegErrInfo    OBJECT-TYPE
        SYNTAX  INTEGER
        ACCESS  read-only
        STATUS  mandatory
        DESCRIPTION
                "The value of this object indicates error
                 information that became an error set to MIB
                 in this table."
--
        ::= { mpAtmCCAtmMulticastRegistration 99 }



--
--
--

mpAtmCCAtmMulticastCtlTable OBJECT-TYPE
        SYNTAX  SEQUENCE OF MpAtmCCAtmMultiCtlEntry
        ACCESS  not-accessible
        STATUS  mandatory
        DESCRIPTION
                "This table used when control of the multicast root
                 or leaf PVC."
        --
        ::= { mpAtmCCAtmMulticast 2 }

mpAtmCCAtmMultiCtlEntry OBJECT-TYPE
        SYNTAX  MpAtmCCAtmMultiCtlEntry
        ACCESS  not-accessible
        STATUS  mandatory
        DESCRIPTION
                "An entry in the mpAtmCCAtmMulticastCtlTable."
        --
        INDEX{
               mpAtmCCAtmMultiIfIndex,
               mpAtmCCAtmMultiVpi,
               mpAtmCCAtmMultiVci
             }
        ::= { mpAtmCCAtmMulticastCtlTable 1 }

MpAtmCCAtmMultiCtlEntry ::=
        SEQUENCE {
               mpAtmCCAtmMultiIfIndex
                   INTEGER,
               mpAtmCCAtmMultiVpi
                   INTEGER,
               mpAtmCCAtmMultiVci
                   INTEGER,
               mpAtmCCAtmMultiAdminStatus
                   INTEGER,
               mpAtmCCAtmMultiOperStatus
                   INTEGER,
               mpAtmCCAtmMultiErrInfo
                   INTEGER
        }

mpAtmCCAtmMultiIfIndex    OBJECT-TYPE
        SYNTAX  INTEGER
        ACCESS  not-accessible
        STATUS  mandatory
        DESCRIPTION
                "The value of this object is equal to MIB II's ifIndex value
                 of the ATM interface port."
--              ifIndex
        ::= { mpAtmCCAtmMultiCtlEntry 1 }

mpAtmCCAtmMultiVpi    OBJECT-TYPE
        SYNTAX  INTEGER
        ACCESS  not-accessible
        STATUS  mandatory
        DESCRIPTION
                "The VPI value of this PVC."
--              VPI
        ::= { mpAtmCCAtmMultiCtlEntry 2 }

mpAtmCCAtmMultiVci    OBJECT-TYPE
        SYNTAX  INTEGER
        ACCESS  not-accessible
        STATUS  mandatory
        DESCRIPTION
                "The VCI value of this PVC."
--              VCI
        ::= { mpAtmCCAtmMultiCtlEntry 3 }

mpAtmCCAtmMultiAdminStatus    OBJECT-TYPE
        SYNTAX  INTEGER{
                        up(1),
                        down(2)
                       }
        ACCESS  read-write
        STATUS  mandatory
        DESCRIPTION
                "The value of this object identifies the desired
                 administrative status of this Multicast-PVC.
                 The up and down states indicate that the traffic
                 flow is enabled and disabled respectively on this
                 Multicast-PVC."
--
        DEFVAL { down }
        ::= { mpAtmCCAtmMultiCtlEntry 4 }

mpAtmCCAtmMultiOperStatus    OBJECT-TYPE
        SYNTAX  INTEGER{
                        up(1),
                        down(2)
                       }
        ACCESS  read-only
        STATUS  mandatory
        DESCRIPTION
                "The value of this object identifies the desired
                 operational status of this Multicast-PVC."
--
        ::= { mpAtmCCAtmMultiCtlEntry 5 }

mpAtmCCAtmMultiErrInfo    OBJECT-TYPE
        SYNTAX  INTEGER
        ACCESS  read-only
        STATUS  mandatory
        DESCRIPTION
                "The value of this object indicates error
                 information that became an error set to MIB
                 in this table."
--
        ::= { mpAtmCCAtmMultiCtlEntry 99 }



--
--
--

mpAtmCCAtmMulticastConfTable OBJECT-TYPE
        SYNTAX  SEQUENCE OF MpAtmCCAtmMultiConfEntry
        ACCESS  not-accessible
        STATUS  mandatory
        DESCRIPTION
                "This table indicate that infom the ATM-Multicast-PVC."
        --
        ::= { mpAtmCCAtmMulticast 3 }

mpAtmCCAtmMultiConfEntry OBJECT-TYPE
        SYNTAX  MpAtmCCAtmMultiConfEntry
        ACCESS  not-accessible
        STATUS  mandatory
        DESCRIPTION
                "An entry in the mpAtmCCAtmMulticastConfTable."
        --
        INDEX{
               mpAtmCCAtmMultiRootIfIndex,
               mpAtmCCAtmMultiRootVpi,
               mpAtmCCAtmMultiRootVci,
               mpAtmCCAtmMultiLeafIfIndex,
               mpAtmCCAtmMultiLeafVpi,
               mpAtmCCAtmMultiLeafVci
             }
        ::= { mpAtmCCAtmMulticastConfTable 1 }

MpAtmCCAtmMultiConfEntry ::=
        SEQUENCE {
               mpAtmCCAtmMultiConfRootIfIndex
                   INTEGER,
               mpAtmCCAtmMultiConfRootVpi
                   INTEGER,
               mpAtmCCAtmMultiConfRootVci
                   INTEGER,
               mpAtmCCAtmMultiConfLeafIfIndex
                   INTEGER,
               mpAtmCCAtmMultiConfLeafVpi
                   INTEGER,
               mpAtmCCAtmMultiConfLeafVci
                   INTEGER,
               mpAtmCCAtmMultiConfRootAdminStatus
                   INTEGER,
               mpAtmCCAtmMultiConfRootOperStatus
                   INTEGER,
               mpAtmCCAtmMultiConfLeafAdminStatus
                   INTEGER,
               mpAtmCCAtmMultiConfLeafOperStatus
                   INTEGER,
               mpAtmCCAtmMultiConfTrafficDescrIndex
                   AtmTrafficDescrParamIndex,
               mpAtmCCAtmMultiConfSlotNumber
                   INTEGER,
               mpAtmCCAtmMultiConfVcRdiResponse
                   INTEGER,
               mpAtmCCAtmMultiConfPvcId
                   INTEGER,
               mpAtmCCAtmMultiConfSeqNo
                   INTEGER,
               mpAtmCCAtmMultiConfShaperRate
                   INTEGER,
               mpAtmCCAtmMultiConfRootVpTunneling
                   INTEGER,
               mpAtmCCAtmMultiConfLeafVpTunneling
                   INTEGER,
               mpAtmCCAtmMultiConfNextLeaf
                   INTEGER
        }

mpAtmCCAtmMultiConfRootIfIndex    OBJECT-TYPE
        SYNTAX  INTEGER
        ACCESS  read-only
        STATUS  mandatory
        DESCRIPTION
                "The value of this object is equal to MIB II's ifIndex value
                 of the ATM interface port."
--
        ::= { mpAtmCCAtmMultiConfEntry 1 }

mpAtmCCAtmMultiConfRootVpi    OBJECT-TYPE
        SYNTAX  INTEGER
        ACCESS  read-only
        STATUS  mandatory
        DESCRIPTION
                "The VPI value of the Multicast-Root-PVC."
--
        ::= { mpAtmCCAtmMultiConfEntry 2 }

mpAtmCCAtmMultiConfRootVci    OBJECT-TYPE
        SYNTAX  INTEGER
        ACCESS  read-only
        STATUS  mandatory
        DESCRIPTION
                "The VCI value of the Multicast-Root-PVC."
--
        ::= { mpAtmCCAtmMultiConfEntry 3 }
mpAtmCCAtmMultiConfLeafIfIndex    OBJECT-TYPE
        SYNTAX  INTEGER
        ACCESS  read-only
        STATUS  mandatory
        DESCRIPTION
                "The value of this object is equal to MIB II's ifIndex value
                 of the ATM interface port."
--
        ::= { mpAtmCCAtmMultiConfEntry 4 }

mpAtmCCAtmMultiConfLeafVpi    OBJECT-TYPE
        SYNTAX  INTEGER
        ACCESS  read-only
        STATUS  mandatory
        DESCRIPTION
                "The VPI value of the Multicast-Leaf-PVC."
--
        ::= { mpAtmCCAtmMultiConfEntry 5 }

mpAtmCCAtmMultiConfLeafVci    OBJECT-TYPE
        SYNTAX  INTEGER
        ACCESS  read-only
        STATUS  mandatory
        DESCRIPTION
                "The VCI value of the Multicast-Leaf-PVC."
--
        ::= { mpAtmCCAtmMultiConfEntry 6 }

mpAtmCCAtmMultiConfRootAdminStatus    OBJECT-TYPE
        SYNTAX  INTEGER{
                        up(1),
                        down(2)
                       }
        ACCESS  read-only
        STATUS  mandatory
        DESCRIPTION
                "The value of this object identifies the desired
                 administrative status of this Multicast-Root-PVC."
--
        ::= { mpAtmCCAtmMultiConfEntry 7 }

mpAtmCCAtmMultiConfRootOperStatus    OBJECT-TYPE
        SYNTAX  INTEGER{
                        up(1),
                        down(2)
                       }
        ACCESS  read-only
        STATUS  mandatory
        DESCRIPTION
                "The value of this object identifies the desired
                 operational status of this Multicast-Root-PVC."
--
        ::= { mpAtmCCAtmMultiConfEntry 8 }

mpAtmCCAtmMultiConfLeafAdminStatus    OBJECT-TYPE
        SYNTAX  INTEGER{
                        up(1),
                        down(2)
                       }
        ACCESS  read-only
        STATUS  mandatory
        DESCRIPTION
                "The value of this object identifies the desired
                 administrative status of this Multicast-Leaf-PVC."
--
        ::= { mpAtmCCAtmMultiConfEntry 9 }

mpAtmCCAtmMultiConfLeafOperStatus    OBJECT-TYPE
        SYNTAX  INTEGER{
                        up(1),
                        down(2)
                       }
        ACCESS  read-only
        STATUS  mandatory
        DESCRIPTION
                "The value of this object identifies the desired
                 operational status of this Multicast-Leaf-PVC."
--
        ::= { mpAtmCCAtmMultiConfEntry 10 }

mpAtmCCAtmMultiConfTrafficDescrIndex    OBJECT-TYPE
        SYNTAX  AtmTrafficDescrParamIndex
        ACCESS  read-only
        STATUS  mandatory
        DESCRIPTION
                "The value of this object identifies
                 in the ATM Traffic Descriptor Table which
                 applies of this Multicast-PVC."
--
        ::= { mpAtmCCAtmMultiConfEntry 11 }

mpAtmCCAtmMultiConfSlotNumber    OBJECT-TYPE
        SYNTAX  INTEGER
        ACCESS  read-only
        STATUS  mandatory
        DESCRIPTION
                "The value of this object identifies the slot number
                 which used the Multicast Card."
--
--
        ::= { mpAtmCCAtmMultiConfEntry 12 }

mpAtmCCAtmMultiConfVcRdiResponse    OBJECT-TYPE
        SYNTAX  INTEGER{
                        true(1),
                        false(2)
                       }
        ACCESS  read-only
        STATUS  mandatory
        DESCRIPTION
                "he value of this object identifies that responds to the
                 VC-AIS or not when the VC-RDI received."
--
        ::= { mpAtmCCAtmMultiConfEntry 13 }

mpAtmCCAtmMultiConfPvcId    OBJECT-TYPE
        SYNTAX  INTEGER
        ACCESS  read-only
        STATUS  mandatory
        DESCRIPTION
                "The value of this object identifies the desired
                 this connection."
--
        ::= { mpAtmCCAtmMultiConfEntry 14 }

mpAtmCCAtmMultiConfSeqNo    OBJECT-TYPE
        SYNTAX  INTEGER
        ACCESS  read-only
        STATUS  mandatory
        DESCRIPTION
                "Order information in this connection."
--
        ::= { mpAtmCCAtmMultiConfEntry 15 }

mpAtmCCAtmMultiConfShaperRate    OBJECT-TYPE
        SYNTAX  INTEGER
        ACCESS  read-only
        STATUS  mandatory
        DESCRIPTION
                "The bandwidth value of this Multicast-PVC in cell per
                 second."
--
        ::= { mpAtmCCAtmMultiConfEntry 16 }

mpAtmCCAtmMultiConfRootVpTunneling    OBJECT-TYPE
        SYNTAX  INTEGER{
                        ture(1),
                        false(2)
                       }
        ACCESS  read-only
        STATUS  mandatory
        DESCRIPTION
                "The value of this object identifies the port (at the
                 Multicast-Root-PVC) VP-Tunneling indication.
                   1:VP-Tunneling
                   2:Not VP-Tunneling"
--
        ::= { mpAtmCCAtmMultiConfEntry 17 }

mpAtmCCAtmMultiConfLeafVpTunneling    OBJECT-TYPE
        SYNTAX  INTEGER{
                        ture(1),
                        false(2)
                       }
        ACCESS  read-only
        STATUS  mandatory
        DESCRIPTION
                "The value of this object identifies the port (at the
                 Multicast-Leaf-PVC) VP-Tunneling indication."
--
        ::= { mpAtmCCAtmMultiConfEntry 18 }

mpAtmCCAtmMultiConfNextLeaf    OBJECT-TYPE
        SYNTAX  INTEGER{
                        ture(1),
                        false(2)
                       }
        ACCESS  read-only
        STATUS  mandatory
        DESCRIPTION
                "The value of this object identifies the
                 last segment."
--
--
--
--
        ::= { mpAtmCCAtmMultiConfEntry 19 }


END
