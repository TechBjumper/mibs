ZTE-AN-SECURITY-PACKET-FILTER-MIB    DEFINITIONS ::= BEGIN
    IMPORTS     
        MacAddress,RowStatus                            FROM SNMPv2-TC
        MODULE-IDENTITY,  OBJECT-TYPE,Integer32, 
        NOTIFICATION-TYPE                               FROM SNMPv2-SMI
        ifIndex                                         FROM IF-MIB
        ZxAnIfIndex,VlanId                              FROM ZTE-AN-TC-MIB
        zxAnServiceSecurity                             FROM ZTE-AN-SMI
        zxAnSubIfIndex                                  FROM ZTE-AN-IF-MIB;
       
    zxAnSecurityPacketFilterMib    MODULE-IDENTITY
        LAST-UPDATED    "201208131100Z"
        ORGANIZATION    "ZTE Corporation"
        CONTACT-INFO    "Zhang WeiPing
                         Mail: zhang.weiping@zte.com.cn
                         Tel : 021-68896470"
        DESCRIPTION     "This MIB defines zte Access Node managed objects."
        REVISION        "201208131100Z"
        DESCRIPTION
                        "Initial version of this MIB module."          
        ::=  {  zxAnServiceSecurity  35  }  
             
    zxAnSecPacketFilterObjects OBJECT IDENTIFIER 
        ::= {zxAnSecurityPacketFilterMib 2}
        
--------------------------------------------------------------------------------
-- Following objects are defined.
-- 1.Security L2CP Filter Management
--------------------------------------------------------------------------------

--------------------------------------------------------------------------------
-- 1.Security L2CP Filter Management
--------------------------------------------------------------------------------
    zxAnSecL2cpFiltObjects OBJECT IDENTIFIER ::= {zxAnSecPacketFilterObjects 2}  
    
    zxAnSecL2cpFiltGlobalObjects OBJECT IDENTIFIER 
        ::= {zxAnSecL2cpFiltObjects 1}   
 
    zxAnSecL2cpFiltVlanConfNextId  OBJECT-TYPE
        SYNTAX      Integer32(0..32)
        MAX-ACCESS  read-only
        STATUS      current
        DESCRIPTION
            "This object contains an unused value for zxAnSecL2cpFiltVlanConfId 
             in the zxAnSecL2cpFiltVlanConfTable.
             The value 0 indicates that no unassigned entries are available.             
            "
        ::= { zxAnSecL2cpFiltGlobalObjects 1 }

    zxAnSecL2cpFiltCapabilities  OBJECT-TYPE 
        SYNTAX  BITS {
            supportL2cpFiltVlanConfVlanList(0)
        }
        MAX-ACCESS  read-only
        STATUS      current
        DESCRIPTION   
            "The management capabilities of layer-2 control protocol filter.
             The bit value 1 means the function represented by this bit is 
             supported by this equipment.
             bit 0: value 1 means supporting zxAnSecL2cpFiltVlanConfVlanList, 
             and not supporting zxAnSecL2cpFiltVlanConfVid and
             zxAnSecL2cpFiltVlanConfVlanMask in zxAnSecL2cpFiltVlanConfTable.

             NOTE: No recommended to display it in NMS."
        ::= { zxAnSecL2cpFiltGlobalObjects 100 }
      
    zxAnSecL2cpFiltVlanConfTable   OBJECT-TYPE
        SYNTAX      SEQUENCE  OF  ZxAnSecL2cpFiltVlanConfEntry
        MAX-ACCESS  not-accessible
        STATUS      current
        DESCRIPTION 
            "This table includes the L2CP filter records for forwarding or 
             discarding."
        ::=  { zxAnSecL2cpFiltObjects  2 }

    zxAnSecL2cpFiltVlanConfEntry   OBJECT-TYPE
        SYNTAX      ZxAnSecL2cpFiltVlanConfEntry
        MAX-ACCESS  not-accessible
        STATUS      current
        DESCRIPTION 
            "An entry in zxAnSecL2cpFiltVlanConfTable.            
             To create an entry, the VLAN and MAC should not conflict.             
             "
        INDEX       { zxAnSecL2cpFiltVlanConfId }
        ::=  { zxAnSecL2cpFiltVlanConfTable 1 }       

    ZxAnSecL2cpFiltVlanConfEntry  ::=  SEQUENCE 
    {
        zxAnSecL2cpFiltVlanConfId                Integer32,
        zxAnSecL2cpFiltVlanConfDestMac           MacAddress,
        zxAnSecL2cpFiltVlanConfMacMask           MacAddress,
        zxAnSecL2cpFiltVlanConfVid               Integer32,
        zxAnSecL2cpFiltVlanConfVlanMask          Integer32,
        zxAnSecL2cpFiltVlanConfFwdPolicy         INTEGER,
        zxAnSecL2cpFiltVlanConfVlanList          OCTET STRING,
        zxAnSecL2cpFiltVlanConfRowStatus         RowStatus
    }
    
    zxAnSecL2cpFiltVlanConfId  OBJECT-TYPE 
        SYNTAX          Integer32(1..32)         
        MAX-ACCESS      not-accessible
        STATUS          current
        DESCRIPTION     
            "This object indicates the L2CP filter records ID. "                 
        ::=  {  zxAnSecL2cpFiltVlanConfEntry  1  }
        
    zxAnSecL2cpFiltVlanConfDestMac  OBJECT-TYPE 
        SYNTAX          MacAddress         
        MAX-ACCESS      read-create
        STATUS          current
        DESCRIPTION     
            "This object indicates the packet destination MAC address of the 
             L2CP filter record. "                 
        ::=  {  zxAnSecL2cpFiltVlanConfEntry  2  }        
        
    zxAnSecL2cpFiltVlanConfMacMask  OBJECT-TYPE 
        SYNTAX          MacAddress         
        MAX-ACCESS      read-create
        STATUS          current
        DESCRIPTION     
            "This is the wildcard mask for the zxAnSecL2cpFiltVlanConfDestMac 
             bits that must match. 1 bits in the mask indicate the 
             corresponding bits in the zxAnSecL2cpFiltVlanConfDestMac must match 
             in order for the matching to be successful, and 0 bits are don't 
             care bits in the matching. 
             A value of zero causes only packets of source address the same as 
             zxAnSecL2cpFiltVlanConfDestMac to match." 
        DEFVAL { 'FFFFFFFFFFFF'H }                  
        ::=  {  zxAnSecL2cpFiltVlanConfEntry  3  }

    zxAnSecL2cpFiltVlanConfVid  OBJECT-TYPE 
        SYNTAX          Integer32(1..4094)          
        MAX-ACCESS      read-create
        STATUS          current
        DESCRIPTION     
            "This object indicates the VLAN value of the packet."                  
        ::=  {  zxAnSecL2cpFiltVlanConfEntry  4  }

    zxAnSecL2cpFiltVlanConfVlanMask  OBJECT-TYPE 
        SYNTAX          Integer32(0..4095)          
        MAX-ACCESS      read-create
        STATUS          current
        DESCRIPTION     
            "This is the wildcard mask for the zxAnSecL2cpFiltVlanConfVid 
             bits that must match. 1 bits in the mask indicate the 
             corresponding bits in the zxAnSecL2cpFiltVlanConfVid must match 
             in order for the matching to be successful, and 0 bits are don't 
             care bits in the matching. 
             A value of zero causes only packets of source address the same as 
             zxAnSecL2cpFiltVlanConfVid to match." 
        DEFVAL { 4095 }                
        ::=  {  zxAnSecL2cpFiltVlanConfEntry  5  }

    zxAnSecL2cpFiltVlanConfFwdPolicy  OBJECT-TYPE 
        SYNTAX          INTEGER 
        {
            discard(1),
            forward(2)
        }          
        MAX-ACCESS      read-create
        STATUS          current
        DESCRIPTION     
            "This object indicates the forwarding policy of L2 packets,
             its values are as follow:
             discard       (1) - discard this packet;
             forward       (2) - the packet is transmitted transparently. " 
        DEFVAL { discard }                
        ::=  {  zxAnSecL2cpFiltVlanConfEntry  6  }
   
     zxAnSecL2cpFiltVlanConfVlanList  OBJECT-TYPE
        SYNTAX          OCTET STRING (SIZE (512))
        MAX-ACCESS      read-create
        STATUS          current
        DESCRIPTION
            "The VLAN list for layer-2 control protocol packet filter.
             A bit value of 1 indicates the associated VLAN is in the object."
        ::=  { zxAnSecL2cpFiltVlanConfEntry  7 }
        
    zxAnSecL2cpFiltVlanConfRowStatus    OBJECT-TYPE    
        SYNTAX          RowStatus
        MAX-ACCESS      read-create
        STATUS          current
        DESCRIPTION     
            "RowStatus of the zxAnSecL2cpFiltVlanConfTable table."
        ::=  {  zxAnSecL2cpFiltVlanConfEntry  50  }
                
    zxAnSecL2cpFiltDefaultTable   OBJECT-TYPE
        SYNTAX      SEQUENCE  OF  ZxAnSecL2cpFiltDefaultEntry
        MAX-ACCESS  not-accessible
        STATUS      current
        DESCRIPTION 
            "This table includes the default L2CP filter records."
        ::=  { zxAnSecL2cpFiltObjects  3 }

    zxAnSecL2cpFiltDefaultEntry   OBJECT-TYPE
        SYNTAX      ZxAnSecL2cpFiltDefaultEntry
        MAX-ACCESS  not-accessible
        STATUS      current
        DESCRIPTION 
            "An entry in zxAnSecL2cpFiltDefaultTable."
        INDEX       { zxAnSecL2cpFiltDefaultId }
        ::=  { zxAnSecL2cpFiltDefaultTable 1 }

    ZxAnSecL2cpFiltDefaultEntry  ::=  SEQUENCE 
    {
        zxAnSecL2cpFiltDefaultId                 Integer32, 
        zxAnSecL2cpFiltDefaultDestMac            MacAddress,
        zxAnSecL2cpFiltDefaultMacMask            MacAddress, 
        zxAnSecL2cpFiltDefaultFwdPolicy          INTEGER       
    }
    
    zxAnSecL2cpFiltDefaultId  OBJECT-TYPE 
        SYNTAX          Integer32(1..32)         
        MAX-ACCESS      not-accessible
        STATUS          current
        DESCRIPTION     
            "This object indicates the default L2CP filter records ID."                 
        ::=  {  zxAnSecL2cpFiltDefaultEntry  1  }
        
    zxAnSecL2cpFiltDefaultDestMac  OBJECT-TYPE 
        SYNTAX          MacAddress         
        MAX-ACCESS      read-only
        STATUS          current
        DESCRIPTION     
            "This object indicates the packet destination MAC address of the 
             default L2CP filter record. "                 
        ::=  {  zxAnSecL2cpFiltDefaultEntry  2  }        
        
    zxAnSecL2cpFiltDefaultMacMask  OBJECT-TYPE 
        SYNTAX          MacAddress         
        MAX-ACCESS      read-only
        STATUS          current
        DESCRIPTION     
            "This is the wildcard mask for the zxAnSecL2cpFiltDefaultDestMac 
             bits that must match. 1 bits in the mask indicate the 
             corresponding bits in the zxAnSecL2cpFiltDefaultDestMac must match 
             in order for the matching to be successful, and 0 bits are don't 
             care bits in the matching. 
             A value of zero causes only packets of source address the same as 
             zxAnSecL2cpFiltDefaultDestMac to match." 
        DEFVAL { 'FFFFFFFFFFFF'H }                  
        ::=  {  zxAnSecL2cpFiltDefaultEntry  3  }

    zxAnSecL2cpFiltDefaultFwdPolicy  OBJECT-TYPE 
        SYNTAX          INTEGER 
        {
            discard(1),
            forward(2)
        }          
        MAX-ACCESS      read-only
        STATUS          current
        DESCRIPTION     
            "This object indicates the forwarding policy of L2 packets,
             its values are as follow:
             discard     (1) - discard this packet;
             forward     (2) - the packet is transmitted transparently. " 
        DEFVAL { discard }                
        ::=  {  zxAnSecL2cpFiltDefaultEntry  4  }        
   
END
