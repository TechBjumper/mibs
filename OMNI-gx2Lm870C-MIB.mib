OMNI-gx2Lm870C-MIB DEFINITIONS ::= BEGIN

    IMPORTS
	IpAddress, TimeTicks, Counter            
					      FROM RFC1155-SMI
	OBJECT-TYPE                     
					      FROM RFC-1212
	sysUpTime, DisplayString        
					      FROM RFC1213-MIB
	TRAP-TYPE                       
					      FROM RFC-1215
	gi, motproxies                   
					      FROM NLS-BBNIDENT-MIB
	gx2Lm870C
					      FROM GX2HFC-MIB

	trapIdentifier,trapNetworkElemModelNumber,
	trapNetworkElemSerialNum, trapPerceivedSeverity,
	trapNetworkElemOperState, trapNetworkElemAlarmStatus,
	trapNetworkElemAdminState, trapNetworkElemAvailStatus,
	trapText, trapNETrapLastTrapTimeStamp, trapChangedObjectId,
	trapChangedValueInteger, trapChangedValueDisplayString
					      FROM NLSBBN-TRAPS-MIB;



	       -- This MIB module uses the extended OBJECT-TYPE macro as
	       -- defined in RFC1212 and the TRAP-TYPE macro as defined
	       -- in RFC 1215.

		   --REVISION	"1" Jan 20, 2003
		   --DESCRIPTION
		   --			Added revision and description comment section

		--    OMNISTAR Laser Module (Forward Path Transmetter)  MIB MODULE

	-- This MIB module defines information for management of HFC networks
		-- 
		-- The MIB module assumes that all generic (static) network element
		-- information is defined in a different module such as the HFC module
		-- The MIB consists of two groups:
		-- the device type descriptor subgroup and 
		-- gx2Lm870C Network Elements subgroup.
		-- The device type descriptor subgroup is used to define 
		-- parameters specific to gx2Lm870C device type.
		-- These parameters are common across all network elements
		-- from gx2Lm870C device type.
		--
		-- The gx2Lm870C Network Elements subgroup is
		-- a list of gx2Lm870C type elements in the
		-- current network topology with nominal
		-- and current parameter values for the
		-- individual network elements; the individual
		-- network elements are identified by  
		-- index from hfcCommonTable.
		-- That implies what hfcCommonTableIndex and
		-- gx2Lm870CTableIndex are equal for each individual
		-- network element.
		-- This table is an extension of the hfcCommonTable
		-- for all elements of gx2Lm870C type.
		--
		-- Both groups are mandatory for management of gx2Lm870C devices.

-- ****************************************************************************
		--
		-- All floating point numbers will be represented by an IEEE 32 Bit number.
		-- Conversion of this number must be done on the user interface to view the 
		-- actual floating point number. 
		--

		Float ::= Counter  -- UNSIGNED (32 BITS) 

-- ****************************************************************************

		-- gx2Lm870C Device Descriptor subgroup.

		-- The device type descriptor subgroup is used to define 
		-- parameters specific to gx2Lm870C device type.
		-- These parameters are common across all network elements
		-- from gx2Lm870C device type.


		gx2Lm870CDescriptor OBJECT IDENTIFIER ::= {gx2Lm870C 1}



--*****************************************************************************
		--              gx2Lm870C Table
		
		-- Contains a list of all gx2Lm870C type devices in
		-- the network. Each device is characterized with
		-- current network topology information, with nominal
		-- and current parameter values for the
		-- individual network elements;
		--
		-- The individual network elements indentified by  
		-- index from hfcCommonTable.
		-- That implies what hfcCommonTableIndex and
		-- gx2Lm870CTableIndex are equal for each individual
		-- nettwork element.
		-- This table should be used as an extension of the hfcCommonTable
		-- for all elements of gx2Lm870C type.


	       gx2lm870CAnalogTable                    OBJECT-TYPE
			 SYNTAX             SEQUENCE OF Gx2Lm870CAnalogEntry
			 ACCESS             not-accessible
			 STATUS             mandatory
			 DESCRIPTION
			 "This table contains gx2Lm870C specific parameters with
			  nominal and current values."
			 ::= { gx2Lm870C 2 }


	       gx2lm870CAnalogEntry               OBJECT-TYPE
			 SYNTAX             Gx2Lm870CAnalogEntry
			 ACCESS             not-accessible
			 STATUS             mandatory
			 DESCRIPTION
			 "This list contains the analog parameters and descriptions."
			 INDEX { gx2Lm870CAnalogTableIndex }
			 ::= { gx2lm870CAnalogTable  1}

--*************************************************************************
  	       gx2lm870CDigitalTable                    OBJECT-TYPE
  			 SYNTAX             SEQUENCE OF Gx2Lm870CDigitalEntry
  			 ACCESS             not-accessible
  			 STATUS             mandatory
  			 DESCRIPTION
  			 "This table contains gx2Lm870C specific parameters with
  			  discrete values."
  			 ::= { gx2Lm870C 3 }
  
  	       gx2lm870CDigitalEntry               OBJECT-TYPE
  			 SYNTAX             Gx2Lm870CDigitalEntry
  			 ACCESS             not-accessible
  			 STATUS             mandatory
  			 DESCRIPTION
  			 "This list contains digital parameters and descriptions."
  			 INDEX { gx2Lm870CDigitalTableIndex }
  			 ::= { gx2lm870CDigitalTable  2}
--*************************************************************************
	       gx2lm870CStatusTable                    OBJECT-TYPE
			 SYNTAX             SEQUENCE OF Gx2Lm870CStatusEntry
			 ACCESS             not-accessible
			 STATUS             mandatory
			 DESCRIPTION
			 "This table contains gx2Lm870C specific parameters with
			  current values."
			 ::= { gx2Lm870C 4 }

	       gx2lm870CStatusEntry               OBJECT-TYPE
			 SYNTAX             Gx2Lm870CStatusEntry
			 ACCESS             not-accessible
			 STATUS             mandatory
			 DESCRIPTION
			 "This list contains Status parameters and descriptions."
			 INDEX { gx2Lm870CStatusTableIndex }
			 ::= { gx2lm870CStatusTable  3}

--*************************************************************************
	       gx2lm870CFactoryTable                    OBJECT-TYPE
			 SYNTAX             SEQUENCE OF Gx2Lm870CFactoryEntry
			 ACCESS             not-accessible
			 STATUS             mandatory
			 DESCRIPTION
			 "This table contains gx2Lm870C specific parameters with
			  stored factory values."
			 ::= { gx2Lm870C 5 }

	       gx2lm870CFactoryEntry               OBJECT-TYPE
			 SYNTAX             Gx2Lm870CFactoryEntry
			 ACCESS             not-accessible
			 STATUS             mandatory
			 DESCRIPTION
			 "This list contains Factory parameters and descriptions."
			 INDEX { gx2Lm870CFactoryTableIndex }
			 ::= { gx2lm870CFactoryTable  4}
--*************************************************************************

	      Gx2Lm870CAnalogEntry    ::= SEQUENCE  
	       {
		gx2Lm870CAnalogTableIndex         INTEGER,
		
		--           Analog Parameters

		lm870ClabelFanCurrent			DisplayString (SIZE (0..80)),
		lm870CuomFanCurrent				DisplayString (SIZE (0..80)),
		lm870CmajorHighFanCurrent		Float, 
		lm870CmajorLowFanCurrent		Float, 
		lm870CminorHighFanCurrent		Float,
		lm870CminorLowFanCurrent		Float, 
		lm870CcurrentValueFanCurrent	Float, 
		lm870CstateFlagFanCurrent		INTEGER,
		lm870CminValueFanCurrent		Float,
		lm870CmaxValueFanCurrent 		Float,
		lm870CalarmStateFanCurrent		INTEGER,

		lm870Clabel12Volt				DisplayString (SIZE (0..80)),
		lm870Cuom12Volt					DisplayString (SIZE (0..80)),
		lm870CmajorHigh12Volt			Float, 
		lm870CmajorLow12Volt			Float, 
		lm870CminorHigh12Volt			Float,
		lm870CminorLow12Volt			Float, 
		lm870CcurrentValue12Volt		Float, 
		lm870CstateFlag12Volt			INTEGER,
		lm870CminValue12Volt			Float,
		lm870CmaxValue12Volt			Float,
		lm870CalarmState12Volt			INTEGER,

		lm870ClabelModTemp				DisplayString (SIZE (0..80)),
		lm870CuomModTemp				DisplayString (SIZE (0..80)),
		lm870CmajorHighModTemp			Float, 
		lm870CmajorLowModTemp			Float, 
		lm870CminorHighModTemp			Float,
		lm870CminorLowModTemp			Float, 
		lm870CcurrentValueModTemp		Float, 
		lm870CstateFlagModTemp			INTEGER,
		lm870CminValueModTemp			Float,
		lm870CmaxValueModTemp			Float,
		lm870CalarmStateModTemp			INTEGER,

		lm870ClabelOmiOffset			DisplayString (SIZE (0..80)),
		lm870CuomOmiOffset				DisplayString (SIZE (0..80)),
		lm870CmajorHighOmiOffset		Float, 
		lm870CmajorLowOmiOffset			Float, 
		lm870CminorHighOmiOffset		Float,
		lm870CminorLowOmiOffset			Float, 
		lm870CcurrentValueOmiOffset		Float, 
		lm870CstateFlagOmiOffset		INTEGER,
		lm870CminValueOmiOffset			Float,
		lm870CmaxValueOmiOffset 		Float,
		lm870CalarmStateOmiOffset		INTEGER,

		lm870ClabelOPTPower				DisplayString (SIZE (0..80)),
		lm870CuomOPTPower				DisplayString (SIZE (0..80)),
		lm870CmajorHighOPTPower			Float, 
		lm870CmajorLowOPTPower			Float, 
		lm870CminorHighOPTPower			Float,
		lm870CminorLowOPTPower			Float, 
		lm870CcurrentValueOPTPower		Float, 
		lm870CstateFlagOPTPower			INTEGER,
		lm870CminValueOPTPower			Float,
		lm870CmaxValueOPTPower 			Float,
		lm870CalarmStateOPTPower		INTEGER,

		lm870ClabelLaserBias			DisplayString (SIZE (0..80)),
		lm870CuomLaserBias				DisplayString (SIZE (0..80)),
		lm870CmajorHighLaserBias		Float, 
		lm870CmajorLowLaserBias			Float, 
		lm870CminorHighLaserBias		Float,
		lm870CminorLowLaserBias			Float, 
		lm870CcurrentValueLaserBias		Float, 
		lm870CstateFlagLaserBias		INTEGER,
		lm870CminValueLaserBias			Float,
		lm870CmaxValueLaserBias 		Float,
		lm870CalarmStateLaserBias		INTEGER,

		lm870ClabelTecCurrent			DisplayString (SIZE (0..80)),
		lm870CuomTecCurrent				DisplayString (SIZE (0..80)),
		lm870CmajorHighTecCurrent		Float, 
		lm870CmajorLowTecCurrent		Float, 
		lm870CminorHighTecCurrent		Float,
		lm870CminorLowTecCurrent		Float, 
		lm870CcurrentValueTecCurrent	Float, 
		lm870CstateFlagTecCurrent		INTEGER,
		lm870CminValueTecCurrent		Float,
		lm870CmaxValueTecCurrent 		Float,
		lm870CalarmStateTecCurrent		INTEGER,
		
		lm870ClabelOmiAlarmSetpoint			DisplayString (SIZE (0..80)),
		lm870CuomOmiAlarmSetpoint  			DisplayString (SIZE (0..80)),
		lm870CmajorHighOmiAlarmSetpoint		Float, 
		lm870CmajorLowOmiAlarmSetpoint 		Float, 
		lm870CminorHighOmiAlarmSetpoint		Float,
		lm870CminorLowOmiAlarmSetpoint 		Float, 
		lm870CcurrentValueOmiAlarmSetpoint	Float, 
		lm870CstateFlagOmiAlarmSetpoint		INTEGER,
		lm870CminValueOmiAlarmSetpoint	  	Float,
		lm870CmaxValueOmiAlarmSetpoint	  	Float,
		lm870CalarmStateOmiAlarmSetpoint  	INTEGER

		}

		-- ****************  Digital Parameters ***********************

	      Gx2Lm870CDigitalEntry    ::= SEQUENCE  
	       {
		gx2Lm870CDigitalTableIndex         INTEGER,
		
		lm870ClabelOMIOffsetAlarms			DisplayString (SIZE (0..80)),
		lm870CenumOMIOffsetAlarms			DisplayString (SIZE (0..80)),
		lm870CvalueOMIOffsetAlarms			INTEGER,
		lm870CstateFlagOMIOffsetAlarms  	INTEGER,

		lm870ClabelFactoryDefault			DisplayString (SIZE (0..80)),
		lm870CenumFactoryDefault			DisplayString (SIZE (0..80)),
		lm870CvalueFactoryDefault			INTEGER,
		lm870CstateFlagFactoryDefault   	INTEGER,

		lm870ClabelOMISetpoint				DisplayString (SIZE (0..80)),
		lm870CenumOMISetpoint				DisplayString (SIZE (0..80)),
		lm870CvalueOMISetpoint				INTEGER,
		lm870CstateFlagOMISetpoint		   	INTEGER

  		}

		-- ****************  Status Parameters ************************************
	    Gx2Lm870CStatusEntry    ::= SEQUENCE  
	    {
		gx2Lm870CStatusTableIndex		INTEGER,

		lm870ClabelBoot					DisplayString (SIZE (0..80)),
		lm870CvalueBoot					INTEGER,
		lm870CstateflagBoot				INTEGER,
		
		lm870ClabelFlash				DisplayString (SIZE (0..80)),
		lm870CvalueFlash				INTEGER,
		lm870CstateflagFlash			INTEGER,

		lm870ClabelRFOverload	 		DisplayString (SIZE (0..80)),
		lm870CvalueRFOverload			INTEGER,
		lm870CstateflagRFOverload		INTEGER,

		lm870ClabelRFPower		 		DisplayString (SIZE (0..80)),
		lm870CvalueRFPower 				INTEGER,
		lm870CstateflagRFPower			INTEGER,

		lm870ClabelFactoryDataCRC 		DisplayString (SIZE (0..80)),
		lm870CvalueFactoryDataCRC		INTEGER,
		lm870CstateflagFactoryDataCRC	INTEGER,

		lm870ClabelAlarmDataCrc			DisplayString (SIZE (0..80)),
		lm870CvalueAlarmDataCrc			INTEGER,
		lm870CstateflagAlarmDataCrc		INTEGER,

		lm870ClabelModSetDataCRC		DisplayString (SIZE (0..80)),
		lm870CvalueModSetDataCRC 		INTEGER,
		lm870CstateflagModSetDataCRC	INTEGER,

		lm870ClabelOptCalDataCRC		DisplayString (SIZE (0..80)),
		lm870CvalueOptCalDataCRC 		INTEGER,
		lm870CstateflagOptCalDataCRC	INTEGER,

		lm870ClabelRFCalDataCRC			DisplayString (SIZE (0..80)),
		lm870CvalueRFCalDataCRC 		INTEGER,
		lm870CstateflagRFCalDataCRC		INTEGER

		}


		-- ****************  Factory Parameters *************************************
	    Gx2Lm870CFactoryEntry    ::= SEQUENCE  
	    {
		gx2Lm870CFactoryTableIndex		INTEGER,
		lm870CbootControlByte  			INTEGER,
		lm870CbootStatusByte   			INTEGER,
		lm870Cbank1CRC    				INTEGER,
		lm870Cbank2CRC    				INTEGER,
		lm870CprgEEPROMByte    			INTEGER,
		lm870CfactoryCRC    			INTEGER,
		lm870CcalculateCRC    			INTEGER,
		lm870ChourMeter    				INTEGER,
		lm870CflashPrgCntA    			INTEGER,
		lm870CflashPrgCntB    			INTEGER,
		lm870CflashBankARev    			DisplayString (SIZE (0..80)),
		lm870CflashBankBRev    			DisplayString (SIZE (0..80))


		}
            -- ************** Analog Parameters ****************************
		gx2Lm870CAnalogTableIndex			OBJECT-TYPE
			   SYNTAX				INTEGER (1..4294967295)
			   ACCESS				read-only
			   STATUS				mandatory
			   DESCRIPTION			
			   "The value of this object identifies the network
			    element. This index is equal to the
			    hfcCommonTableIndex for the same element."
			   ::= { gx2lm870CAnalogEntry 1}

-- New Parameter

		lm870ClabelFanCurrent           OBJECT-TYPE
			   SYNTAX           DisplayString (SIZE (0..80))
			   ACCESS           read-only
			   STATUS           optional
			   DESCRIPTION
			   "The value of this object provides the label of the
			    Fan Current Analog parameter."
			   ::= { gx2lm870CAnalogEntry 2}

		lm870CuomFanCurrent             OBJECT-TYPE
			   SYNTAX           DisplayString (SIZE (0..80))
			   ACCESS           read-only
			   STATUS           optional
			   DESCRIPTION
			   "The value of this object provides the Unit of Measure of the
			    Fan Current Analog parameter."
			   ::= { gx2lm870CAnalogEntry 3}

		lm870CmajorHighFanCurrent       OBJECT-TYPE
			   SYNTAX           Float 
			   ACCESS           read-only
			   STATUS           mandatory
			   DESCRIPTION
			   "The value of this object provides the Major High alarm value
			    of the Fan Current Analog parameter.
			   This value is a floating point number that is represented as an IEEE 32 bit number."
			   ::= { gx2lm870CAnalogEntry 4}


		lm870CmajorLowFanCurrent        OBJECT-TYPE
			   SYNTAX           Float 
			   ACCESS           read-only
			   STATUS           mandatory
			   DESCRIPTION
			   "The value of this object provides the Major Low alarm value
			    of the Fan Current Analog parameter.
			   This value is a floating point number that is represented as an IEEE 32 bit number."
			   ::= { gx2lm870CAnalogEntry 5}

		lm870CminorHighFanCurrent       OBJECT-TYPE
			   SYNTAX           Float
			   ACCESS           read-only
			   STATUS           mandatory
			   DESCRIPTION
			   "The value of this object provides the Minor High alarm value
			    of the Fan Current Analog parameter.
			   This value is a floating point number that is represented as an IEEE 32 bit number."
			   ::= { gx2lm870CAnalogEntry 6}

		lm870CminorLowFanCurrent        OBJECT-TYPE
			   SYNTAX           Float 
			   ACCESS           read-only
			   STATUS           mandatory
			   DESCRIPTION
			   "The value of this object provides the Minor Low alarm value
			    of the Fan Current Analog parameter.
			   This value is a floating point number that is represented as an IEEE 32 bit number."
			   ::= { gx2lm870CAnalogEntry 7}

		lm870CcurrentValueFanCurrent    OBJECT-TYPE
			   SYNTAX           Float 
			   ACCESS           read-only
			   STATUS           mandatory
			   DESCRIPTION
			   "The value of this object provides the Current value
			    of the Fan Current Analog parameter.
			   This value is a floating point number that is represented as an IEEE 32 bit number."
			   ::= { gx2lm870CAnalogEntry 8}

		lm870CstateFlagFanCurrent       OBJECT-TYPE
			   SYNTAX           INTEGER
								{
								hidden(1),
								read-only(2),
								updateable(3)
								}
			   ACCESS           read-only
			   STATUS           mandatory
			   DESCRIPTION
			   "The value of this object provides the state
			    of the Fan Current Analog parameter. (0-Hidden	
			          1-Read-Only, 2-Updateable)."
			   ::= { gx2lm870CAnalogEntry 9}

		lm870CminValueFanCurrent        OBJECT-TYPE
			   SYNTAX           Float
			   ACCESS           read-only
			   STATUS           mandatory
			   DESCRIPTION
			   "The value of this object provides the minimum value
			    the Fan Current Analog parameter can achive.
			   This value is a floating point number that is represented as an IEEE 32 bit number."
			   ::= { gx2lm870CAnalogEntry 10}

		lm870CmaxValueFanCurrent        OBJECT-TYPE
			   SYNTAX           Float
			   ACCESS           read-only
			   STATUS           mandatory
			   DESCRIPTION
			   "The value of this object provides the maximum value
			    the Fan Current Analog parameter can achive.
			   This value is a floating point number that is represented as an IEEE 32 bit number."
			   ::= { gx2lm870CAnalogEntry 11}

		lm870CalarmStateFanCurrent      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Fan Current Analog parameter."
			   ::= { gx2lm870CAnalogEntry 12}

-- New Parameter

		lm870Clabel12Volt               OBJECT-TYPE
			   SYNTAX           DisplayString (SIZE (0..80))
			   ACCESS           read-only
			   STATUS           optional
			   DESCRIPTION
			   "The value of this object provides the label of the
			    12v Current Analog parameter."
			   ::= { gx2lm870CAnalogEntry 13}

		lm870Cuom12Volt                 OBJECT-TYPE
			   SYNTAX           DisplayString (SIZE (0..80))
			   ACCESS           read-only
			   STATUS           optional
			   DESCRIPTION
			   "The value of this object provides the Unit of Measure of the
			    12v Current Analog parameter."
			   ::= { gx2lm870CAnalogEntry 14}

		lm870CmajorHigh12Volt           OBJECT-TYPE
			   SYNTAX           Float 
			   ACCESS           read-only
			   STATUS           mandatory
			   DESCRIPTION
			   "The value of this object provides the Major High alarm value
			    of the 12v Current Analog parameter.
			   This value is a floating point number that is represented as an IEEE 32 bit number."
			   ::= { gx2lm870CAnalogEntry 15}


		lm870CmajorLow12Volt            OBJECT-TYPE
			   SYNTAX           Float 
			   ACCESS           read-only
			   STATUS           mandatory
			   DESCRIPTION
			   "The value of this object provides the Major Low alarm value
			    of the 12v Current Analog parameter.
			   This value is a floating point number that is represented as an IEEE 32 bit number."
			   ::= { gx2lm870CAnalogEntry 16}

		lm870CminorHigh12Volt           OBJECT-TYPE
			   SYNTAX           Float
			   ACCESS           read-only
			   STATUS           mandatory
			   DESCRIPTION
			   "The value of this object provides the Minor High alarm value
			    of the 12v Current Analog parameter.
			   This value is a floating point number that is represented as an IEEE 32 bit number."
			   ::= { gx2lm870CAnalogEntry 17}

		lm870CminorLow12Volt            OBJECT-TYPE
			   SYNTAX           Float 
			   ACCESS           read-only
			   STATUS           mandatory
			   DESCRIPTION
			   "The value of this object provides the Minor Low alarm value
			    of the 12v Current Analog parameter.
			   This value is a floating point number that is represented as an IEEE 32 bit number."
			   ::= { gx2lm870CAnalogEntry 18}

		lm870CcurrentValue12Volt        OBJECT-TYPE
			   SYNTAX           Float 
			   ACCESS           read-only
			   STATUS           mandatory
			   DESCRIPTION
			   "The value of this object provides the Current value
			    of the 12v Current Analog parameter.
			   This value is a floating point number that is represented as an IEEE 32 bit number."
			   ::= { gx2lm870CAnalogEntry 19}

		lm870CstateFlag12Volt           OBJECT-TYPE
			   SYNTAX           INTEGER
								{
								hidden(1),
								read-only(2),
								updateable(3)
								}
			   ACCESS           read-only
			   STATUS           mandatory
			   DESCRIPTION
			   "The value of this object provides the state
			    of the 12v Current Analog parameter. (0-Hidden	
			          1-Read-Only, 2-Updateable)."
			   ::= { gx2lm870CAnalogEntry 20}

		lm870CminValue12Volt            OBJECT-TYPE
			   SYNTAX           Float
			   ACCESS           read-only
			   STATUS           mandatory
			   DESCRIPTION
			   "The value of this object provides the minimum value
			    the 12v Current Analog parameter can achive.
			   This value is a floating point number that is represented as an IEEE 32 bit number."
			   ::= { gx2lm870CAnalogEntry 21}

		lm870CmaxValue12Volt            OBJECT-TYPE
			   SYNTAX           Float
			   ACCESS           read-only
			   STATUS           mandatory
			   DESCRIPTION
			   "The value of this object provides the maximum value
			    the 12v Current Analog parameter can achive.
			   This value is a floating point number that is represented as an IEEE 32 bit number."
			   ::= { gx2lm870CAnalogEntry 22}

		lm870CalarmState12Volt          OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the 12v Current Analog parameter."
			   ::= { gx2lm870CAnalogEntry 23}
-- New Parameter

		lm870ClabelModTemp              OBJECT-TYPE
			   SYNTAX           DisplayString (SIZE (0..80))
			   ACCESS           read-only
			   STATUS           optional
			   DESCRIPTION
			   "The value of this object provides the label of the
			    Module Temperature Analog parameter."
			   ::= { gx2lm870CAnalogEntry 24}

		lm870CuomModTemp                OBJECT-TYPE
			   SYNTAX           DisplayString (SIZE (0..80))
			   ACCESS           read-only
			   STATUS           optional
			   DESCRIPTION
			   "The value of this object provides the Unit of Measure of the
			    Module Temperature Analog parameter."
			   ::= { gx2lm870CAnalogEntry 25}

		lm870CmajorHighModTemp          OBJECT-TYPE
			   SYNTAX           Float 
			   ACCESS           read-only
			   STATUS           mandatory
			   DESCRIPTION
			   "The value of this object provides the Major High alarm value
			    of the Module Temperature Analog parameter.
			   This value is a floating point number that is represented as an IEEE 32 bit number."
			   ::= { gx2lm870CAnalogEntry 26}


		lm870CmajorLowModTemp           OBJECT-TYPE
			   SYNTAX           Float 
			   ACCESS           read-only
			   STATUS           mandatory
			   DESCRIPTION
			   "The value of this object provides the Major Low alarm value
			    of the Module Temperature Analog parameter.
			   This value is a floating point number that is represented as an IEEE 32 bit number."
			   ::= { gx2lm870CAnalogEntry 27}

		lm870CminorHighModTemp          OBJECT-TYPE
			   SYNTAX           Float
			   ACCESS           read-only
			   STATUS           mandatory
			   DESCRIPTION
			   "The value of this object provides the Minor High alarm value
			    of the Module Temperature Analog parameter.
			   This value is a floating point number that is represented as an IEEE 32 bit number."
			   ::= { gx2lm870CAnalogEntry 28}

		lm870CminorLowModTemp           OBJECT-TYPE
			   SYNTAX           Float 
			   ACCESS           read-only
			   STATUS           mandatory
			   DESCRIPTION
			   "The value of this object provides the Minor Low alarm value
			    of the Module Temperature Analog parameter.
			   This value is a floating point number that is represented as an IEEE 32 bit number."
			   ::= { gx2lm870CAnalogEntry 29}

		lm870CcurrentValueModTemp       OBJECT-TYPE
			   SYNTAX           Float 
			   ACCESS           read-only
			   STATUS           mandatory
			   DESCRIPTION
			   "The value of this object provides the Current value
			    of the Module Temperature Analog parameter.
			   This value is a floating point number that is represented as an IEEE 32 bit number."
			   ::= { gx2lm870CAnalogEntry 30}

		lm870CstateFlagModTemp          OBJECT-TYPE
			   SYNTAX           INTEGER
								{
								hidden(1),
								read-only(2),
								updateable(3)
								}
			   ACCESS           read-only
			   STATUS           mandatory
			   DESCRIPTION
			   "The value of this object provides the state
			    of the Module Temperature Analog parameter. (0-Hidden	
			          1-Read-Only, 2-Updateable)."
			   ::= { gx2lm870CAnalogEntry 31}

		lm870CminValueModTemp           OBJECT-TYPE
			   SYNTAX           Float
			   ACCESS           read-only
			   STATUS           mandatory
			   DESCRIPTION
			   "The value of this object provides the minimum value
			    the Module Temperature Analog parameter can achive.
			   This value is a floating point number that is represented as an IEEE 32 bit number."
			   ::= { gx2lm870CAnalogEntry 32}

		lm870CmaxValueModTemp           OBJECT-TYPE
			   SYNTAX           Float
			   ACCESS           read-only
			   STATUS           mandatory
			   DESCRIPTION
			   "The value of this object provides the maximum value
			    the Module Temperature Analog parameter can achive.
			   This value is a floating point number that is represented as an IEEE 32 bit number."
			   ::= { gx2lm870CAnalogEntry 33}

		lm870CalarmStateModTemp         OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Module Temperature Analog parameter."
			   ::= { gx2lm870CAnalogEntry 34}

-- New Parameter

		lm870ClabelOmiOffset             OBJECT-TYPE
			   SYNTAX           DisplayString (SIZE (0..80))
			   ACCESS           read-only
			   STATUS           optional
			   DESCRIPTION
			   "The value of this object provides the label of the
			    OMI Offset Analog parameter."
			   ::= { gx2lm870CAnalogEntry 35}

		lm870CuomOmiOffset               OBJECT-TYPE
			   SYNTAX           DisplayString (SIZE (0..80))
			   ACCESS           read-only
			   STATUS           optional
			   DESCRIPTION
			   "The value of this object provides the Unit of Measure of the
			    OMI Offset Analog parameter."
			   ::= { gx2lm870CAnalogEntry 36}

		lm870CmajorHighOmiOffset         OBJECT-TYPE
			   SYNTAX           Float 
			   ACCESS           read-only
			   STATUS           mandatory
			   DESCRIPTION
			   "The value of this object provides the Major High alarm value
			    of the OMI Offset Analog parameter.
			   This value is a floating point number that is represented as an IEEE 32 bit number."
			   ::= { gx2lm870CAnalogEntry 37}


		lm870CmajorLowOmiOffset          OBJECT-TYPE
			   SYNTAX           Float 
			   ACCESS           read-only
			   STATUS           mandatory
			   DESCRIPTION
			   "The value of this object provides the Major Low alarm value
			    of the OMI Offset Analog parameter.
			   This value is a floating point number that is represented as an IEEE 32 bit number."
			   ::= { gx2lm870CAnalogEntry 38}

		lm870CminorHighOmiOffset         OBJECT-TYPE
			   SYNTAX           Float
			   ACCESS           read-only
			   STATUS           mandatory
			   DESCRIPTION
			   "The value of this object provides the Minor High alarm value
			    of the OMI Offset Analog parameter.
			   This value is a floating point number that is represented as an IEEE 32 bit number."
			   ::= { gx2lm870CAnalogEntry 39}

		lm870CminorLowOmiOffset          OBJECT-TYPE
			   SYNTAX           Float 
			   ACCESS           read-only
			   STATUS           mandatory
			   DESCRIPTION
			   "The value of this object provides the Minor Low alarm value
			    of the OMI Offset Analog parameter.
			   This value is a floating point number that is represented as an IEEE 32 bit number."
			   ::= { gx2lm870CAnalogEntry 40}

		lm870CcurrentValueOmiOffset      OBJECT-TYPE
			   SYNTAX           Float 
			   ACCESS           read-only
			   STATUS           mandatory
			   DESCRIPTION
			   "The value of this object provides the Current value
			    of the OMI Offset Analog parameter.
			   This value is a floating point number that is represented as an IEEE 32 bit number."
			   ::= { gx2lm870CAnalogEntry 41}

		lm870CstateFlagOmiOffset         OBJECT-TYPE
			   SYNTAX           INTEGER
								{
								hidden(1),
								read-only(2),
								updateable(3)
								}
			   ACCESS           read-only
			   STATUS           mandatory
			   DESCRIPTION
			   "The value of this object provides the state
			    of the OMI Offset Analog parameter. (0-Hidden	
			          1-Read-Only, 2-Updateable)."
			   ::= { gx2lm870CAnalogEntry 42}

		lm870CminValueOmiOffset          OBJECT-TYPE
			   SYNTAX           Float
			   ACCESS           read-only
			   STATUS           mandatory
			   DESCRIPTION
			   "The value of this object provides the minimum value
			    the OMI Offset Analog parameter can achive.
			   This value is a floating point number that is represented as an IEEE 32 bit number."
			   ::= { gx2lm870CAnalogEntry 43}

		lm870CmaxValueOmiOffset          OBJECT-TYPE
			   SYNTAX           Float
			   ACCESS           read-only
			   STATUS           mandatory
			   DESCRIPTION
			   "The value of this object provides the maximum value
			    the OMI Offset Analog parameter can achive.
			   This value is a floating point number that is represented as an IEEE 32 bit number."
			   ::= { gx2lm870CAnalogEntry 44}

		lm870CalarmStateOmiOffset        OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the OMI Offset Analog parameter."
			   ::= { gx2lm870CAnalogEntry 45}
-- New Parameter

		lm870ClabelOPTPower           OBJECT-TYPE
			   SYNTAX           DisplayString (SIZE (0..80))
			   ACCESS           read-only
			   STATUS           optional
			   DESCRIPTION
			   "The value of this object provides the label of the
			    Optical Power Analog parameter."
			   ::= { gx2lm870CAnalogEntry 46}

		lm870CuomOPTPower             OBJECT-TYPE
			   SYNTAX           DisplayString (SIZE (0..80))
			   ACCESS           read-only
			   STATUS           optional
			   DESCRIPTION
			   "The value of this object provides the Unit of Measure of the
			    Optical Power Analog parameter.."
			   ::= { gx2lm870CAnalogEntry 47}

		lm870CmajorHighOPTPower       OBJECT-TYPE
			   SYNTAX           Float 
			   ACCESS           read-only
			   STATUS           mandatory
			   DESCRIPTION
			   "The value of this object provides the Major High alarm value
			    of the Optical Power  Analog parameter.
			   This value is a floating point number that is represented as an IEEE 32 bit number."
			   ::= { gx2lm870CAnalogEntry 48}


		lm870CmajorLowOPTPower        OBJECT-TYPE
			   SYNTAX           Float 
			   ACCESS           read-only
			   STATUS           mandatory
			   DESCRIPTION
			   "The value of this object provides the Major Low alarm value
			    of the Optical Power Analog parameter.
			   This value is a floating point number that is represented as an IEEE 32 bit number."
			   ::= { gx2lm870CAnalogEntry 49}

		lm870CminorHighOPTPower       OBJECT-TYPE
			   SYNTAX           Float
			   ACCESS           read-only
			   STATUS           mandatory
			   DESCRIPTION
			   "The value of this object provides the Minor High alarm value
			    of the Optical Power Analog parameter.
			   This value is a floating point number that is represented as an IEEE 32 bit number."
			   ::= { gx2lm870CAnalogEntry 50}

		lm870CminorLowOPTPower        OBJECT-TYPE
			   SYNTAX           Float 
			   ACCESS           read-only
			   STATUS           mandatory
			   DESCRIPTION
			   "The value of this object provides the Minor Low alarm value
			    of the Optical Power Analog parameter.
			   This value is a floating point number that is represented as an IEEE 32 bit number."
			   ::= { gx2lm870CAnalogEntry 51}

		lm870CcurrentValueOPTPower    OBJECT-TYPE
			   SYNTAX           Float 
			   ACCESS           read-only
			   STATUS           mandatory
			   DESCRIPTION
			   "The value of this object provides the Current value
			    of the Optical Power Analog parameter.
			   This value is a floating point number that is represented as an IEEE 32 bit number."
			   ::= { gx2lm870CAnalogEntry 52}

		lm870CstateFlagOPTPower       OBJECT-TYPE
			   SYNTAX           INTEGER
								{
								hidden(1),
								read-only(2),
								updateable(3)
								}
			   ACCESS           read-only
			   STATUS           mandatory
			   DESCRIPTION
			   "The value of this object provides the state
			    of the Optical Power Analog parameter. (0-Hidden	
			          1-Read-Only, 2-Updateable)."
			   ::= { gx2lm870CAnalogEntry 53}

		lm870CminValueOPTPower        OBJECT-TYPE
			   SYNTAX           Float
			   ACCESS           read-only
			   STATUS           mandatory
			   DESCRIPTION
			   "The value of this object provides the minimum value
			    the Optical Power Analog parameter can achive.
	   		   This value is a floating point number that is represented as an IEEE 32 bit number."
			   ::= { gx2lm870CAnalogEntry 54}

		lm870CmaxValueOPTPower        OBJECT-TYPE
			   SYNTAX           Float
			   ACCESS           read-only
			   STATUS           mandatory
			   DESCRIPTION
			   "The value of this object provides the maximum value
			    the Optical Power Analog parameter can achive.
			   This value is a floating point number that is represented as an IEEE 32 bit number."
			   ::= { gx2lm870CAnalogEntry 55}

		lm870CalarmStateOPTPower      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Optical Power Analog parameter."
			   ::= { gx2lm870CAnalogEntry 56}

-- New Parameter

		lm870ClabelLaserBias            OBJECT-TYPE
			   SYNTAX           DisplayString (SIZE (0..80))
			   ACCESS           read-only
			   STATUS           optional
			   DESCRIPTION
			   "The value of this object provides the label of the
			    Laser Bias Current Analog parameter."
			   ::= { gx2lm870CAnalogEntry 57}

		lm870CuomLaserBias              OBJECT-TYPE
			   SYNTAX           DisplayString (SIZE (0..80))
			   ACCESS           read-only
			   STATUS           optional
			   DESCRIPTION
			   "The value of this object provides the Unit of Measure of the
			    Laser Bias Analog parameter."
			   ::= { gx2lm870CAnalogEntry 58}

		lm870CmajorHighLaserBias        OBJECT-TYPE
			   SYNTAX           Float 
			   ACCESS           read-only
			   STATUS           mandatory
			   DESCRIPTION
			   "The value of this object provides the Major High alarm value
			    of the Laser Bias Analog parameter.
			   This value is a floating point number that is represented as an IEEE 32 bit number."
			   ::= { gx2lm870CAnalogEntry 59}


		lm870CmajorLowLaserBias         OBJECT-TYPE
			   SYNTAX           Float 
			   ACCESS           read-only
			   STATUS           mandatory
			   DESCRIPTION
			   "The value of this object provides the Major Low alarm value
			    of the Laser Bias Analog parameter.
			   This value is a floating point number that is represented as an IEEE 32 bit number."
			   ::= { gx2lm870CAnalogEntry 60}

		lm870CminorHighLaserBias        OBJECT-TYPE
			   SYNTAX           Float
			   ACCESS           read-only
			   STATUS           mandatory
			   DESCRIPTION
			   "The value of this object provides the Minor High alarm value
			    of the Laser Bias Analog parameter.
			   This value is a floating point number that is represented as an IEEE 32 bit number."
			   ::= { gx2lm870CAnalogEntry 61}

		lm870CminorLowLaserBias         OBJECT-TYPE
			   SYNTAX           Float 
			   ACCESS           read-only
			   STATUS           mandatory
			   DESCRIPTION
			   "The value of this object provides the Minor Low alarm value
			    of the Laser Bias Analog parameter.
			   This value is a floating point number that is represented as an IEEE 32 bit number."
			   ::= { gx2lm870CAnalogEntry 62}

		lm870CcurrentValueLaserBias     OBJECT-TYPE
			   SYNTAX           Float 
			   ACCESS           read-only
			   STATUS           mandatory
			   DESCRIPTION
			   "The value of this object provides the Current value
			    of the Laser Bias Analog parameter.
			   This value is a floating point number that is represented as an IEEE 32 bit number."
			   ::= { gx2lm870CAnalogEntry 63}

		lm870CstateFlagLaserBias        OBJECT-TYPE
			   SYNTAX           INTEGER
								{
								hidden(1),
								read-only(2),
								updateable(3)
								}
			   ACCESS           read-only
			   STATUS           mandatory
			   DESCRIPTION
			   "The value of this object provides the state
			    of the Laser Bias Analog parameter. (0-Hidden	
			          1-Read-Only, 2-Updateable)."
			   ::= { gx2lm870CAnalogEntry 64}

		lm870CminValueLaserBias         OBJECT-TYPE
			   SYNTAX           Float
			   ACCESS           read-only
			   STATUS           mandatory
			   DESCRIPTION
			   "The value of this object provides the minimum value
			    the Laser Bias Analog parameter can achive.
			   This value is a floating point number that is represented as an IEEE 32 bit number."
			   ::= { gx2lm870CAnalogEntry 65}

		lm870CmaxValueLaserBias         OBJECT-TYPE
			   SYNTAX           Float
			   ACCESS           read-only
			   STATUS           mandatory
			   DESCRIPTION
			   "The value of this object provides the maximum value
			    the Laser Bias Analog parameter can achive.
   			   This value is a floating point number that is represented as an IEEE 32 bit number."
			   ::= { gx2lm870CAnalogEntry 66}

		lm870CalarmStateLaserBias       OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Laser Bias Analog parameter."
			   ::= { gx2lm870CAnalogEntry 67}
-- New Parameter

		lm870ClabelTecCurrent           OBJECT-TYPE
			   SYNTAX           DisplayString (SIZE (0..80))
			   ACCESS           read-only
			   STATUS           optional
			   DESCRIPTION
			   "The value of this object provides the label of the
			    TEC Current Analog parameter."
			   ::= { gx2lm870CAnalogEntry 68}

		lm870CuomTecCurrent             OBJECT-TYPE
			   SYNTAX           DisplayString (SIZE (0..80))
			   ACCESS           read-only
			   STATUS           optional
			   DESCRIPTION
			   "The value of this object provides the Unit of Measure of the
			    TEC Current Analog parameter.."
			   ::= { gx2lm870CAnalogEntry 69}

		lm870CmajorHighTecCurrent       OBJECT-TYPE
			   SYNTAX           Float 
			   ACCESS           read-only
			   STATUS           mandatory
			   DESCRIPTION
			   "The value of this object provides the Major High alarm value
			    of the TEC Current Analog parameter.
			   This value is a floating point number that is represented as an IEEE 32 bit number."
			   ::= { gx2lm870CAnalogEntry 70}


		lm870CmajorLowTecCurrent        OBJECT-TYPE
			   SYNTAX           Float 
			   ACCESS           read-only
			   STATUS           mandatory
			   DESCRIPTION
			   "The value of this object provides the Major Low alarm value
			    of the TEC Current Analog parameter.
			   This value is a floating point number that is represented as an IEEE 32 bit number."
			   ::= { gx2lm870CAnalogEntry 71}

		lm870CminorHighTecCurrent       OBJECT-TYPE
			   SYNTAX           Float
			   ACCESS           read-only
			   STATUS           mandatory
			   DESCRIPTION
			   "The value of this object provides the Minor High alarm value
			    of the TEC Current Analog parameter.
			   This value is a floating point number that is represented as an IEEE 32 bit number."
			   ::= { gx2lm870CAnalogEntry 72}

		lm870CminorLowTecCurrent        OBJECT-TYPE
			   SYNTAX           Float 
			   ACCESS           read-only
			   STATUS           mandatory
			   DESCRIPTION
			   "The value of this object provides the Minor Low alarm value
			    of the TEC Current Analog parameter.
			   This value is a floating point number that is represented as an IEEE 32 bit number."
			   ::= { gx2lm870CAnalogEntry 73}

		lm870CcurrentValueTecCurrent    OBJECT-TYPE
			   SYNTAX           Float 
			   ACCESS           read-only
			   STATUS           mandatory
			   DESCRIPTION
			   "The value of this object provides the Current value
			    of the TEC Current Analog parameter.
			   This value is a floating point number that is represented as an IEEE 32 bit number."
			   ::= { gx2lm870CAnalogEntry 74}

		lm870CstateFlagTecCurrent       OBJECT-TYPE
			   SYNTAX           INTEGER
								{
								hidden(1),
								read-only(2),
								updateable(3)
								}
			   ACCESS           read-only
			   STATUS           mandatory
			   DESCRIPTION
			   "The value of this object provides the state
			    of the TEC Current Analog parameter. (0-Hidden	
			          1-Read-Only, 2-Updateable)."
			   ::= { gx2lm870CAnalogEntry 75}

		lm870CminValueTecCurrent        OBJECT-TYPE
			   SYNTAX           Float
			   ACCESS           read-only
			   STATUS           mandatory
			   DESCRIPTION
			   "The value of this object provides the minimum value
			    the TEC Current Analog parameter can achive.
	   		   This value is a floating point number that is represented as an IEEE 32 bit number."
			   ::= { gx2lm870CAnalogEntry 76}

		lm870CmaxValueTecCurrent        OBJECT-TYPE
			   SYNTAX           Float
			   ACCESS           read-only
			   STATUS           mandatory
			   DESCRIPTION
			   "The value of this object provides the maximum value
			    the TEC Current Analog parameter can achive.
			   This value is a floating point number that is represented as an IEEE 32 bit number."
			   ::= { gx2lm870CAnalogEntry 77}

		lm870CalarmStateTecCurrent      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the TEC Current Analog parameter."
			   ::= { gx2lm870CAnalogEntry 78}

-- New Parameter

		lm870ClabelOmiAlarmSetpoint           OBJECT-TYPE
			   SYNTAX           DisplayString (SIZE (0..80))
			   ACCESS           read-only
			   STATUS           optional
			   DESCRIPTION
			   "The value of this object provides the label of the
			    OMI Offset Alarm Setpoint Analog parameter."
			   ::= { gx2lm870CAnalogEntry 79}

		lm870CuomOmiAlarmSetpoint             OBJECT-TYPE
			   SYNTAX           DisplayString (SIZE (0..80))
			   ACCESS           read-only
			   STATUS           optional
			   DESCRIPTION
			   "The value of this object provides the Unit of Measure of the
			    OMI Offset Alarm Setpoint Analog parameter.."
			   ::= { gx2lm870CAnalogEntry 80}

		lm870CmajorHighOmiAlarmSetpoint       OBJECT-TYPE
			   SYNTAX           Float 
			   ACCESS           read-only
			   STATUS           mandatory
			   DESCRIPTION
			   "The value of this object provides the Major High alarm value
			    of the OMI Offset Alarm Setpoint Analog parameter.
			   This value is a floating point number that is represented as an IEEE 32 bit number."
			   ::= { gx2lm870CAnalogEntry 81}


		lm870CmajorLowOmiAlarmSetpoint        OBJECT-TYPE
			   SYNTAX           Float 
			   ACCESS           read-only
			   STATUS           mandatory
			   DESCRIPTION
			   "The value of this object provides the Major Low alarm value
			    of the OMI Offset Alarm Setpoint Analog parameter.
			   This value is a floating point number that is represented as an IEEE 32 bit number."
			   ::= { gx2lm870CAnalogEntry 82}

		lm870CminorHighOmiAlarmSetpoint       OBJECT-TYPE
			   SYNTAX           Float
			   ACCESS           read-only
			   STATUS           mandatory
			   DESCRIPTION
			   "The value of this object provides the Minor High alarm value
			    of the OMI Offset Alarm Setpoint Analog parameter.
			   This value is a floating point number that is represented as an IEEE 32 bit number."
			   ::= { gx2lm870CAnalogEntry 83}

		lm870CminorLowOmiAlarmSetpoint        OBJECT-TYPE
			   SYNTAX           Float 
			   ACCESS           read-only
			   STATUS           mandatory
			   DESCRIPTION
			   "The value of this object provides the Minor Low alarm value
			    of the OMI Offset Alarm Setpoint Analog parameter.
			   This value is a floating point number that is represented as an IEEE 32 bit number."
			   ::= { gx2lm870CAnalogEntry 84}

		lm870CcurrentValueOmiAlarmSetpoint    OBJECT-TYPE
			   SYNTAX           Float 
			   ACCESS           read-only
			   STATUS           mandatory
			   DESCRIPTION
			   "The value of this object provides the Current value
			    of the OMI Offset Alarm Setpoint Analog parameter.
			   This value is a floating point number that is represented as an IEEE 32 bit number."
			   ::= { gx2lm870CAnalogEntry 85}

		lm870CstateFlagOmiAlarmSetpoint       OBJECT-TYPE
			   SYNTAX           INTEGER
								{
								hidden(1),
								read-only(2),
								updateable(3)
								}
			   ACCESS           read-only
			   STATUS           mandatory
			   DESCRIPTION
			   "The value of this object provides the state
			    of the OMI Offset Alarm Setpoint Analog parameter. (0-Hidden	
			          1-Read-Only, 2-Updateable)."
			   ::= { gx2lm870CAnalogEntry 86}

		lm870CminValueOmiAlarmSetpoint        OBJECT-TYPE
			   SYNTAX           Float
			   ACCESS           read-only
			   STATUS           mandatory
			   DESCRIPTION
			   "The value of this object provides the minimum value
			    the OMI Offset Alarm Setpoint Analog parameter can achive.
	   		   This value is a floating point number that is represented as an IEEE 32 bit number."
			   ::= { gx2lm870CAnalogEntry 87}

		lm870CmaxValueOmiAlarmSetpoint        OBJECT-TYPE
			   SYNTAX           Float
			   ACCESS           read-only
			   STATUS           mandatory
			   DESCRIPTION
			   "The value of this object provides the maximum value
			    the OMI Offset Alarm Setpoint Analog parameter can achive.
			   This value is a floating point number that is represented as an IEEE 32 bit number."
			   ::= { gx2lm870CAnalogEntry 88}

		lm870CalarmStateOmiAlarmSetpoint      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the OMI Offset Alarm Setpoint Analog parameter."
			   ::= { gx2lm870CAnalogEntry 89}


-- ************************ Digital parameters **********************************

		gx2Lm870CDigitalTableIndex              OBJECT-TYPE
			   SYNTAX           INTEGER (1..4294967295) 
			   ACCESS           read-only
			   STATUS           mandatory
			   DESCRIPTION
			   "The value of this object identifies the network
			    element. This index is equal to the
			    hfcCommonTableIndex for the same element."
			   ::= { gx2lm870CDigitalEntry 1}

-- New parameter
		lm870ClabelOMIOffsetAlarms		OBJECT-TYPE
			   SYNTAX       		DisplayString (SIZE (0..80))         
			   ACCESS           	read-only
			   STATUS           	optional
			   DESCRIPTION
			   "The value of this object provides the label of the
			    OMI Offset Alarm mode  Digital parameter."
			   ::= { gx2lm870CDigitalEntry 2}

		lm870CenumOMIOffsetAlarms               		OBJECT-TYPE
			   SYNTAX       		DisplayString (SIZE (0..80))         
			   ACCESS           	read-only
			   STATUS           	optional
			   DESCRIPTION
			   "The value of this object represents the Enumeration values
			    possible for the OMI Offset Alarm modeDigital parameter. Each Enumerated 
			    values is separated by a common. The first value has a enumerated value of 1."
			   ::= { gx2lm870CDigitalEntry 3}

		lm870CvalueOMIOffsetAlarms                	OBJECT-TYPE
			   SYNTAX       		INTEGER
					    		{
							off(1),
							on(2),
							set(3)
					    		}
			   ACCESS           	read-write
			   STATUS           	mandatory
			   DESCRIPTION
			   "The value of this object is the current value of the parameter. Note that the value to be read
			   will always be 1 or 2 because the set value (3) is always changed to the on 
			   value (2) by the firmware"
			   ::= { gx2lm870CDigitalEntry 4}

		lm870CstateFlagOMIOffsetAlarms              OBJECT-TYPE
			   SYNTAX       		INTEGER
								{
								hidden(1),
								read-only(2),
								updateable(3)
								}
			   ACCESS           	read-only
			   STATUS           	mandatory
			   DESCRIPTION
			   "The value of this object provides the state
			    of the OMI Offset Alarm mode  Digital parameter. (0-Hidden	
			          1-Read-Only, 2-Updateable)."
			   ::= { gx2lm870CDigitalEntry 5}

-- New parameter
		lm870ClabelFactoryDefault                OBJECT-TYPE
			   SYNTAX       		DisplayString (SIZE (0..80))         
			   ACCESS           	read-only
			   STATUS           	optional
			   DESCRIPTION
			   "The value of this object provides the label of the
			    Reset to Factory Default Control  Digital parameter."
			   ::= { gx2lm870CDigitalEntry 6}

		lm870CenumFactoryDefault               	      OBJECT-TYPE
			   SYNTAX          	DisplayString (SIZE (0..80))         
			   ACCESS           	read-only
			   STATUS           	optional
			   DESCRIPTION
			   "The value of this object represents the Enumeration values
			    possible for the Reste to Factory Default Digital parameter. Each Enumerated values is
			    separated by a common. The first value has a enumerated value of 1."
			   ::= { gx2lm870CDigitalEntry 7}

		lm870CvalueFactoryDefault                OBJECT-TYPE
			   SYNTAX       		INTEGER
					    		{
							off(1),
							on(2)
					    		}
			   ACCESS           	read-write
			   STATUS           	mandatory
			   DESCRIPTION
			   "The value of this object is the current value of the parameter."
			   ::= { gx2lm870CDigitalEntry 8}

		lm870CstateFlagFactoryDefault            OBJECT-TYPE
			   SYNTAX      		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2lm870CDigitalEntry 9}

-- New parameter
		lm870ClabelOMISetpoint		OBJECT-TYPE
			   SYNTAX       		DisplayString (SIZE (0..80))         
			   ACCESS           	read-only
			   STATUS           	obsolete
			   DESCRIPTION
			   "The value of this object provides the label of the
			    OMI Setpoint  Digital parameter."
			   ::= { gx2lm870CDigitalEntry 10}

		lm870CenumOMISetpoint               		OBJECT-TYPE
			   SYNTAX       		DisplayString (SIZE (0..80))         
			   ACCESS           	read-only
			   STATUS           	obsolete
			   DESCRIPTION
			   "The value of this object represents the Enumeration values
			    possible for the OMI Setpoint Digital parameter. Each Enumerated 
			    values is separated by a common. The first value has a enumerated value of 1."
			   ::= { gx2lm870CDigitalEntry 11}

		lm870CvalueOMISetpoint                	OBJECT-TYPE
			   SYNTAX       		INTEGER
			   ACCESS           	read-only
			   STATUS           	obsolete
			   DESCRIPTION
			   "The value of this object is the current value of the OMI Setpoint parameter."
			   ::= { gx2lm870CDigitalEntry 12}

		lm870CstateFlagOMISetpoint              OBJECT-TYPE
 				 SYNTAX       		INTEGER
								{
								hidden(1),
								read-only(2),
								updateable(3)
								}
			   ACCESS           	read-only
			   STATUS				obsolete
			   DESCRIPTION
			   "The value of this object provides the state
			    of the OMI Setpoint  Digital parameter. (0-Hidden	
			          1-Read-Only, 2-Updateable)."
			   ::= { gx2lm870CDigitalEntry 13}


-- *********** STATUS *****************
		gx2Lm870CStatusTableIndex			OBJECT-TYPE
			   SYNTAX				INTEGER (1..4294967295)
			   ACCESS				read-only
			   STATUS				mandatory
			   DESCRIPTION			
			   "The value of this object identifies the network
			    element. This index is equal to the
			    hfcCommonTableIndex for the same element."
			   ::= { gx2lm870CStatusEntry 1}

--New Parameter
		lm870ClabelBoot               	OBJECT-TYPE
			   SYNTAX       		DisplayString (SIZE (0..80))         
			   ACCESS           	read-only
			   STATUS           	optional
			   DESCRIPTION
			   "The value of this object provides the label of the
			    Boot Status  Status parameter."
			   ::= { gx2lm870CStatusEntry 2}

		lm870CvalueBoot              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current value of
			    the boot status parameter (0-Ok, 1-Undetermined
			    2-Warning, 3-Minor, 4-Major, 5-Critical)."
			   ::= { gx2lm870CStatusEntry 3}

		lm870CstateflagBoot     	OBJECT-TYPE
			   SYNTAX       		INTEGER
								{
								hidden(1),
								read-only(2),
								updateable(3)
								}
			   ACCESS           	read-only
			   STATUS           	mandatory
			   DESCRIPTION
			   "The value of this object provides the state
			    of the the boot status parameter. (0-Hidden 1-Read-Only, 2-Updateable)."
			   ::= { gx2lm870CStatusEntry  4}



--New Parameter
		lm870ClabelFlash               	OBJECT-TYPE
			   SYNTAX       		DisplayString (SIZE (0..80))         
			   ACCESS           	read-only
			   STATUS           	optional
			   DESCRIPTION
			   "The value of this object provides the label of the
			    Flash Status Status parameter."
			   ::= { gx2lm870CStatusEntry 5}

		lm870CvalueFlash              	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current value of
			    the Flash Status parameter (0-Ok, 1-Undetermined
			    2-Warning, 3-Minor, 4-Major, 5-Critical)."
			   ::= { gx2lm870CStatusEntry 6}

		lm870CstateflagFlash     	OBJECT-TYPE
			   SYNTAX       		INTEGER
								{
								hidden(1),
								read-only(2),
								updateable(3)
								}
			   ACCESS           	read-only
			   STATUS           	mandatory
			   DESCRIPTION
			   "The value of this object provides the state	current
			    of the the Flash Status parameter. (0-Hidden 1-Read-Only, 2-Updateable)."
			   ::= { gx2lm870CStatusEntry  7}

--New Parameter
		lm870ClabelRFOverload           OBJECT-TYPE
			   SYNTAX       		DisplayString (SIZE (0..80))         
			   ACCESS           	read-only
			   STATUS           	optional
			   DESCRIPTION
			   "The value of this object provides the label for the
			    RF Overload Status parameter."
			   ::= { gx2lm870CStatusEntry 8}

		lm870CvalueRFOverload          	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current value of
			    the RF Overload parameter (0-Ok, 1-Undetermined
			    2-Warning, 3-Minor, 4-Major, 5-Critical)."
			   ::= { gx2lm870CStatusEntry 9}

		lm870CstateflagRFOverload     	OBJECT-TYPE
			   SYNTAX       		INTEGER
								{
								hidden(1),
								read-only(2),
								updateable(3)
								}
			   ACCESS           	read-only
			   STATUS           	mandatory
			   DESCRIPTION
			   "The value of this object provides the current state
			    of the RF Overload parameter. (0-Hidden 1-Read-Only, 2-Updateable)."
			   ::= { gx2lm870CStatusEntry  10}


--New Parameter
		lm870ClabelRFPower           OBJECT-TYPE
			   SYNTAX       		DisplayString (SIZE (0..80))         
			   ACCESS           	read-only
			   STATUS           	optional
			   DESCRIPTION
			   "The value of this object provides the label for the
			    RF Power Status parameter."
			   ::= { gx2lm870CStatusEntry 11}

		lm870CvalueRFPower          	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current value of
			    the RF Power parameter (0-Ok, 1-Undetermined
			    2-Warning, 3-Minor, 4-Major, 5-Critical)."
			   ::= { gx2lm870CStatusEntry 12}

		lm870CstateflagRFPower     	OBJECT-TYPE
			   SYNTAX       		INTEGER
								{
								hidden(1),
								read-only(2),
								updateable(3)
								}
			   ACCESS           	read-only
			   STATUS           	mandatory
			   DESCRIPTION
			   "The value of this object provides the current state
			    of the RF Power parameter. (0-Hidden 1-Read-Only, 2-Updateable)."
			   ::= { gx2lm870CStatusEntry  13}


--New Parameter
		lm870ClabelFactoryDataCRC           OBJECT-TYPE
			   SYNTAX       		DisplayString (SIZE (0..80))         
			   ACCESS           	read-only
			   STATUS           	optional
			   DESCRIPTION
			   "The value of this object provides the label of the
			    Factory Data CRC Status parameter."
			   ::= { gx2lm870CStatusEntry 14}

		lm870CvalueFactoryDataCRC          	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current value of
			    the Factory Data CRC parameter (0-Ok, 1-Undetermined
			    2-Warning, 3-Minor, 4-Major, 5-Critical)."
			   ::= { gx2lm870CStatusEntry 15}

		lm870CstateflagFactoryDataCRC     	OBJECT-TYPE
			   SYNTAX       		INTEGER
								{
								hidden(1),
								read-only(2),
								updateable(3)
								}
			   ACCESS           	read-only
			   STATUS           	mandatory
			   DESCRIPTION
			   "The value of this object provides the current state
			    of the the Factory Data CRC parameter. (0-Hidden 1-Read-Only, 2-Updateable)."
			   ::= { gx2lm870CStatusEntry  16}


--New Parameter
		lm870ClabelAlarmDataCrc               	      OBJECT-TYPE
			   SYNTAX       		DisplayString (SIZE (0..80))         
			   ACCESS           	read-only
			   STATUS           	optional
			   DESCRIPTION
			   "The value of this object provides the label of the
			    Alarm Data Crc parameter."
			   ::= { gx2lm870CStatusEntry 17}

		lm870CvalueAlarmDataCrc              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current value of
			    the Alarm Data Crc parameter (0-Ok, 1-Undetermined
			    2-Warning, 3-Minor, 4-Major, 5-Critical)."
			   ::= { gx2lm870CStatusEntry 18}

		lm870CstateflagAlarmDataCrc     	OBJECT-TYPE
			   SYNTAX       		INTEGER
								{
								hidden(1),
								read-only(2),
								updateable(3)
								}
			   ACCESS           	read-only
			   STATUS           	mandatory
			   DESCRIPTION
			   "The value of this object provides the current state
			    of the the Alarm Data Crc parameter. (0-Hidden 1-Read-Only, 2-Updateable)."
			   ::= { gx2lm870CStatusEntry  19}

--New Parameter
		
		lm870ClabelModSetDataCRC       OBJECT-TYPE
			   SYNTAX               DisplayString (SIZE (0..80))         
			   ACCESS           	read-only
			   STATUS           	optional
			   DESCRIPTION
			   "The value of this object provides the label of the
			    Module Settings Data Crc parameter."
			   ::= { gx2lm870CStatusEntry 20}

		lm870CvalueModSetDataCRC              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current value of
			    the Module Settings Data Crc parameter (0-Ok, 1-Undetermined
			    2-Warning, 3-Minor, 4-Major, 5-Critical)."
			   ::= { gx2lm870CStatusEntry 21}

		lm870CstateflagModSetDataCRC     	OBJECT-TYPE
			   SYNTAX       		INTEGER
								{
								hidden(1),
								read-only(2),
								updateable(3)
								}
			   ACCESS           	read-only
			   STATUS           	mandatory
			   DESCRIPTION
			   "The value of this object provides the current state
			    of the the Module Settings Data Crc parameter. (0-Hidden 1-Read-Only, 2-Updateable)."
			   ::= { gx2lm870CStatusEntry  22}

--New Parameter
		
		lm870ClabelOptCalDataCRC       OBJECT-TYPE
			   SYNTAX               DisplayString (SIZE (0..80))         
			   ACCESS           	read-only
			   STATUS           	optional
			   DESCRIPTION
			   "The value of this object provides the label of the
			    Optical Calibration Data Crc parameter."
			   ::= { gx2lm870CStatusEntry 23}

		lm870CvalueOptCalDataCRC              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current value of
			    the Optical Calibration Data Crc parameter (0-Ok, 1-Undetermined
			    2-Warning, 3-Minor, 4-Major, 5-Critical)."
			   ::= { gx2lm870CStatusEntry 24}

		lm870CstateflagOptCalDataCRC     	OBJECT-TYPE
			   SYNTAX       		INTEGER
								{
								hidden(1),
								read-only(2),
								updateable(3)
								}
			   ACCESS           	read-only
			   STATUS           	mandatory
			   DESCRIPTION
			   "The value of this object provides the current state
			    of the the Optical Calibration Data Crc parameter. (0-Hidden 1-Read-Only, 2-Updateable)."
			   ::= { gx2lm870CStatusEntry  25}

--New Parameter
		
		lm870ClabelRFCalDataCRC       OBJECT-TYPE
			   SYNTAX               DisplayString (SIZE (0..80))         
			   ACCESS           	read-only
			   STATUS           	optional
			   DESCRIPTION
			   "The value of this object provides the label of the
			    RF Calibration Data Crc parameter."
			   ::= { gx2lm870CStatusEntry 26}

		lm870CvalueRFCalDataCRC              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current value of
			    the RF Calibration Data Crc parameter (0-Ok, 1-Undetermined
			    2-Warning, 3-Minor, 4-Major, 5-Critical)."
			   ::= { gx2lm870CStatusEntry 27}

		lm870CstateflagRFCalDataCRC     	OBJECT-TYPE
			   SYNTAX       		INTEGER
								{
								hidden(1),
								read-only(2),
								updateable(3)
								}
			   ACCESS           	read-only
			   STATUS           	mandatory
			   DESCRIPTION
			   "The value of this object provides the current state
			    of the the RF Calibration Data Crc parameter. (0-Hidden 1-Read-Only, 2-Updateable)."
			   ::= { gx2lm870CStatusEntry  28}

            -- ************ FACTORY DATA ****************
		gx2Lm870CFactoryTableIndex			OBJECT-TYPE
			   SYNTAX				INTEGER (1..4294967295)
			   ACCESS				read-only
			   STATUS				mandatory
			   DESCRIPTION			
			   "The value of this object identifies the network
			    element. This index is equal to the
			    hfcCommonTableIndex for the same element."
			   ::= { gx2lm870CFactoryEntry 1}

		lm870CbootControlByte          	OBJECT-TYPE
			   SYNTAX       		INTEGER
			   ACCESS           	read-only
			   STATUS           	mandatory
			   DESCRIPTION
			   "The value of this object indicates which bank the firmware
			    is currently being boot from."
			   ::= { gx2lm870CFactoryEntry 2}

		lm870CbootStatusByte          	OBJECT-TYPE
			   SYNTAX       		INTEGER
			   ACCESS           	read-only
			   STATUS           	mandatory
			   DESCRIPTION
			   "This object indicates the status of the last boot"
			   ::= { gx2lm870CFactoryEntry 3}

		lm870Cbank1CRC          		OBJECT-TYPE
			   SYNTAX       		INTEGER
			   ACCESS           	read-only
			   STATUS           	mandatory
			   DESCRIPTION
			   "This object provides the CRC code of bank 0."
			   ::= { gx2lm870CFactoryEntry 4}

		lm870Cbank2CRC          		OBJECT-TYPE
			   SYNTAX       		INTEGER
			   ACCESS           	read-only
			   STATUS           	mandatory
			   DESCRIPTION
			   "This object provides the CRC code of bank 1."
			   ::= { gx2lm870CFactoryEntry 5}

		lm870CprgEEPROMByte          		OBJECT-TYPE
			   SYNTAX       		INTEGER
			   ACCESS           	read-only
			   STATUS           	mandatory
			   DESCRIPTION
			   "This object indicates if the EEPROM has been programmed"
			   ::= { gx2lm870CFactoryEntry 6}

		lm870CfactoryCRC          		OBJECT-TYPE
			   SYNTAX       		INTEGER
			   ACCESS           	read-only
			   STATUS           	mandatory
			   DESCRIPTION
			   "This object provides the CRC code for the Factory data."
			   ::= { gx2lm870CFactoryEntry 7}

		lm870CcalculateCRC          		OBJECT-TYPE
			   SYNTAX       		INTEGER
					    		{
							factory(1),
							settings(2),
							alarm(3),
							opticalCal(4),
							rfCal(5)
					    		}
			   ACCESS           	read-only
			   STATUS           	mandatory
			   DESCRIPTION
			   "This object indicates which of the Emnums will have the CRC calculated."
			   ::= { gx2lm870CFactoryEntry 8}

		lm870ChourMeter          		OBJECT-TYPE
			   SYNTAX       		INTEGER
			   ACCESS           	read-only
			   STATUS           	mandatory
			   DESCRIPTION
			   "This object provides the hour meter reading of the module."
			   ::= { gx2lm870CFactoryEntry 9}

		lm870CflashPrgCntA          		OBJECT-TYPE
			   SYNTAX       		INTEGER
			   ACCESS           	read-only
			   STATUS           	mandatory
			   DESCRIPTION
			   "This object provides the number of times Bank 1 flash has been 
                      programmed."
			   ::= { gx2lm870CFactoryEntry 10}

		lm870CflashPrgCntB          		OBJECT-TYPE
			   SYNTAX       		INTEGER
			   ACCESS           	read-only
			   STATUS           	mandatory
			   DESCRIPTION
			   "This object provides the number of times Bank 1 flash has been 
                      programmed."
			   ::= { gx2lm870CFactoryEntry 11}

		lm870CflashBankARev          		OBJECT-TYPE
			   SYNTAX       		DisplayString (SIZE (0..80))
			   ACCESS           	read-only
			   STATUS           	mandatory
			   DESCRIPTION
			   "This object provides the revision of flash bank 0."
			   ::= { gx2lm870CFactoryEntry 12}

		lm870CflashBankBRev          		OBJECT-TYPE
			   SYNTAX       		DisplayString (SIZE (0..80))
			   ACCESS           	read-only
			   STATUS           	mandatory
			   DESCRIPTION
			   "This object provides the revision of flash bank 1."
			   ::= { gx2lm870CFactoryEntry 13}



-- ****************************************************************
--
-- TRAP DEFINITIONS
--
--
-- Every trap generated by an HFC agents will include first 9 identical
-- fields. If particular variable is not supported in
-- particular TRAP-TYPE then default value will be returned.
--
-- DESCRIPTION will include explanation of use of generic
-- variables (trapAdditionalInfo******.)  If no
-- DESCRIPTION is given then generic variables will contain
-- default values.
--
-- *****************************************************************

--***************************************************************************
-- ***********!!! THE TRAP SECTION HAS NOT BEEN COMPLETED YET !!! ***********
--***************************************************************************

-- **************************************************************************
--                        LM870C Laser Module traps
-- **************************************************************************
   trapLM870CConfigChangeInteger TRAP-TYPE
       ENTERPRISE gx2Lm870C
       VARIABLES
	       {       
		trapIdentifier,
		trapNetworkElemModelNumber,
		trapNetworkElemSerialNum,
		trapPerceivedSeverity,
		trapNetworkElemOperState,
		trapNetworkElemAlarmStatus,  
		trapNetworkElemAdminState,
		trapNetworkElemAvailStatus,
		trapText,
		trapChangedObjectId,
		trapChangedValueInteger,
		trapNETrapLastTrapTimeStamp
	       }
       DESCRIPTION
	"This trap is issued if configuration of a single variable
	 with integer type was changed (via ANY interface).  
	 TrapChangedValueInteger variable may contain current reading
	 of that variable.
	 trapPerceivedSeverity - 'indeterminate'"
  ::= 1

   trapLMCConfigChangeDisplayString TRAP-TYPE
       ENTERPRISE gx2Lm870C
       VARIABLES
	       {       
		trapIdentifier,
		trapNetworkElemModelNumber,
		trapNetworkElemSerialNum,
		trapPerceivedSeverity,
		trapNetworkElemOperState,
		trapNetworkElemAlarmStatus,  
		trapNetworkElemAdminState,
		trapNetworkElemAvailStatus,
		trapText,
		trapChangedObjectId,
		trapChangedValueDisplayString,
		trapNETrapLastTrapTimeStamp
	       }
       DESCRIPTION
	"This trap is issued if configuration of a single variable
	 with DispalayString type was changed (via ANY interface).  
	 TrapChangedValueDisplayString variable may contain current reading
	 of that variable.
	 trapPerceivedSeverity - 'indeterminate'"
  ::= 2

  trapLMCFanCurrentAlarm TRAP-TYPE
	ENTERPRISE gx2Lm870C
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules Fan Current 
	 parameter goes out of range.
	 trapAdditionalInfoInteger variable contains current reading of 
	 the this parameter."
  ::= 3

  trapLMC12vAlarm TRAP-TYPE
	ENTERPRISE gx2Lm870C
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules 12 Volt parameter goes out of range.
	 trapAdditionalInfoInteger variable contains current reading of 
	 the this parameter."
  ::= 4

  trapLMCModuleTempAlarm TRAP-TYPE
	ENTERPRISE gx2Lm870C
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Module Temperature goes out of range."
  ::= 5

  trapLMCRFPowerAlarm TRAP-TYPE
	ENTERPRISE gx2Lm870C
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules RF Power parameter 
	 goes out of range.
	 trapAdditionalInfoInteger variable contains current reading of 
	 the this parameter."
  ::= 6
  
  trapLMCOPTPowerAlarm TRAP-TYPE
	ENTERPRISE gx2Lm870C
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules Optical Power parameter 
	 goes out of range.
	 trapAdditionalInfoInteger variable contains current reading of 
	 the this parameter."
  ::= 7

  trapLMCLaserBiasAlarm TRAP-TYPE
	ENTERPRISE gx2Lm870C
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Bias parameter goes out of range.
	 trapAdditionalInfoInteger variable contains current reading of 
	 the this parameter."
  ::= 8
     
  trapLMCTECCurrentAlarm TRAP-TYPE
	ENTERPRISE gx2Lm870C
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules TEC Current parameter 
	 goes out of range.
	 trapAdditionalInfoInteger variable contains current reading of 
	 the this parameter."
  ::= 9

  trapLMCFlashAlarm TRAP-TYPE
	ENTERPRISE gx2Lm870C
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules detects an error during
	Flash memory operations."
  ::= 10

  trapLMCBankBootAlarm TRAP-TYPE
	ENTERPRISE gx2Lm870C
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules detects an error while booting
	from bank 0 or bank 1."
  ::= 11

	trapLMCAlarmDataCRCAlarm TRAP-TYPE
	ENTERPRISE gx2Lm870C
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Alarm Data CRC is incorrect."
  ::= 12

	trapLMCModSetDataCRCAlarm TRAP-TYPE
	ENTERPRISE gx2Lm870C
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Module Settings CRC is incorrect."
  ::= 13

	trapLMCFactoryDataCRCAlarm TRAP-TYPE
	ENTERPRISE gx2Lm870C
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Factory Data CRC is incorrect."
  ::= 14

	trapLMCResetFactoryDefaultAlarm TRAP-TYPE
	ENTERPRISE gx2Lm870C
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Factory Default Reset occurs."
  ::= 15

	trapLMCOPCalDataCRCAlarm TRAP-TYPE
	ENTERPRISE gx2Lm870C
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Optical Calibration Data CRC is incorrect."
  ::= 16

	trapLMCRFCalDataCRCAlarm TRAP-TYPE
	ENTERPRISE gx2Lm870C
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the RF Calibration Data CRC is incorrect."
  ::= 17

	trapLMCRFOverloadAlarm TRAP-TYPE
	ENTERPRISE gx2Lm870C
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the RF Overload alarm occurs."
  ::= 18

	trapLMCOMIoffsetAlarm TRAP-TYPE
	ENTERPRISE gx2Lm870C
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when an OMI Offset alarm occurs."
  ::= 19

  END
