ZXR10-SYSLOG-SERVER-MIB DEFINITIONS ::= BEGIN
    
   IMPORTS
       MODULE-IDENTITY, OBJECT-TYPE,
       enterprises,  TEXTUAL-CONVENTION,IpAddress         FROM SNMPv2-SMI   
       Ipv6Address         FROM IPV6-TC   
       DisplayString                    FROM SNMPv2-TC;   
   

                 
    syslogserver MODULE-IDENTITY
        LAST-UPDATED "201308070000Z"
        ORGANIZATION "ZTE Corporation."
        CONTACT-INFO
               "      sun nianhua
               Tel:    +86-25-52870000
               E-Mail: sun.nianhua1@zte.com.cn
               "
        DESCRIPTION 
                "The MIB module to describe the SYSLOG protocol."
        REVISION "201308070000Z"
        DESCRIPTION
                "modify:    syslogServerSourceInfo
                "
        REVISION "200901120000Z"
        DESCRIPTION
               "Initial version of this MIB module."
        ::= { zxr10 327 }                
    
    syslogServerSourceInfo OBJECT IDENTIFIER ::= { syslogserver 1 }    
    
    syslogServerFacilityInfo OBJECT IDENTIFIER ::= { syslogserver 2 }   
    
    syslogServerHostInfo OBJECT IDENTIFIER ::= { syslogserver 3 }  
    
    syslogServerLevelInfo OBJECT IDENTIFIER ::= { syslogserver 4 }
     
    zte OBJECT IDENTIFIER ::= { enterprises 3902 }
    zxr10 OBJECT IDENTIFIER ::= { zte 3}   
  
    FacilityValue ::= TEXTUAL-CONVENTION
       STATUS       current
       DESCRIPTION "enum for facility value"
       SYNTAX       INTEGER
                 {                    
                    kern(0),
                    user(1),
                    mail(2),
                    daemon(3),
                    auth1(4), 
                    syslog(5),
                    lpr(6),
                    news(7),                            
                    uucp(8),
                    clock1(9),
                    auth2(10),
                    ftp(11),
                    ntp(12),
                    logAudit(13),
                    logAlert(14),
                    clock2(15),
                    local0(16),
                    local1(17),
                    local2(18),
                    local3(19),
                    local4(20),
                    local5(21),
                    local6(22),
                    local7(23) 
                 }
                        
    IpType ::= TEXTUAL-CONVENTION
       STATUS       current
       DESCRIPTION "enum for ip type"
       SYNTAX       INTEGER
                {                    
                    ipv4(0),
                    mng(1),
                    ipv4Vrf(2),
                    ipv6(3),
                    ipv6Vrf(4)
                }
                
    SyslogLevel ::= TEXTUAL-CONVENTION
       STATUS       current
       DESCRIPTION "enum for syslog level"
       SYNTAX       INTEGER
                   {
                       emergency(1),
                       alert(2),
                       critical(3),
                       error(4),
                       warning(5),
                       notification(6),
                       information(7),
                       debugging(8)
                    }       
      
    CommonIPAddr ::= TEXTUAL-CONVENTION
       STATUS       current
       DESCRIPTION "An octet string containing common IP address information."
       SYNTAX       OCTET STRING (SIZE (44))        
      
    SyslogInetAddressIPv6 ::= TEXTUAL-CONVENTION
       DISPLAY-HINT "2x:2x:2x:2x:2x:2x:2x:2x"
       STATUS       current
       DESCRIPTION
         "Represents an IPv6 network address:

           Octets   Contents         Encoding
            1-16    IPv6 address     network-byte order


         This textual convention SHOULD NOT be used directly in object
         definitions, as it restricts addresses to a specific format.
         However, if it is used, it MAY be used either on its own or in
         conjunction with InetAddressType, as a pair."
       SYNTAX       OCTET STRING (SIZE (16))
     
                   
    syslogServerSourceIPv4 OBJECT-TYPE
        SYNTAX      CommonIPAddr
        MAX-ACCESS  read-only
        STATUS      current
        DESCRIPTION
            "Syslog server source IPv4 address."
        ::= { syslogServerSourceInfo 1} 
        
    syslogServerSourceIPv6 OBJECT-TYPE
        SYNTAX      CommonIPAddr
        MAX-ACCESS  read-only
        STATUS      current
        DESCRIPTION
            "Syslog server source IPv6 address."
        ::= { syslogServerSourceInfo 2}

   syslogServerSourceInterfaceName  OBJECT-TYPE
        SYNTAX   DisplayString
        MAX-ACCESS  read-only
        STATUS  current
        DESCRIPTION
            "A string description of the InterfaceName."
        ::= { syslogServerSourceInfo 3 } 

    syslogServerFacility OBJECT-TYPE
        SYNTAX      FacilityValue
        MAX-ACCESS  read-only
        STATUS      current
        DESCRIPTION
            "Syslog server facility."
        ::= { syslogServerFacilityInfo 1}      
    
    syslogServerHostTable  OBJECT-TYPE
        SYNTAX  SEQUENCE OF SyslogServerHostEntry
        MAX-ACCESS  not-accessible
        STATUS  current
        DESCRIPTION
            "Syslog server host table"
        ::= { syslogServerHostInfo 1 }
        
    syslogServerHostEntry  OBJECT-TYPE
        SYNTAX  SyslogServerHostEntry
        MAX-ACCESS  not-accessible
        STATUS  current
        DESCRIPTION
            " "
        INDEX  {
                   syslogServerHostIpType, 
                   syslogServerHostIpAddress,
                   syslogServerHostInterfaceName,
                   syslogServerHostVpnName                   
               }
        ::= { syslogServerHostTable 1 }
              
    SyslogServerHostEntry ::=
        SEQUENCE {
            syslogServerHostIpType
                IpType,
            syslogServerHostIpAddress
                DisplayString,        
            syslogServerHostVpnName
                DisplayString,
            syslogServerFport 
                INTEGER,
            syslogServerLport
                INTEGER,
            syslogServerEnableType 
                DisplayString,            
            syslogServerHostInterfaceName
                DisplayString,            
            syslogServerHostSourceIPv4
                IpAddress,            
            syslogServerHostSourceIPv6
                Ipv6Address           
        }     
 
    syslogServerHostIpType  OBJECT-TYPE
        SYNTAX   IpType
        MAX-ACCESS  read-only
        STATUS  current
        DESCRIPTION
            "A string description of the syslog server host IP type."
        ::= { syslogServerHostEntry 1 }

    syslogServerHostIpAddress  OBJECT-TYPE
        SYNTAX   DisplayString
        MAX-ACCESS  read-only
        STATUS  current
        DESCRIPTION
            "Syslog server host IP Address."
        ::= { syslogServerHostEntry 2 }  
   
    syslogServerHostVpnName  OBJECT-TYPE
        SYNTAX   DisplayString
        MAX-ACCESS  read-only
        STATUS  current
        DESCRIPTION
            "A string description of the VpnName."
        ::= { syslogServerHostEntry 3 } 
        
   syslogServerFport  OBJECT-TYPE
        SYNTAX   INTEGER(1..65535)
        MAX-ACCESS  read-only
        STATUS  current
        DESCRIPTION
            "Syslog server host fport."
        ::= { syslogServerHostEntry 4 }   

   syslogServerLport  OBJECT-TYPE
        SYNTAX   INTEGER(1..65535)
        MAX-ACCESS  read-only
        STATUS  current
        DESCRIPTION
            "Syslog server host lport."
        ::= { syslogServerHostEntry 5 }   
   
   syslogServerEnableType  OBJECT-TYPE
        SYNTAX   DisplayString
        MAX-ACCESS  read-only
        STATUS  current
        DESCRIPTION
            "Syslog server host enable log type."
        ::= { syslogServerHostEntry 6 }   

        
   syslogServerHostInterfaceName  OBJECT-TYPE
        SYNTAX   DisplayString
        MAX-ACCESS  read-only
        STATUS  current
        DESCRIPTION
            "A string description of the InterfaceName."
        ::= { syslogServerHostEntry 8 } 
         
   syslogServerHostSourceIPv4  OBJECT-TYPE
        SYNTAX   IpAddress
        MAX-ACCESS  read-only
        STATUS  current
        DESCRIPTION
            "Syslog server host source IPv4."
        ::= { syslogServerHostEntry 9 }         
         
   syslogServerHostSourceIPv6  OBJECT-TYPE
        SYNTAX   Ipv6Address
        MAX-ACCESS  read-only
        STATUS  current
        DESCRIPTION
            "Syslog server host source IPv6."
        ::= { syslogServerHostEntry 10 }         
      
   syslogServerLevel OBJECT-TYPE
        SYNTAX      SyslogLevel
        MAX-ACCESS  read-write
        STATUS      current
        DESCRIPTION
            "Syslog server level."
        DEFVAL     {notification}
        ::= { syslogServerLevelInfo 1} 
        
           
END
