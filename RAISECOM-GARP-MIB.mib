--MibName=RAISECOM-VRRP-MIB
-- *****************************************************************
-- RAISECOM-VRRP-MIB.mib:  Raisecom VRRP MIB file
--
-- 20110728,tangyoucan 
--
--
-- Copyright (c) 2000-2011 by Raisecom Technology Co., Ltd. 
-- All rights reserved.
-- 01,20111231,yangkewei,ROS00008218,advent 
-- *****************************************************************
RAISECOM-GARP-MIB  DEFINITIONS ::= BEGIN

IMPORTS
     MODULE-IDENTITY, OBJECT-TYPE,
     NOTIFICATION-TYPE, Counter32,
     Integer32, IpAddress, mib-2        FROM SNMPv2-SMI

     RowStatus, TimeInterval,
     MacAddress, TruthValue             FROM SNMPv2-TC  
     
	 EnableVar                          FROM SWITCH-TC
     MODULE-COMPLIANCE, OBJECT-GROUP,
     NOTIFICATION-GROUP                 FROM SNMPv2-CONF
	 EnabledStatus                      FROM P-BRIDGE-MIB            
     dot1dBasePort                      FROM BRIDGE-MIB
	 raisecomAgent                      FROM RAISECOM-BASE-MIB;
  
    raisecomGarp MODULE-IDENTITY
        LAST-UPDATED    "201107280000Z"
        ORGANIZATION    "Raisecom Technology Co., Ltd."
        CONTACT-INFO
                "Raisecom Science & Technology Co., ltd.
                 E-mail: support@raisecom.com"
        DESCRIPTION
                "description of garp manage object."
                ::= { raisecomAgent 42} 
                	   
-- *******************************************************************
--  RAISECOM GARP MIB Groups
-- ******************************************************************* 
    raisecomGarpNotifications       OBJECT IDENTIFIER ::= { raisecomGarp 0 }
    raisecomGarpCommonObjects       OBJECT IDENTIFIER ::= { raisecomGarp 1 }
    raisecomGarpApplicationObjects  OBJECT IDENTIFIER ::= { raisecomGarp 2 }
    raisecomGvrpObjects             OBJECT IDENTIFIER ::= { raisecomGarpApplicationObjects 1 }
    raisecomGmrpObjects             OBJECT IDENTIFIER ::= { raisecomGarpApplicationObjects 2 }
    raisecomGarpConformance         OBJECT IDENTIFIER ::= { raisecomGarp 3 }

--garp port table  
raisecomGarpPortTable OBJECT-TYPE
    SYNTAX      SEQUENCE OF RaisecomGarpPortEntry
    MAX-ACCESS  not-accessible
    STATUS      current
    DESCRIPTION
        "A table of GARP control information about every bridge
        port.  This is indexed by dot1dBasePort."
    ::= { raisecomGarpCommonObjects 1 }
  
raisecomGarpPortEntry OBJECT-TYPE
    SYNTAX      RaisecomGarpPortEntry
    MAX-ACCESS  not-accessible
    STATUS      current
    DESCRIPTION
        "GARP timer information for a bridge port."
    INDEX  { dot1dBasePort }
    ::= { raisecomGarpPortTable 1 }

RaisecomGarpPortEntry ::= SEQUENCE {
        raisecomGarpPortJoinTime            TimeInterval,
        raisecomGarpPortLeaveTime           TimeInterval,
        raisecomGarpPortLeaveAllTime        TimeInterval,
        raisecomGarpPortStatisticClear      EnableVar,
        raisecomGvrpPortStatisticClear      EnableVar,
        raisecomGmrpPortStatisticClear      EnableVar
    }

raisecomGarpPortJoinTime OBJECT-TYPE
    SYNTAX      TimeInterval
    MAX-ACCESS  read-write
    STATUS      current
    DESCRIPTION
        "The GARP Join time, in centiseconds."
    DEFVAL      { 20 }
    ::= { raisecomGarpPortEntry 1 }

raisecomGarpPortLeaveTime OBJECT-TYPE
    SYNTAX      TimeInterval
    MAX-ACCESS  read-write
    STATUS      current
    DESCRIPTION
        "The GARP Leave time, in centiseconds."
    DEFVAL      { 60 }
    ::= { raisecomGarpPortEntry 2 }

raisecomGarpPortLeaveAllTime OBJECT-TYPE
    SYNTAX      TimeInterval
    MAX-ACCESS  read-write
    STATUS      current
    DESCRIPTION
        "The GARP LeaveAll time, in centiseconds."
    DEFVAL      { 1000 }
    ::= { raisecomGarpPortEntry 3 }  
    
raisecomGarpPortStatisticClear	OBJECT-TYPE
          SYNTAX    EnableVar 
          ACCESS    read-write
          STATUS    current 
          DESCRIPTION
                 "Clear garp Statistics informations for this port. 
                 Read operation not supported" 
          DEFVAL {disable}
          ::= { raisecomGarpPortEntry 4 } 

raisecomGvrpPortStatisticClear	OBJECT-TYPE
          SYNTAX    EnableVar 
          ACCESS    read-write
          STATUS    current 
          DESCRIPTION
                 "Clear gvrp Statistics informations for this port. 
                 Read operation not supported" 
          DEFVAL {disable}
          ::= { raisecomGarpPortEntry 5 } 

raisecomGmrpPortStatisticClear	OBJECT-TYPE
          SYNTAX    EnableVar 
          ACCESS    read-write
          STATUS    current 
          DESCRIPTION
                 "Clear gmrp Statistics informations for this port. 
                 Read operation not supported" 
          DEFVAL {disable}
          ::= { raisecomGarpPortEntry 6 } 

--gvrp mib define         	
raisecomGvrpStatus OBJECT-TYPE
		SYNTAX EnabledStatus
		MAX-ACCESS read-write
		STATUS current
		DESCRIPTION
		"The administrative status requested by management for
        GVRP.  The value enabled(1) indicates that GVRP should
        be enabled on this device, on all ports for which it has
        not been specifically disabled.  When disabled(2), GVRP
        is disabled on all ports, and all GVRP packets will be
        forwarded transparently.  This object affects all GVRP
        Applicant and Registrar state machines.  A transition
        from disabled(2) to enabled(1) will cause a reset of all
        GVRP state machines on all ports.

        The value of this object MUST be retained across
        reinitializations of the management system."
		DEFVAL      { disabled }
		::= { raisecomGvrpObjects 1 }

raisecomGvrpMaxVlan OBJECT-TYPE
    SYNTAX      INTEGER
    MAX-ACCESS  read-only
    STATUS      current
    DESCRIPTION
        "The max vlan num this device support."
    ::= { raisecomGvrpObjects 2 }
		  
raisecomGvrpPortTable OBJECT-TYPE
		SYNTAX SEQUENCE OF RaisecomGvrpPortEntry
        MAX-ACCESS not-accessible
        STATUS current
        DESCRIPTION
            "A table of garp for port."
        ::= { raisecomGvrpObjects 3}
        
raisecomGvrpPortEntry OBJECT-TYPE
        SYNTAX RaisecomGvrpPortEntry
        MAX-ACCESS not-accessible
        STATUS current
        DESCRIPTION
            "Table entry for garp of port statistics."
        INDEX  { dot1dBasePort }
        ::= { raisecomGvrpPortTable 1 }
         
RaisecomGvrpPortEntry ::= SEQUENCE {
        raisecomGvrpPortStatus                      EnabledStatus,
        raisecomGvrpPortFailedRegistrations         Counter32,
        raisecomGvrpPortLastPduOrigin               MacAddress, 
        raisecomGvrpPortRestrictedVlanRegistration  TruthValue,
        raisecomGvrpPortRegistrationMode	        INTEGER,
        raisecomGvrpPortRunStatus			        EnableVar
}
          
raisecomGvrpPortStatus OBJECT-TYPE
    SYNTAX      EnabledStatus
    MAX-ACCESS  read-write
    STATUS      current
    DESCRIPTION
        "The state of GVRP operation on this port.  The value
        enabled(1) indicates that GVRP is enabled on this port,
        as long as dot1qGvrpStatus is also enabled for this
        device.  When disabled(2) but dot1qGvrpStatus is still
        enabled for the device, GVRP is disabled on this port:
        any GVRP packets received will be silently discarded, and
        no GVRP registrations will be propagated from other
        ports.  This object affects all GVRP Applicant and
        Registrar state machines on this port.  A transition
        from disabled(2) to enabled(1) will cause a reset of all
        GVRP state machines on this port.

        The value of this object MUST be retained across
        reinitializations of the management system."
    DEFVAL      { disabled }
    ::= { raisecomGvrpPortEntry 1 }

raisecomGvrpPortLastPduOrigin OBJECT-TYPE
    SYNTAX      MacAddress
    MAX-ACCESS  read-only
    STATUS      current
    DESCRIPTION
        "The Source MAC Address of the last GVRP message
        received on this port."
    ::= { raisecomGvrpPortEntry 2 }  

raisecomGvrpPortFailedRegistrations OBJECT-TYPE
    SYNTAX      Counter32
    MAX-ACCESS  read-only
    STATUS      current
    DESCRIPTION
        "The total number of failed GVRP registrations, for any
        reason, on this port."
    ::= { raisecomGvrpPortEntry 3 }
    
raisecomGvrpPortRestrictedVlanRegistration OBJECT-TYPE
    SYNTAX      TruthValue
    MAX-ACCESS  read-write
    STATUS      current
    DESCRIPTION
        "The state of Restricted VLAN Registration on this port.
         If the value of this control is true(1), then creation
         of a new dynamic VLAN entry is permitted only if there
         is a Static VLAN Registration Entry for the VLAN concerned,
         in which the Registrar Administrative Control value for
         this port is Normal Registration.

        The value of this object MUST be retained across
        reinitializations of the management system."
    REFERENCE
        "IEEE 802.1u clause 11.2.3.2.3, 12.10.1.7."
    DEFVAL      { false }
    ::= { raisecomGvrpPortEntry 4 }
        
raisecomGvrpPortRegistrationMode	OBJECT-TYPE
          SYNTAX INTEGER{
                    normal(1),
                    fixed(2),
                    forbidden(3)
                    }
          ACCESS    read-write
          STATUS    current    
          DESCRIPTION
                 "GVRP registration information.
                 normal:This is the default configuration.Allow create, register and 
                 unregister vlans dynamiclly at this port.
                 fixed: Allow create and register vlan manually at this port.Prevent 
                 from unregistering vlans or registering known vlans of this port at 
                 another trunk port.
                 forbidden: Unregister all vlans but vlan 1, forbid to create or register
                 any other vlans at this port."  
          DEFVAL {normal}
          ::= { raisecomGvrpPortEntry 5 } 

raisecomGvrpPortRunStatus	OBJECT-TYPE
          SYNTAX    EnableVar 
          ACCESS    read-only
          STATUS    current
          DESCRIPTION
                 "It indicates whether the port gvrp function is running." 
          DEFVAL {disable}
          ::= { raisecomGvrpPortEntry 6 } 
--gvrp statistic table              		
raisecomGvrpPortStatisticTable OBJECT-TYPE
		SYNTAX SEQUENCE OF RaisecomGvrpPortStatisticEntry
        MAX-ACCESS not-accessible
        STATUS current
        DESCRIPTION
            "A table of garp for port statistics."
        ::= { raisecomGvrpObjects 4}
    
raisecomGvrpPortStatisticEntry OBJECT-TYPE
        SYNTAX RaisecomGvrpPortStatisticEntry
        MAX-ACCESS not-accessible
        STATUS current
        DESCRIPTION
            "Table entry for garp of port statistics."
        INDEX    {dot1dBasePort} 
        ::= { raisecomGvrpPortStatisticTable 1 }
        
        
RaisecomGvrpPortStatisticEntry ::= SEQUENCE {
        raisecomGvrpPortFrameRx				 INTEGER,
        raisecomGvrpPortFrameTx				 INTEGER,
        raisecomGvrpPortFrameDiscard	     INTEGER
        }

raisecomGvrpPortFrameRx	OBJECT-TYPE
          SYNTAX    INTEGER 
          ACCESS    read-only
          STATUS    current
          DESCRIPTION
                 "Number of GVRP frames received for this port."
          ::= { raisecomGvrpPortStatisticEntry 1 } 
          
raisecomGvrpPortFrameTx	OBJECT-TYPE
          SYNTAX    INTEGER 
          ACCESS    read-only
          STATUS    current
          DESCRIPTION
                 "Number of GVRP frames transmitted for this port."
          ::= { raisecomGvrpPortStatisticEntry 2 } 
         
raisecomGvrpPortFrameDiscard	OBJECT-TYPE
          SYNTAX    INTEGER 
          ACCESS    read-only
          STATUS    current
          DESCRIPTION
                 "Number of discarded GVRP frames for this port."
          ::= { raisecomGvrpPortStatisticEntry 3 }  
   		
--gmrp mib define 
raisecomGmrpStatus OBJECT-TYPE
		SYNTAX EnabledStatus
		MAX-ACCESS read-write
		STATUS current
		DESCRIPTION
		"The administrative status requested by management for
        GVRP.  The value enabled(1) indicates that GMRP should
        be enabled on this device, on all ports for which it has
        not been specifically disabled.  When disabled(2), GVRP
        is disabled on all ports, and all GMRP packets will be
        forwarded transparently.  This object affects all GMRP
        Applicant and Registrar state machines.  A transition
        from disabled(2) to enabled(1) will cause a reset of all
        GMRP state machines on all ports.

        The value of this object MUST be retained across
        reinitializations of the management system."
		DEFVAL      { disabled }
		::= { raisecomGmrpObjects 1 } 

raisecomGmrpMaxGroup OBJECT-TYPE
    SYNTAX      INTEGER
    MAX-ACCESS  read-only
    STATUS      current
    DESCRIPTION
        "The max group num this device support."
    ::= { raisecomGmrpObjects 2 }
 
-- -------------------------------------------------------------
-- The GMRP Port Configuration and Status Table
-- -------------------------------------------------------------

raisecomGmrpPortTable OBJECT-TYPE
    SYNTAX      SEQUENCE OF RaisecomGmrpPortEntry
    MAX-ACCESS  not-accessible
    STATUS      current
    DESCRIPTION
        "A table of GMRP control and status information about
        every bridge port.  Augments the dot1dBasePortTable."
    ::= { raisecomGmrpObjects 3 }

raisecomGmrpPortEntry OBJECT-TYPE
    SYNTAX      RaisecomGmrpPortEntry
    MAX-ACCESS  not-accessible
    STATUS      current
    DESCRIPTION
        "GMRP control and status information for a bridge port."
    INDEX    {dot1dBasePort} 
    ::= { raisecomGmrpPortTable 1 }

RaisecomGmrpPortEntry ::=
    SEQUENCE {
        raisecomGmrpPortStatus
            EnabledStatus,
        raisecomGmrpPortFailedRegistrations
            Counter32,
        raisecomGmrpPortLastPduOrigin
            MacAddress,
        raisecomGmrpPortRestrictedGroupRegistration
            TruthValue , 
        raisecomGmrpPortRegistrationMode	        
            INTEGER,
        raisecomGmrpPortRunStatus
            TruthValue
    }

raisecomGmrpPortStatus OBJECT-TYPE
    SYNTAX      EnabledStatus
    MAX-ACCESS  read-write
    STATUS      current
    DESCRIPTION
        "The administrative state of GMRP operation on this port.  The
        value enabled(1) indicates that GMRP is enabled on this port
        in all VLANs as long as dot1dGmrpStatus is also enabled(1).
        A value of disabled(2) indicates that GMRP is disabled on
        this port in all VLANs: any GMRP packets received will
        be silently discarded, and no GMRP registrations will be
        propagated from other ports.  Setting this to a value of
        enabled(1) will be stored by the agent but will only take
        effect on the GMRP protocol operation if dot1dGmrpStatus
        also indicates the value enabled(1).  This object affects
        all GMRP Applicant and Registrar state machines on this
        port.  A transition from disabled(2) to enabled(1) will
        cause a reset of all GMRP state machines on this port.

        The value of this object MUST be retained across
        reinitializations of the management system."
    DEFVAL      { enabled }
    ::= { raisecomGmrpPortEntry 1 }

raisecomGmrpPortFailedRegistrations OBJECT-TYPE
    SYNTAX      Counter32
    MAX-ACCESS  read-only
    STATUS      current
    DESCRIPTION
        "The total number of failed GMRP registrations, for any
        reason, in all VLANs, on this port."
    ::= { raisecomGmrpPortEntry 2 }

raisecomGmrpPortLastPduOrigin OBJECT-TYPE
    SYNTAX      MacAddress
    MAX-ACCESS  read-only
    STATUS      current
    DESCRIPTION
        "The Source MAC Address of the last GMRP message
        received on this port."
    ::= { raisecomGmrpPortEntry 3 }

raisecomGmrpPortRestrictedGroupRegistration OBJECT-TYPE
    SYNTAX      TruthValue
    MAX-ACCESS  read-write
    STATUS      current
    DESCRIPTION
        "The state of Restricted Group Registration on this port.
         If the value of this control is true(1), then creation
         of a new dynamic entry is permitted only if there is a
         Static Filtering Entry for the VLAN concerned, in which
         the Registrar Administrative Control value is Normal
         Registration.

        The value of this object MUST be retained across
        reinitializations of the management system."
    REFERENCE
        "IEEE 802.1t clause 10.3.2.3, 14.10.1.3."
    DEFVAL      { false }
    ::= { raisecomGmrpPortEntry 4 }  

raisecomGmrpPortRegistrationMode	OBJECT-TYPE
          SYNTAX INTEGER{
                    normal(1),
                    fixed(2),
                    forbidden(3)
                    }
          ACCESS    read-write
          STATUS    current    
          DESCRIPTION
                 "GMRP registration information.
                 normal:This is the default configuration.Allow create, register and 
                 unregister vlans dynamiclly at this port.
                 fixed: Allow create and register group manually at this port.Prevent 
                 from unregistering vlans or registering known groups of this port at 
                 another trunk port.
                 forbidden: Unregister all groups, forbid to create or register
                 any other groups at this port."  
          DEFVAL {normal}
          ::= { raisecomGmrpPortEntry 5 } 
    
raisecomGmrpPortRunStatus	OBJECT-TYPE
          SYNTAX    EnableVar 
          ACCESS    read-only
          STATUS    current
          DESCRIPTION
                 "It indicates whether the port gmrp function is running." 
          DEFVAL {disable}
          ::= { raisecomGmrpPortEntry 6 } 
    
--gmrp statistic table  
raisecomGmrpPortStatisticTable OBJECT-TYPE
		SYNTAX SEQUENCE OF RaisecomGmrpPortStatisticEntry
        MAX-ACCESS not-accessible
        STATUS current
        DESCRIPTION
            "A table of gmrp for port statistics."
        ::= { raisecomGmrpObjects 4}
    
raisecomGmrpPortStatisticEntry OBJECT-TYPE
        SYNTAX RaisecomGmrpPortStatisticEntry
        MAX-ACCESS not-accessible
        STATUS current
        DESCRIPTION
            "Table entry for gmrp of port statistics."
        INDEX    {dot1dBasePort}
        ::= { raisecomGmrpPortStatisticTable 1 }
                
RaisecomGmrpPortStatisticEntry ::= SEQUENCE {
        raisecomGmrpPortFrameRx				 INTEGER,
        raisecomGmrpPortFrameTx				 INTEGER,
        raisecomGmrpPortFrameDiscard	     INTEGER
        }

raisecomGmrpPortFrameRx	OBJECT-TYPE
          SYNTAX    INTEGER 
          ACCESS    read-only
          STATUS    current
          DESCRIPTION
                 "Number of GMRP frames received for this port."
          ::= { raisecomGmrpPortStatisticEntry 1 } 
          
raisecomGmrpPortFrameTx	OBJECT-TYPE
          SYNTAX    INTEGER 
          ACCESS    read-only
          STATUS    current
          DESCRIPTION
                 "Number of GMRP frames transmitted for this port."
          ::= { raisecomGmrpPortStatisticEntry 2 } 
         
raisecomGmrpPortFrameDiscard	OBJECT-TYPE
          SYNTAX    INTEGER 
          ACCESS    read-only
          STATUS    current
          DESCRIPTION
                 "Number of discarded GMRP frames for this port."
          ::= { raisecomGmrpPortStatisticEntry 3 }     
          			
END
